-- **SDOC***********************************************************************
-- *****************************************************************************
--
--             Copyright(c) 2005 Mediatrix Telecom, Inc.
--
--  NOTICE:
--   This document contains information that is confidential and proprietary to
--   Mediatrix Telecom, Inc.
--
--   Mediatrix Telecom, Inc. reserves all rights to this document as well as to
--   the Intellectual Property of the document and the technology and know-how
--   that it includes and represents.
--
--   This publication cannot be reproduced, neither in whole nor in part, in any
--   form whatsoever, without prior written approval by Mediatrix Telecom, Inc.
--
--   Mediatrix Telecom, Inc. reserves the right to revise this publication and
--   make changes at any time and without the obligation to notify any person
--   and/or entity of such revisions and/or changes.
--
-- *****************************************************************************
-- **EDOC***********************************************************************

MX-PPPOA-MIB
DEFINITIONS ::= BEGIN

IMPORTS
        MODULE-IDENTITY,
        OBJECT-TYPE
    FROM SNMPv2-SMI
        MODULE-COMPLIANCE,
        OBJECT-GROUP
    FROM SNMPv2-CONF
        mediatrixConfig
    FROM MX-SMI
        MxEnableState
    FROM MX-TC;

pppoaMIB MODULE-IDENTITY
    LAST-UPDATED "200603060000Z"
    ORGANIZATION "Mediatrix Telecom, Inc."
    CONTACT-INFO "Mediatrix Telecom, Inc.
                  4229, Garlock Street
                  Sherbrooke (Quebec)
                  Canada, J1L 2C8
                  Phone: (819) 829-8749
                  http://www.mediatrix.com"
    DESCRIPTION  "This MIB is used to customize properties of the PPPoA service."

    -- *************************************************************************
    -- Revision history
    -- *************************************************************************
    REVISION    "200603060000Z"
    DESCRIPTION "Corrected the description of variable pppoaEnable."
    REVISION    "200504120000Z"
    DESCRIPTION "Creation."
   ::= { mediatrixConfig 350 }

pppoaMIBObjects OBJECT IDENTIFIER ::= { pppoaMIB 1 }
pppoaConformance OBJECT IDENTIFIER ::= { pppoaMIB 5 }


    -- *************************************************************************
    -- pppoaMIBObjects.
    -- *************************************************************************
    pppoaEnable OBJECT-TYPE
        SYNTAX      MxEnableState
        MAX-ACCESS  read-write
        STATUS      current
        DESCRIPTION "Enable/disable the PPPoA service.

                     enable :  The PPPoA service is enabled. The unit tries to establish a PPPoA
                               connection to the edge aggregation router.

                     disable : The PPPoA service is disabled.

                     If both this variable and pppoeEnable from the MX-PPPOE-MIB are set to enable,
                     PPPoE has priority over PPPoA (PPPoA will not be enabled).

                     This variable's semantics are different depending on the protocol and hardware
                     platform.
                     Please refer to the documentation shipped with your device for more
                     details."
        DEFVAL      { disable }
        ::= { pppoaMIBObjects  50 }


    -- *************************************************************************
    -- Conformance information
    -- *************************************************************************
    pppoaCompliances OBJECT IDENTIFIER ::= { pppoaConformance 1 }

    pppoaComplVer1 MODULE-COMPLIANCE
        STATUS      current
        DESCRIPTION
            "List of groups required to support the PPPoA service."
        MODULE  -- This Module
            MANDATORY-GROUPS {
                                pppoaConnectionCustomizationVer1
                             }
        ::= { pppoaCompliances 1 }

    -- *************************************************************************
    --  MIB variable grouping
    -- *************************************************************************
    pppoaGroups OBJECT IDENTIFIER ::= { pppoaConformance 5 }

    pppoaConnectionCustomizationVer1 OBJECT-GROUP
        OBJECTS {
                    pppoaEnable
                }
        STATUS current
        DESCRIPTION "A collection of objects that defines the characteristics of a PPPoA connection."
        ::= { pppoaGroups 10 }

END

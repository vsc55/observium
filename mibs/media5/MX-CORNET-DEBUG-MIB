-- ****************************************************************************
-- ****************************************************************************
--
--             Copyright(c) 2005 Mediatrix Telecom, Inc.
--
--  NOTICE:
--   This document contains information that is confidential and proprietary to
--   Mediatrix Telecom, Inc.
--
--   Mediatrix Telecom, Inc. reserves all rights to this document as well as to
--   the Intellectual Property of the document and the technology and know-how
--   that it includes and represents.
--
--   This publication cannot be reproduced, neither in whole nor in part, in any
--   form whatsoever, without prior written approval by Mediatrix Telecom, Inc.
--
--   Mediatrix Telecom, Inc. reserves the right to revise this publication and
--   make changes at any time and without the obligation to notify any person
--   and/or entity of such revisions and/or changes.
--
-- ****************************************************************************
-- ****************************************************************************

MX-CORNET-DEBUG-MIB
DEFINITIONS ::= BEGIN

IMPORTS
        MODULE-IDENTITY,
        OBJECT-IDENTITY,
        OBJECT-TYPE,
        Unsigned32
    FROM SNMPv2-SMI
        OBJECT-GROUP,
        MODULE-COMPLIANCE
    FROM SNMPv2-CONF
        mediatrixExperimental
    FROM MX-SMI;

corNetDebugMIB MODULE-IDENTITY
    LAST-UPDATED "200505180000Z"
    ORGANIZATION "Mediatrix Telecom, Inc."
    CONTACT-INFO "Mediatrix Telecom, Inc.
                  4229, Garlock Street
                  Sherbrooke (Quebec)
                  Canada, J1L 2C8
                  Phone: (819) 829-8749
                  http://www.mediatrix.com"
    DESCRIPTION "This MIB contains CorNet debug configuration objects."

    -- ************************************************************************
    -- Revision history
    -- ************************************************************************
    REVISION    "200505180000Z"
    DESCRIPTION "Creation."
    ::= { mediatrixExperimental 110 }

corNetDebugMIBObjects  OBJECT IDENTIFIER ::= { corNetDebugMIB 1 }
corNetDebugConformance OBJECT IDENTIFIER ::= { corNetDebugMIB 2 }

    -- ************************************************************************
    -- CorNet Debug Variables
    -- ************************************************************************
    corNetDebugToMSecTraceLevel OBJECT-TYPE
        SYNTAX      INTEGER {
                              disabled(0),
                              error(10),
                              warning(20),
                              highPriorityInfo(30),
                              mediumPriorityInfo(40),
                              lowPriorityInfo(50),
                              all(1000)
                            }
        MAX-ACCESS  read-write
        STATUS      current
        DESCRIPTION "Sets the ToMSec syslog trace level.

                     The following are the possible values vs information needed:

                     disabled:
                        No information.

                     error:
                        Error information.

                     warning:
                        Warning information.

                     highPriorityInfo:
                        High priority information.

                     mediumPriorityInfo:
                        Medium priority information.

                     lowPriorityInfo:
                        Low priority information.

                     all:
                        All information.

                     Note that the selected level includes all lower levels, e.g., highPriorityInfo contains warning and error."
        DEFVAL      { disabled }
        ::= { corNetDebugMIBObjects  50 }


    -- ************************************************************************
    -- Conformance information
    -- ************************************************************************
    corNetDebugCompliances OBJECT IDENTIFIER ::= { corNetDebugConformance 1 }

    corNetDebugBasicComplVer1 MODULE-COMPLIANCE
        STATUS      current
        DESCRIPTION "Minimal definitions for the CorNet protocol debug group."
        MODULE -- This Module
            MANDATORY-GROUPS {
                                corNetDebugGroupVer1
                             }
        ::= { corNetDebugCompliances 5 }


    -- ************************************************************************
    -- MIB variable grouping
    -- ************************************************************************
    corNetDebugGroups OBJECT IDENTIFIER ::= { corNetDebugConformance 2 }

    corNetDebugGroupVer1 OBJECT-GROUP
        OBJECTS {
                    corNetDebugToMSecTraceLevel
                }
        STATUS      current
        DESCRIPTION "This group holds the objects that define the
                     CorNet debug group."
        ::= { corNetDebugGroups 5 }
END

-- **SDOC***********************************************************************
-- *****************************************************************************
--
--             Copyright(c) 2005 Mediatrix Telecom, Inc.
--
--  NOTICE:
--   This document contains information that is confidential and proprietary to
--   Mediatrix Telecom, Inc.
--
--   Mediatrix Telecom, Inc. reserves all rights to this document as well as to
--   the Intellectual Property of the document and the technology and know-how
--   that it includes and represents.
--
--   This publication cannot be reproduced, neither in whole nor in part, in any
--   form whatsoever, without prior written approval by Mediatrix Telecom, Inc.
--
--   Mediatrix Telecom, Inc. reserves the right to revise this publication and
--   make changes at any time and without the obligation to notify any person
--   and/or entity of such revisions and/or changes.
--
-- *****************************************************************************
-- **EDOC***********************************************************************

MX-SECURITY-CERTIFICATES-MIB
DEFINITIONS ::= BEGIN

IMPORTS
        MODULE-IDENTITY,
        OBJECT-TYPE
    FROM SNMPv2-SMI
        MODULE-COMPLIANCE,
        OBJECT-GROUP
    FROM SNMPv2-CONF
        mediatrixMgmt
    FROM MX-SMI
        MxEnableState
    FROM MX-TC;

securityCertificatesMIB MODULE-IDENTITY
    LAST-UPDATED "200504210000Z"
    ORGANIZATION "Mediatrix Telecom, Inc."
    CONTACT-INFO "Mediatrix Telecom, Inc.
                  4229, Garlock Street
                  Sherbrooke (Quebec)
                  Canada, J1L 2C8
                  Phone: (819) 829-8749
                  http://www.mediatrix.com"
    DESCRIPTION  "This MIB is used to manage the security certificates."

    -- *************************************************************************
    -- Revision history
    -- *************************************************************************
    REVISION    "200504210000Z"
    DESCRIPTION "Creation."
   ::= { mediatrixMgmt 200 }

securityCertificatesMIBObjects OBJECT IDENTIFIER ::= { securityCertificatesMIB 1 }
securityCertificatesConformance OBJECT IDENTIFIER ::= { securityCertificatesMIB 5 }


    -- *************************************************************************
    -- securityCertificatesMIBObjects.
    -- *************************************************************************

    -- *************************************************************************
    -- certificateTable
    -- *************************************************************************
    certificateTable OBJECT-TYPE
        SYNTAX      SEQUENCE OF CertificateEntry
        MAX-ACCESS  not-accessible
        STATUS      current
        DESCRIPTION "A table of X.509 security certificates that are installed on this unit."
        ::= { securityCertificatesMIBObjects 500 }

        certificateEntry OBJECT-TYPE
            SYNTAX      CertificateEntry
            MAX-ACCESS  not-accessible
            STATUS      current
            DESCRIPTION "A row in the certificateTable table."
            INDEX       {
                            certificateName
                        }
            ::= { certificateTable 50 }

            CertificateEntry ::= SEQUENCE
                {
                    certificateName              OCTET STRING,
                    certificateSubjectCommonName OCTET STRING,
                    certificateExpirationDate    OCTET STRING
                }

            certificateName OBJECT-TYPE
                SYNTAX      OCTET STRING (SIZE (1..6))
                MAX-ACCESS  read-only
                STATUS      current
                DESCRIPTION "The name of the certificate.
                
                             Displays the file name of the certificate, without the extension."
                ::= { certificateEntry 50 }

            certificateSubjectCommonName OBJECT-TYPE
                SYNTAX  OCTET STRING (SIZE(0..128))
                MAX-ACCESS  read-only
                STATUS  current
                DESCRIPTION "The certificate's subject name.
                             
                             If the certificate contains a subject field, displays the common name.
                             Otherwise, displays the first non-empty subject alternative name from the following list:
                                - Uniform Resource Identifier
                                - DNS name
                                - IP Address
                                - RFC 822 name
                             
                             See RFC 3280 sections 4.1.2.6 and 4.2.1.7 for details."
                DEFVAL { "" }
                ::=  { certificateEntry 100 }

            certificateExpirationDate OBJECT-TYPE
                SYNTAX  OCTET STRING (SIZE(10))
                MAX-ACCESS  read-only
                STATUS  current
                DESCRIPTION "The certificate's expiration date.
                             
                             Displays the date at which the certificate expires. The format is MM/DD/YYYY in universal time.
                                                             
                             See RFC 3280 section 4.1.2.5 for details."
                DEFVAL { "" }
                ::=  { certificateEntry 150 }


    -- *************************************************************************
    -- Conformance information
    -- *************************************************************************
    securityCertificatesCompliances OBJECT IDENTIFIER ::= { securityCertificatesConformance 1 }

    securityCertificatesComplVer1 MODULE-COMPLIANCE
        STATUS      current
        DESCRIPTION
            "List of groups required to support the management of security certificates."
        MODULE  -- This Module
            MANDATORY-GROUPS {
                                securityCertificatesVer1
                             }
        ::= { securityCertificatesCompliances 1 }

    -- *************************************************************************
    --  MIB variable grouping
    -- *************************************************************************
    securityCertificatesGroups OBJECT IDENTIFIER ::= { securityCertificatesConformance 5 }

    securityCertificatesVer1 OBJECT-GROUP
        OBJECTS {
                    certificateSubjectCommonName,
                    certificateExpirationDate
                }
        STATUS current
        DESCRIPTION "A collection of objects that defines the characteristics of a security certificate."
        ::= { securityCertificatesGroups 10 }

END

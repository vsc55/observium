-- **SDOC***********************************************************************
-- *****************************************************************************
--
--             Copyright(c) 2004 Mediatrix Telecom, Inc.
--
--  NOTICE:
--   This document contains information that is confidential and proprietary
--   to Mediatrix Telecom, Inc.
--
--   Mediatrix Telecom, Inc. reserves all rights to this document as well as
--   to the Intellectual Property of the document and the technology and
--   know-how that it includes and represents.
--
--   This publication cannot be reproduced, neither in whole nor in part, in
--   any form whatsoever without written prior approval by
--   Mediatrix Telecom, Inc.
--
--   Mediatrix Telecom, Inc. reserves the right to revise this publication
--   and make changes at any time and without the obligation to notify any
--   person and/or entity of such revisions and/or changes.
--
-- *****************************************************************************
-- *****************************************************************************
--
-- Root for modules used to configure the CorNet signaling protocol.
--
-- *****************************************************************************
-- **EDOC***********************************************************************

MX-CORNET-MIB
DEFINITIONS ::= BEGIN

IMPORTS
        OBJECT-TYPE,
        MODULE-IDENTITY,
        OBJECT-IDENTITY
    FROM SNMPv2-SMI
        OBJECT-GROUP,
        NOTIFICATION-GROUP,
        MODULE-COMPLIANCE
    FROM SNMPv2-CONF
        mediatrixIpTelephonySignaling,
        ipAddressStatus,
        ipAddressConfig
    FROM MX-SMI
        ifIndex
    FROM RFC1213-MIB;

corNet OBJECT-IDENTITY
       STATUS      current
       DESCRIPTION "Root for MIBs that contain CorNet configuration objects."
       ::= { mediatrixIpTelephonySignaling 40 }


    ipAddressStatusCorNet OBJECT IDENTIFIER ::= { ipAddressStatus 130 }
    ipAddressConfigCorNet OBJECT IDENTIFIER ::= { ipAddressConfig 130 }
    ipAddressConfigCorNetStatic OBJECT IDENTIFIER ::= { ipAddressConfigCorNet 10 }


END

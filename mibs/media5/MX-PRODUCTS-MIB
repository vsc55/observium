-- **SDOC***********************************************************************
-- *****************************************************************************
--
--              Copyright(c) 2007 Media5 Corporation
--              Copyright(c) 2008 Media5 Corporation ("Media5")
--
--  NOTICE:
--   This document contains information that is confidential and proprietary to
--   Media5.
--
--   Media5 reserves all rights to this document as well as to the Intellectual
--   Property of the document and the technology and know-how that it includes
--   and represents.
--
--   This publication cannot be reproduced, neither in whole nor in part, in any
--   form whatsoever without prior written approval by Media5.
--
--   Media5 reserves the right to revise this publication and make changes at
--   any time and without the obligation to notify any person and/or entity of
--   such revisions and/or changes.
--
-- *****************************************************************************
-- **EDOC***********************************************************************

MX-PRODUCTS-MIB
DEFINITIONS ::= BEGIN

IMPORTS
        MODULE-IDENTITY
    FROM SNMPv2-SMI
        mediatrixModules,
        mediatrixProducts
    FROM MX-SMI;

mxProductsMIB MODULE-IDENTITY
    LAST-UPDATED "201106280000Z"
    ORGANIZATION "Mediatrix Telecom"
    CONTACT-INFO "Mediatrix Telecom
                  4229, Garlock Street
                  Sherbrooke (Quebec)
                  Canada
                  Phone: (819) 829-8749
                  Web: http://www.Mediatrix.com"
    DESCRIPTION "This module contains objectID for each Mediatrix product.
                 This objectID is used in the sysObjectID to identify the product."

    -- *************************************************************************
    -- Revision history
    -- *************************************************************************
    REVISION    "201106280000Z"
    DESCRIPTION "Added Mediatrix LP16 and LP24 product names."
    REVISION    "200808120000Z"
    DESCRIPTION "Added the Ciena LE46 VM product name."
    REVISION    "200806170000Z"
    DESCRIPTION "Added Mediatrix 4104 Plus product name."
    REVISION    "200712110000Z"
    DESCRIPTION "Added Mediatrix 4102 and 0102 product name."
    REVISION    "200703210000Z"
    DESCRIPTION "Added mediatrix4104 product name."
    REVISION    "200701080000Z"
    DESCRIPTION "Added mediatrix4108, mediatrix4116 and mediatrix4124 product
                 names."
    REVISION    "200506230000Z"
    DESCRIPTION "Added mediatrixLiaison312 and mediatrixLiaison322 product names."
    REVISION    "200503290000Z"
    DESCRIPTION "Modified mediatrix512 and mediatrix522 product names for
                 mediatrixLiaison512 and mediatrixLiaison522."
    REVISION    "200502240000Z"
    DESCRIPTION "Added Mediatrix 512 and 522 product names."
    REVISION    "200402020000Z"
    DESCRIPTION "Added the Mediatrix 2102 product."
    REVISION    "200302210000Z"
    DESCRIPTION "Added the Mediatrix 1204 product."
    REVISION    "200202120000Z"
    DESCRIPTION "Added the Mediatrix-III-4FXS-4M product."
    REVISION    "200108210000Z"
    DESCRIPTION "Creation"

        ::= { mediatrixModules 2 }

    mediatrix-III-4FXS       OBJECT IDENTIFIER ::= { mediatrixProducts 1 }
    mediatrix-III-4FXO       OBJECT IDENTIFIER ::= { mediatrixProducts 2 }
    mediatrix1102            OBJECT IDENTIFIER ::= { mediatrixProducts 3 }
    mediatrix1104            OBJECT IDENTIFIER ::= { mediatrixProducts 4 }
    mediatrix1124            OBJECT IDENTIFIER ::= { mediatrixProducts 5 }
    mediatrix-III-4FXS-4M    OBJECT IDENTIFIER ::= { mediatrixProducts 6 }
    mediatrix1204            OBJECT IDENTIFIER ::= { mediatrixProducts 7 }
    mediatrix2102            OBJECT IDENTIFIER ::= { mediatrixProducts 8 }
    mediatrixLiaison312      OBJECT IDENTIFIER ::= { mediatrixProducts 9 }
    mediatrixLiaison322      OBJECT IDENTIFIER ::= { mediatrixProducts 10 }
    mediatrixLiaison512      OBJECT IDENTIFIER ::= { mediatrixProducts 18 }
    mediatrixLiaison522      OBJECT IDENTIFIER ::= { mediatrixProducts 19 }
    mediatrix0102            OBJECT IDENTIFIER ::= { mediatrixProducts 20 }
    mediatrix4102            OBJECT IDENTIFIER ::= { mediatrixProducts 21 }
    mediatrix4104            OBJECT IDENTIFIER ::= { mediatrixProducts 22 }
    mediatrix4104Plus        OBJECT IDENTIFIER ::= { mediatrixProducts 23 }
    mediatrix4108            OBJECT IDENTIFIER ::= { mediatrixProducts 25 }
    mediatrix4116            OBJECT IDENTIFIER ::= { mediatrixProducts 30 }
    mediatrix4124            OBJECT IDENTIFIER ::= { mediatrixProducts 35 }
    cienaLE46VM              OBJECT IDENTIFIER ::= { mediatrixProducts 40 }
    mediatrixLP16            OBJECT IDENTIFIER ::= { mediatrixProducts 45 }
    mediatrixLP24            OBJECT IDENTIFIER ::= { mediatrixProducts 50 }

END

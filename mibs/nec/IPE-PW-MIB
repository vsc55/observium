--
-- ASN.1 MIB Definitions
-- Output Date: Tue Jul 12 15:00:48 2016
--

IPE-PW-MIB DEFINITIONS ::= BEGIN

-----------------------------------------------
-- IMPORTS Definitions
-----------------------------------------------

    IMPORTS
        InterfaceIndex
            FROM IF-MIB
        enterprises, Integer32, IpAddress, NOTIFICATION-TYPE, OBJECT-TYPE,
        Opaque
            FROM SNMPv2-SMI
        DisplayString, MacAddress, RowStatus, TEXTUAL-CONVENTION
            FROM SNMPv2-TC;

-----------------------------------------------
-- Textual Convention Definitions
-----------------------------------------------

    IpeEnableDisableValue ::= TEXTUAL-CONVENTION
        STATUS       current
        DESCRIPTION  ""
        SYNTAX       INTEGER { invalid(0), disabled(1), enabled(2) }

    IpePwIndex ::= TEXTUAL-CONVENTION
        DISPLAY-HINT "d"
        STATUS       current
        DESCRIPTION  ""
        SYNTAX       Integer32 (1..256)

    IpeVlanIndex ::= TEXTUAL-CONVENTION
        DISPLAY-HINT "d"
        STATUS       current
        DESCRIPTION  
            "VLAN ID.
            Value '4095' is reserved, and cannot set to the system."
        SYNTAX       Integer32 (1..4094)

-----------------------------------------------
-- Begin User MIB Object Definitions
-----------------------------------------------

    nec OBJECT IDENTIFIER
        ::= { enterprises 119 }

    nec-mib OBJECT IDENTIFIER
        ::= { nec 2 }

    necProductDepend OBJECT IDENTIFIER
        ::= { nec-mib 3 }

    radioEquipment OBJECT IDENTIFIER
        ::= { necProductDepend 69 }

    pasoNeoIpe-common OBJECT IDENTIFIER
        ::= { radioEquipment 501 }

-----------------------------------------------
-- IPE COMMON Group Definitions
-----------------------------------------------

    provisioningGroup OBJECT IDENTIFIER
        ::= { pasoNeoIpe-common 5 }

-----------------------------------------------
-- provisioningGroup Definitions
-----------------------------------------------

    provPwGroup OBJECT IDENTIFIER
        ::= { provisioningGroup 42 }

    provPwTdmLineTable OBJECT-TYPE
        SYNTAX       SEQUENCE OF ProvPwTdmLineEntry
        MAX-ACCESS   not-accessible
        STATUS       current
        DESCRIPTION  ""
        ::= { provPwGroup 4 }

    provPwTdmLineEntry OBJECT-TYPE
        SYNTAX       ProvPwTdmLineEntry
        MAX-ACCESS   not-accessible
        STATUS       current
        DESCRIPTION  ""
        INDEX        { provPwTdmLineIfIndex }
        ::= { provPwTdmLineTable 1 }

    ProvPwTdmLineEntry ::= SEQUENCE {
        provPwTdmLineIfIndex      InterfaceIndex,
        provPwTdmLineNEAddress    IpAddress,
        provPwTdmLineFrameMode    INTEGER,
        provPwTdmLineCasMode      IpeEnableDisableValue,
        provPwTdmLineCrc4Mode     IpeEnableDisableValue,
        provPwTdmLineJtrBfrDepth  INTEGER,
        provPwTdmLineDstMacCheck  IpeEnableDisableValue
    }

    provPwTdmLineIfIndex OBJECT-TYPE
        SYNTAX       InterfaceIndex
        MAX-ACCESS   not-accessible
        STATUS       current
        DESCRIPTION  "Index of this table."
        ::= { provPwTdmLineEntry 1 }

    provPwTdmLineNEAddress OBJECT-TYPE
        SYNTAX       IpAddress
        MAX-ACCESS   not-accessible
        STATUS       current
        DESCRIPTION  "reserved."
        ::= { provPwTdmLineEntry 2 }

    provPwTdmLineFrameMode OBJECT-TYPE
        SYNTAX       INTEGER { invalid(0), unframed(1) }
        MAX-ACCESS   read-write
        STATUS       current
        DESCRIPTION  "Frame Mode"
        DEFVAL       { unframed }
        ::= { provPwTdmLineEntry 3 }

    provPwTdmLineCasMode OBJECT-TYPE
        SYNTAX       IpeEnableDisableValue
        MAX-ACCESS   read-write
        STATUS       current
        DESCRIPTION  "PCM Codec (CAS)"
        DEFVAL       { disabled }
        ::= { provPwTdmLineEntry 4 }

    provPwTdmLineCrc4Mode OBJECT-TYPE
        SYNTAX       IpeEnableDisableValue
        MAX-ACCESS   read-write
        STATUS       current
        DESCRIPTION  "PCM Codec (CRC)"
        DEFVAL       { disabled }
        ::= { provPwTdmLineEntry 5 }

    provPwTdmLineJtrBfrDepth OBJECT-TYPE
        SYNTAX       INTEGER {
                         invalid(0),
                         jtr2ms(1),
                         jtr4ms(2),
                         jtr8ms(3),
                         jtr16ms(4),
                         jtr32ms(5),
                         jtr64ms(6),
                         jtr128ms(7)
                     }
        MAX-ACCESS   read-write
        STATUS       current
        DESCRIPTION  "Jitter Buffer"
        DEFVAL       { jtr8ms }
        ::= { provPwTdmLineEntry 6 }

    provPwTdmLineDstMacCheck OBJECT-TYPE
        SYNTAX       IpeEnableDisableValue
        MAX-ACCESS   read-write
        STATUS       current
        DESCRIPTION  "Destination MAC check"
        DEFVAL       { enabled }
        ::= { provPwTdmLineEntry 7 }

    provPwTdmTable OBJECT-TYPE
        SYNTAX       SEQUENCE OF ProvPwTdmEntry
        MAX-ACCESS   not-accessible
        STATUS       current
        DESCRIPTION  ""
        ::= { provPwGroup 5 }

    provPwTdmEntry OBJECT-TYPE
        SYNTAX       ProvPwTdmEntry
        MAX-ACCESS   not-accessible
        STATUS       current
        DESCRIPTION  ""
        INDEX        { provPwTdmPwIndex }
        ::= { provPwTdmTable 1 }

    ProvPwTdmEntry ::= SEQUENCE {
        provPwTdmPwIndex            IpePwIndex,
        provPwTdmNEAddress          IpAddress,
        provPwTdmIfIndex            InterfaceIndex,
        provPwTdmRtpHdrUsed         IpeEnableDisableValue,
        provPwTdmFrameLength        Integer32,
        provPwTdmEncapMode          INTEGER,
        provPwTdmRowStatus          RowStatus,
        provPwTdmAdaptiveClkSource  IpeEnableDisableValue
    }

    provPwTdmPwIndex OBJECT-TYPE
        SYNTAX       IpePwIndex
        MAX-ACCESS   not-accessible
        STATUS       current
        DESCRIPTION  "Index of this table."
        ::= { provPwTdmEntry 1 }

    provPwTdmNEAddress OBJECT-TYPE
        SYNTAX       IpAddress
        MAX-ACCESS   not-accessible
        STATUS       current
        DESCRIPTION  "reserved."
        ::= { provPwTdmEntry 2 }

    provPwTdmIfIndex OBJECT-TYPE
        SYNTAX       InterfaceIndex
        MAX-ACCESS   read-create
        STATUS       current
        DESCRIPTION  "MSE E1 Channel"
        ::= { provPwTdmEntry 3 }

    provPwTdmRtpHdrUsed OBJECT-TYPE
        SYNTAX       IpeEnableDisableValue
        MAX-ACCESS   read-create
        STATUS       current
        DESCRIPTION  "RTP Header"
        DEFVAL       { disabled }
        ::= { provPwTdmEntry 4 }

    provPwTdmFrameLength OBJECT-TYPE
        SYNTAX       Integer32 (1..8)
        MAX-ACCESS   read-create
        STATUS       current
        DESCRIPTION  "Capsule E1 Frame Size"
        DEFVAL       { 8 }
        ::= { provPwTdmEntry 5 }

    provPwTdmEncapMode OBJECT-TYPE
        SYNTAX       INTEGER { invalid(0), tdmOverEther(1) }
        MAX-ACCESS   read-create
        STATUS       current
        DESCRIPTION  "PWE Mode"
        DEFVAL       { tdmOverEther }
        ::= { provPwTdmEntry 6 }

    provPwTdmRowStatus OBJECT-TYPE
        SYNTAX       RowStatus
        MAX-ACCESS   read-create
        STATUS       current
        DESCRIPTION  "RowStatus of this table."
        ::= { provPwTdmEntry 7 }

    provPwTdmAdaptiveClkSource OBJECT-TYPE
        SYNTAX       IpeEnableDisableValue
        MAX-ACCESS   read-create
        STATUS       current
        DESCRIPTION  "Adaptive Clock"
        DEFVAL       { disabled }
        ::= { provPwTdmEntry 8 }

    provPwOverEthTable OBJECT-TYPE
        SYNTAX       SEQUENCE OF ProvPwOverEthEntry
        MAX-ACCESS   not-accessible
        STATUS       current
        DESCRIPTION  "PW over ETHER setting Table."
        ::= { provPwGroup 11 }

    provPwOverEthEntry OBJECT-TYPE
        SYNTAX       ProvPwOverEthEntry
        MAX-ACCESS   not-accessible
        STATUS       current
        DESCRIPTION  ""
        INDEX        { provPwOverEthPwIndex }
        ::= { provPwOverEthTable 1 }

    ProvPwOverEthEntry ::= SEQUENCE {
        provPwOverEthPwIndex        IpePwIndex,
        provPwOverEthNEAddress      IpAddress,
        provPwOverEthVlanId         IpeVlanIndex,
        provPwOverEthTpid           OCTET STRING,
        provPwOverEthCosValue       Integer32,
        provPwOverEthEcid           Integer32,
        provPwOverEthName           DisplayString,
        provPwOverEthDstMacAddress  MacAddress
    }

    provPwOverEthPwIndex OBJECT-TYPE
        SYNTAX       IpePwIndex
        MAX-ACCESS   not-accessible
        STATUS       current
        DESCRIPTION  "Index of this table."
        ::= { provPwOverEthEntry 1 }

    provPwOverEthNEAddress OBJECT-TYPE
        SYNTAX       IpAddress
        MAX-ACCESS   not-accessible
        STATUS       current
        DESCRIPTION  "reserved."
        ::= { provPwOverEthEntry 2 }

    provPwOverEthVlanId OBJECT-TYPE
        SYNTAX       IpeVlanIndex
        MAX-ACCESS   read-create
        STATUS       current
        DESCRIPTION  "VLAN ID"
        ::= { provPwOverEthEntry 3 }

    provPwOverEthTpid OBJECT-TYPE
        SYNTAX       OCTET STRING (SIZE(2..2))
        MAX-ACCESS   read-create
        STATUS       obsolete
        DESCRIPTION  "TPID"
        DEFVAL       { 'ff00'h }
        ::= { provPwOverEthEntry 4 }

    provPwOverEthCosValue OBJECT-TYPE
        SYNTAX       Integer32 (0..7)
        MAX-ACCESS   read-create
        STATUS       current
        DESCRIPTION  "CoS Value"
        DEFVAL       { 5 }
        ::= { provPwOverEthEntry 5 }

    provPwOverEthEcid OBJECT-TYPE
        SYNTAX       Integer32 (1..1048575)
        MAX-ACCESS   read-create
        STATUS       current
        DESCRIPTION  "ECID"
        ::= { provPwOverEthEntry 6 }

    provPwOverEthName OBJECT-TYPE
        SYNTAX       DisplayString (SIZE(0..32))
        MAX-ACCESS   read-create
        STATUS       current
        DESCRIPTION  "PWE Service Name"
        DEFVAL       { "" }
        ::= { provPwOverEthEntry 7 }

    provPwOverEthDstMacAddress OBJECT-TYPE
        SYNTAX       MacAddress
        MAX-ACCESS   read-create
        STATUS       current
        DESCRIPTION  "Destination MAC Address"
        ::= { provPwOverEthEntry 8 }

-----------------------------------------------
-- End User MIB Object Definitions
-----------------------------------------------

END

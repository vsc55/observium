--
-- ASN.1 MIB Definitions
-- Output Date: Tue Jul 12 15:00:44 2016
--

IPE-TERM-MIB DEFINITIONS ::= BEGIN

-----------------------------------------------
-- IMPORTS Definitions
-----------------------------------------------

    IMPORTS
        enterprises, Integer32, IpAddress, NOTIFICATION-TYPE, OBJECT-TYPE,
        Opaque
            FROM SNMPv2-SMI
        TEXTUAL-CONVENTION
            FROM SNMPv2-TC;

-----------------------------------------------
-- Textual Convention Definitions
-----------------------------------------------

    OffOnValue ::= TEXTUAL-CONVENTION
        STATUS       current
        DESCRIPTION  "Off/On Type"
        SYNTAX       INTEGER { invalid(0), off(1), on(2) }

    SeverityValue ::= TEXTUAL-CONVENTION
        STATUS       current
        DESCRIPTION  "Severity (CCITT Rec. X.733)"
        SYNTAX       INTEGER {
                         cleared(1),
                         indetermine(2),
                         critical(3),
                         major(4),
                         minor(5),
                         warning(6)
                     }

-----------------------------------------------
-- Begin User MIB Object Definitions
-----------------------------------------------

    nec OBJECT IDENTIFIER
        ::= { enterprises 119 }

    nec-mib OBJECT IDENTIFIER
        ::= { nec 2 }

    necProductDepend OBJECT IDENTIFIER
        ::= { nec-mib 3 }

    radioEquipment OBJECT IDENTIFIER
        ::= { necProductDepend 69 }

    pasoNeoIpe-common OBJECT IDENTIFIER
        ::= { radioEquipment 501 }

-----------------------------------------------
-- IPE COMMON Group Definitions
-----------------------------------------------

    alarmStatusGroup OBJECT IDENTIFIER
        ::= { pasoNeoIpe-common 3 }

-----------------------------------------------
-- alarmStatusGroup Definitions
-----------------------------------------------

    asTermCardGroup OBJECT IDENTIFIER
        ::= { alarmStatusGroup 36 }

    asTermCardTable OBJECT-TYPE
        SYNTAX       SEQUENCE OF AsTermCardEntry
        MAX-ACCESS   not-accessible
        STATUS       current
        DESCRIPTION  "TERM card object for iPASO1000."
        ::= { asTermCardGroup 1 }

    asTermCardEntry OBJECT-TYPE
        SYNTAX       AsTermCardEntry
        MAX-ACCESS   not-accessible
        STATUS       current
        DESCRIPTION  ""
        INDEX        { asTermCardIndex }
        ::= { asTermCardTable 1 }

    AsTermCardEntry ::= SEQUENCE {
        asTermCardIndex      Integer32,
        asTermCardNEAddress  IpAddress,
        termAlarm            SeverityValue,
        termComFailAlarm     SeverityValue,
        termUnequipped       SeverityValue,
        termTypeMismatch     SeverityValue,
        termCardChange       OffOnValue
    }

    asTermCardIndex OBJECT-TYPE
        SYNTAX       Integer32
        MAX-ACCESS   not-accessible
        STATUS       current
        DESCRIPTION  "Index of this table."
        ::= { asTermCardEntry 1 }

    asTermCardNEAddress OBJECT-TYPE
        SYNTAX       IpAddress
        MAX-ACCESS   not-accessible
        STATUS       current
        DESCRIPTION  "reserved."
        ::= { asTermCardEntry 2 }

    termAlarm OBJECT-TYPE
        SYNTAX       SeverityValue
        MAX-ACCESS   read-only
        STATUS       current
        DESCRIPTION  "Module Alarm"
        ::= { asTermCardEntry 3 }

    termComFailAlarm OBJECT-TYPE
        SYNTAX       SeverityValue
        MAX-ACCESS   read-only
        STATUS       current
        DESCRIPTION  "Communication FAIL"
        ::= { asTermCardEntry 4 }

    termUnequipped OBJECT-TYPE
        SYNTAX       SeverityValue
        MAX-ACCESS   read-only
        STATUS       current
        DESCRIPTION  "Unequipped"
        ::= { asTermCardEntry 5 }

    termTypeMismatch OBJECT-TYPE
        SYNTAX       SeverityValue
        MAX-ACCESS   read-only
        STATUS       current
        DESCRIPTION  "Type Mismatch"
        ::= { asTermCardEntry 6 }

    termCardChange OBJECT-TYPE
        SYNTAX       OffOnValue
        MAX-ACCESS   read-only
        STATUS       current
        DESCRIPTION  "TERM Card Change"
        ::= { asTermCardEntry 7 }

-----------------------------------------------
-- End User MIB Object Definitions
-----------------------------------------------

END

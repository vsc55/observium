--
-- ASN.1 MIB Definitions
-- Output Date: Tue Jul 12 15:00:59 2016
--

IPE-MSTP-MIB DEFINITIONS ::= BEGIN

-----------------------------------------------
-- IMPORTS Definitions
-----------------------------------------------

    IMPORTS
        BridgeId
            FROM BRIDGE-MIB
        InterfaceIndex
            FROM IF-MIB
        Counter32, enterprises, Integer32, IpAddress, NOTIFICATION-TYPE,
        OBJECT-TYPE, Opaque
            FROM SNMPv2-SMI
        DisplayString, RowStatus, TEXTUAL-CONVENTION
            FROM SNMPv2-TC;

-----------------------------------------------
-- Textual Convention Definitions
-----------------------------------------------

    EnableDisableValue ::= TEXTUAL-CONVENTION
        STATUS       current
        DESCRIPTION  "Enable/Disable Type"
        SYNTAX       INTEGER { invalid(0), disable(1), enable(2) }

    IpeBridgePriority ::= TEXTUAL-CONVENTION
        DISPLAY-HINT "d"
        STATUS       current
        DESCRIPTION  ""
        SYNTAX       Integer32 (0..61440)

    IpePortPathCost ::= TEXTUAL-CONVENTION
        DISPLAY-HINT "d"
        STATUS       current
        DESCRIPTION  ""
        SYNTAX       Integer32 (0..200000000)

    IpePortPriority ::= TEXTUAL-CONVENTION
        DISPLAY-HINT "d"
        STATUS       current
        DESCRIPTION  ""
        SYNTAX       Integer32 (0..240)

    IpePortRole ::= TEXTUAL-CONVENTION
        DISPLAY-HINT "d"
        STATUS       current
        DESCRIPTION  ""
        SYNTAX       INTEGER {
                         invalid(0),
                         disabled(1),
                         alternate(2),
                         backup(3),
                         root(4),
                         designated(5)
                     }

    IpePortState ::= TEXTUAL-CONVENTION
        DISPLAY-HINT "d"
        STATUS       current
        DESCRIPTION  ""
        SYNTAX       INTEGER {
                         invalid(0),
                         disabled(1),
                         blocking(2),
                         listening(3),
                         learning(4),
                         forwarding(5),
                         restricted(8),
                         guarded(9)
                     }

    IpeVlanList ::= TEXTUAL-CONVENTION
        STATUS       current
        DESCRIPTION  ""
        SYNTAX       OCTET STRING (SIZE(512..512))

-----------------------------------------------
-- Begin User MIB Object Definitions
-----------------------------------------------

    nec OBJECT IDENTIFIER
        ::= { enterprises 119 }

    nec-mib OBJECT IDENTIFIER
        ::= { nec 2 }

    necProductDepend OBJECT IDENTIFIER
        ::= { nec-mib 3 }

    radioEquipment OBJECT IDENTIFIER
        ::= { necProductDepend 69 }

    pasoNeoIpe-common OBJECT IDENTIFIER
        ::= { radioEquipment 501 }

-----------------------------------------------
-- IPE COMMON Group Definitions
-----------------------------------------------

    alarmStatusGroup OBJECT IDENTIFIER
        ::= { pasoNeoIpe-common 3 }

    provisioningGroup OBJECT IDENTIFIER
        ::= { pasoNeoIpe-common 5 }

    maintenanceGroup OBJECT IDENTIFIER
        ::= { pasoNeoIpe-common 6 }

-----------------------------------------------
-- alarmStatusGroup Definitions
-----------------------------------------------

    asMstpGroup OBJECT IDENTIFIER
        ::= { alarmStatusGroup 44 }

    asMstpBridgeCistTable OBJECT-TYPE
        SYNTAX       SEQUENCE OF AsMstpBridgeCistEntry
        MAX-ACCESS   not-accessible
        STATUS       current
        DESCRIPTION  
            "The Common and Internal Spanning Tree (CIST) Alarm/Status
            table."
        ::= { asMstpGroup 1 }

    asMstpBridgeCistEntry OBJECT-TYPE
        SYNTAX       AsMstpBridgeCistEntry
        MAX-ACCESS   not-accessible
        STATUS       current
        DESCRIPTION  "A CIST Table Entry."
        INDEX        { asMstpBridgeCistIndex }
        ::= { asMstpBridgeCistTable 1 }

    AsMstpBridgeCistEntry ::= SEQUENCE {
        asMstpBridgeCistIndex         Integer32,
        asMstpBridgeCistNEAddress     IpAddress,
        asMstpBridgeCistRegionalRoot  BridgeId,
        asMstpBridgeCistTopChanges    Counter32,
        asMstpBridgeCistRoot          BridgeId
    }

    asMstpBridgeCistIndex OBJECT-TYPE
        SYNTAX       Integer32 (1..1)
        MAX-ACCESS   not-accessible
        STATUS       current
        DESCRIPTION  "Index of this table."
        ::= { asMstpBridgeCistEntry 1 }

    asMstpBridgeCistNEAddress OBJECT-TYPE
        SYNTAX       IpAddress
        MAX-ACCESS   not-accessible
        STATUS       obsolete
        DESCRIPTION  "reserved."
        ::= { asMstpBridgeCistEntry 2 }

    asMstpBridgeCistRegionalRoot OBJECT-TYPE
        SYNTAX       BridgeId
        MAX-ACCESS   read-only
        STATUS       current
        DESCRIPTION  
            "In an MSTP Bridge, the CIST Regional Root Identifier parameter,
            i.e. the Bridge Identifier of the current CIST Regional Root."
        ::= { asMstpBridgeCistEntry 3 }

    asMstpBridgeCistTopChanges OBJECT-TYPE
        SYNTAX       Counter32
        MAX-ACCESS   read-only
        STATUS       current
        DESCRIPTION  
            "MSTP Topology Changed Status. The total number of topology
            chagnes detected by this bridge since the equipment was last
            initialized."
        ::= { asMstpBridgeCistEntry 4 }

    asMstpBridgeCistRoot OBJECT-TYPE
        SYNTAX       BridgeId
        MAX-ACCESS   read-only
        STATUS       current
        DESCRIPTION  "MSTP CIST Root"
        ::= { asMstpBridgeCistEntry 5 }

    asMstpBridgeMstTable OBJECT-TYPE
        SYNTAX       SEQUENCE OF AsMstpBridgeMstEntry
        MAX-ACCESS   not-accessible
        STATUS       current
        DESCRIPTION  
            "In an MSTP Bridge, the MSTP Table. Each row in the Table
            represents information regarding a Bridge's Bridge Protocol
            Entity for the specified Spanning Tree instance.
            
            Entries in this table is retained across reinitializations of the
            management system."
        ::= { asMstpGroup 2 }

    asMstpBridgeMstEntry OBJECT-TYPE
        SYNTAX       AsMstpBridgeMstEntry
        MAX-ACCESS   not-accessible
        STATUS       current
        DESCRIPTION  "A MSTP Table entry."
        INDEX        { asMstpBridgeMstIndex }
        ::= { asMstpBridgeMstTable 1 }

    AsMstpBridgeMstEntry ::= SEQUENCE {
        asMstpBridgeMstIndex         Integer32,
        asMstpBridgeMstNEAddress     IpAddress,
        asMstpBridgeMstRegionalRoot  BridgeId,
        asMstpBridgeMstTopChanges    Counter32
    }

    asMstpBridgeMstIndex OBJECT-TYPE
        SYNTAX       Integer32 (1..4)
        MAX-ACCESS   not-accessible
        STATUS       current
        DESCRIPTION  "Index of this table."
        ::= { asMstpBridgeMstEntry 1 }

    asMstpBridgeMstNEAddress OBJECT-TYPE
        SYNTAX       IpAddress
        MAX-ACCESS   not-accessible
        STATUS       obsolete
        DESCRIPTION  "reserved."
        ::= { asMstpBridgeMstEntry 2 }

    asMstpBridgeMstRegionalRoot OBJECT-TYPE
        SYNTAX       BridgeId
        MAX-ACCESS   read-only
        STATUS       current
        DESCRIPTION  
            "In an MSTP Bridge, the Designated Root parameter value, i.e. the
            Bridge Identifier of the Root Bridge for the MSTI."
        ::= { asMstpBridgeMstEntry 3 }

    asMstpBridgeMstTopChanges OBJECT-TYPE
        SYNTAX       Counter32
        MAX-ACCESS   read-only
        STATUS       current
        DESCRIPTION  
            "In an MSTP Bridge, count of the times tcWhile has been
            non-zero for any Port for the MSTI since the Bridge was powered
            on or initialized."
        ::= { asMstpBridgeMstEntry 4 }

    asMstpPortCistTable OBJECT-TYPE
        SYNTAX       SEQUENCE OF AsMstpPortCistEntry
        MAX-ACCESS   not-accessible
        STATUS       current
        DESCRIPTION  
            "The CIST Port Table. Each row in the Table represents
            information regarding a specific Port within the Bridge's Bridge
            Protocol Entity, for the CIST."
        ::= { asMstpGroup 3 }

    asMstpPortCistEntry OBJECT-TYPE
        SYNTAX       AsMstpPortCistEntry
        MAX-ACCESS   not-accessible
        STATUS       current
        DESCRIPTION  "A CIST Port Table entry."
        INDEX        { asMstpPortCistIfIndex }
        ::= { asMstpPortCistTable 1 }

    AsMstpPortCistEntry ::= SEQUENCE {
        asMstpPortCistIfIndex             InterfaceIndex,
        asMstpPortCistNEAddress           IpAddress,
        asMstpPortCistRole                IpePortRole,
        asMstpPortCistState               IpePortState,
        asMstpPortCistRegionalRoot        BridgeId,
        asMstpPortCistProtoVersion        INTEGER,
        asMstpPortCistPathCost            Integer32,
        asMstpPortCistInvalidBpdu         INTEGER,
        asMstpPortCistDesignatedPathCost  Integer32,
        asMstpPortCistDesignatedBridge    BridgeId,
        asMstpPortCistDesignatedPort      OCTET STRING,
        asMstpPortCistForwardTransitions  Counter32,
        asMstpPortCistOperEdgePort        INTEGER
    }

    asMstpPortCistIfIndex OBJECT-TYPE
        SYNTAX       InterfaceIndex
        MAX-ACCESS   not-accessible
        STATUS       current
        DESCRIPTION  "Index of this table."
        ::= { asMstpPortCistEntry 1 }

    asMstpPortCistNEAddress OBJECT-TYPE
        SYNTAX       IpAddress
        MAX-ACCESS   not-accessible
        STATUS       obsolete
        DESCRIPTION  "reserved."
        ::= { asMstpPortCistEntry 2 }

    asMstpPortCistRole OBJECT-TYPE
        SYNTAX       IpePortRole
        MAX-ACCESS   read-only
        STATUS       current
        DESCRIPTION  
            "The current Port Role for the Port (i.e., Root, Alternate,
            Designated, or Backup), for the CIST."
        ::= { asMstpPortCistEntry 3 }

    asMstpPortCistState OBJECT-TYPE
        SYNTAX       IpePortState
        MAX-ACCESS   read-only
        STATUS       current
        DESCRIPTION  
            "In an MSTP Bridge, the current state of the Port (i.e.,
            Disabled, Listening, Learning, Forwarding, or Blocking), for the
            MSTI."
        ::= { asMstpPortCistEntry 4 }

    asMstpPortCistRegionalRoot OBJECT-TYPE
        SYNTAX       BridgeId
        MAX-ACCESS   read-only
        STATUS       current
        DESCRIPTION  
            "In an MSTP Bridge, the CIST Regional Root Identifier, i.e. the
            Bridge Identifier of the current CIST Regional Root, for the
            CIST."
        ::= { asMstpPortCistEntry 5 }

    asMstpPortCistProtoVersion OBJECT-TYPE
        SYNTAX       INTEGER { invalid(0), stp(1), rstp(2), mstp(3) }
        MAX-ACCESS   read-only
        STATUS       current
        DESCRIPTION  
            "In an MSTP Bridge, the current version of xSTP Protocol for the
            Port."
        ::= { asMstpPortCistEntry 6 }

    asMstpPortCistPathCost OBJECT-TYPE
        SYNTAX       Integer32
        MAX-ACCESS   read-only
        STATUS       current
        DESCRIPTION  
            "In an MSTP Bridge, the CIST Path Cost parameter, i.e. the
            CISTpath cost from the transmitting Bridge to the CIST Regional
            Root. The sum (about 20 possible out of the given range) of
            multiple port path costs. Also, if the 'transmitting Bridge' is
            the 'CIST Regional Root', then this value could be zero."
        ::= { asMstpPortCistEntry 7 }

    asMstpPortCistInvalidBpdu OBJECT-TYPE
        SYNTAX       INTEGER { invalid(0) }
        MAX-ACCESS   read-only
        STATUS       current
        DESCRIPTION  "MSTP IST Invalid BPDU Received status"
        ::= { asMstpPortCistEntry 8 }

    asMstpPortCistDesignatedPathCost OBJECT-TYPE
        SYNTAX       Integer32
        MAX-ACCESS   read-only
        STATUS       current
        DESCRIPTION  
            "In an MSTP Bridge, the CIST Path Cost parameter, i.e. the CIST
            path cost from the transmitting Bridge to the CIST Regional Root.
            The sum (about 20 possible out of the given range) of multiple
            port path costs. Also, if the 'transmitting Bridge' is the 'CIST
            Regional Root', then this value could be zero."
        ::= { asMstpPortCistEntry 9 }

    asMstpPortCistDesignatedBridge OBJECT-TYPE
        SYNTAX       BridgeId
        MAX-ACCESS   read-only
        STATUS       current
        DESCRIPTION  
            "In an MSTP Bridge, the Designated Root parameter value, i.e. the
            Bridge Identifier of the Root Bridge for the MSTI."
        ::= { asMstpPortCistEntry 10 }

    asMstpPortCistDesignatedPort OBJECT-TYPE
        SYNTAX       OCTET STRING
        MAX-ACCESS   read-only
        STATUS       current
        DESCRIPTION  
            "The CIST Regional Root Identifier component of the Port's port
            priority vector for the CIST."
        ::= { asMstpPortCistEntry 11 }

    asMstpPortCistForwardTransitions OBJECT-TYPE
        SYNTAX       Counter32
        MAX-ACCESS   read-only
        STATUS       current
        DESCRIPTION  
            "The number of times this port has transitioned from the Learning
            state to the Forwarding state."
        ::= { asMstpPortCistEntry 12 }

    asMstpPortCistOperEdgePort OBJECT-TYPE
        SYNTAX       INTEGER { alarmOff(0), alarmOn(1) }
        MAX-ACCESS   read-only
        STATUS       current
        DESCRIPTION  
            "The operational value of the Edge Port parameter.
            If the port whose 'provMstpPortCistEdgePort' is 'enable' receives
            the BPDU, the object will be changed to alarmOn.
            
            When the 'provMstpPortCistEdgePort' is 'disable', the object
            always shows 'alarmOff'."
        ::= { asMstpPortCistEntry 13 }

    asMstpPortMstTable OBJECT-TYPE
        SYNTAX       SEQUENCE OF AsMstpPortMstEntry
        MAX-ACCESS   not-accessible
        STATUS       current
        DESCRIPTION  
            "The MSTP Port Table. Each row in the Table represents
            information
            regarding a specific Port within the Bridge's Bridge Protocol
            Entity, for a given MSTI."
        ::= { asMstpGroup 4 }

    asMstpPortMstEntry OBJECT-TYPE
        SYNTAX       AsMstpPortMstEntry
        MAX-ACCESS   not-accessible
        STATUS       current
        DESCRIPTION  "A MSTP Port Table entry."
        INDEX        { asMstpPortMstIfIndex, asMstpPortMstIndex }
        ::= { asMstpPortMstTable 1 }

    AsMstpPortMstEntry ::= SEQUENCE {
        asMstpPortMstIfIndex             InterfaceIndex,
        asMstpPortMstIndex               Integer32,
        asMstpPortMstNEAddress           IpAddress,
        asMstpPortMstRole                IpePortRole,
        asMstpPortMstState               IpePortState,
        asMstpPortMstRegionalRoot        BridgeId,
        asMstpPortMstPathCost            Integer32,
        asMstpPortMstDesignatedPathCost  Integer32,
        asMstpPortMstDesignatedBridge    BridgeId,
        asMstpPortMstDesignatedPort      OCTET STRING
    }

    asMstpPortMstIfIndex OBJECT-TYPE
        SYNTAX       InterfaceIndex
        MAX-ACCESS   not-accessible
        STATUS       current
        DESCRIPTION  "Index of this table."
        ::= { asMstpPortMstEntry 1 }

    asMstpPortMstIndex OBJECT-TYPE
        SYNTAX       Integer32 (1..4)
        MAX-ACCESS   not-accessible
        STATUS       current
        DESCRIPTION  "Index of this table."
        ::= { asMstpPortMstEntry 2 }

    asMstpPortMstNEAddress OBJECT-TYPE
        SYNTAX       IpAddress
        MAX-ACCESS   not-accessible
        STATUS       obsolete
        DESCRIPTION  "reserved."
        ::= { asMstpPortMstEntry 3 }

    asMstpPortMstRole OBJECT-TYPE
        SYNTAX       IpePortRole
        MAX-ACCESS   read-only
        STATUS       current
        DESCRIPTION  
            "In an MSTP Bridge, the current Port Role for the Port (i.e.,
            Root, Alternate, Designated, or Backup), for the MSTI."
        ::= { asMstpPortMstEntry 4 }

    asMstpPortMstState OBJECT-TYPE
        SYNTAX       IpePortState
        MAX-ACCESS   read-only
        STATUS       current
        DESCRIPTION  
            "In an MSTP Bridge, the current state of the Port (i.e.,
            Disabled, Listening, Learning, Forwarding, or Blocking), for the
            MSTI."
        ::= { asMstpPortMstEntry 5 }

    asMstpPortMstRegionalRoot OBJECT-TYPE
        SYNTAX       BridgeId
        MAX-ACCESS   read-only
        STATUS       current
        DESCRIPTION  
            "In an MSTP Bridge, the Regional Root Identifier component of the
            Port's MSTI port priority vector for the MSTI."
        ::= { asMstpPortMstEntry 6 }

    asMstpPortMstPathCost OBJECT-TYPE
        SYNTAX       Integer32
        MAX-ACCESS   read-only
        STATUS       current
        DESCRIPTION  
            "In an MSTP Bridge, the Port's Port Path Cost parameter value for
            the MSTI."
        ::= { asMstpPortMstEntry 7 }

    asMstpPortMstDesignatedPathCost OBJECT-TYPE
        SYNTAX       Integer32
        MAX-ACCESS   read-only
        STATUS       current
        DESCRIPTION  
            "In an MSTP Bridge, the Internal Root Path Cost component of the
            Port's MSTI port priority vector for the MSTI."
        ::= { asMstpPortMstEntry 8 }

    asMstpPortMstDesignatedBridge OBJECT-TYPE
        SYNTAX       BridgeId
        MAX-ACCESS   read-only
        STATUS       current
        DESCRIPTION  
            "In an MSTP Bridge, the Designated Bridge Identifier component of
            the Port's MSTI port priority vector for the MSTI."
        ::= { asMstpPortMstEntry 9 }

    asMstpPortMstDesignatedPort OBJECT-TYPE
        SYNTAX       OCTET STRING
        MAX-ACCESS   read-only
        STATUS       current
        DESCRIPTION  
            "In an MSTP Bridge, the Designated Port Identifier component of
            the Port's MSTI port priority vector for the MSTI."
        ::= { asMstpPortMstEntry 10 }

-----------------------------------------------
-- provisioningGroup Definitions
-----------------------------------------------

    provMstpGroup OBJECT IDENTIFIER
        ::= { provisioningGroup 44 }

    provMstpBridgeTable OBJECT-TYPE
        SYNTAX       SEQUENCE OF ProvMstpBridgeEntry
        MAX-ACCESS   not-accessible
        STATUS       current
        DESCRIPTION  
            "In an MSTP Bridge Table represents information regarding a
            Bridge's Bridge Protocol."
        ::= { provMstpGroup 1 }

    provMstpBridgeEntry OBJECT-TYPE
        SYNTAX       ProvMstpBridgeEntry
        MAX-ACCESS   not-accessible
        STATUS       current
        DESCRIPTION  ""
        INDEX        { provMstpBridgeIndex }
        ::= { provMstpBridgeTable 1 }

    ProvMstpBridgeEntry ::= SEQUENCE {
        provMstpBridgeIndex            Integer32,
        provMstpBridgeNEAddress        IpAddress,
        provMstpBridgeEnable           EnableDisableValue,
        provMstpBridgeMaxAge           Integer32,
        provMstpBridgeHelloTime        Integer32,
        provMstpBridgeForwardDelay     Integer32,
        provMstpBridgeTxHoldCount      Integer32,
        provMstpBridgeAmrAutoPathCost  EnableDisableValue,
        provMstpBridgeAmrAutoConv      EnableDisableValue,
        provMstpBridgeLagAutoPathCost  EnableDisableValue,
        provMstpBridgeLagAutoConv      EnableDisableValue,
        provMstpBridgeMaxHopCount      Integer32,
        provMstpBridgeRegionName       DisplayString,
        provMstpBridgeRevisionNum      Integer32,
        provMstpBridgeBpduFilter       EnableDisableValue,
        provMstpBridgeBpduGuardTimer   Integer32
    }

    provMstpBridgeIndex OBJECT-TYPE
        SYNTAX       Integer32 (1..1)
        MAX-ACCESS   not-accessible
        STATUS       current
        DESCRIPTION  "Index of this table."
        ::= { provMstpBridgeEntry 1 }

    provMstpBridgeNEAddress OBJECT-TYPE
        SYNTAX       IpAddress
        MAX-ACCESS   not-accessible
        STATUS       current
        DESCRIPTION  "reserved."
        ::= { provMstpBridgeEntry 2 }

    provMstpBridgeEnable OBJECT-TYPE
        SYNTAX       EnableDisableValue
        MAX-ACCESS   read-write
        STATUS       current
        DESCRIPTION  "Enable/Disable MSTP function."
        DEFVAL       { disable }
        ::= { provMstpBridgeEntry 3 }

    provMstpBridgeMaxAge OBJECT-TYPE
        SYNTAX       Integer32 (6..40)
        UNITS        "seconds"
        MAX-ACCESS   read-write
        STATUS       current
        DESCRIPTION  
            "The value that all bridges use for MaxAge when this bridge is
            acting as the root."
        DEFVAL       { 20 }
        ::= { provMstpBridgeEntry 4 }

    provMstpBridgeHelloTime OBJECT-TYPE
        SYNTAX       Integer32 (1..2)
        UNITS        "seconds"
        MAX-ACCESS   read-write
        STATUS       current
        DESCRIPTION  
            "The value that all bridges use for HelloTime when this bridge is
            acting as the root.
            
            Note: This object cannot be modified, acting as read-only
            object."
        DEFVAL       { 2 }
        ::= { provMstpBridgeEntry 5 }

    provMstpBridgeForwardDelay OBJECT-TYPE
        SYNTAX       Integer32 (4..30)
        UNITS        "seconds"
        MAX-ACCESS   read-write
        STATUS       current
        DESCRIPTION  
            "The value that all bridges use for ForwardDelay when this bridge
            is acting as the root."
        DEFVAL       { 15 }
        ::= { provMstpBridgeEntry 6 }

    provMstpBridgeTxHoldCount OBJECT-TYPE
        SYNTAX       Integer32 (1..10)
        MAX-ACCESS   read-write
        STATUS       current
        DESCRIPTION  
            "The value used by the Port Transmit state machine to limit
            the maximum transmission rate."
        DEFVAL       { 6 }
        ::= { provMstpBridgeEntry 7 }

    provMstpBridgeMaxHopCount OBJECT-TYPE
        SYNTAX       Integer32 (1..40)
        MAX-ACCESS   read-write
        STATUS       current
        DESCRIPTION  "In an MSTP Bridge, the MaxHops parameter."
        DEFVAL       { 20 }
        ::= { provMstpBridgeEntry 12 }

    provMstpBridgeRegionName OBJECT-TYPE
        SYNTAX       DisplayString (SIZE(0..32))
        MAX-ACCESS   read-write
        STATUS       current
        DESCRIPTION  
            "In an MSTP Bridge, the Configuration Name in the MST
            Configuration Identifier."
        DEFVAL       { "" }
        ::= { provMstpBridgeEntry 13 }

    provMstpBridgeRevisionNum OBJECT-TYPE
        SYNTAX       Integer32 (0..65535)
        MAX-ACCESS   read-write
        STATUS       current
        DESCRIPTION  
            "In an MSTP Bridge, the Revision number in the MST Configuration
            Identifier."
        DEFVAL       { 0 }
        ::= { provMstpBridgeEntry 14 }

    provMstpBridgeBpduFilter OBJECT-TYPE
        SYNTAX       EnableDisableValue
        MAX-ACCESS   read-write
        STATUS       current
        DESCRIPTION  "BPDU Filter (MSTP)"
        DEFVAL       { disable }
        ::= { provMstpBridgeEntry 15 }

    provMstpBridgeBpduGuardTimer OBJECT-TYPE
        SYNTAX       Integer32 (0..0|10..1000000)
        UNITS        "seconds"
        MAX-ACCESS   read-write
        STATUS       current
        DESCRIPTION  "BPDU Guard Timer"
        DEFVAL       { 0 }
        ::= { provMstpBridgeEntry 16 }

    provMstpBridgeCistTable OBJECT-TYPE
        SYNTAX       SEQUENCE OF ProvMstpBridgeCistEntry
        MAX-ACCESS   not-accessible
        STATUS       current
        DESCRIPTION  
            "The Common and Internal Spanning Tree (CIST) Provisioning
            Table."
        ::= { provMstpGroup 2 }

    provMstpBridgeCistEntry OBJECT-TYPE
        SYNTAX       ProvMstpBridgeCistEntry
        MAX-ACCESS   not-accessible
        STATUS       current
        DESCRIPTION  "A CIST Table entry."
        INDEX        { provMstpBridgeCistIndex }
        ::= { provMstpBridgeCistTable 1 }

    ProvMstpBridgeCistEntry ::= SEQUENCE {
        provMstpBridgeCistIndex      Integer32,
        provMstpBridgeCistNEAddress  IpAddress,
        provMstpBridgeCistPriority   IpeBridgePriority,
        provMstpBridgeCistVlanList   IpeVlanList
    }

    provMstpBridgeCistIndex OBJECT-TYPE
        SYNTAX       Integer32 (1..1)
        MAX-ACCESS   not-accessible
        STATUS       current
        DESCRIPTION  "Index of this table."
        ::= { provMstpBridgeCistEntry 1 }

    provMstpBridgeCistNEAddress OBJECT-TYPE
        SYNTAX       IpAddress
        MAX-ACCESS   not-accessible
        STATUS       current
        DESCRIPTION  "reserved."
        ::= { provMstpBridgeCistEntry 2 }

    provMstpBridgeCistPriority OBJECT-TYPE
        SYNTAX       IpeBridgePriority
        MAX-ACCESS   read-write
        STATUS       current
        DESCRIPTION  
            "The value of the write-able portion of the Bridge ID (i.e., the
            first two octets of the (8 octet long) Bridge ID).  The other
            (last) 6 octets of the Bridge ID are given by the value of Base
            MAC Address,
            permissible values are 0-61440, in steps of 4096."
        DEFVAL       { 32768 }
        ::= { provMstpBridgeCistEntry 3 }

    provMstpBridgeCistVlanList OBJECT-TYPE
        SYNTAX       IpeVlanList
        MAX-ACCESS   read-write
        STATUS       current
        DESCRIPTION  
            "This object contains the 4096 bit vector indicating which VIDs
            are assigned to this MSTID.
            The high order bit of the first octet corresponds to the first
            bit of the vector, while the low order bit of the last octet
            corresponds to the last bit of this portion of the vector.
            A bit that is on (equal to 1) indicates that the corresponding
            VID is assigned to this MSTID.
            
            One VID cannot be shared by multiple instances. If the configured
            VID is assigned to other instance, the VID is removed from the
            other instance and assigned to the requested instance.
            If the VID is not assigned to any MSTI, the VID will be assigned
            to to CIST automatically. But the VID is not assigned to any MSTI
            and CIST by removing from provMstpBridgeCistVlanList, the VID is
            not assigned automatically. The manager must care of such
            situation, and must assign the VID manually."
        ::= { provMstpBridgeCistEntry 4 }

    provMstpBridgeMstTable OBJECT-TYPE
        SYNTAX       SEQUENCE OF ProvMstpBridgeMstEntry
        MAX-ACCESS   not-accessible
        STATUS       current
        DESCRIPTION  
            "In an MSTP Bridge, the MSTP Table. Each row in the Table
            represents information regarding a Bridge's Bridge Protocol
            Entity for the specified Spanning Tree instance."
        ::= { provMstpGroup 3 }

    provMstpBridgeMstEntry OBJECT-TYPE
        SYNTAX       ProvMstpBridgeMstEntry
        MAX-ACCESS   not-accessible
        STATUS       current
        DESCRIPTION  "A MSTP Table entry."
        INDEX        { provMstpBridgeMstIndex }
        ::= { provMstpBridgeMstTable 1 }

    ProvMstpBridgeMstEntry ::= SEQUENCE {
        provMstpBridgeMstIndex        Integer32,
        provMstpBridgeMstNEAddress    IpAddress,
        provMstpBridgeMstPriority     IpeBridgePriority,
        provMstpBridgeMstVlanList     IpeVlanList,
        provMstpBridgeMstInstanceNum  Integer32,
        provMstpBridgeMstRowStatus    RowStatus
    }

    provMstpBridgeMstIndex OBJECT-TYPE
        SYNTAX       Integer32 (1..4)
        MAX-ACCESS   not-accessible
        STATUS       current
        DESCRIPTION  "Index of this table."
        ::= { provMstpBridgeMstEntry 1 }

    provMstpBridgeMstNEAddress OBJECT-TYPE
        SYNTAX       IpAddress
        MAX-ACCESS   not-accessible
        STATUS       obsolete
        DESCRIPTION  "reserved."
        ::= { provMstpBridgeMstEntry 2 }

    provMstpBridgeMstPriority OBJECT-TYPE
        SYNTAX       IpeBridgePriority
        MAX-ACCESS   read-create
        STATUS       current
        DESCRIPTION  
            "In an MSTP Bridge, the Bridge Priority parameter value for the
            MSTI, i.e. the four most significant bits of the Bridge
            Identifier for the MSTI."
        DEFVAL       { 32768 }
        ::= { provMstpBridgeMstEntry 3 }

    provMstpBridgeMstVlanList OBJECT-TYPE
        SYNTAX       IpeVlanList
        MAX-ACCESS   read-create
        STATUS       current
        DESCRIPTION  
            "This object contains the 4096 bit vector indicating which VIDs
            are assigned to this MSTID.
            The high order bit of the first octet corresponds to the first
            bit of this portion of the vector, while the low order bit of the
            last octet corresponds to the last bit of this portion of the
            vector.
            A bit that is on (equal to 1) indicates that the corresponding
            VID is assigned to this MSTID.
            
            One VID cannot be shared by multiple instances. If the configured
            VID is assigned to other instance, the VID is removed from the
            other instance and assigned to the requested instance.
            If the VID is not assigned to any MSTI, the VID will be assigned
            to to CIST automatically."
        ::= { provMstpBridgeMstEntry 4 }

    provMstpBridgeMstInstanceNum OBJECT-TYPE
        SYNTAX       Integer32 (1..4093)
        MAX-ACCESS   read-create
        STATUS       current
        DESCRIPTION  
            "In an MSTP Bridge, this parameter is the MSTID, i.e. the
            identifier of a Spanning Tree (or MST) Instance."
        ::= { provMstpBridgeMstEntry 5 }

    provMstpBridgeMstRowStatus OBJECT-TYPE
        SYNTAX       RowStatus
        MAX-ACCESS   read-create
        STATUS       current
        DESCRIPTION  "RowStatus of this table."
        ::= { provMstpBridgeMstEntry 6 }

    provMstpPortCistTable OBJECT-TYPE
        SYNTAX       SEQUENCE OF ProvMstpPortCistEntry
        MAX-ACCESS   not-accessible
        STATUS       current
        DESCRIPTION  
            "The CIST Port Table. Each row in the Table represents
            information regarding a specific Port within the Bridge's Bridge
            Protocol Entity, for the CIST."
        ::= { provMstpGroup 4 }

    provMstpPortCistEntry OBJECT-TYPE
        SYNTAX       ProvMstpPortCistEntry
        MAX-ACCESS   not-accessible
        STATUS       current
        DESCRIPTION  "A CIST Port Table entry."
        INDEX        { provMstpPortCistIfIndex }
        ::= { provMstpPortCistTable 1 }

    ProvMstpPortCistEntry ::= SEQUENCE {
        provMstpPortCistIfIndex       InterfaceIndex,
        provMstpPortCistNEAddress     IpAddress,
        provMstpPortCistPriority      IpePortPriority,
        provMstpPortCistEnable        EnableDisableValue,
        provMstpPortCistEdgePort      EnableDisableValue,
        provMstpPortCistPathCost      IpePortPathCost,
        provMstpPortCistBpduGuard     EnableDisableValue,
        provMstpPortCistRestrictRole  EnableDisableValue
    }

    provMstpPortCistIfIndex OBJECT-TYPE
        SYNTAX       InterfaceIndex
        MAX-ACCESS   not-accessible
        STATUS       current
        DESCRIPTION  "Index of this table."
        ::= { provMstpPortCistEntry 1 }

    provMstpPortCistNEAddress OBJECT-TYPE
        SYNTAX       IpAddress
        MAX-ACCESS   not-accessible
        STATUS       obsolete
        DESCRIPTION  "reserved."
        ::= { provMstpPortCistEntry 2 }

    provMstpPortCistPriority OBJECT-TYPE
        SYNTAX       IpePortPriority
        MAX-ACCESS   read-write
        STATUS       current
        DESCRIPTION  "STP Port Priority (MSTP - CIST)"
        DEFVAL       { 0 }
        ::= { provMstpPortCistEntry 3 }

    provMstpPortCistEnable OBJECT-TYPE
        SYNTAX       EnableDisableValue
        MAX-ACCESS   read-write
        STATUS       current
        DESCRIPTION  "CIST Enable (MSTP)"
        DEFVAL       { disable }
        ::= { provMstpPortCistEntry 4 }

    provMstpPortCistEdgePort OBJECT-TYPE
        SYNTAX       EnableDisableValue
        MAX-ACCESS   read-write
        STATUS       current
        DESCRIPTION  "Edge Port (MSTP - CIST)"
        DEFVAL       { disable }
        ::= { provMstpPortCistEntry 5 }

    provMstpPortCistPathCost OBJECT-TYPE
        SYNTAX       IpePortPathCost
        MAX-ACCESS   read-write
        STATUS       current
        DESCRIPTION  "STP Port Path Cost (MSTP - CIST)"
        ::= { provMstpPortCistEntry 6 }

    provMstpPortCistBpduGuard OBJECT-TYPE
        SYNTAX       EnableDisableValue
        MAX-ACCESS   read-write
        STATUS       current
        DESCRIPTION  "BPDU Guard (MSTP - CIST)"
        DEFVAL       { disable }
        ::= { provMstpPortCistEntry 7 }

    provMstpPortCistRestrictRole OBJECT-TYPE
        SYNTAX       EnableDisableValue
        MAX-ACCESS   read-write
        STATUS       current
        DESCRIPTION  "Root Guard (MSTP - CIST)"
        DEFVAL       { disable }
        ::= { provMstpPortCistEntry 8 }

    provMstpPortMstTable OBJECT-TYPE
        SYNTAX       SEQUENCE OF ProvMstpPortMstEntry
        MAX-ACCESS   not-accessible
        STATUS       current
        DESCRIPTION  ""
        ::= { provMstpGroup 5 }

    provMstpPortMstEntry OBJECT-TYPE
        SYNTAX       ProvMstpPortMstEntry
        MAX-ACCESS   not-accessible
        STATUS       current
        DESCRIPTION  ""
        INDEX        { provMstpPortMstIfIndex, provMstpPortMstIndex }
        ::= { provMstpPortMstTable 1 }

    ProvMstpPortMstEntry ::= SEQUENCE {
        provMstpPortMstIfIndex    InterfaceIndex,
        provMstpPortMstIndex      Integer32,
        provMstpPortMstNEAddress  IpAddress,
        provMstpPortMstPriority   IpePortPriority,
        provMstpPortMstEnable     EnableDisableValue,
        provMstpPortMstPathCost   IpePortPathCost
    }

    provMstpPortMstIfIndex OBJECT-TYPE
        SYNTAX       InterfaceIndex
        MAX-ACCESS   not-accessible
        STATUS       current
        DESCRIPTION  "Index of this table."
        ::= { provMstpPortMstEntry 1 }

    provMstpPortMstIndex OBJECT-TYPE
        SYNTAX       Integer32 (1..4)
        MAX-ACCESS   not-accessible
        STATUS       current
        DESCRIPTION  "Index of this table."
        ::= { provMstpPortMstEntry 2 }

    provMstpPortMstNEAddress OBJECT-TYPE
        SYNTAX       IpAddress
        MAX-ACCESS   not-accessible
        STATUS       obsolete
        DESCRIPTION  "reserved."
        ::= { provMstpPortMstEntry 3 }

    provMstpPortMstPriority OBJECT-TYPE
        SYNTAX       IpePortPriority
        MAX-ACCESS   read-write
        STATUS       current
        DESCRIPTION  "STP Port Priority (MSTP - MSTI)"
        DEFVAL       { 0 }
        ::= { provMstpPortMstEntry 4 }

    provMstpPortMstEnable OBJECT-TYPE
        SYNTAX       EnableDisableValue
        MAX-ACCESS   read-write
        STATUS       current
        DESCRIPTION  "MST Enable (MSTP)"
        DEFVAL       { disable }
        ::= { provMstpPortMstEntry 5 }

    provMstpPortMstPathCost OBJECT-TYPE
        SYNTAX       IpePortPathCost
        MAX-ACCESS   read-write
        STATUS       current
        DESCRIPTION  "STP Port Path Cost (MSTP - MSTI)"
        ::= { provMstpPortMstEntry 6 }

-----------------------------------------------
-- maintenanceGroup Definitions
-----------------------------------------------

    maintMstpGroup OBJECT IDENTIFIER
        ::= { maintenanceGroup 44 }

    maintMstpBridgeTable OBJECT-TYPE
        SYNTAX       SEQUENCE OF MaintMstpBridgeEntry
        MAX-ACCESS   not-accessible
        STATUS       current
        DESCRIPTION  ""
        ::= { maintMstpGroup 1 }

    maintMstpBridgeEntry OBJECT-TYPE
        SYNTAX       MaintMstpBridgeEntry
        MAX-ACCESS   not-accessible
        STATUS       current
        DESCRIPTION  ""
        INDEX        { maintMstpBridgeIndex }
        ::= { maintMstpBridgeTable 1 }

    MaintMstpBridgeEntry ::= SEQUENCE {
        maintMstpBridgeIndex      Integer32,
        maintMstpBridgeNEAddress  IpAddress,
        maintMstpBridgeModeClear  INTEGER
    }

    maintMstpBridgeIndex OBJECT-TYPE
        SYNTAX       Integer32 (1..1)
        MAX-ACCESS   not-accessible
        STATUS       current
        DESCRIPTION  "Index of this table."
        ::= { maintMstpBridgeEntry 1 }

    maintMstpBridgeNEAddress OBJECT-TYPE
        SYNTAX       IpAddress
        MAX-ACCESS   not-accessible
        STATUS       current
        DESCRIPTION  "reserved."
        ::= { maintMstpBridgeEntry 2 }

    maintMstpBridgeModeClear OBJECT-TYPE
        SYNTAX       INTEGER { none(1), clear(2) }
        MAX-ACCESS   read-write
        STATUS       current
        DESCRIPTION  "MSTP Clear"
        ::= { maintMstpBridgeEntry 3 }

-----------------------------------------------
-- End User MIB Object Definitions
-----------------------------------------------

END

--
-- Load12.MIB
-- MIB generated by MG-SOFT Visual MIB Builder Version 3.0 Build 253
-- Tuesday, July 13, 2004 at 11:37:50
--

--  Load12.MIB
-- MIB generated by MG-SOFT Visual MIB Builder Version 3.0 Build 253
-- Sunday, April 18, 2004 at 13:25:43
-- 
--  Load12.MIB
-- MIB generated by MG-SOFT Visual MIB Builder Version 3.0 Build 253
-- Sunday, April 11, 2004 at 13:05:36
-- 
--  Load12.MIB
-- MIB generated by MG-SOFT Visual MIB Builder Version 3.0 Build 253
-- Sunday, April 11, 2004 at 12:23:34
-- 
-- =========================================================
-- Version 1.3.16 - 25-Oct-2009 - Shlomi Biton
--  =================================================================== 
-- Adding INET Addresses MIB items: genOpServerInetAddressType and 
-- genOpServerInetAddress.
--
-- =========================================================
-- Version 1.3.15 - 29-Oct-2007 - Shlomi Biton
--  =================================================================== 
-- Adding the values of swBootRuntimeImage(35) and swBootComponentImage(36)
-- to genAppFileType.
--
-- ========================================================
-- ========================================================
-- MIB: Lucent Common Download / Upload MIB
-- =========================================================
-- Version 1.3.14 - 14/6/2007 - Spector Pesah
--  =================================================================== 
-- Add new file location flash(7) to genAppFileLocation.                
--
-- ========================================================
-- MIB: Lucent Common Download / Upload MIB
-- =========================================================
-- Version 1.3.13 - 14/7/2006 - Spector Pesah
--  =================================================================== 
-- New error code3 were defined for genOpLastFailureIndex - 210 error  related to 
-- validation of encryption key, and wrongAuthFileID -  reported when attempt is made to
-- download auth file with wrong AFID  
--        
-- Version 1.3.12 - 23-Jan-2006 - Shlomi Biton
-- 1. Adding new enumerations to genOpIndex - uploadAuthFile(22), uploadLicFile(23), 
--    uploadSyslogFile(24) and uploadCDRFile(25). 
-- 2. Adding new enumeration to genOpProtocolType - usb(7).
-- 3. Adding note to genOpFileName regarding usb mass storage devices.       
-- 4. Adding new enumerations to genAppFileType - syslogFile(22) and cdrFile(23).
--
-- Version 1.3.11 - 13/10/2004 - Shlomi Biton
-- 
-- Fixing Compilation Error
--
-- Version 1.3.10 - 13/7/2004 - Shlomi Biton
-- 
-- New error codes were defined for genOpLastFailureIndex - error related to 
-- vlidation of digital signature of a Gateway image
-- 
-- Renaming genAppFileType 3 values:
-- 	1. phoneScriptFile(17)
-- ====================================================================Version 1.3.9 - 31/May/2004 - Shlomi Biton
-- 
-- Changing the phoneConfig term to phoneScript
-- Renaming genOpIndex 4 values:
-- 		1. downloadPhoneScriptFile(14)
-- 		2. uploadPhoneScriptFile(15)
-- Renaming genAppFileType 3 values:
-- 	1. phoneScriptFile(17)
-- ====================================================================
--  
-- Version 1.3.8 - 12/May/2004 - Shlomi Biton
-- 
-- This version includes new Operation for tftp server images and configuration files and 
-- also for DHCP leased file. 
-- In general TFTP server will support downloading images and Scripts files (configuration files)
-- and also uploading script files.
-- The DHCP server will support uploading leased files.
-- The exact changes are as follows:
-- Adding to genOpIndex 4 values:
-- 		1. downloadPhoneConfigFile(14)
-- 		2. uploadPhoneConfigFile(15)
-- 	3. downloadPhoneImageFile(16)
-- 		4. uploadDhcpBindingFile(17)     
-- Adding to genAppFileType 3 values:
-- 	1. phoneConfigFile(17)
-- 	2. phoneImageFile(18)
-- 	3. dhcpBindingFile(19)
-- ====================================================================
-- 
-- Version 1.3.7 - 11/May/2004 - Pesah Spector
-- 
-- This version includes new Operation for license file download as defined in
-- "GW Licensing SRAD for VPN and Firewall Features" SRAD (CID 103067)
--  
-- The Gateway will support a new enumeration value in genOpIndex MIB Table entry used for the 
-- download license file operation = downloadLicFile (13).
-- The Gateway will support a new enumeration value in genAppFileType MIB Table entry to 
-- represent license file presence = licenseFile (16).
-- ====================================================================
-- 
-- Version 1.3.6 - 11/Apr/2004 - Pesah Spector
-- 
-- This version includes new Operation for authentication file download as defined in
-- ASG SRAD for Gateways CID 101994
-- swNonDownLoadRunTimeImage(14) changed from 13 to 14 because of the conflict with 
-- swAPImage enumeration value
-- ====================================================================
-- 
-- Version 1.3.5 - 7/Nov/2002 - Pesah Spector
-- 
-- This version includes new constants defined for secure copy protocol
-- (SCP) and the G700 product line
-- 
-- 1. genOpProtocolType MIB variable was augmeneted with two new 
--    values- scp(5) and sftp(6)
-- 
-- 2. genOpLastFailureIndex MIB variable was augmented with two new 
--    failure indications û server authentication failure and device authentication failure, 
--    The server authentication fails when server is unknown to device, 
--    device authentication fails when server cannot authenticate device in 
--    "hostbased" authentication. The new constants are sshServerAuth(108) and sshDeviceAuth(109)
-- 
-- 3. To support images of non-downloadable code like, a bootstrap code a definition of
--    genAppFileType object type was augmented with a new enumerated value 
--    swNonDownLoadRunTimeImage(13). This change was entailed by G700 development.
-- 
-- ========================================================================
-- Version: 1.3.4			13, September 2000
-- 
-- Version 1.3.4 - 13/Sep/2000 - ItaiZ
-- 1. syncStandbyAgent(11) replaces 
--    copyConfigToStandbyAgent(11),copySoftwareToStandbyAgent(12)
-- Version 1.3.3 - 13/Sep/2000 - ItaiZ
-- 1. Support for P550/P880  stand-by Agent
--  Added copyConfigToStandbyAgent(11),copySoftwareToStandbyAgent(12) to 
--  genOpIndex.
-- 2. genAppFileId is now bounded by range (1..65535).
-- =========================================================
-- 
-- Copyright 1999 Lucent Technologies, Ltd.
-- All Rights Reserved.
-- 
-- Reproduction of this document is authorized on condition
-- that the foregoing copyright notice is included.
-- 
-- This Lucent Technologies SNMP Management Information Base 
-- Specification embodies Lucent Technologies confidential and
-- proprietary intellectual property.  Lucent Technologies retains all
-- title and ownership in the Specification, including any revisions
-- 
-- It is Lucent Technologies intent to encourage the widespread use of this
-- Specification in connection with the management of Lucent Technologies
-- products.
-- 
-- Lucent Technologies grants vendors, end-users, and other interested
-- parties a non-exclusive license to use this Specification in connection
-- with the management of Lucent Technologies products.
-- 
-- This Specification is supplied "as is," and Lucent Technologies makes
-- no warranty, either express or implied, as to the use,
-- operation, condition, or performance of the Specification.
-- 
-- =========================================================
-- 
-- Overview:
-- 
-- The Load MIB defines upload, download and copy of application software
-- and configuration information.
-- 
-- The genOperations group
-- 
--   Each row in the genOpTable represents an operation that this system can
--   perform. A walk of this table should provide a list of available 
--   operations that can be performed by the system.  The genOpTable contains
--   all configuration information nessary to perform upload, download, and
--   copy operations within the system.  Source, Destination, operational 
--   trigger, opertional status and error logging information are contained 
--   on a per row basis (each row again representing an operation that 
--   this table can perform).
-- 
-- The genApplication Group
-- 
--   Table of Application (FILE) entries.  Each row uniquely defines an
--   application in the system.  Applications can be defined as any entity 
--   that can be read or written from or to the system.  This includes 
--   software images, boot code, configuration files, prom code, etc. 
--   Each row contains information used to catalog the application (FILE)
--   entries present in the system. A walk of the genAppFileTable should
--   provide a directory-like listing of all application software, 
--   bootcode, configuration files and misc. accessable embedded software
--   in the system.  Each entry contains information about the application 
--   such as type, size, version number and date stamp.
-- 
-- =========================================================

    LOAD-MIB DEFINITIONS ::= BEGIN
 
        IMPORTS
            enterprises, IpAddress, Integer32, OBJECT-TYPE, MODULE-IDENTITY            
                FROM SNMPv2-SMI    
                InetAddress, InetAddressType
    			FROM INET-ADDRESS-MIB        
            DisplayString, RowStatus            
                FROM SNMPv2-TC;
    
    
        load MODULE-IDENTITY 
            LAST-UPDATED "190009131420Z"		-- September 13, 1900 at 14:20 GMT
            ORGANIZATION 
                "Lucent Technologies Inc."
            CONTACT-INFO 
                "Itai Zilbershtein -- izilbers@avaya.com
                Yigal Nehaysi -- ynehaysi@avaya.com
                Virginia Brown -- vibrown@avaya.com"
            DESCRIPTION 
                "Lucent Common Download / Upload Private MIB"
            REVISION "190009131555Z"		-- September 13, 1900 at 15:55 GMT
            DESCRIPTION
                "Rev 1.3.4 -one action sync all files between standby and 
                active agent in the P550/P880."
            REVISION "190009131420Z"		-- September 13, 1900 at 14:20 GMT
            DESCRIPTION
                "Rev 1.3.3 -Support for P550/P880  stand-by Agent."
            ::= { lucentMibs 53 }
        
    
    
--
-- Node definitions
--
    
--  September 13, 1900 at 14:20 GMT
-- September 13, 1900 at 14:20 GMT
-- September 13, 1900 at 15:55 GMT
-- 
-- Node definitions
-- 
--  September 13, 1900 at 14:20 GMT
-- September 13, 1900 at 15:55 GMT
-- September 13, 1900 at 14:20 GMT
-- 
-- Node definitions
-- 
--   13 Sep. 2000
-- September 13, 1900 at 14:20 GMT
-- September 13, 1900 at 14:20 GMT
-- September 13, 1900 at 15:55 GMT
-- 
-- Node definitions
-- 
        lucent OBJECT IDENTIFIER ::= { enterprises 1751 }
        
        lucentProducts OBJECT IDENTIFIER ::= { lucent 1 }
        
        lucentMibs OBJECT IDENTIFIER ::= { lucent 2 }
        
--     Groups in the Load mib
        genOperations OBJECT IDENTIFIER ::= { load 1 }
        
--     The genOperations group
-- 
        genLoadNumberOfSession OBJECT-TYPE
            SYNTAX Integer32
            MAX-ACCESS read-only
            STATUS current
            DESCRIPTION
                "The number of operational sessions in progress in this system"
            ::= { genOperations 1 }
        
        genOpTable OBJECT-TYPE
            SYNTAX SEQUENCE OF GenOpEntry
            MAX-ACCESS not-accessible
            STATUS current
            DESCRIPTION
                "Table of configuration attributes which define the operational 
                functions and the results on a per module basis.  This group provides
                the mechanism by which available operations are initiated, monitored 
                and reported."
            ::= { genOperations 2 }
        
        genOpEntry OBJECT-TYPE
            SYNTAX GenOpEntry
            MAX-ACCESS not-accessible
            STATUS current
            DESCRIPTION
                "An entry in the table, containing data about a single modules 
                operations."
            INDEX { genOpModuleId, genOpIndex }
            ::= { genOpTable 1 }
        
        GenOpEntry ::=
            SEQUENCE { 
                genOpModuleId
                    INTEGER,
                genOpIndex
                    INTEGER,
                genOpRunningState
                    INTEGER,
                genOpSourceIndex
                    Integer32,
                genOpDestIndex
                    Integer32,
                genOpServerIP
                    IpAddress,
                genOpUserName
                    DisplayString,
                genOpPassword
                    OCTET STRING,
                genOpProtocolType
                    INTEGER,
                genOpFileName
                    DisplayString,
                genOpRunningStateDisplay
                    DisplayString,
                genOpLastFailureIndex
                    INTEGER,
                genOpLastFailureDisplay
                    DisplayString,
                genOpLastWarningDisplay
                    DisplayString,
                genOpErrorLogIndex
                    Integer32,
                genOpResetSupported
                    INTEGER,
                genOpEnableReset
                    INTEGER,
                genOpNextBootImageIndex
                    Integer32,
                genOpLastBootImageIndex
                    Integer32,
                genOpFileSystemType
                    INTEGER,
                genOpReportSpecificFlags
                    INTEGER,
                genOpOctetsReceived
                    Integer32,
        		genOpServerInetAddressType 
        			InetAddressType,
    			genOpServerInetAddress 
    				InetAddress
    		}

        genOpModuleId OBJECT-TYPE
            SYNTAX INTEGER (1..255)
            MAX-ACCESS read-only
            STATUS current
            DESCRIPTION
                "Index which identifies the module inside the chassis for which this
                entry contains information. Equals the number of the slot by which
                the group is accessed or the stackable index."
            ::= { genOpEntry 1 }
        
        genOpIndex OBJECT-TYPE
            SYNTAX INTEGER
                {
                uploadConfig(1),
                downloadConfig(2),
                report(3),
                uploadSoftware(4),
                downloadSoftware(5),
                localConfigFileCopy(6),
                localSWFileCopy(7),
                uploadLogfile(8),
                eraseFile(9),
                show(10),
                syncStandbyAgent(11),
                downloadAuthFile(12),
                downloadLicFile(13),
                downloadPhoneScriptFile(14),
                uploadPhoneScriptFile(15),
                downloadPhoneImageFile(16),
                uploadDhcpBindingFile(17),
                uploadAnnouncements(18), 	-- Reserved for AVAYA-LOAD-MIB
                downloadAnnouncements(19), 	-- Reserved for AVAYA-LOAD-MIB
                renameAnnouncement(20), 	-- Reserved for AVAYA-LOAD-MIB
                eraseAnnouncement(21), 		-- Reserved for AVAYA-LOAD-MIB
                uploadAuthFile(22),
                uploadLicFile(23),
                uploadSyslogFile(24),
                uploadCDRFile(25),
                backupConfig(28), 			-- Reserved for AVAYA-LOAD-MIB
                restore(29) 				-- Reserved for AVAYA-LOAD-MIB
                }
            MAX-ACCESS read-only
            STATUS current
            DESCRIPTION
                "Index to identify the operation supported by this row entry. 
                Each operation type that is supported by this module should be 
                represented by a unique row in this MIB Table.  A walk of this 
                MIB table should reveal all the operations that are supported by 
                the device.          
                
                Note: genOpServerIP is used for IPv4 addresses only. 
                genOpServerInetAddressType/genOpServerInetAddress are used for IPv4/IPv6 
                addresses. 
                
                The operations supported are:
                
                uploadConfig -- 
                    The 'genOpDestIndex' should be set to 0 (to indicate destination
                        of server).
                    The 'genOpServerIP' should be set to the server to which the
                        config will be saved.
                    The 'genOpProtocolType' should be set to the IP protocol used
                        to transport the file.
                    The 'genOpSourceIndex' should be set to the 'genAppFileId'
                        of the config file you are uploading.
                    The 'genOpFileName' should be set to the name and path of the
                               config file on the TFTP server.
                
                downloadConfig --
                    The 'genOpDestIndex' should be set to the 'genAppFileId' of
                        the config file you are downloading to (if one does not
                        exist, you'll need to RowCreate it in the 'genAppFileTable').
                    The 'genOpServerIP' should be set to the server from which the
                        config will be copied.
                    The 'genOpProtocolType' should be set to the IP protocol used
                        to transport the file.
                    The 'genOpSourceIndex' should be set to 0 (to indicate source
                        of server).
                    The 'genOpFileName' should be set to the name and path of the
                               config file on the TFTP server.
                
                report --
                
                uploadSoftware -- 
                    The 'genOpDestIndex' should be set to 0 (to indicate destination
                         of server).
                    The 'genOpServerIP' should be set to the server to which the
                        config file will be saved.
                    The 'genOpProtocolType' should be set to the IP protocol used
                         to transport the file.
                    The 'genOpSourceIndex' should be set to the 'genAppFileId' of
                               the software file you are uploading.
                    The 'genOpFileName' should be set to the name and path of the
                               image file on the TFTP server.
                
                downloadSoftware --
                    The 'genOpDestIndex' should be set to the 'genAppFileId' of
                               the software file you are downloading to (if one does not
                               exist, you'll need to RowCreate it in the 'genAppFileTable').
                    The 'genOpServerIP' should be set to the server from which the
                               config file will be copied.
                    The 'genOpProtocolType' should be set to the IP protocol used
                               to transport the file.
                    The 'genOpSourceIndex' should be set to 0 (to indicate source
                               of server).
                    The 'genOpFileName' should be set to the name and path of the
                               image file on the TFTP server.
                
                localConfigFileCopy -- (using a 'genOpType' of 'localPeerTransport')
                    The 'genOpDestIndex' should be set to the 'genAppFileId' of the
                        config file you are copying to (if one does not exist
                        you'll need to RowCreate it in the 'genAppFileTable').
                    The 'genOpSourceIndex' should be set to the 'genAppFileId'
                               of the config file you are copying from.
                    The 'genOpServerIP' should be set to NULL.
                    The 'genOpProtocolType' should be set to 'localPeerTransport'.
                    The 'genOpFileName' should be set to NULL.
                
                localSWFileCopy -- (using a 'genOpType' of 'localPeerTransport')
                    The 'genOpDestIndex' should be set to the 'genAppFileId' of
                               the software file you are copying to (if one does not
                        exist you'll need to RowCreate it in the 'genAppFileTable').
                    The 'genOpSourceIndex' should be set to the 'genAppFileId' of
                               the software file you are copying from.
                    The 'genOpServerIP' should be set to NULL.
                    The 'genOpProtocolType' should be set to 'localPeerTransport'.
                    The 'genOpFileName' should be set to NULL.
                
                localConfigFileCopy -- (using a 'genOpType' of 'localServerTransport')
                    The 'genOpDestIndex' should be set to the 'genAppFileId' of the
                        config file you are copying to (if one does not exist you'll
                        need to RowCreate it in the 'genAppFileTable') or ZERO (0)
                        if copying to a localServer.
                    The 'genOpSourceIndex' should be set to the 'genAppFileId' of
                        the config file you are copying from or ZERO (0) if
                        copying from a localServer.
                    The 'genOpServerIP' should be set to the address of the local
                         server.
                    The 'genOpProtocolType' should be set to 'localServerTransport'.
                
                localSWFileCopy -- (using a 'genOpType' of 'localServerTransport')
                    The 'genOpDestIndex' should be set to the 'genAppFileId' of the
                               software file you are copying to (if one does not exist
                        you'll need to RowCreate it in the 'genAppFileTable').
                    The 'genOpSourceIndex' should be set to the 'genAppFileId'
                        of the software file you are copying from.
                    The 'genOpServerIP' should be set to the address of the local
                        server.
                    The 'genOpProtocolType' should be set to 'localServerTransport'.
                
                uploadLogfile --
                    The 'genOpDestIndex' should be set to 0 (to indicate destination
                               of server).
                    The 'genOpSourceIndex' should be set to the 'genAppFileId' of
                        the log file you are copying from.
                    The 'genOpServerIP' should be set to the server to which the
                        config will be saved.
                    The 'genOpProtocolType' should be set to the IP protocol used
                        to transport the file.
                    The 'genOpFileName' should be set to the name and path of the
                               log file on the TFTP server.
                
                eraseFile --
                    The 'genOpDestIndex' Is not applicable for this command.
                    The 'genOpSourceIndex' should be set to the 'genAppFileId'
                        of the file you wish to erase.
                    The 'genOpServerIP' should be set to 0.
                    The 'genOpProtocolType' should be set to 0.	
                    The 'genOpFileName' should be set to NULL.
                
                show -- 
                    Reporting information to the CLI.
                syncStandbyAgent(11) -- copy configuration AND software image files
                           to the (non-active) standby agent in a P550/P880.
                    The 'genOpDestIndex' should be set to 1
                    The 'genOpSourceIndex' should be set to 1
                    The 'genOpServerIP' should be set to NULL.
                    The 'genOpProtocolType' should be set to 'localPeerTransport'.
                    The 'genOpFileName' should be set to NULL.                     
                    
                downloadAuthFile (12) --  copy Services Logins authentication file to the
                                          device. 
                    The 'genOpDestIndex' should be set to the 'genAppFileId' of
                        the auth file you are downloading to (if one does not
                        exist, you'll need to RowCreate it in the 'genAppFileTable').
                    The 'genOpServerIP' should be set to the server from which the
                        config will be copied.
                    The 'genOpProtocolType' should be set to the IP protocol used
                        to transport the file.
                    The 'genOpSourceIndex' should be set to 0 (to indicate source
                        of server).
                    The 'genOpFileName' should be set to the name and path of the
                               config file on the TFTP/ftp/scp server.
                
                downloadLicFile (13) - --  copy SLicense file to the device. 
                
                    The 'genOpDestIndex' should be set to the 'genAppFileId' of
                        the auth file you are downloading to (if one does not
                        exist, you'll need to RowCreate it in the 'genAppFileTable').
                    The 'genOpServerIP' should be set to the server from which the
                        config will be copied.
                    The 'genOpProtocolType' should be set to the IP protocol used
                        to transport the file.
                    The 'genOpSourceIndex' should be set to 0 (to indicate source
                        of server).
                    The 'genOpFileName' should be set to the name and path of the
                               config file on the TFTP/ftp/scp server. 
                               
                downloadPhoneScriptFile (14) - copy IP phone configuration file 
                (or other endpoints configuration files) to the 
                device TFTP Server directory. IP Phone configuration file includes 
                Setting File and Upgrade Script. Non Volatile Storage.
                
                    The 'genOpDestIndex' should be set to the 'genAppFileId' of
                        the phone configuration file you are downloading to (if one does not
                        exist, you'll need to RowCreate it in the 'genAppFileTable').
                    The 'genOpServerIP' should be set to the server from which the
                        config will be copied.
                    The 'genOpProtocolType' should be set to the IP protocol used
                        to transport the file.
                    The 'genOpSourceIndex' should be set to 0 (to indicate source
                        of server).
                    The 'genOpFileName' should be set to the name and path of the
                               config file on the TFTP/ftp/scp server. 
                               
                uploadPhoneScriptFile(15) - copy IP phone configuration file 
                	(or other endpoints configuration files) from the device 
                	TFTP Server directory to remote server.
                IP Phone configuration file	includes Setting File and Upgrade Script.
                    The 'genOpDestIndex' should be set to 0 (to indicate destination
                        of server).
                    The 'genOpServerIP' should be set to the server to which the
                        config will be saved.
                    The 'genOpProtocolType' should be set to the IP protocol used
                        to transport the file.
                    The 'genOpSourceIndex' should be set to the 'genAppFileId'
                        of the config file you are uploading.
                    The 'genOpFileName' should be set to the name and path of the
                               config file on the TFTP/ftp/scp server.
                
                downloadPhoneImageFile(16) - copy IP phone images file (or other endpoints images files)
                	to the device TFTP Server Directory. Volatile Storage. 
                    The 'genOpDestIndex' should be set to the 'genAppFileId' of
                               the software file you are downloading to (if one does not
                               exist, you'll need to RowCreate it in the 'genAppFileTable').
                    The 'genOpServerIP' should be set to the server from which the
                               config file will be copied.
                    The 'genOpProtocolType' should be set to the IP protocol used
                               to transport the file.
                    The 'genOpSourceIndex' should be set to 0 (to indicate source
                               of server).
                    The 'genOpFileName' should be set to the name and path of the
                               image file on the TFTP/ftp server.
                
                uploadDhcpBindingFile(17) - copy DHCP Binding File from the device to remote server.  
                The binding file includes information of IP , MAC couples and leased time. 
                Non Volatile Storage.
                The 'genOpDestIndex' should be set to 0 (to indicate destination
                        of server).
                    The 'genOpServerIP' should be set to the server to which the
                        config will be saved.
                    The 'genOpProtocolType' should be set to the IP protocol used
                        to transport the file.
                    The 'genOpSourceIndex' should be set to the 'genAppFileId'
                        of the config file you are uploading.
                    The 'genOpFileName' should be set to the name and path of the
                               config file on the TFTP/ftp/scp server.
                               
                uploadAuthFile(22) - copy authentication File from the device to remote server.  
                The 'genOpDestIndex' should be set to 0 (to indicate destination
                        of server).
                    The 'genOpServerIP' should be set to the server to which the
                        config will be saved.
                    The 'genOpProtocolType' should be set to the IP protocol used
                        to transport the file.
                    The 'genOpSourceIndex' should be set to the 'genAppFileId'
                        of the config file you are uploading.
                    The 'genOpFileName' should be set to the name and path of the
                               config file on the TFTP/ftp/scp server.


                uploadLicFile(23) - copy License File from the device to remote server.  
                The 'genOpDestIndex' should be set to 0 (to indicate destination
                        of server).
                    The 'genOpServerIP' should be set to the server to which the
                        config will be saved.
                    The 'genOpProtocolType' should be set to the IP protocol used
                        to transport the file.
                    The 'genOpSourceIndex' should be set to the 'genAppFileId'
                        of the config file you are uploading.
                    The 'genOpFileName' should be set to the name and path of the
                               config file on the TFTP/ftp/scp server.


                uploadSyslogFile(24) - copy Syslog File from the device to remote server.  
                The 'genOpDestIndex' should be set to 0 (to indicate destination
                        of server).
                    The 'genOpServerIP' should be set to the server to which the
                        config will be saved.
                    The 'genOpProtocolType' should be set to the IP protocol used
                        to transport the file.
                    The 'genOpSourceIndex' should be set to the 'genAppFileId'
                        of the config file you are uploading.
                    The 'genOpFileName' should be set to the name and path of the
                               config file on the TFTP/ftp/scp server.


                uploadCDRFile(25) - copy CDR File from the device to remote server.  
                The 'genOpDestIndex' should be set to 0 (to indicate destination
                        of server).
                    The 'genOpServerIP' should be set to the server to which the
                        config will be saved.
                    The 'genOpProtocolType' should be set to the IP protocol used
                        to transport the file.
                    The 'genOpSourceIndex' should be set to the 'genAppFileId'
                        of the config file you are uploading.
                    The 'genOpFileName' should be set to the name and path of the
                               config file on the TFTP/ftp/scp server.
                	"
            ::= { genOpEntry 2 }
        
        genOpRunningState OBJECT-TYPE
            SYNTAX INTEGER
                {
                idle(1),
                beginOperation(2),
                waitingIp(3),
                runningIp(4),
                copyingLocal(5),
                readingConfiguration(6),
                executing(7)
                }
            MAX-ACCESS read-write
            STATUS current
            DESCRIPTION
                "Identifies the operation to perform and the state of that operation.
                This field acts as both the trigger to initiate the operation (via
                the beginOperation) and the status field of the operation itself 
                (i.e. waiting-ip, running-ip, etc.).  It is expected that all 
                dependent MIB objects will be set before the trigger is set to
                beginOperation. The operations completion is triggered by the 
                return to the idle state.
                
                idle(1), - Operation not in progress
                beginOperation(2), - Trigger by NMS to start the operation
                waitingIp(3), - Communication phase; waiting for response
                runningIp(4), - Communication phase; transferring data
                copyingLocal(5), - Local operation
                readingConfiguration(6), - Parsing / Executing configuration file
                executing(7) - Executing Command (such as erasing a file or reporting)
                "
            DEFVAL { idle }
            ::= { genOpEntry 3 }
        
        genOpSourceIndex OBJECT-TYPE
            SYNTAX Integer32
            MAX-ACCESS read-write
            STATUS current
            DESCRIPTION
                "The index value (taken from the genAppFileTable) of the source of
                the operation.	NOTE: A value of zero (0) here indicates that the
                Server (specified below) is the	source."
            ::= { genOpEntry 4 }
        
        genOpDestIndex OBJECT-TYPE
            SYNTAX Integer32
            MAX-ACCESS read-write
            STATUS current
            DESCRIPTION
                "The index value (taken from the genAppFileTable) of the destination
                of the operation.  NOTE: A value of zero (0) here indicates that 
                the Server (specified below) is the Destination."
            ::= { genOpEntry 5 }
        
        genOpServerIP OBJECT-TYPE
            SYNTAX IpAddress
            MAX-ACCESS read-write
            STATUS current
            DESCRIPTION
                "The IP Address of the server from/to which the file has to be
                Download/Upload.  NOTE: In the case of localPeerTransport this
                value should be NULL."
            ::= { genOpEntry 6 }
        
        genOpUserName OBJECT-TYPE
            SYNTAX DisplayString (SIZE (0..128))
            MAX-ACCESS read-write
            STATUS current
            DESCRIPTION
                "Contains the username to be used if the protocol specified in
                genOpProtocolType requires one. The default value will be the
                empty string"
            DEFVAL { '00'h }
            ::= { genOpEntry 7 }
        
        genOpPassword OBJECT-TYPE
            SYNTAX OCTET STRING (SIZE (0..128))
            MAX-ACCESS read-write
            STATUS current
            DESCRIPTION
                "Contains the password to be used if the protocol specified in
                genOpProtocolType requires one. The default value will be the
                empty string"
            DEFVAL { '00'h }
            ::= { genOpEntry 8 }
        
        genOpProtocolType OBJECT-TYPE
            SYNTAX INTEGER
                {
                tftp(1),
                ftp(2),
                localPeerTransport(3),
                localServerTransport(4),
                scp(5),
                sftp(6),
                usb(7)
                }
            MAX-ACCESS read-write
            STATUS current
            DESCRIPTION
                "Identifies the protocol between the management station and the
                device for Download/Upload of the file."
            ::= { genOpEntry 9 }
        
        genOpFileName OBJECT-TYPE
            SYNTAX DisplayString
            MAX-ACCESS read-write
            STATUS current
            DESCRIPTION
                "The location (including the FULL path) of the file in the server.
                NOTE: In the case of localPeerTransport this value should be NULL.
                
                In case of genOpProtocolType==usb(7) the file name shall include 
                the prefix of the usbdevice/file system as follows: 
                /usbdevice0-127/backupdirectory/backupsubdirectory/filename. 
                An example can be: 
                /usbdevice0/backupg350/IPPHONE/46xx_settings.txt.
                
                If there is only one usb mass storage device connected to the gateway then
                use /usbdevice0/ to copy from/to this device files. 
                "
            ::= { genOpEntry 10 }
        
        genOpRunningStateDisplay OBJECT-TYPE
            SYNTAX DisplayString (SIZE (0..64))
            MAX-ACCESS read-only
            STATUS current
            DESCRIPTION
                "The state of the operation for Display on the terminal during
                operation process."
            ::= { genOpEntry 11 }
        
        genOpLastFailureIndex OBJECT-TYPE
            SYNTAX INTEGER
                {
                noError(1),
                genError(2),
                configError(3),
                busy(4),
                timeout(5),
                cancelled(6),
                incompatibleFile(7),
                fileTooBig(8),
                protocolError(9),
                flashWriteError(10),
                nvramWriteError(11),
                confFileGenErr(12),
                confFileParseError(13),
                confFileExecError(14),
                undefinedError(100),
                fileNotFound(101),
                accessViolation(102),
                outOfMemory(103),
                illegalOperation(104),
                unknownTransferId(105),
                fileAlreadyExists(106),
                noSuchUser(107),
                sshServerAuth(108),
                sshDeviceAuth(109),
                badChainOfTrust(201),
                badChainOfTrustFormat (202),
                notCodeSigningAuthority (203),
                illegalDSA (204),
                badPublicKeyFormat(205),
                illegalDSKeySize(206),
                badDSFormat(207),
                authDSFailure(208),
                configFileSecretIntegrityFault(210),
                wrongAuthFileID(211)
                }
            MAX-ACCESS read-only
            STATUS current
            DESCRIPTION
                "While a download is in progress this will 
                always be 'no-error'.  After a download is complete 
                this indicates the success or failure of the download.
                If it is anything other than 'no-error' then 
                'genOpLastFailureDisplay' will contain a textual 
                description of the error.  Error codes from 100 
                upwards are errors returned from a TFTP server.  
                errors below this are locally generated.
                
                Configuration files may return errors after download
                as a result of reading a config file into the system.
                
                confFileGenErr     - General (unknown error)
                confFileParseError - Reading of config file resulted in 
                		     parsing errors.
                confFileExecError  - Reading of config file resulted in
                		     execution errors.
                sshServerAuth      - SCP server failed to authenticated himself 
                                            to a device.
                sshDeviceAuth(109)- device failed to authenticate to the SCP server 
                                            (unknown user/bad password)
                badChainOfTrust(201) - Failed to authenticate the download with Trusted 
                                       Certificate Root Authority
                badChainOfTrustFormat (202) - Not supported chain of trust format	
                notCodeSigningAuthority (203) Software image was signed by non-authorized 
                                              Certificate Authority
                illegalDSA (204) - Software image is signed with non FIPS 140-2 
                                   certified algorithm	 
                badPublicKeyFormat(205) - Not supported public key format.	
                illegalDSKeySize(206) - Software image is signed with non FIPS 140-2 
                                        certified key size
                badDSFormat(207) - Not supported digital signature format	
                authDSFailure(208) - Failed to authenticate digital image signature
   		    configFileSecretIntegrityFault(210) - The configuration file was 
  		                                                        encrypted with a different key. 
		                                                         Configuration download operation was aborted.

                "
            ::= { genOpEntry 12 }
        
        genOpLastFailureDisplay OBJECT-TYPE
            SYNTAX DisplayString (SIZE (0..64))
            MAX-ACCESS read-only
            STATUS current
            DESCRIPTION
                "Contains the last error, Null if there is no error."
            ::= { genOpEntry 13 }
        
        genOpLastWarningDisplay OBJECT-TYPE
            SYNTAX DisplayString (SIZE (0..64))
            MAX-ACCESS read-only
            STATUS current
            DESCRIPTION
                "Last warning which didn't stop the operation (not fatal error)."
            ::= { genOpEntry 14 }
        
        genOpErrorLogIndex OBJECT-TYPE
            SYNTAX Integer32
            MAX-ACCESS read-write
            STATUS current
            DESCRIPTION
                "The Index in the 'genAppFileTable' under which an error log has
                been created.  In the case of file that produce errors this file
                should contain a log of errors that occurred. (This item should
                be zero if it does not exist)"
            ::= { genOpEntry 15 }
        
        genOpResetSupported OBJECT-TYPE
            SYNTAX INTEGER
                {
                supported(1),
                notSupported(2)
                }
            MAX-ACCESS read-only
            STATUS current
            DESCRIPTION
                "Indicates if a reset (after operation completion) is supported by
                this Module."
            ::= { genOpEntry 16 }
        
        genOpEnableReset OBJECT-TYPE
            SYNTAX INTEGER
                {
                enable(1),
                disable(2)
                }
            MAX-ACCESS read-write
            STATUS current
            DESCRIPTION
                "Whether to do a reset after the operation completed successfully."
            ::= { genOpEntry 17 }
        
        genOpNextBootImageIndex OBJECT-TYPE
            SYNTAX Integer32
            MAX-ACCESS read-write
            STATUS current
            DESCRIPTION
                "The row in the 'genAppFileTable' of the default Application that
                the device will boot from when a standard reboot is performed."
            ::= { genOpEntry 18 }
        
        genOpLastBootImageIndex OBJECT-TYPE
            SYNTAX Integer32
            MAX-ACCESS read-only
            STATUS current
            DESCRIPTION
                "The Index in the 'genAppFileTable' of the default Application
                that the device	was last booted from."
            ::= { genOpEntry 19 }
        
        genOpFileSystemType OBJECT-TYPE
            SYNTAX INTEGER
                {
                static(1),
                dynamic(2)
                }
            MAX-ACCESS read-only
            STATUS current
            DESCRIPTION
                "Indicates what type of file system is supported by this module.
                A value of 'static' indicates that rows in the 'genAppFileTable'
                are not removable nor can new entries be created.  
                
                A value of 'dynamic' indicates that entries in the 'genAppFileTable'
                are both removable and can be created."
            ::= { genOpEntry 20 }
        
--     without OSPF database
        genOpReportSpecificFlags OBJECT-TYPE
            SYNTAX INTEGER
                {
                fullReport(1),
                partialReport(2),
                notSupported(255)
                }
            MAX-ACCESS read-write
            STATUS current
            DESCRIPTION
                "Contain modifiers to the Report operation.
                
                fullReport - Full configuration report
                partialReport - A report without the information stored
                                       in the OSPF database
                notSupported - For operations other than report, this MIB
                                      has no meaning and can return not Supported or
                                      not be supported."
            ::= { genOpEntry 21 }
        
        genOpOctetsReceived OBJECT-TYPE
            SYNTAX Integer32
            MAX-ACCESS read-only
            STATUS current
            DESCRIPTION
                "While a download is in progress this indicates the number
                of bytes transferred so far. "
            ::= { genOpEntry 22 }
            
                             
        genOpServerInetAddressType OBJECT-TYPE
    		SYNTAX     InetAddressType
    		MAX-ACCESS read-write
    		STATUS     current
    		DESCRIPTION
           		"The address type of genOpServerInetAddress. "
    		::= { genOpEntry 23 }
    		
	
		genOpServerInetAddress OBJECT-TYPE
    		SYNTAX     InetAddress
    		MAX-ACCESS read-write
    		STATUS     current
    		DESCRIPTION
           		"The Inet Address of the remote file server.  
                1. The address type of this object is specified in 
                genOpInetAddressType.
                2. Management applications can use genOpServerIP or 
                genOpServerInetAddressType/genOpServerInetAddress
                to set IPv4 server address and only 
                genOpServerInetAddressType/genOpServerInetAddress
                to set IPv6 server address.         
				3. The genOpServerInetAddressType must always been set before the genOpServerInetAddress is set
				(the genOpServerInetAddress must conform to the genOpServerInetAddressType).                  
				4. Setting genOpServerIP address mib item will change genOpServerInetAddressType to 
				IPv4(1) and genOpServerInetAddress to IPv4 address configured.
				5. Setting genOpServerInetAddress as IPv4 address will also set genOpServerIP. 
				6. Setting genOpServerInetAddress as IPv6 address will also set genOpServerIP to 
				0.0.0.0.
				7. Default of genOpServerInetAddressType is unknown(0) and genOpServerInetAddress
				is zero length.  
				8. Setting genOpServerInetAddressType to IPv4 will return 
				genOpServerIP and genOpServerInetAddress to default value of  0.0.0.0. 
				Setting genOpServerInetAddressType to value other than IPv4 return 
				genOpServerIP to default value of  0.0.0.0 and genOpServerInetAddress
				to default value of null string.
                "
    		::= { genOpEntry 24 }

        
        genApplications OBJECT IDENTIFIER ::= { load 2 }
        
--     The genApplication Group
-- 
        genAppFileTable OBJECT-TYPE
            SYNTAX SEQUENCE OF GenAppFileEntry
            MAX-ACCESS not-accessible
            STATUS current
            DESCRIPTION
                "Table of Application (FILE) entries.  Each row uniquely defines
                an application in the system.  Applications can be defined as
                any entity that can be read or written from or to the system.
                This includes software images, boot code, configuration files,
                prom code, etc."
            ::= { genApplications 1 }
        
        genAppFileEntry OBJECT-TYPE
            SYNTAX GenAppFileEntry
            MAX-ACCESS not-accessible
            STATUS current
            DESCRIPTION
                "An entry in the table, containing data about a single application
                / config file."
            INDEX { genOpModuleId, genAppFileId }
            ::= { genAppFileTable 1 }
        
        GenAppFileEntry ::=
            SEQUENCE { 
                genAppFileId
                    INTEGER,
                genAppFileName
                    DisplayString,
                genAppFileType
                    INTEGER,
                genAppFileDescription
                    DisplayString,
                genAppFileSize
                    Integer32,
                genAppFileVersionNumber
                    OCTET STRING,
                genAppFileLocation
                    INTEGER,
                genAppFileDateStamp
                    DisplayString,
                genAppFileRowStatus
                    RowStatus
             }

        genAppFileId OBJECT-TYPE
            SYNTAX INTEGER (1..65535)
            MAX-ACCESS read-only
            STATUS current
            DESCRIPTION
                "Index which uniquely identifies the application. 
                NOTE: This index CANNOT BE ZERO (0) since the index of zero is
                reserved as an indication of network server location in the
                genOpSourceIndex and genOpDestIndex above."
            ::= { genAppFileEntry 1 }
        
        genAppFileName OBJECT-TYPE
            SYNTAX DisplayString (SIZE (0..64))
            MAX-ACCESS read-create
            STATUS current
            DESCRIPTION
                "The name of the application."
            ::= { genAppFileEntry 2 }
        
        genAppFileType OBJECT-TYPE
            SYNTAX INTEGER
                {
                runningConfiguration(1),
                startupConfiguration(2),
                defaultConfiguration(3),
                report(4),
                genConfigFile(5),
                logFile(6),
                nvramFile(7),
                swRuntimeImage(8),
                swBootImage(9),
                swComponent(10),
                other(11),
                swWebImage(12),
                swAPImage(13),
                swNonDownLoadRunTimeImage(14),
                asgAuthFile(15),
                licenseFile(16),
                phoneScriptFile(17),
                phoneImageFile(18),
                dhcpBindingFile(19),
                announcementFile(20), 	-- Reserved for AVAYA-LOAD-MIB
                backupDatabase(21), 	-- Reserved for AVAYA-LOAD-MIB
                syslogFile(22),
				cdrFile(23),    
				swRuntimeServicePack(24),  	-- Reserved for AVAYA-LOAD-MIB
				swComponentServicePack(25),	-- Reserved for AVAYA-LOAD-MIB
				trustedCertificate(26),     -- Reserved for AVAYA-LOAD-MIB
				certificateRequest(27),		-- Reserved for AVAYA-LOAD-MIB
				serverCertificate(28),		-- Reserved for AVAYA-LOAD-MIB
				privateKey(29),				-- Reserved for AVAYA-LOAD-MIB
				staticLanguagePack(30), 	-- Reserved for AVAYA-LOAD-MIB
				phoneAvayaUnicodeMessageFile(31),	-- Reserved for AVAYA-LOAD-MIB
				phoneCustomUnicodeMessageFile(32),	-- Reserved for AVAYA-LOAD-MIB
				startupConfigurationWizardTaskFile(33),	-- Reserved for AVAYA-LOAD-MIB
				genConfigurationWizardTaskFile(34),		-- Reserved for AVAYA-LOAD-MIB
				swBootRuntimeImage(35),        
				swBootComponentImage(36)
                }
            MAX-ACCESS read-create
            STATUS current
            DESCRIPTION
                "The type (class) of the application. This class serves to catagorize
                the many application files in the system into some fixed types:
                
                runningConfiguration -- This entry represents a virtual file in
                        the system.  Use of this entry in the genOpTable should
                               serve to cause the system to generate it's configuration 
                        or to force the system to read a new config into it's
                               configuration.
                
                startupConfiguration -- This entry represents a real file that
                               is used at start-up to configure the device.
                
                defaultConfiguration -- This entry represents a file which contains
                        the default configuration of the device.
                
                report -- ??
                
                genConfigFile -- This entry represents a file which contains
                        configuration information (similar to the 
                               'startupConfiguration' above but is not automatically
                               read by the device.  This entry is used to represent
                               'alternate', 'backup' or 'experimental' configurations
                               that the user may which to store on the device.
                
                nvramFile -- This entry represents a file that is contain in the
                        nvram files system that does not fit any of the other
                               pre-defined types.
                
                swRuntimeImage -- This entry represents a software images that
                        contains operational code that is currently being used
                        to run the device.
                
                swBootImage -- This entry represents a software image that
                               contain operational code that is used to initally boot
                        the device.
                
                swComponent -- This entry represents a file that is stored as an
                        'alternate', 'backup' or 'experimental' version of 
                        operational code.
                
                other -- other 
                
                swWebImage -- The Image file of the embedded Web application
                               (java application, etc).
                
                swAPImage  -- the firmware of the Light AP. Device stores the image to 
                              support Light AP firmwareless operation. 
                              image boot service
                swNonDownLoadRunTimeImage - image of a non-downloadable code e.g.
                                                       a bootstrap code
                
                asgAuthFile   - encrypted Services Logins file  
                
                licenseFile   - file controlling licensed features activation
                
                phoneScriptFile(17) - Avaya IP Phone Configuration files 
                				(or other endpoints configuration files) as Setting file 
                				and Upgrade Script, Stored in device TFTP Server directory, 
                				Non Volatile Storage.
                
                phoneImageFile(18) - Avaya IP Phone Images files (or other endpoints images files),
                stored in device TFTP Server directory, Volatile Storage.
                
                dhcpBindingFile(19) - Device DHCP server IP binding file. Includes information about 
                bindings of IP to MAC and leased time.
                                                       
                "
            ::= { genAppFileEntry 3 }
        
        genAppFileDescription OBJECT-TYPE
            SYNTAX DisplayString (SIZE (0..64))
            MAX-ACCESS read-create
            STATUS current
            DESCRIPTION
                "A description of the application."
            ::= { genAppFileEntry 4 }
        
        genAppFileSize OBJECT-TYPE
            SYNTAX Integer32
            MAX-ACCESS read-create
            STATUS current
            DESCRIPTION
                "The size (expressed as the number of bytes) of the application."
            ::= { genAppFileEntry 5 }
        
        genAppFileVersionNumber OBJECT-TYPE
            SYNTAX OCTET STRING
            MAX-ACCESS read-only
            STATUS current
            DESCRIPTION
                "The current version of the application. If this files does not
                carry a version this field should be NULL."
            ::= { genAppFileEntry 6 }
        
        genAppFileLocation OBJECT-TYPE
            SYNTAX INTEGER
                {
                ram(1),
                flashBankA(2),
                flashBankB(3),
                nvram(4),
                bootProm(5),
                flash(7)
                }
            MAX-ACCESS read-create
            STATUS current
            DESCRIPTION
                "The physical location of the application."
            ::= { genAppFileEntry 7 }
        
        genAppFileDateStamp OBJECT-TYPE
            SYNTAX DisplayString (SIZE (0..64))
            MAX-ACCESS read-only
            STATUS current
            DESCRIPTION
                "The time stamp is the Real Time if supported otherwise sysUpTime.
                The convention for this field is as follows:
                
                Real Time: Entry is prefixed with an 'R' character and time is
                   formatted using the convention for date-and-time (rfc1903)
                
                   DISPLAY-HINT 'R-2d-1d-1d,1d:1d:1d.1d,1a1d:1d'
                
                           field  octets  contents                  range 
                           -----  ------  --------                  ----- 
                             1      1-2   year                      0..65536 
                             2       3    month                     1..12 
                             3       4    day                       1..31 
                             4       5    hour                      0..23 
                             5       6    minutes                   0..59 
                             6       7    seconds                   0..60 
                                          (use 60 for leap-second) 
                             7       8    deci-seconds              0..9 
                             8       9    direction from UTC        '+' / '-' 
                             9      10    hours from UTC            0..11 
                            10      11    minutes from UTC          0..59 
                
                           For example, Tuesday May 26, 1992 at 1:30:15 PM EDT would be 
                           displayed as: 
                
                                       R-1992-5-26,13:30:15.0,-4:0 
                
                           Note that if only local time is known, then timezone 
                           information (fields 8-10) is not present.
                
                SysUpTime: Entry is prefixed with an 'S' character and time is
                   formatted using a portion of that date-and-time convention
                
                   DISPLAY-HINT 'S-1d-1d,1d:1d:1d.1d'
                
                           field  octets  contents                  range 
                           -----  ------  --------                  ----- 
                             1       3    month                     1..12 
                             2       4    day                       1..31 
                             3       5    hour                      0..23 
                             4       6    minutes                   0..59 
                             5       7    seconds                   0..60 
                             6       8    deci-seconds              0..9 
                
                           For example,
                                            S-5-26,13:30:15.0
                
                    Represents a file that has existed in the system for 5 months, 
                    26 days, 13 hours, 30 minutes, 15 seconds exactly.  This value
                    will be reset after a reboot of the system."
            ::= { genAppFileEntry 8 }
        
        genAppFileRowStatus OBJECT-TYPE
            SYNTAX RowStatus
            MAX-ACCESS read-create
            STATUS current
            DESCRIPTION
                "The status of this entry in the table.  Note the available states:
                active(1), -- Fully configured and active.
                notInService(2) -- NOT SUPPORTED.
                notReady(3), -- Entry NOT FULLY configured.
                createAndGo(4), -- Used to add new Applications in the system. 
                createAndWait(5) -- Used to add new Applications in the system.   
                destroy(6) -- Used to delete Applications in the system."
            ::= { genAppFileEntry 9 }
        
    
    END

--
-- Load12.MIB
--

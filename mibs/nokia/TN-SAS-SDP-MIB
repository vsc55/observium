TN-SAS-SDP-MIB DEFINITIONS ::= BEGIN

-- (c) Copyright 2021 Nokia Networks.  All rights reserved.
-- This software is the confidential and proprietary property of
-- Nokia and may only be used in accordance with the terms of the
-- license agreement provided with this software.

IMPORTS
    MODULE-IDENTITY, OBJECT-TYPE,
    Counter64                                   FROM SNMPv2-SMI

    TruthValue                                  FROM SNMPv2-TC

    tnSASObjs, tnSASModules                     FROM TROPIC-GLOBAL-REG

    sdpBindEntry, sdpBindBaseStatsEntry         FROM TN-SDP-MIB
    ;

tnSASServicesSdpMIBModule   MODULE-IDENTITY
    LAST-UPDATED    "201507300000Z"
    ORGANIZATION    "Nokia"
    CONTACT-INFO
        "Nokia 7210 Support
         Web: http://www.nokia.com/comps/pages/carrier_support.jhtml"
    DESCRIPTION
        "This  document  is the SNMP MIB module to manage and provision
        the various services of the Nokia 7210 SR system.

        This   SNMP   MIB  module  (Specification)  embodies  Nokia's
        proprietary  intellectual  property.  Nokia retains all title
        and ownership in the Specification, including any revisions.

        Nokia  grants  all interested parties a non-exclusive license
        to  use and distribute an unmodified copy of this Specification
        in  connection with management of Nokia products, and without
        fee,  provided  this copyright notice and license appear on all
        copies.

        This  Specification  is  supplied `as is', and Nokia makes no
        warranty,  either express or implied, as to the use, operation,
        condition, or performance of the Specification."

--
--  Revision History
--

    REVISION        "201507300000Z"
    DESCRIPTION     "Added the MIB support for TN-SAS-SDP-MIB"

    REVISION        "200710010000Z"
    DESCRIPTION     "Rev 1.0                01 FEB 2011 00:00
                     1.0 release of the TN-SAS-SDP-MIB from TN-SAS-SERV-MIB."

    ::= { tnSASModules 12 }

-- --------------------------------------------------------------------
--      TN-SERV-MIB organisation
-- --------------------------------------------------------------------
tnSASSdpObjs             OBJECT IDENTIFIER ::= { tnSASObjs 12 }

-- tmnxSASSdpConformance      OBJECT IDENTIFIER ::= { timetraSASConfs 13 }

-- -------------------------
-- SDP Bind Extension Table
-- -------------------------
sdpBindExtnTable OBJECT-TYPE
    SYNTAX          SEQUENCE OF SdpBindExtnEntry
    MAX-ACCESS      not-accessible
    STATUS          current
    DESCRIPTION     "This table extends the SDP binding information
                     available in sdpBindTable"
    ::= { tnSASSdpObjs 4 }

sdpBindExtnEntry OBJECT-TYPE
    SYNTAX          SdpBindExtnEntry
    MAX-ACCESS      not-accessible
    STATUS          current
    DESCRIPTION     "Information about a specific SDP binding."
    AUGMENTS   { sdpBindEntry }
    ::= { sdpBindExtnTable 1 }

SdpBindExtnEntry ::=
    SEQUENCE {
        sdpBindIngressExtraVlanTagDropCount   TruthValue
    }

sdpBindIngressExtraVlanTagDropCount   OBJECT-TYPE
    SYNTAX TruthValue
    MAX-ACCESS read-create
    STATUS current
    DESCRIPTION
        "When set to 'true', couting of extra tag dropped packet will be
         enabled, It will be set only for required SDP's"
    DEFVAL { false }
    ::= { sdpBindExtnEntry 1 }


-- ----------------------------------
-- SDP Bind Base stats Extension Table
-- ----------------------------------

sdpBindBaseStatsExtnTable OBJECT-TYPE
    SYNTAX          SEQUENCE OF SdpBindBaseStatsExtnEntry
    MAX-ACCESS      not-accessible
    STATUS          current
    DESCRIPTION     "This table extends the SDP binding stats information
                     available in sdpBindBaseStatsTable"
    ::= { tnSASSdpObjs 5 }

 sdpBindBaseStatsExtnEntry OBJECT-TYPE
    SYNTAX          SdpBindBaseStatsExtnEntry
    MAX-ACCESS      not-accessible
    STATUS          current
    DESCRIPTION     "Basic statistics about a specific SDP binding."
    AUGMENTS   { sdpBindBaseStatsEntry }
    ::= { sdpBindBaseStatsExtnTable 1 }

SdpBindBaseStatsExtnEntry ::=
    SEQUENCE {
         sdpBindIngressExtraVlanTagDroppedPackets       Counter64,
         sdpBindIngressExtraVlanTagDroppedOctets        Counter64
         }

sdpBindIngressExtraVlanTagDroppedPackets   OBJECT-TYPE
    SYNTAX Counter64
    MAX-ACCESS read-only
    STATUS current
    DESCRIPTION
        "Counter to track of extra v-lan tag dropped packets"
    ::= { sdpBindBaseStatsExtnEntry 1 }

sdpBindIngressExtraVlanTagDroppedOctets   OBJECT-TYPE
    SYNTAX Counter64
    MAX-ACCESS read-only
    STATUS current
    DESCRIPTION
        "Counter to track of extra v-lan tag dropped octets"
    ::= { sdpBindBaseStatsExtnEntry 2 }

-- ----------------------------------------------------------------------------
-- Compliance/Conformance Information Removed
-- ----------------------------------------------------------------------------

END

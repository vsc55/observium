TN-OAM-TEST-MIB DEFINITIONS ::= BEGIN

-- (c) Copyright 2021 Nokia Networks.  All rights reserved.
-- This software is the confidential and proprietary property of
-- Nokia and may only be used in accordance with the terms of the
-- license agreement provided with this software.

IMPORTS
        MODULE-IDENTITY, OBJECT-TYPE, IpAddress,
        Integer32, Unsigned32, Gauge32, Counter32, Counter64
            FROM SNMPv2-SMI

        TEXTUAL-CONVENTION, RowStatus, StorageType, TruthValue,
        DateAndTime, MacAddress, TimeStamp
            FROM SNMPv2-TC

        SnmpAdminString
            FROM SNMP-FRAMEWORK-MIB

        InetAddressType, InetAddress, InetAddressPrefixLength
            FROM INET-ADDRESS-MIB

        InterfaceIndexOrZero
            FROM IF-MIB

        RouterID
            FROM OSPF-MIB

--        AtmVpIdentifier, AtmVcIdentifier
--                FROM ATM-TC-MIB

--        MplsLabel
--            FROM MPLS-LDP-MIB

        -- Alphasort
        IpAddressPrefixLength, SdpBindId, TFCName, TItemDescription,
        TLNamedItemOrEmpty, TNamedItemOrEmpty,
--      TNamedItem, TPolicyStatementNameOrEmpty,
        TProfile, TmnxAdminState,
--      TmnxBgpRouteTarget, TmnxEncapVal,
        TmnxMplsTpGlobalID, TmnxMplsTpNodeID, TmnxPwGlobalIdOrZero,
--      TmnxPortID,
        TmnxServId, TmnxSpokeSdpIdOrZero, TmnxStrSapId,
--      TmnxTunnelID, TmnxTunnelType, TmnxVPNRouteDistinguisher,
--      TmnxVcId, TmnxVcType, TmnxMobGwId,
        TmnxVRtrID, TmnxVcIdOrNone
            FROM TN-TC-MIB

        tnSRMIBModules, tnSRObjs,
        tnSRNotifyPrefix
            FROM TROPIC-GLOBAL-REG

        SdpId, SdpBindVcType
            FROM TN-SERV-MIB

        Dot1agCfmMepIdOrZero
            FROM IEEE8021-CFM-MIB

        tnSysSwitchId
            FROM TROPIC-SYSTEM-MIB

        ;

tnOamTestMIBModule MODULE-IDENTITY
        LAST-UPDATED "202106040000Z"
        ORGANIZATION "Nokia"
        CONTACT-INFO
            "Nokia SROS Support
             Web: http:-- support.nokia.com"

        DESCRIPTION
        "This document is the SNMP MIB module to manage and provision the
        Nokia SROS OAM tests.

        This SNMP MIB module (Specification) embodies Nokia's
        proprietary intellectual property.  Nokia retains
        all title and ownership in the Specification, including any
        revisions.

        Nokia grants all interested parties a non-exclusive
        license to use and distribute an unmodified copy of this
        Specification in connection with management of Nokia
        products, and without fee, provided this copyright notice and
        license appear on all copies.

        This Specification is supplied 'as is', and Nokia
        makes no warranty, either express or implied, as to the use,
        operation, condition, or performance of the Specification."
--
--  Revision History
--

      REVISION        "202106040000Z"
      DESCRIPTION     "Added DESCRIPTION for ethCfmTwoWayLm in the following tables:
                       tnOamPingCtlTable
                       tnOamPingResultsTable
                       tnOamPingHistoryTable
                       tnOamEthCfmPingCtlTable."

      REVISION        "202006190000Z"
      DESCRIPTION     "Added following DESCRIPTION in tnOamSaaCtlTable:
                       tnOamSaaCtlAlmProfName."

      REVISION        "201911150000Z"
      DESCRIPTION     "1) Updated DESCRIPTION of the following:
                          tnOamPingCtlInterval.
                       2) Added the following to tnOamPingCtlIntervalUnits:
                          decimilliseconds(3)."

      REVISION        "201903290000Z"
      DESCRIPTION     "Added the following to tnOamPingCtlTestMode:
                       ethCfmOneWayDelay(24)."

      REVISION        "201508240000Z"
      DESCRIPTION     "Changed SYNTAX of the following from TmnxOamPingRtnCode
                       to Integer32:
                       tnOamPingHistoryReturnCode."

      REVISION        "201508050000Z"
      DESCRIPTION     "1) Added the below table:
                          tnOamVccvTrNextPwSegmentTable
                          tnOamVccvTrNextPwID
                          tnOamVccvTrNextPwType
                          tnOamVccvTrNextSenderAddrType
                          tnOamVccvTrNextSenderAddr
                          tnOamVccvTrNextRemoteAddrType
                          tnOamVccvTrNextRemoteAddr
                          tnOamVccvTrNextSaiiGlobalI
                          tnOamVccvTrNextSaiiPrefix
                          tnOamVccvTrNextSaiiAcId
                          tnOamVccvTrNextTaiiGlobalId
                          tnOamVccvTrNextTaiiPrefix
                          tnOamVccvTrNextTaiiAcId
                          tnOamVccvTrNextTpAgi
                          tnOamVccvTrNextTpSaiiGlobalId
                          tnOamVccvTrNextTpSaiiNodeId
                          tnOamVccvTrNextTpSaiiAcId
                          tnOamVccvTrNextTpTaiiGlobalId
                          tnOamVccvTrNextTpTaiiNodeId
                          tnOamVccvTrNextTpTaiiAcId
                       2) Added the below MIBs to tnOamSaaCtlTable:
                          tnOamSaaCtlKeepProbeHistoryAdm
                          tnOamSaaCtlKeepProbeHistoryOpr"

      REVISION        "201505050000Z"
      DESCRIPTION     "1) Added the following MIB tables:
                          tnOamPingResultsTable
                          tnOamPingHistoryTable
                          tnOamLspPingCtlTable
                          tnOamVccvPingCtlTable
                          tnOamEthCfmPingCtlTable
                          tnOamTrCtlTable
                          tnOamTrResultsTable
                          tnOamTrProbeHistoryTable
                          tnOamLspTrCtlTable
                          tnOamLspTrMapTable
                          tnOamVccvTrCtlTable

                       2) Added the following TEXTUAL-CONVENTION:
                          TmnxOamLspAssocChannel
                          TmnxOamLspTestSubMode
                          TmnxOamMplsEchoDownMapTlv
                          TmnxOamMplsEchoDownMapTlvOrNone
                          TmnxOamMplsTpPathType
                          TmnxOamVccvAssocChannel
                          TmnxOamVccvTestSubMode"

      REVISION        "201308220000Z"
      DESCRIPTION     "1) Added the following to TmnxOamTestResult:
                          txResourcesUnavail (4).
                       2) Added the following to tnOamPingCtlTable:
                          tnOamPingCtlIntervalUnits.
                       3) Changed DESCRIPTION for the following:
                          tnOamPingCtlTimeOut
                          tnOamPingCtlInterval.
                       4) Changed range of the following from
                          (1..10000000) to (1..90000):
                          tnOamPingCtlInterval.
                       5) Changed SYNTAX of tnOamSaaCtlLastRunResult
                          from INTEGER to tnOamSaaCtlLastRunResult."

      REVISION        "201303260000Z"
      DESCRIPTION     "Rev 9.x                26 Mar 2013 00:00
                         - add one additional value of thCfmTwoWayLm (23) for tnOamPingCtlTestMode.
                         - add the following in the DESCRIPTION of tnOamPingCtlSize:
                           the minimum, maximum, and default values of  'ethCfmTwoWayDelay':0,  1500,   0
                         - Update the following in the DESCRIPTION of tnOamPingCtlInterval:
                           The applicability, range, and default value of this object vary with
                            tnOamPingCtlTestMode, as shown in the following table.
                            tnOamPingCtlTestMode          Min   Max      Default
                                'ethCfmTwoWayDelay'       100   10000    1000
                                'ethCfmTwoWaySlm'         10    10000    100
                                'ethCfmTwoWayLm'          100   10000    1000
                         "

      REVISION        "201102010000Z"
      DESCRIPTION     "Rev 9.0                1 Feb 2011 00:00
                       9.0 release of the TN-OAM-TEST-MIB."

      REVISION        "200902280000Z"
      DESCRIPTION     "Rev 7.0                28 Feb 2009 00:00
                       7.0 release of the TN-OAM-TEST-MIB."

      REVISION        "200801010000Z"
      DESCRIPTION     "Rev 6.0                01 Jan 2008 00:00
                       6.0 release of the TN-OAM-TEST-MIB."

      REVISION        "200701010000Z"
      DESCRIPTION     "Rev 5.0                01 Jan 2007 00:00
                       5.0 release of the TN-OAM-TEST-MIB."

      REVISION        "200603090000Z"
      DESCRIPTION     "Rev 4.0                09 Mar 2006 00:00
                       4.0 release of the TN-OAM-TEST-MIB."

      REVISION        "200508310000Z"
      DESCRIPTION     "Rev 3.0                31 Aug 2005 00:00
                       3.0 release of the TN-OAM-TEST-MIB."

      REVISION        "200501240000Z"
      DESCRIPTION     "Rev 2.1                24 Jan 2005 00:00
                       2.1 release of the TN-OAM-TEST-MIB."

      REVISION        "200401150000Z"
      DESCRIPTION     "Rev 2.0                15 Jan 2004 00:00
                       2.0 release of the TN-OAM-TEST-MIB."

      REVISION        "200308150000Z"
      DESCRIPTION     "Rev 1.2                15 Aug 2003 00:00
                       1.2 release of the TN-OAM-TEST-MIB."

      REVISION        "200301200000Z"
      DESCRIPTION     "Rev 1.0                20 Jan 2003 00:00
                       1.0 Release of the TN-OAM-TEST-MIB."

      REVISION        "200111150000Z"
      DESCRIPTION     "Rev 0.1                15 Nov 2001 00:00
                       Initial version of the TN-OAM-TEST-MIB."

      ::= { tnSRMIBModules 11 }


tnOamTestObjs         OBJECT IDENTIFIER ::= { tnSRObjs 11 }

    tnOamPingObjs                     OBJECT IDENTIFIER
        ::= { tnOamTestObjs 1 }
--     tnOamPingNotificationObjects      OBJECT IDENTIFIER
--         ::= { tnOamPingObjs 1 }

     tnOamTraceRouteObjs               OBJECT IDENTIFIER
         ::= { tnOamTestObjs 2 }
--     tnOamTraceRouteNotifyObjects      OBJECT IDENTIFIER
--         ::= { tnOamTraceRouteObjs 1 }

    tnOamSaaObjs                      OBJECT IDENTIFIER
        ::= { tnOamTestObjs 3 }
--     tnOamSaaNotifyObjects             OBJECT IDENTIFIER
--         ::= { tnOamSaaObjs 1 }

--     tnOamMobGatewayObjs               OBJECT IDENTIFIER
--         ::= { tnOamTestObjs 4 }

--     tnOamGeneralObjs                  OBJECT IDENTIFIER
--         ::= { tnOamTestObjs 5 }

tnOamTestNotifications        OBJECT IDENTIFIER ::= { tnSRNotifyPrefix 11 }
    tnOamPingNotifyPrefix            OBJECT IDENTIFIER
        ::= { tnOamTestNotifications 1 }
        tnOamPingNotifications            OBJECT IDENTIFIER
           ::= { tnOamPingNotifyPrefix 0}
    tnOamTraceRouteNotifyPrefix      OBJECT IDENTIFIER
        ::= { tnOamTestNotifications 2 }
        tnOamTraceRouteNotifications      OBJECT IDENTIFIER
            ::= { tnOamTraceRouteNotifyPrefix 0}
    tnOamSaaNotifyPrefix             OBJECT IDENTIFIER
        ::= { tnOamTestNotifications 3}
        tnOamSaaNotifications             OBJECT IDENTIFIER
            ::= { tnOamSaaNotifyPrefix 0}

-- tnOamTestConformance          OBJECT IDENTIFIER ::= { tnSRConfs 11 }
--    tnOamPingConformance              OBJECT IDENTIFIER
--        ::= { tnOamTestConformance 1 }
--    tnOamTraceRouteConformance        OBJECT IDENTIFIER
--        ::= { tnOamTestConformance 2 }
--    tnOamSaaConformance               OBJECT IDENTIFIER
--        ::= { tnOamTestConformance 3 }
--    tnOamMobGatewayConformance        OBJECT IDENTIFIER
--        ::= { tnOamTestConformance 4 }
--    tnOamGeneralConformance           OBJECT IDENTIFIER
--        ::= { tnOamTestConformance 5 }


--
-- Textual Conventions
--

TmnxOamLspAssocChannel           ::= TEXTUAL-CONVENTION
    STATUS      current
    DESCRIPTION
        "A value of type TmnxOamLspAssocChannel specifies the launched echo
         request's usage of the Associated Channel (ACH) mechanism, when testing
         an MPLS-TP LSP.

         Values:
            notApplicable(1)
                Used when the test is not testing an MPLS-TP LSP.
            nonIp(2)
                Use the Associated Channel mechanism described in RFC 6426,
                Section 3.3.
            none(3)
                Do not use an Associated Channel, as described in RFC 6426,
                Section 3.1.
            ipv4(4)
                Use the Associated Channel mechanism described in RFC 6426,
                Section 3.2."

    REFERENCE
        "RFC 6426, 'MPLS On-Demand Connectivity Verification and Route Tracing',
         Section 3.1, 'LSP Ping with IP Encapsulation',
         Section 3.3, 'Non-IP-Based On-Demand CV, Using ACH'."
    SYNTAX      INTEGER {
                    notApplicable(1),
                    nonIp(2),
                    none(3),
                    ipv4(4)
                }

TmnxOamLspTestSubMode            ::= TEXTUAL-CONVENTION
    STATUS      current
    DESCRIPTION
        "A value of type TmnxOamLspTestSubMode specifies the type of LSP ping or
         LSP trace route test to perform.

         LSP test types:
             static(2)
                 Perform an LSP ping or LSP trace route test using the RFC 6426
                 'Target FEC Stack' code point 'Static LSP'.
             unspecified(1)
                 Perform any other supported type of LSP ping or trace route
                 test.  Examples:  an LSP ping or trace route test using the RFC
                 4379 'Target FEC Stack' code point 'LDP IPv4 prefix'; an LSP
                 ping or trace route test using the RFC 4379 'Target FEC Stack'
                 code point 'RSVP IPv4 LSP'.
             bgpLabeledPrefix(3)
                 Perform an LSP ping or LSP trace route test using the RFC 4379
                 'Target FEC Stack' code point 'BGP labeled IPv4 prefix'.  In
                 future, 'bgpLabeledPrefix(3)' will also be used for the RFC
                 4379 'Target FEC Stack' code point 'BGP labeled IPv6 prefix'."
    REFERENCE
        "RFC 4379, 'Detecting Multi-Protocol Label Switched (MPLS) Data Plane
         Failures', Section 3.2 ('Target FEC Stack').
         RFC 6426, 'MPLS On-Demand Connectivity Verification and Route Tracing',
         Section 2.3.1 ('Static LSP Sub-TLV')."
    SYNTAX      INTEGER {
                    unspecified(1),
                    static(2),
                    bgpLabeledPrefix(3)
               }


TmnxOamMplsEchoDownMapTlv        ::= TEXTUAL-CONVENTION
    STATUS      current
    DESCRIPTION
        "An object of type TmnxOamMplsEchoDownMapTlv specifies the type of
         downstream mapping TLV in an MPLS echo request PDU.

         'dsmap(1)' specifies the Downstream Mapping TLV, as described in RFC
         4379, Section 3.3.

         'ddmap(2)' specifies the Downstream Detailed Mapping TLV, as described
         in RFC 6424, Section 3.3."
    REFERENCE
        "RFC 4379, 'Detecting Multi-Protocol Label Switched (MPLS) Data Plane
         Failures', Section 3.3 ('Downstream Mapping').
         RFC 6424, 'Mechanism for Performing Label Switched Path Ping (LSP Ping)
         over MPLS Tunnels', Section 3.3 ('Downstream Detailed Mapping TLV')."
    SYNTAX      INTEGER {
                    dsmap(1),
                    ddmap(2)
                }


TmnxOamMplsEchoDownMapTlvOrNone  ::= TEXTUAL-CONVENTION
    STATUS      current
    DESCRIPTION
        "An object of type TmnxOamMplsEchoDownMapTlvOrNone specifies the type of
         downstream mapping TLV in an MPLS echo request PDU (or no downstream
         mapping TLV).

         'dsmap(1)' specifies the Downstream Mapping TLV, as described in RFC
         4379, Section 3.3.

         'ddmap(2)' specifies the Downstream Detailed Mapping TLV, as described
         in RFC 6424, Section 3.3.

         'none(3)'  specifies none of the above TLVs."
    REFERENCE
        "RFC 4379, 'Detecting Multi-Protocol Label Switched (MPLS) Data Plane
         Failures', Section 3.3 ('Downstream Mapping').

         RFC 6424, 'Mechanism for Performing Label Switched Path Ping (LSP Ping)
         over MPLS Tunnels', Section 3.3 ('Downstream Detailed Mapping TLV').

        "
    SYNTAX      INTEGER {
                    dsmap(1),
                    ddmap(2),
                    none(3)
                }

TmnxOamMplsTpPathType            ::= TEXTUAL-CONVENTION
    STATUS      current
    DESCRIPTION
        "A value of type TmnxOamMplsTpPathType specifies the type of an MPLS-TP
         path to be tested.
         Path types:
            working(1) - test the primary path of the MPLS-TP LSP
            protect(2) - test the secondary path of the MPLS-TP LSP
            active(3)  - test the currently-active path of the MPLS-TP LSP"
    REFERENCE
        "RFC 5921, 'A Framework for MPLS in Transport Networks',
         Section 1.3.4, 'MPLS-TP Label Switched Path'."
    SYNTAX      INTEGER {
                    working(1),
                    protect(2),
                    active(3)
                  }

TmnxOamTestMode ::= TEXTUAL-CONVENTION
    STATUS      current
    DESCRIPTION
        "The value of TmnxOamTestMode is an enumerated integer
         that indicates the type of OAM test."
    SYNTAX      INTEGER {
                    notConfigured (0),
                    ping (1),
                    traceroute (2)
                }


TmnxOamPingRtnCode ::= TEXTUAL-CONVENTION
    STATUS      current
    DESCRIPTION
        "The value of TmnxOamPingRtnCode is an enumerated integer
         that indicates the return code received in the OAM ping response
         common header.
            notApplicable       The return code has no significance in the
                                context of the test being conducted.
            fecEgress           Replying router is an egress for the FEC.
            fecNoMap            Replying router has no mapping for the FEC.
            notDownstream       Replying router is not one of the
                                downstream routers.
            downstream          Replying router is one of the downstream
                                routers and its mapping for this FEC on the
                                received interface is the given label.
            downstreamNotLabel  Replying router is one of the downstream
                                routers but its mapping for this FEC is not
                                the given label.
            downstreamNotMac    Replying router is one of the downstream
                                routers but it does not have the given MAC
                                address
            downstreamNotMacFlood   Replying router is one of the downstream
                                routers but it does not have the given MAC
                                address and is unable to flood the request.
            malformedEchoRequest    A malformed echo request was received.
            tlvNotUnderstood    One or more of the TLVs was not understood.
            downstreamNotInMfib Replying router is one of the downstream
                                routers but it does not have an MFIB entry
                                for the given source-group combination.
            downstreamMismatched    Downstream mapping mismatched.
            upstreamIfIdUnkn    Upstream interface index unknown.
            noMplsFwd           Label switched but no MPLS forwarding at
                                stack-depth.
            noLabelAtStackDepth No label entry at stack-depth.
            protoIntfMismatched Protocol not associated with interface at
                                FEC stack-depth.
            terminatedByOneLabel    Premature termination of ping due to
                                label stack shrinking to a single label.
            seeDDMapForRetCodeSubCode   See DDMap TLV for rc and sub-rc.
            fecStackChange    Label Switched with FEC Stack Change.
         "
    SYNTAX INTEGER {
                notApplicable(0),
                fecEgress (1),
                fecNoMap (2),
                notDownstream (3),
                downstream (4),
                downstreamNotLabel (5),
                downstreamNotMac (6),
                downstreamNotMacFlood (7),
                malformedEchoRequest (8),
                tlvNotUnderstood (9),
                downstreamNotInMfib(10),
                downstreamMismatched(11),
                upstreamIfIdUnkn(12),
                noMplsFwd(13),
                noLabelAtStackDepth(14),
                protoIntfMismatched(15),
                terminatedByOneLabel(16),
                seeDDMapForRetCodeSubCode(17),
                fecStackChange(18)
            }

TmnxOamAddressType ::= TEXTUAL-CONVENTION
    STATUS  current
    DESCRIPTION
        "The value of TmnxOamAddressType is an enumerated integer that
         indicates the type of address used in OAM test requests and
         responses."
    SYNTAX  INTEGER {
                unknown (0),
                ipv4Address (1),
                ipv6Address (2),
                macAddress (3),
                sapId (4),
                sdpId (5),
                localCpu (6),
                ipv4Unnumbered (7),
                ipv6Unnumbered (8),
                sdpBindId (9)
            }

TmnxOamResponseStatus ::= TEXTUAL-CONVENTION
    STATUS  current
    DESCRIPTION
        "Used to report the result of an OAM Echo probe operation:

         responseReceived(1) - Operation completes successfully.
         unknown(2) - Operation failed due to unknown error.
         internalError(3) - An implementation detected an error
              in its own processing that caused an operation to fail.
         maxConcurrentLimitReached(4) - The maximum number of
              concurrent active operations would have been exceeded
              if the corresponding operation was allowed.
         requestTimedOut(5) - Operation failed to receive a
              valid reply within the time limit imposed on it.
         unknownOrigSdpId(6) - Invalid or non-existent originating
              SDP-ID.
         downOrigSdpId(7) - The originating SDP-ID is operationally
              down.
         requestTerminated(8) - The OAM ping test was terminated
              by the manager before reply or timeout.
         invalidOriginatorId(9) - The far-end replied with an invalid
              originator-ID error.
         invalidResponderId(10) - The far-end replied with an invalid
              responder-ID error.
         unknownRespSdpId(11) - The far-end replied with an invalid
              response SDP-ID error.
         downRespSdpId(12) - The far-end replied with down (admin or
              oper) response SDP-ID.
         invalidServiceId(13) - Invalid or non-existent originator
              Service-ID (svc-ping).
         invalidSdp(14) - Invalid or non-existent SDP for Service
              (svc-ping).
         downServiceSdp(15) - SDP for the Service is down.
              (svc-ping).
         noServiceEgressLabel(16) - Non-existent Service egress label.
              (svc-ping).
         invalidHostAddress(17) - The IP address for a host
              has been determined to be invalid.  Examples of this
              are broadcast or multicast addresses. (svc-ping).
         invalidMacAddress(18) - The MAC address specified has been
              determined to be invalid. (macPing).
         invalidLspName(19) - The LSP name specified has been determined
              to be invalid. (lspPing).
         macIsLocal(20) - MAC Ping or Trace route not sent because the mac
              address is on a local SAP or CPU. (MAC-Ping/MAC-TR).
         farEndUnreachable(21) - no route to the far end of the GRE SDP
              tunnel.
         downOriginatorId(22) - The ping originator is operationally down.
         downResponderId(23) - The ping responder is operationally down.
         changedResponderId(24) - The ping responder-ID is changed.
         downOrigSvcId(25) - Service on the originator side is
              operationally down. (svc-ping).
         downRespSvcId(26) - Service on the responder side is
              operationally down. (svc-ping).
         noServiceIngressLabel(27) - Non-existent Service ingress label.
              (svc-ping).
         mismatchCustId(28) - Service customer ID mismatch between
              originator and responder. (svc-ping).
         mismatchSvcType(29) - Service type mismatch between originator
              and responder. (svc-ping).
         mismatchSvcMtu(30) - Service MTU mismatch between originator
              and responder. (svc-ping).
         mismatchSvcLabel(31) - Service label mismatch between originator
              and responder. (svc-ping).
         noSdpBoundToSvc(32) - No SDP bound to the Service. (svc-ping).
         downOrigSdpBinding(33) - SDP binding is down on the Originator
              side. (sdp-ping).
         invalidLspPathName(34) - The LSP path name specified is invalid.
              (lsp-ping).
         noLspEndpointAddr(35) - No LSP Endpoint address. (lsp-ping).
         invalidLspId(36) - No active LSP path found. (lsp-ping).
         downLspPath(37) - LSP path is operationally down. (lsp-ping).
         invalidLspProtocol(38) - LSP Protocol is not supported or is
              invalid. (lsp-ping).
         invalidLspLabel(39) - LSP label is invalid. (lsp-ping).
         routeIsLocal(40) - The route is a local route. (vprn-ping).
         noRouteToDest(41) - There is no route to the destination.
              (vprn-ping).
         localExtranetRoute(42) - The route is a local extranet route.
              (vprn-ping).
         srcIpInBgpVpnRoute(43) - The source IP belongs to a BGP-VPN route.
              (vprn-ping).
         srcIpInvalid(44) - The source IP is invalid or there is no route
              to the source. (vprn-ping)
         bgpDaemonBusy(45) - The BGP routing daemon is busy; vprn route target
              information is not retrievable. (vprn-trace)
         mcastNotEnabled(46) - Multicast is not enabled. Multicast trace cannot
              be initiated. (mtrace)
         mTraceNoSGFlow(47) - No (*,G)/(S,G) flow on the router. Multicast
              trace cannot be initiated. (mtrace)
         mTraceSysIpNotCfg(48) - System ip address not configured. It is used
              as the response address in the multicast trace query. (mtrace)
         noFwdEntryInMfib(49) - No forwarding entry could be found for the
              specified source and destination address in the MFIB.
              (mfib-ping)
         dnsNameNotFound(50) -  the domain name specified in the dns query
              does not exist.
         noSocket(51) - unable to get socket. (icmp-ping).
         socketOptVprnIdFail(52) - unable to set SO_VPRNID for socket.
              (icmp-ping).
         socketOptIfInexFail(53) -  unable to set IP_IFINDEX for socket.
              (icmp-ping).
         socketOptNextHopFail(54) - unable to set IP_NEXT_HOP for socket.
              (icmp-ping).
         socketOptMtuDiscFail(55) - unable to set IP_MTU_DISC for socket.
              (icmp-ping).
         socketOptSndbufFail(56) - unable to set SO_SNDBUF for socket.
              (icmp-ping).
         socketOptHdrincFail(57) - unable to set IP_HDRINCL for socket.
              (icmp-ping).
         socketOptTosFail(58) - unable to set IP_TOS for socket. (icmp-ping).
         socketOptTtlFail(59) - unable to set IP_TTL for socket. (icmp-ping).
         bindSocketFail(60) - unable to bind socket. (icmp-ping).
         noRouteByIntf(61) - no route to destination via the specified
              interface. (icmp-ping).
         noIntf(62) - no interface specified. (icmp-ping).
         noLocalIp(63) - unable to find local ip address. (icmp-ping).
         sendtoFail(64) - sendto function failed. (icmp-ping).
         rcvdWrongType(65) - received packet of wrong icmp type. (icmp-ping).
         noDirectInterface(66) - no direct interface to reach destination.
              (icmp-ping).
         nexthopUnreachable (67) - unable to reach the next-hop. (icmp-ping).
         socketOptHwTimeStampFail (68) - unable to set IP_TIM_TIME for socket.
              (icmp-ping).
         noSpokeSdpInVll (69) - unable to find spoke-sdp given SdpId:vc-id
                                (vccv-ping).
         farEndVccvNotSupported (70) - far end does not support the VCCV
                                       options (vccv-ping).
         noVcEgressLabel (71) - no Vc egress label to send vccv-ping.
         socketOptIpSessionFail (72) - unable to set IP_SESSION for socket.
              (icmp-ping).
         rcvdWrongSize(73) - received packet of wrong size. (icmp-ping).
         dnsLookupFail (74) - dns lookup failed. (icmp-ping).
         noIpv6SrcAddrOnIntf (75) - no ipv6 source on the interface (icmp-ping).
         multipathNotSupported (76) - downstream node does not support
                                      multipath (lsp-trace).
         nhIntfNameNotFound (77) - Given next-hop interface name not found
                                      (lsp-ping/trace).
         msPwInvalidReplyMode (78) - MS-PW switching node supports ip-routed
                                     reply mode only (vccv-ping).
         ancpNoAncpString (79) - ANCP string unknown to the system
         ancpNoSubscriber (80) - subscriber unknown to the system
         ancpNoAncpStringForSubscriber (81) - subscriber has no associated
                                              ANCP string.
         ancpNoAccessNodeforAncpString (82) - no access node is found for the
                                              given ANCP string
         ancpNoAncpCapabilityNegotiated (83) - ANCP capability not
                                           negotiated with the involved
                                           DSLAM.
         ancpOtherTestInProgress (84) - another ANCP test is running
                                        for this ANCP string.
         ancpMaxNbrAncpTestsInProgress (85) - max number of concurrent
                                                  ANCP tests reached.
         spokeSdpOperDown (86) - Spoke-sdp is operationally down (vccv-ping).
         noMsPwVccvInReplyDir (87) - Switching node in MS-PW with no vccv
                                    support in echo reply direction.
         p2mpLspNameOrInstInvalid (88) - P2MP LSP name or instance provided is
                                         not valid.
         p2mpLspS2LPathDown (89) - LSP path to S2L is down.
         p2mpLspS2LAddressInvalid (90) - One or more S2L address is not valid.
         p2mpLspNotOperational (91) - P2MP LSP is operationally down.
         p2mpLspTrMultipleReplies (92) - Probe returned multiple responses.
                                         Result may be inconsistent.
         invalidMepId (93) - The user-configured MEP identifier is not valid.
         multipleReplies (94) - more than one reply received, when one was
                                expected.
         packetSizeTooBig (95) - Packet size too big.
         gtpPingError (96) - General GTP Ping Error.
         gtpPingRsrcUnavailable (97) - GTP Path management resource unavailable.
         gtpPingDupRequest (98) - Duplicate request for the same peer.
         gtpPingCleanUpInProg (99) - GTP Path management clean up in progress.
         invalidInterface (100) - The egress interface specified does not exist.
         p2mpLspNotFound (101) - The P2MP-LSP not found given LDP-ID or
                                 sender-address.
         ethCfmSlmInLoss(102) - Synthetic Loss Measurement (SLM) probe lost in
                                transit from far-end node to local agent.
         ethCfmSlmOutLoss(103) - SLM probe lost on transmit from local agent to
                                 far-end node.
         ethCfmSlmUnacknowledged(104) - SLM probe lost but unable to identify
                                        loss reason.
         spokeSdpFecNoBndFound(105) - Spoke-sdp-fec is invalid or has no
                                      associated SDP binding yet.
         mtraceNotSupportedP2mp(106) - mtrace not supported in base routing
                                       context when incoming interface is p2mp
         useFec129Parameters(107) - specify FEC129 parameters for FEC129 PW
                                    instead of sdp-id:vc-id
         dnsServerUnexpectedResponse(108) - nameserver unexpected response.
         dnsServerResponseFormErr(109) - nameserver responded with FORMERR.
         dnsServerResponseServFail(110) - nameserver responded with SERVFAIL.
         dnsServerResponseNotImp(111) - nameserver responded with NOTIMP.
         dnsServerResponseRefused(112) - nameserver responded with REFUSED.
         sendFailUndefinedServiceId(113) - The OAM test cannot be performed
              because the associated service does not exist.
         sendFailWrongServiceType(114) - The OAM test cannot be performed
              because the associated service is of the wrong type.
         sendFailSubnettedService(115) - The OAM test cannot be performed
              on a service with a specified mac subnet length.
         invalidRespServiceId(116) - Invalid or non-existent responder
              Service-ID.
         adminDownOrigSdpBind(117) - SDP binding is administratively down on the
              originator side.
         operDownRespSdpBind(118) - SDP binding is operationally down on the
              responder side.
         adminDownRespSdpBind(119) - SDP binding is administratively down on the
              responder side.
         sdpBindVcidMismatch(120) - SDP binding VC ID mismatch between
              originator and responder.
         sdpBindTypeMismatch(121) - SDP binding type mismatch between originator
              and responder.
         sdpBindVcTypeMismatch(122) - SDP binding VC type mismatch between
              originator and responder.
         sdpBindVlanVcTagMismatch(123) - SDP binding VLAN VC tag mismatch between
              originator and responder.
         adminDownOrigSvc(124) - Service on the originator side is
              administratively down.
         adminDownRespSvc(125) - Service on the responder side is
              administratively down.
         adminDownOrigSdpId(126) - The originating SDP-ID is administratively
              down.
         adminDownRespSdpId(127) - The responding SDP-ID is administratively
              down.
         mTraceSourceIsNotRemote(128) - The multicast trace route test cannot
              be performed because the source address is not remote.
         invalidVirtualRouterId(129) - The OAM test cannot be performed because
              the associated virtual router ID is invalid.
         ldpPrefixIsLocal(130) - The OAM test cannot be performed because the
              associated LDP prefix is local to the system.
         sourceIpIsNotLocal(131) - The OAM test cannot be performed because the
              associated source address is not local to the system.
         nextHopIpIsLocal(132) - The OAM test cannot be performed because the
              associated next hop address is local to the system.
         targetIpIsLocal(133) - The OAM test cannot be performed because the
              associated target address is local to the system.
         invalidControlPlaneOption(134) - The OAM test cannot be performed
              because the control plane send or receive option is not allowed
              with the specified service.
         iomRevisionNotSupported(135) - The OAM test cannot be performed due
              to a mismatch in supported revision with the provisioned IOMs.
         invalidSourceMacOption(136) - The OAM test cannot be performed
              because the source MAC option is not allowed with the specified
              service.
         sendFailSpbMgdService(137) - The OAM test cannot be performed
              on a service which is managed by SPB.
         useStaticPwParameters(138) - The spoke SDP is configured for
              static PW.
         type1Fec129PwNotSupported(139) - The OAM test is not supported on
              type 1 FEC129 pseudowires.
         mplsTpLspPathNotOperational(140) - The OAM test cannot be performed
              because the MPLS-TP LSP path is not operational.
         invalidStaticMplsTpLsp(141)- The OAM test only supports static
              MPLS-TP LSPs
         controlWordNotValid(142) - The control-word for the spoke-sdp is not
              valid for this OAM test
         pwPathIdNotConfigured(143) - The pw-path-id provisioning is not complete.
         notSupportedOnVcSwitchService(144) - The OAM test is not supported on a
              vc-switching service.
         sdpFarEndNotSupported(145) - The OAM test does not support sdp far end
              value.
         mplsTpLspPathShutdown(146) - The MPLS-TP path is currently shutdown
         forceOptionIsBlocked(147) - The force option is currently blocked because
              of the configuration of a related entity
         intfForLspPathIsNotOperational(148) - The interface for the LSP path is
              not operational
         ttlExpired(149) - The destination could not be reached because the
              time-to-live (IPv4) or hop limit (IPv6) was too small. This
              results from an ICMPv4 type 11 code 0 or ICMPv6 type 3 code 0
              message.
         networkUnreachable(150) - The network specified by the destination
              address is unreachable. This results from an ICMPv4 type 3 code 0
              or ICMPv6 type 1 code 0 message.
         hostUnreachable(151) - The host specified by the destination address
              is unreachable. This results from an ICMPv4 type 3 code 1 or
              ICMPv6 type 1 code 3 message.
         bgpLabelPrefixIsLocal(152) - The OAM test cannot be performed because the
              associated BGP Label Route prefix is local to the system.
         bgpLabelPrefixUnknown(153) - The OAM test cannot be performed because the
              BGP Target Fec prefix entry is not found in the Routing Table.
         ldpPrefixUnknown(154) - The OAM test cannot be performed because the
              LDP Target Fec prefix entry is not found in the Routing Table.
         l2tpv3DeliveryTypeUnsupported(155) - The OAM test cannot be performed because the
              the l2TPv3 delivery type is unsupported.
         "
    SYNTAX INTEGER {
                 responseReceived(1),
                 unknown(2),
                 internalError(3),
                 maxConcurrentLimitReached(4),
                 requestTimedOut(5),
                 unknownOrigSdpId(6),
                 downOrigSdpId(7),
                 requestTerminated(8),
                 invalidOriginatorId(9),
                 invalidResponderId(10),
                 unknownRespSdpId(11),
                 downRespSdpId(12),
                 invalidServiceId(13),
                 invalidSdp(14),
                 downServiceSdp(15),
                 noServiceEgressLabel(16),
                 invalidHostAddress(17),
                 invalidMacAddress(18),
                 invalidLspName(19),
                 macIsLocal(20),
                 farEndUnreachable(21),
                 downOriginatorId(22),
                 downResponderId(23),
                 changedResponderId(24),
                 downOrigSvcId(25),
                 downRespSvcId(26),
                 noServiceIngressLabel(27),
                 mismatchCustId(28),
                 mismatchSvcType(29),
                 mismatchSvcMtu(30),
                 mismatchSvcLabel(31),
                 noSdpBoundToSvc(32),
                 downOrigSdpBinding(33),
                 invalidLspPathName(34),
                 noLspEndpointAddr(35),
                 invalidLspId(36),
                 downLspPath(37),
                 invalidLspProtocol(38),
                 invalidLspLabel(39),
                 routeIsLocal(40),
                 noRouteToDest(41),
                 localExtranetRoute(42),
                 srcIpInBgpVpnRoute(43),
                 srcIpInvalid(44),
                 bgpDaemonBusy(45),
                 mcastNotEnabled(46),
                 mTraceNoSGFlow(47),
                 mTraceSysIpNotCfg(48),
                 noFwdEntryInMfib(49),
                 dnsNameNotFound(50),
                 noSocket(51),
                 socketOptVprnIdFail(52),
                 socketOptIfInexFail(53),
                 socketOptNextHopFail(54),
                 socketOptMtuDiscFail(55),
                 socketOptSndbufFail(56),
                 socketOptHdrincFail(57),
                 socketOptTosFail(58),
                 socketOptTtlFail(59),
                 bindSocketFail(60),
                 noRouteByIntf(61),
                 noIntf(62),
                 noLocalIp(63),
                 sendtoFail(64),
                 rcvdWrongType(65),
                 noDirectInterface(66),
                 nexthopUnreachable (67),
                 socketOptHwTimeStampFail(68),
                 noSpokeSdpInVll(69),
                 farEndVccvNotSupported(70),
                 noVcEgressLabel(71),
                 socketOptIpSessionFail(72),
                 rcvdWrongSize(73),
                 dnsLookupFail (74),
                 noIpv6SrcAddrOnIntf (75),
                 multipathNotSupported (76),
                 nhIntfNameNotFound (77),
                 msPwInvalidReplyMode (78),
                 ancpNoAncpString (79),
                 ancpNoSubscriber (80),
                 ancpNoAncpStringForSubscriber (81),
                 ancpNoAccessNodeforAncpString (82),
                 ancpNoAncpCapabilityNegotiated (83),
                 ancpOtherTestInProgress (84),
                 ancpMaxNbrAncpTestsInProgress (85),
                 spokeSdpOperDown (86),
                 noMsPwVccvInReplyDir (87),
                 p2mpLspNameOrInstInvalid (88),
                 p2mpLspS2LPathDown (89),
                 p2mpLspS2LAddressInvalid (90),
                 p2mpLspNotOperational (91),
                 p2mpLspTrMultipleReplies (92),
                 invalidMepId (93),
                 multipleReplies (94),
                 packetSizeTooBig (95),
                 gtpPingError (96),
                 gtpPingRsrcUnavailable (97),
                 gtpPingDupRequest (98),
                 gtpPingCleanUpInProg (99),
                 invalidInterface(100),
                 p2mpLspNotFound(101),
                 ethCfmSlmInLoss(102),
                 ethCfmSlmOutLoss(103),
                 ethCfmSlmUnacknowledged(104),
                 spokeSdpFecNoBndFound(105),
                 mtraceNotSupportedP2mp(106),
                 useFec129Parameters(107),
                 dnsServerUnexpectedResponse(108),
                 dnsServerResponseFormErr(109),
                 dnsServerResponseServFail(110),
                 dnsServerResponseNotImp(111),
                 dnsServerResponseRefused(112),
                 sendFailUndefinedServiceId(113),
                 sendFailWrongServiceType(114),
                 sendFailSubnettedService(115),
                 invalidRespServiceId(116),
                 adminDownOrigSdpBind(117),
                 operDownRespSdpBind(118),
                 adminDownRespSdpBind(119),
                 sdpBindVcidMismatch(120),
                 sdpBindTypeMismatch(121),
                 sdpBindVcTypeMismatch(122),
                 sdpBindVlanVcTagMismatch(123),
                 adminDownOrigSvc(124),
                 adminDownRespSvc(125),
                 adminDownOrigSdpId(126),
                 adminDownRespSdpId(127),
                 mTraceSourceIsNotRemote(128),
                 invalidVirtualRouterId(129),
                 ldpPrefixIsLocal(130),
                 sourceIpIsNotLocal(131),
                 nextHopIpIsLocal(132),
                 targetIpIsLocal(133),
                 invalidControlPlaneOption(134),
                 iomRevisionNotSupported(135),
                 invalidSourceMacOption(136),
                 sendFailSpbMgdService(137),
                 useStaticPwParameters(138),
                 type1Fec129PwNotSupported(139),
                 mplsTpLspPathNotOperational(140),
                 invalidStaticMplsTpLsp(141),
                 controlWordNotValid(142),
                 pwPathIdNotConfigured(143),
                 notSupportedOnVcSwitchService(144),
                 sdpFarEndNotSupported(145),
                 mplsTpLspPathShutdown(146),
                 forceOptionIsBlocked(147),
                 intfForLspPathIsNotOperational(148),
                 ttlExpired(149),
                 networkUnreachable(150),
                 hostUnreachable(151),
                 bgpLabelPrefixIsLocal(152),
                 bgpLabelPrefixUnknown(153),
                 ldpPrefixUnknown(154),
                 l2tpv3DeliveryTypeUnsupported(155)
           }

TmnxOamSignalProtocol ::= TEXTUAL-CONVENTION
    STATUS  current
    DESCRIPTION
        "The value of TmnxOamSignalProtocol is an enumerated integer that
         indicates the type of label signaling protocol used by a
         router in a specific L2 mapping entry."
    SYNTAX  INTEGER {
                unknown (0),
                static  (1),
                bgp     (2),
                ldp     (3),
                rsvpTe  (4),
                crLdp   (5)
            }

TmnxOamTestResponsePlane ::= TEXTUAL-CONVENTION
    STATUS  current
    DESCRIPTION
        "The value of TmnxOamTestResponsePlane is an enumerated integer
         that indicates the respone plane from which the OAM ping or
         traceroute response was received."
    SYNTAX  INTEGER {
                controlPlane (1),
                dataPlane    (2),
                none         (3)
            }

TmnxOamSaaThreshold ::= TEXTUAL-CONVENTION
    STATUS      current
    DESCRIPTION
        "The value of TmnxOamSaaThreshold is a enumerated integer that
         indicates which type of thresholds should be monitored upon
         completion of an OAM ping test run. When the corresponding
         threshold is crossed, a tnOamSaaThreshold notification will be
         generated.

         noThreshold(0) No threshold type is configured.
         inJitter   (1) Monitor the value of jitter calculated for the
                        inbound, one-way, OAM ping responses received
                        for an OAM ping test run.
         outJitter  (2) Monitor the value of jitter calculated for the
                        outbound, one-way, OAM ping requests sent for an
                        OAM ping test run.
         rtJitter   (3) Monitor the value of jitter calculated for the
                        round trip, two-way, OAM ping requests and replies
                        for an OAM ping test run.
         inLoss     (4) Monitor the number of inbound OAM ping responses not
                        received for an OAM ping test run.
         outLoss    (5) Monitor the number of outbound OAM ping requests that
                        could not be sent for an OAM ping test run.
         rtLoss     (6) Monitor the amount of packet loss for a round-trip
                        OAM ping test run.
         inLatency  (7) Monitor the average amount of latency of inbound
                        OAM ping responses for an OAM ping test run.
         outLatency (8) Monitor the average amount of latency of outbound
                        OAM ping requests for an OAM ping test run.
         rtLatency  (9) Monitor the average amount of round-trip latency
                        for an OAM ping test run.
        "
    SYNTAX      INTEGER {
                    noThreshold (0),
                    inJitter    (1),
                    outJitter   (2),
                    rtJitter    (3),
                    inLoss      (4),
                    outLoss     (5),
                    rtLoss      (6),
                    inLatency   (7),
                    outLatency  (8),
                    rtLatency   (9)
                }

TmnxOamVccvAssocChannel          ::= TEXTUAL-CONVENTION
    STATUS      current
    DESCRIPTION
        "A value of type TmnxOamVccvAssocChannel specifies the launched echo
         request's usage of the Associated Channel (ACH) mechanism, when
         performing an MPLS-TP VCCV test.

         Values:
            notApplicable(1)
                Used when the test is not an MPLS-TP VCCV test.
            nonIp(2)
                Use the Associated Channel mechanism described in RFC 6426,
                Section 3.3.
            ipv4(3)
                Use the Associated Channel mechanism described in RFC 6426,
                Section 3.2."
    REFERENCE
        "RFC 6426, 'MPLS On-Demand Connectivity Verification and Route Tracing',
         Section 3.2, 'On-Demand CV with IP Encapsulation, over ACH',
         Section 3.3, 'Non-IP-Based On-Demand CV, Using ACH'."
    SYNTAX      INTEGER {
                    notApplicable(1),
                    nonIp(2),
                    ipv4(3)
    }

TmnxOamVccvTestSubMode           ::= TEXTUAL-CONVENTION
    STATUS      current
    DESCRIPTION
        "A value of type TmnxOamVccvTestSubMode specifies the type of VCCV ping
         or VCCV trace route test to perform.

         VCCV test types:
             static(2)
                 Perform a VCCV ping or VCCV trace route test using the RFC
                 6426 'Target FEC Stack' code point 'Static Pseudowire'.
             unspecified(1)
                 Perform any other supported type of VCCV ping or trace route
                 test.  Examples:  a VCCV ping or VCCV trace route test using
                 the RFC 4379 'Target FEC Stack' code point 'FEC 128
                 Pseudowire'; a VCCV ping or VCCV trace route test using the RFC
                 4379 'Target FEC Stack' code point 'FEC 129 Pseudowire'."
    REFERENCE
        "RFC 4379, 'Detecting Multi-Protocol Label Switched (MPLS) Data Plane
         Failures', Section 3.2 ('Target FEC Stack').
         RFC 6426, 'MPLS On-Demand Connectivity Verification and Route Tracing',
         Section 2.3.2 ('Static Pseudowire Sub-TLV')."
    SYNTAX      INTEGER {
                    unspecified(1),
                    static(2)
    }

TmnxOamVcType ::= TEXTUAL-CONVENTION
    STATUS          current
    DESCRIPTION
        "The value of TmnxOamVcType is an enumerated integer that
         indicates the type of SDP binding, mesh or spoke,  associated
         with a VC ID.

         NOTE: In releases of this mib prior to R4.0, the textual convention
         TmnxVcType was used to indicate either a mesh, 'ethernet (5)',
         or spoke, 'vpls (11)', type of SDP binding for a VC ID.  In
         release 4.0, the TmnxVcType enumeration 'vpls (11)' is changed to
         'ipipe (11)' and can no longer can be used to represent a spoke SDP
         binding.  This new enumerated textual convention, TmnxOamVcType, has
         been created for use in this mib.  The same enumerated values used in
         previous releases are still used to indicate a mesh or spoke VC ID."
    SYNTAX          INTEGER {
                        meshSdp (5),
                        spokeSdp (11)
                    }


-- TmnxOamLTtraceDisStatusBits ::= TEXTUAL-CONVENTION
--     STATUS      current
--     DESCRIPTION
--         "The value of TmnxOamLTtraceDisStatusBits is an enumerated integer
--          that describes the LDP tree trace discovery status in BITS. This
--          indicates different reason values when the tree discovery
--          of an IP Address FEC is not completely successful.
--             timeout (0)        One or more trace requests for an IP Address
--                               FEC were timedout.
--             maxPath (1)        reached the maximum allowed path limit
--                               for an IP Address FEC.
--             maxHop (2)         reached the maximum allowed hop limit.
--             unexploredPath (3) could not discover all possible paths.
--             noResource (4)     no more internal resource to complete
--                               the discovery.
--          "
--     SYNTAX BITS {
--                 timeout (0),
--                 maxPath (1),
--                 maxHop (2),
--                 unexploredPath (3),
--                 noResource (4)
--             }

TmnxOamTestResult                ::= TEXTUAL-CONVENTION
    STATUS      current
    DESCRIPTION
        "The value of TmnxOamTestResult is an enumerated integer that describes
         the result of a ping or trace test run.
             undetermined      (0) The result is, as yet, unknown.
             success           (1) The test was successful.
             failed            (2) The test failed.
             aborted           (3) The test was terminated before completion.
             txResourcesUnavail(4) The test did not start because transmit
                                   resources are unavailable."
     SYNTAX INTEGER {
                undetermined      (0),
                success           (1),
                failed            (2),
                aborted           (3),
                txResourcesUnavail(4)
            }

--
--  Nokia SROS series OAM Ping General Objects
--
--
-- tnOamPingMaxConcurrentTests   OBJECT-TYPE
--     SYNTAX      Unsigned32
--     UNITS       "tests"
--     MAX-ACCESS  read-write
--     STATUS      current
--     DESCRIPTION
--         "The maximum number of concurrent active OAM ping tests
--          that are allowed within an agent implementation.  A value of
--          zero (0) for this object implies that there is no limit for
--          the number of concurrent active tests in effect."
--     DEFVAL { 0 }
--     ::= { tnOamPingObjs 2 }
--
--
--  Nokia SROS series OAM Ping Control Table Scalar
--
tnOamPingCtlAttributeTotal OBJECT-TYPE
   SYNTAX         Integer32
   MAX-ACCESS     read-only
   STATUS         current
   DESCRIPTION    "."
   ::= { tnOamPingObjs 3 }

--
--  Nokia SROS series OAM Ping Control Table
--
tnOamPingCtlTable     OBJECT-TYPE
    SYNTAX      SEQUENCE OF TnOamPingCtlEntry
    MAX-ACCESS  not-accessible
    STATUS      current
    DESCRIPTION
        "Defines the  SROS OAM ping Control Table for providing,
         via SNMP, the capability of performing  SROS OAM ping
         test operations.  The results of these tests are stored in the
         tnOamPingResultsTable and the tnOamPingHistoryTable."
   ::= { tnOamPingObjs 4 }

tnOamPingCtlEntry OBJECT-TYPE
    SYNTAX      TnOamPingCtlEntry
    MAX-ACCESS  not-accessible
    STATUS      current
    DESCRIPTION
        "Defines an entry in the tnOamPingCtlTable.  The first index
         element, tnOamPingCtlOwnerIndex, is of type SnmpAdminString,
         a textual convention that allows for use of the SNMPv3
         View-Based Access Control Model (RFC 2575 [11], VACM)
         and allows a management application to identify its entries.
         The second index, tnOamPingCtlTestIndex, enables the same
         management application to have multiple outstanding requests."
    INDEX {
             tnSysSwitchId,
             -- tnOamPingCtlOwnerIndex,
             tnOamPingCtlTestIndex
          }
    ::= { tnOamPingCtlTable 1 }

TnOamPingCtlEntry ::=
    SEQUENCE {
        -- tnOamPingCtlOwnerIndex             SnmpAdminString,
        tnOamPingCtlTestIndex              SnmpAdminString,
        tnOamPingCtlRowStatus              RowStatus,
        tnOamPingCtlStorageType            StorageType,
        tnOamPingCtlDescr                  SnmpAdminString,
        tnOamPingCtlTestMode               INTEGER,
        tnOamPingCtlAdminStatus            INTEGER,
        tnOamPingCtlOrigSdpId              SdpId,
        tnOamPingCtlRespSdpId              SdpId,
        tnOamPingCtlFcName                 TFCName,
        tnOamPingCtlProfile                TProfile,
        tnOamPingCtlMtuStartSize           Unsigned32,
        tnOamPingCtlMtuEndSize             Unsigned32,
        tnOamPingCtlMtuStepSize            Unsigned32,
--        tnOamPingCtlTargetAddressType      InetAddressType,
--        tnOamPingCtlTargetAddress          InetAddress,
        tnOamPingCtlTargetIpAddress        IpAddress,
        tnOamPingCtlServiceId              TmnxServId,
        tnOamPingCtlLocalSdp               TruthValue,
        tnOamPingCtlRemoteSdp              TruthValue,
        tnOamPingCtlSize                   Unsigned32,
        tnOamPingCtlTimeOut                Unsigned32,
        tnOamPingCtlProbeCount             Unsigned32,
        tnOamPingCtlInterval               Unsigned32,
        tnOamPingCtlMaxRows                Unsigned32,
        tnOamPingCtlTrapGeneration         BITS,
        tnOamPingCtlTrapProbeFailureFilter Unsigned32,
        tnOamPingCtlTrapTestFailureFilter  Unsigned32,
        tnOamPingCtlSAA                    TruthValue,
        tnOamPingCtlRuns                   Counter32,
        tnOamPingCtlFailures               Counter32,
        tnOamPingCtlLastRunResult          TmnxOamTestResult,
        tnOamPingCtlLastChanged            TimeStamp,
        tnOamPingCtlVRtrID                 TmnxVRtrID,
        tnOamPingCtlTgtAddrType            InetAddressType,
        tnOamPingCtlTgtAddress             InetAddress,
        tnOamPingCtlSrcAddrType            InetAddressType,
        tnOamPingCtlSrcAddress             InetAddress,
        tnOamPingCtlDnsName                OCTET STRING,
        tnOamPingCtlDNSRecord              INTEGER,
        tnOamPingCtlIntervalUnits          INTEGER
    }

-- tnOamPingCtlOwnerIndex OBJECT-TYPE
--     SYNTAX      SnmpAdminString (SIZE(1..32))
--     MAX-ACCESS  not-accessible
--     STATUS      current
--     DESCRIPTION
--        "To facilitate the provisioning of access control by a
--         security administrator using the View-Based Access
--         Control Model (RFC 2575, VACM) for tables in which
--         multiple users may need to independently create or
--         modify entries, the initial index is used as an 'owner
--         index'.  Such an initial index has a syntax of
--         SnmpAdminString, and can thus be trivially mapped to a
--         security name or group name as defined in VACM, in
--         accordance with a security policy.

--         When used in conjunction with such a security policy all
--         entries in the table belonging to a particular user (or
--         group) will have the same value for this initial index.
--         For a given user's entries in a particular table, the
--         object identifiers for the information in these entries
--         will have the same sub identifiers (except for the 'column'
--         sub identifier) up to the end of the encoded owner index.
--         To configure VACM to permit access to this portion of the
--         table, one would create vacmViewTreeFamilyTable entries
--         with the value of vacmViewTreeFamilySubtree including
--         the owner index portion, and vacmViewTreeFamilyMask
--         'wildcarding' the column sub identifier.  More elaborate
--         configurations are possible."
--     ::= { tnOamPingCtlEntry 1 }

tnOamPingCtlTestIndex OBJECT-TYPE
    SYNTAX      SnmpAdminString (SIZE(1..32))
    MAX-ACCESS  not-accessible
    STATUS      current
    DESCRIPTION
        "The test name index of the Nokia SROS OAM ping test.
         This is locally unique, within the scope of an
         tnOamPingCtlOwnerIndex."
    ::= { tnOamPingCtlEntry 1 }

tnOamPingCtlRowStatus OBJECT-TYPE
    SYNTAX      RowStatus
    MAX-ACCESS  read-create
    STATUS      current
    DESCRIPTION
        "This object allows entries to be created and deleted
         in the tnOamPingCtlTable.  Deletion of an entry in this
         table results in all corresponding (same
         tnOamPingCtlOwnerIndex and tnOamPingCtlTestIndex index
         values) tnOamPingResultsTable and tnOamPingHistoryTable
         entries being deleted.

         Activation of a Nokia SROS OAM ping operation is controlled
         via tnOamPingCtlAdminStatus and not by changing
         this object's value to active(1).

         The values for configuration objects required for the type of
         test specified in tnOamPingCtlTestMode MUST be specified
         prior to a transition to active(1) state being
         accepted.

         Transitions in and out of active(1) state are not allowed while
         an entry's tnOamPingResultsOperStatus is active(1) with the
         exception that deletion of an entry in this table by setting
         its RowStatus object to destroy(6) will stop an active Nokia
         SROS OAM ping operation.

         The operational state of an Nokia SROS OAM ping operation
         can be determined by examination of its
         tnOamPingResultsOperStatus object."
    REFERENCE
        "See definition of RowStatus in RFC 2579, 'Textual
        Conventions for SMIv2.'"
    ::= { tnOamPingCtlEntry 2 }

tnOamPingCtlStorageType OBJECT-TYPE
    SYNTAX      StorageType
    MAX-ACCESS  read-create
    STATUS      current
    DESCRIPTION
        "The storage type for this conceptual row.
         Conceptual rows having the value 'permanent' need not
         allow write-access to any columnar objects in the row."
    DEFVAL { volatile }
    ::= { tnOamPingCtlEntry 3 }

tnOamPingCtlDescr OBJECT-TYPE
    SYNTAX      SnmpAdminString
    MAX-ACCESS  read-create
    STATUS      current
    DESCRIPTION
        "The purpose of this object is to provide a
         descriptive name of the OAM ping test."
    DEFVAL      { ''H }   -- the empty string
    ::= { tnOamPingCtlEntry 4 }

tnOamPingCtlTestMode     OBJECT-TYPE
    SYNTAX      INTEGER {
                    none (0),
                    sdpPing (1),
                    mtuPing (2),
                    svcPing (3),
                    -- macQuery (4),  obsolete
                    macPing (5),
                    macPopulate (6),
                    macPurge (7),
                    lspPing (8),
                    vprnPing (9),
                    atmPing (10),
                    mfibPing (11),
                    cpePing (12),
                    mrInfo (13),
                    vccvPing (14),
                    icmpPing (15),
                    dnsPing (16),
                    ancpLoopback (17),
                    p2mpLspPing (18),
                    ethCfmLoopback (19),
                    ethCfmTwoWayDelay (20),
                    mobGtpPing (21),
                    ethCfmTwoWaySlm (22),
                    ethCfmTwoWayLm (23),
                    ethCfmOneWayDelay (24)
                }
    MAX-ACCESS  read-create
    STATUS      current
    DESCRIPTION
        "Specifies the type of OAM ping test defined by this entry.
         The configuration parameters unique to a specific test type are to
         be found in an sparsely dependent table extension for that test type.

         none    -  the test type is unspecified.

         sdpPing -  tests SDP connectivity and round trip time.

         mtuPing -  tests MTU path size.

         svcPing -  determines the existence and operative state of the
                    service ID on the far end ESR.
                    NOTE: This is a one-shot test.

         macQuery - obsolete.  Originally specified functionality is as follows.
                  - determines a specific address mapping for the service ID.
                    See tnOamMacPingCtlTable for additional parameters.
                    NOTE: This is a one-shot test.

         macPing -  determines address mappings for the service ID.
                    See tnOamMacPingCtlTable for additional parameters.

         macPopulate - populates an OAM MAC address into the FIBs.
                    See tnOamMacPingCtlTable for additional parameters.
                    NOTE: This is a one-shot test.

         macPurge - deletes an OAM MAC address from the FIBs.
                    See tnOamMacPingCtlTable for additional parameters.
                    NOTE: This is a one-shot test.

         lspPing -  tests LSP path connectivity and round trip time.
                    See tnOamLspPingCtlTable for additional parameters.

         vprnPing - tests IP path connectivity and round trip time within
                    a specified VPRN service.  See tnOamVprnPingCtlTable
                    for additional parameters.

         atmPing  - tests ATM path connectivity and round trip time on an
                    ATM VCC.  See tnOamAtmPingCtlTable for additional
                    parameters.

         mfibPing - tests IP multicast connectivity and round trip time
                    within a specified VPLS service.
                    See tnOamMfibPingCtlTable for additional parameters.

         cpePing  - determines IP connectivity to a CPE
                    within a specified VPLS service.
                    See tnOamCpePingCtlTable for additional parameters.

         mrInfo   - Get multicast router's capabilities and the list of
                    interfaces with neighbors.

        vccvPing  - tests pseudowire connectivity and round trip time.
                    See tnOamVccvPingCtlTable for additional parameters.

        icmpPing  - tests IP connectivity and round trip time.
                    See tnOamIcmpPingCtlTable for additional parameters.

        dnsPing   - tests DNS name resolution connectivity and round trip time.

        ancpLoopback - send an OAM loopback test request to the access node.
                    See tnOamAncpTestCtlTable for additional parameters.

        p2mpLspPing -  tests P2MP LSP path connectivity and round trip time.
                    Test mode cannot be p2mpLspPing if SAA is enabled.  See
                    tnOamP2mpLspPingCtlTable for additional parameters.

        ethCfmLoopback - performs Ethernet Connectivity Fault Management (CFM)
                    loopback tests.  This MIB supports the SAA form of this
                    test only (the OAM form uses a separate set of objects - see
                    IEEE8021-CFM-MIB).  Additional parameters for the SAA
                    ethCfmLoopback test are in tnOamEthCfmPingCtlTable.

        ethCfmTwoWayDelay - performs Ethernet Connectivity Fault Management
                    (CFM) two way delay tests.  This MIB supports the SAA form
                    of this test only (the OAM form uses a separate set of
                    objects - see IEEE8021-CFM-MIB).  Additional parameters for
                    the SAA ethCfmTwoWayDelay test are in
                    tnOamEthCfmPingCtlTable.
        ethCfmOneWayDelay - performs Ethernet Connectivity Fault Management
                    (CFM) one way delay tests.  This MIB supports the SAA form
                    of this test only (the OAM form uses a separate set of
                    objects - see IEEE8021-CFM-MIB).  Additional parameters for
                    the SAA ethCfmOneWayDelay test are in
                    tnOamEthCfmPingCtlTable.

        mobGtpPing - Tests GTP (GPRS Tunnelling Protocol) path connectivity.
        ethCfmTwoWaySlm  - performs Ethernet Connectivity Fault Management
                    (CFM) two way Synthetic Loss Measurement (SLM) tests. This
                    MIB supports the SAA form of this test only (the OAM form
                    uses a separate set of objects - see
                    TN-IEEE8021-CFM-MIB). Additional parameters for the SAA
                    ethCfmTwoWaySlm test are in tnOamEthCfmPingCtlTable.
        ethCfmTwoWayLm  - performs Ethernet Connectivity Fault Management
                    (CFM) two way Loss Measurement (LM) tests. This
                    MIB supports the SAA form of this test only (the OAM form
                    uses a separate set of objects - see
                    TN-IEEE8021-CFM-MIB). Additional parameters for the SAA
                    ethCfmTwoWayLm test are in tnOamEthCfmPingCtlTable.
        "

    DEFVAL { none }
    ::= { tnOamPingCtlEntry 5 }

tnOamPingCtlAdminStatus OBJECT-TYPE
    SYNTAX      INTEGER {
                          enabled(1), -- test should be started
                          disabled(2) -- test should be stopped
                        }
    MAX-ACCESS  read-create
    STATUS      current
    DESCRIPTION
        "Reflects the desired state that a tnOamPingCtlEntry should be
         in:

           enabled(1)  - Attempt to activate the test as defined by
                         this tnOamPingCtlEntry.
           disabled(2) - Deactivate the test as defined by this
                         tnOamPingCtlEntry.

         An attempt to set tnOamPingCtlAdminStatus to 'enabled' will fail
         if the parameters required by a particular OAM ping test mode have
         not been previously set.  Upon completion of an OAM ping test,
         the agent will reset the value of this object to 'disabled'.
         When this object has the value 'enabled' an attempt to modify
         any of the test parameters will fail with an inconsistentValue
         error.

         If tnOamPingCtlTestMode equals either
         'sdpPing' or 'mtuPing', tnOamPingCtlOrigSdpId must have already
         been set.

         If tnOamPingCtlTestMode equals 'mtuPing',
         tnOamPingCtlMtuStartSize and tnOamPingCtlMtuEndSize must also
         have already been set.

         If tnOamPingCtlTestMode equals 'svcPing',
         tnOamPingCtlTgtAddress and tnOamPingCtlServiceId must have
         already been set.

         If tnOamPingCtlTestMode equals 'cpePing',
         tnOamPingCtlTgtAddress, and tnOamCpePingCtlSourceIpAddr
         are required.

         If tnOamPingCtlTestMode equals 'icmpPing', tnOamPingCtlTgtAddress
         must have already been set.

         If tnOamPingCtlTestMode equals 'dnsPing', tnOamPingCtlTgtAddress
         must have already been set.

         If tnOamPingCtlSAA has the value 'true' and tnOamSaaCtlAdminStatus
         has a value 'outOfService', an attempt to set this object to 'enabled'
         will fail with an inconsistentValue error.

         Refer to the corresponding tnOamPingResultsOperStatus to determine
         the operational state of the test defined by this entry."
    DEFVAL { disabled }
    ::= { tnOamPingCtlEntry 6 }

tnOamPingCtlOrigSdpId    OBJECT-TYPE
    SYNTAX      SdpId
    MAX-ACCESS  read-create
    STATUS      current
    DESCRIPTION
        "Specifies the originating SDP-ID to be used for performing
         a sdp-ping or mtu-ping operation.  This parameter is required
         only if tnOamPingCtlTestMode has a value of either 'sdpPing'
         or 'mtuPing'.

         The far-end address of the specified SDP-ID is the expected
         responder-id within each OAM reply message received.  The
         specified SDP-ID defines the encapsulation of the SDP tunnel
         encapsulation used to reach the far-end.  This can be IP/GRE
         or MPLS.  The value of tnOamPingCtlFcName is used to define
         the outgoing forwarding class used for the SDP encapsulation.

         If the value of tnOamPingCtlOrigSdpId is invalid, or the SDP
         is administratively down, or unavailable, the OAM Echo request
         message probe is not sent and an appropriate error value is
         written to tnOamPingHistoryStatus for that probe entry.  Once
         the interval timer expires, the next probe attempt will be made
         if required."
    DEFVAL { 0 } -- invalid Sdp-ID
    ::= { tnOamPingCtlEntry 7 }

tnOamPingCtlRespSdpId    OBJECT-TYPE
    SYNTAX      SdpId
    MAX-ACCESS  read-create
    STATUS      current
    DESCRIPTION
        "Specifies the return SDP-ID to be used by the far-end node for
         its message reply.  This parameter is optional and is valid only if
         tnOamPingCtlTestMode has a value of 'sdpPing'.

         If this SDP-ID does not exist on the far-end, terminates on another
         node different than the originating node, or some other issue
         prevents the far-end from using the specified SDP-ID, the OAM Echo
         message reply is sent using generic IP/GRE OAM encapsulation.  The
         received forwarding class (as mapped on the ingress network interface
         for the far-end) defines the forwarding class encapsulation for the
         reply message."
    DEFVAL { 0 }    -- invalid SDP-ID
    ::= { tnOamPingCtlEntry 8 }

tnOamPingCtlFcName       OBJECT-TYPE
    SYNTAX      TFCName
    MAX-ACCESS  read-create
    STATUS      current
    DESCRIPTION
        "The value of tnOamPingCtlFcName specifies the forwarding class to be
         used when launching the probe(s).  The forwarding class name must be
         present in the index column of TIMETRA-QOS-MIB::tFCNameTable.  This
         object is optional.

         As shown in the following table
         a) this object is applicable to a subset of the test types, and
         b) the default forwarding class depends on the test type.

         tnOamPingCtlTestMode   Applicable?   Default
         ----------------------   -----------   -------
         'cpePing'                yes           'be'
         'ethCfmLoopback'         yes           'nc'
         'ethCfmTwoWayDelay'      yes           'nc'
         'ethCfmOneWayDelay'      yes           'nc'
          ethCfmTwoWaySlm'        yes           'nc'
          ethCfmTwoWayLm'         yes           'nc'
         'icmpPing'               yes           'nc'
         'lspPing'                yes           'be'
         'macPing'                yes           'be'
         'p2mpLspPing'            yes           'be'
         'sdpPing'                yes           'be'
         'vccvPing'               yes           'be'
         'vprnPing'               yes           'be'
         otherwise                no            N/A

         For 'ethCfmLoopback','ethCfmTwoWayDelay','ethCfmOneWayDelay', 'ethCfmTwoWaySlm'
         and ethCfmTwoWayLm, the
         forwarding class depends on whether the request is configured to egress
         on a network port or an access port.  In the network port case, the
         forwarding class is the forwarding class of the pseudowire.  In the
         access port case, the forwarding class is that of the SAP's egress
         encapsulation policy.

         For 'lspPing' this is the forwarding class of the LSP tunnel.

         For 'macPing' or 'sdpPing' this is the forwarding class of the SDP
         encapsulation.

         For 'p2mpLspPing' this is the forwarding class of the P2MP LSP tree.

         For 'vccvPing' this is the forwarding class of the pseudowire.

         If forwarding classes are mapped by the applicable QoS policy, the
         probe(s) may be launched using a different forwarding class than the
         forwarding class specified by this object."
    DEFVAL { "be" }
    ::= { tnOamPingCtlEntry 9 }

tnOamPingCtlProfile      OBJECT-TYPE
    SYNTAX      TProfile
    MAX-ACCESS  read-create
    STATUS      current
    DESCRIPTION
        "The value of tnOamPingCtlProfile specifies the profile to be used
         with the forwarding class specified in tnOamPingCtlFcName.  This
         object is optional.

         As shown in the following table
         a) this object is applicable to a subset of the test types, and
         b) the default profile value depends on the test type.

         tnOamPingCtlTestMode   Applicable?   Default
         ----------------------   -----------   -------
         'cpePing'                yes           'out(2)'
         'ethCfmLoopback'         yes           'in(1)'
         'ethCfmTwoWayDelay'      yes           'in(1)'
         'ethCfmOneWayDelay'      yes           'in(1)'
         'ethCfmTwoWaySlm'        yes           'in(1)'
         'ethCfmTwoWayLm'         yes           'in(1)'
         'icmpPing'               no            N/A
         'lspPing'                yes           'out(2)'
         'macPing'                yes           'out(2)'
         'p2mpLspPing'            yes           'out(2)'
         'sdpPing'                yes           'out(2)'
         'vccvPing'               yes           'out(2)'
         'vprnPing'               yes           'out(2)'
         otherwise                no            N/A"
     DEFVAL { out }
     ::= { tnOamPingCtlEntry 10 }

tnOamPingCtlMtuStartSize       OBJECT-TYPE
    SYNTAX      Unsigned32 (0|40..9198)
    UNITS       "Octets"
    MAX-ACCESS  read-create
    STATUS      current
    DESCRIPTION
        "The value of tnOamPingCtlMtuStartSize specifies the size of the first
         OAM Echo message sent as part of an 'mtuPing' test.

         Setting this object to a non-zero value is a prerequisite for starting
         an 'mtuPing' test.  Its value must be less than or equal to the value
         of tnOamPingCtlMtuEndSize.

         An attempt to set this object from a non-zero value to zero will fail
         with a wrongValue error.

         Changing the message size is a method of checking the ability of an
         SDP to support a particular path-mtu value. The size of the message
         does not include the SDP encapsulation, VC-Label (if applied) or any
         DLC headers or trailers."
    DEFVAL { 0 }
    ::= { tnOamPingCtlEntry 11 }

tnOamPingCtlMtuEndSize         OBJECT-TYPE
    SYNTAX      Unsigned32 (0|40..9198)
    UNITS       "Octets"
    MAX-ACCESS  read-create
    STATUS      current
    DESCRIPTION
        "The value of tnOamPingCtlMtuEndSize specifies the size of the last
         OAM Echo message sent as part of an 'mtuPing' test.

         Setting this object to a non-zero value is a prerequisite for starting
         an 'mtuPing' test.  Its value must be greater than or equal to
         the value of tnOamPingCtlMtuStartSize.

         An attempt to set this object from a non-zero value to zero will fail
         with a wrongValue error."
    DEFVAL { 0 }
    ::= { tnOamPingCtlEntry 12 }

tnOamPingCtlMtuStepSize      OBJECT-TYPE
    SYNTAX      Unsigned32 (1..512)
    UNITS       "Octets"
    MAX-ACCESS  read-create
    STATUS      current
    DESCRIPTION
        "Specifies the number of octets by which to increment the
         OAM Echo message request size for each message request sent
         when tnOamPingCtlTestMode is set equal to 'mtuPing'.  If the
         next incremented message size is greater than
         tnOamPingCtlMtuEndSize, the last message has already been
         sent.  The next size message is not sent until a reply is
         received or three messages have timed out at the current
         size.

         This parameter is optional."
    DEFVAL { 32 }
    ::= { tnOamPingCtlEntry 13 }

tnOamPingCtlTargetIpAddress  OBJECT-TYPE
    SYNTAX      IpAddress
    MAX-ACCESS  read-create
    STATUS      obsolete
    DESCRIPTION
        "Specifies the Ipv4 address to be used as the destination for
         performing an OAM ping operation when tnOamPingCtlTestMode has
         a value of 'svcPing' or 'vprnPing'.  This parameter is
         required for 'svcPing', 'vprnPing', 'cpePing' and 'mrinfo'.

         This object was obsoleted in release 4.0 and replaced with
         InetAddress objects tnOamPingCtlTgtAddrType and
         tnOamPingCtlTgtAddress."
    DEFVAL { '00000000'h }     -- 0.0.0.0
    ::= { tnOamPingCtlEntry 14 }

tnOamPingCtlServiceId          OBJECT-TYPE
    SYNTAX      TmnxServId (0..2147483647)
    MAX-ACCESS  read-create
    STATUS      current
    DESCRIPTION
        "The value of tnOamPingCtlServiceId specifies the service ID of the
         service being tested.

         The applicability of tnOamPingCtlServiceId varies with the test type,
         as shown in the following table.

         tnOamPingCtlTestMode   Applicability    Related Virtual Router Object
         ----------------------   -------------    -----------------------------
         'cpePing'                mandatory        none
         'icmpPing'               optional         tnOamPingCtlVRtrID
         'macPing'                mandatory        none
         'macPopulate'            mandatory        none
         'macPurge'               mandatory        none
         'mfibPing'               mandatory        none
         'mrInfo'                 optional         tnOamPingCtlVRtrID
         'svcPing'                mandatory        none
         'vprnPing'               mandatory        none
         otherwise                not applicable   none

         When tnOamPingCtlServiceId is mandatory, a non-zero value must be
         provided.

         When tnOamPingCtlServiceId is optional, it is used to specify a VPRN
         service.  The test must use the VPRN service's virtual router.

         When a related virtual router object is shown, the interaction is
         described in the DESCRIPTION clause of the listed object.

         Service IDs larger than 2147483647 are internal, so they are excluded
         from the range.

         The default value is the null service ID."
    DEFVAL { 0 }  -- null service ID
    ::= { tnOamPingCtlEntry 15 }

tnOamPingCtlLocalSdp     OBJECT-TYPE
    SYNTAX      TruthValue
    MAX-ACCESS  read-create
    STATUS      current
    DESCRIPTION
        "When the value of tnOamPingCtlLocalSdp is 'true', the 'svcPing' test
         determines an egress SDP-ID that is bound to the service that has
         the far-end IP address specified in tnOamPingCtlTgtAddress
         assigned to it.  The far-end address of the specified SDP-ID is
         the expected responder-id within the OAM Echo reply message.  The
         SDP-ID defines the encapsulation of the SDP tunnel encapsulation
         used to reach the far-end.  This can be IP/GRE or MPLS.  On the
         originator egress, the Service-ID must have an associated VC-Label
         to reach the far-end address of the SDP-ID and the SDP-ID must be
         operational for the message to be sent.
         This object is optional and valid only when tnOamPingCtlTestMode is
         equal to 'svcPing'."
    DEFVAL { false }
    ::= { tnOamPingCtlEntry 16 }

tnOamPingCtlRemoteSdp        OBJECT-TYPE
    SYNTAX      TruthValue
    MAX-ACCESS  read-create
    STATUS      current
    DESCRIPTION
        "The value of tnOamPingCtlRemoteSdp specifies the encapsulation of the
         ping reply to be sent by the far end node.

         When tnOamPingCtlRemoteSdp is 'false', the far-end node sends the
         reply using the generic IP/GRE OAM encapsulation.

         When tnOamPingCtlRemoteSdp is 'true', the far-end node sends the
         reply using the same service tunnel encapsulation labeling used for the
         associated service traffic.  If that labeling cannot be found, the
         generic IP/GRE OAM encapsulation is used.

         This object is optional and is applicable only when
         tnOamPingCtlTestMode is equal to 'svcPing'."
    DEFVAL { false }
    ::= { tnOamPingCtlEntry 17 }

tnOamPingCtlSize OBJECT-TYPE
    SYNTAX      Unsigned32 (0..16384)
    UNITS       "octets"
    MAX-ACCESS  read-create
    STATUS      current
    DESCRIPTION
        "The value of tnOamPingCtlSize specifies the size of the OAM Echo
         message.

         This parameter is optional and is valid only if tnOamPingCtlTestMode
         has a value of 'sdpPing', 'macPing', 'lspPing', 'vprnPing',
         'mfibPing', 'vccvPing', 'icmpPing', 'p2mpLspPing', 'ethCfmLoopback',
         or 'ethCfmTwoWaySlm'.

         The minimum, maximum, and default values for the
         tnOamPingCtlTestMode cases are:

          'ethCfmLoopback' :       0,  1500,   0
          'ethCfmTwoWaySlm':       0,  1500,   0
          'ethCfmTwoWayDelay':     0,  1500,   0
          'ethCfmOneWayDelay':     0,  1500,   0
          'icmpPing'       :       0, 16384,  56
          'lspPing'        :      80,  9198,  80 - LSP prefix specified
                           :      92,  9198,  92 - LSP name specified
          'macPing'        :       1,  9198,  72
          'mfibPing'       :       1,  9198,  72
          'p2mpLspPing'    :   92|97,  9198,  92 - LSP name, 0 S2L specified
                           : 104|109,  9198, 104 - LSP name, 1 S2L specified
                           : 112|117,  9198, 112 - LSP name, 2 S2L specified
                           : 120|125,  9198, 120 - LSP name, 3 S2L specified
                           : 128|133,  9198, 128 - LSP name, 4 S2L specified
                           : 136|141,  9198, 136 - LSP name, 5 S2L specified
                           :   88|93,  9198,  88 - LDP id, 0 leaf-addr specified
                           : 100|105,  9198, 100 - LDP id, 1 leaf-addr specified
                           : 108|113,  9198, 108 - LDP id, 2 leaf-addr specified
                           : 116|121,  9198, 116 - LDP id, 3 leaf-addr specified
                           : 124|129,  9198, 124 - LDP id, 4 leaf-addr specified
                           : 132|137,  9198, 132 - LDP id, 5 leaf-addr specified
                           :   92|97,  9198,  92 - LDP SSM, 0 leaf-addr specified
                           : 104|109,  9198, 104 - LDP SSM, 1 leaf-addr specified
                           : 112|117,  9198, 112 - LDP SSM, 2 leaf-addr specified
                           : 120|125,  9198, 120 - LDP SSM, 3 leaf-addr specified
                           : 128|133,  9198, 128 - LDP SSM, 4 leaf-addr specified
                           : 136|141,  9198, 136 - LDP SSM, 5 leaf-addr specified
          'sdpPing'        :      72,  9198,  72
          'vccvPing'       :      88,  9198,  88 - FEC 128 pseudowire
                           :     120,  9198, 120 - FEC 129 pseudowire
          'vprnPing'       :       1,  9198,  72

         An RSVP-TE P2MP LSP consists of source-to-leaf (S2L) sub-LSPs.

         For P2MP LSP ping, a gap in the supported range of tnOamPingCtlSize
         arises from the inclusion of the Pad TLV (see RFC 4379 section 3.4).
         For example, when no S2L sub-LSP is specified for a RSVP P2MP LSP,
         the minimum ping size is 92. But the next valid minimum ping size
         is 97 due to the inclusion of the Pad TLV.

         When the OAM message is encapsulated in an IP/GRE SDP, the
         IP 'DF' (Don't Fragment) bit is set.  If any segment of the path
         between the sender and receiver cannot handle the message size,
         the message is discarded.  MPLS LSPs are not expected to fragment
         the message either, as the message contained in the LSP is not an
         IP packet.

         When tnOamPingCtlTestMode has a value of 'ethCfmLoopback', or
         'ethCfmTwoWaySlm' the value of this object specifies the number of
         octets in the Value field of the Data TLV of the Ethernet CFM packet.
         If zero is specified, the packet has no Data TLV.

         When tnOamPingCtlTestMode has a value of 'icmpPing', the value
         of this object specifies the payload size following the ICMP
         header.

         When tnOamPingCtlTestMode has a value of 'mtuPing', changing the
         message size is a method of checking the ability of an SDP
         to support a particular path-mtu value.  The size of the message
         does not include the SDP encapsulation, VC-Label (if applied)
         or any DLC headers or trailers.

         Before 6.0 release, the minimum size in 'sdpPing' is 40 octets.
         Such shorter packet has no timestamp information but should still
         be accepted for interoperability purpose. However, new 'sdpPing'
         should include the timestamp information."
    DEFVAL { 72 }
    ::= { tnOamPingCtlEntry 18 }

tnOamPingCtlTimeOut OBJECT-TYPE
    SYNTAX      Unsigned32 (1..120000)
    UNITS       "milliseconds"
    MAX-ACCESS  read-create
    STATUS      current
    DESCRIPTION
        "The value of tnOamPingCtlTimeOut specifies the time-out value,
         in milliseconds, to be used during a test run.

         Timers (with duration configured using the tnOamPingCtlTimeOut value)
         are used in one of two ways during a test run.
         1.  Per Probe:  a timer is started each time a probe is sent.  If the
             timer expires before the probe response arrives, the probe is
             declared failed.  This is the traditional time-out method for a
             sequence of probes.
             OR
         2.  Per Test:  a timer is started once per test run, when the last
             probe of the test run is sent.  ANY probe which does not have a
             response when the timer expires is declared failed.

         'Per Probe' or 'Per Test' is chosen based on the
         tnOamPingCtlTestMode value.  The choice is not configurable.

         The accepted minimum, maximum, and default values for
         tnOamPingCtlTimeOut depend on tnOamPingCtlTestMode, as shown in the
         following table in seconds.  The table also shows the timer usage
         for the test mode.

         tnOamPingCtlTestMode      Min     Max      Def     Timer Usage
         ----------------------    ---     ---      ---     -----------
         'atmPing'                 1       10       5       Per Probe
         'dnsPing'                 1       120      5       Per Probe
         'ethCfmLoopback'          1       10       5       Per Probe
         'ethCfmTwoWayDelay'       1       10       5       Per Test
         'ethCfmOneWayDelay'       1       10       5       Per Test
         'ethCfmTwoWaySlm'         1       10       5       Per Test
         'ethCfmTwoWayLm'          1000    10000    1000    Per Test
         'icmpPing'                1       10       5       Per Test
         'lspPing'                 1       10       5       Per Probe
         'macPing'                 1       10       5       Per Probe
         'mfibPing'                1       100      5       Per Probe
         'mtuPing'                 1       10       5       Per Probe
         'p2mpLspPing'             1       120      10      Per Probe
         'sdpPing'                 1       10       5       Per Probe
         'vccvPing'                1       10       5       Per Probe
         'vprnPing'                1       100      5       Per Probe
         otherwise  .........  the value of tnOamPingCtlTimeOut is irrelevant"
    DEFVAL { 1000 }
    ::= { tnOamPingCtlEntry 19 }

tnOamPingCtlProbeCount OBJECT-TYPE
    SYNTAX      Unsigned32 (1..100000)
    UNITS       "probes"
    MAX-ACCESS  read-create
    STATUS      current
    DESCRIPTION
        "The value of tnOamPingCtlProbeCount specifies the number of probes to
         send during the test.

         The maximum probe count depends on the value of tnOamPingCtlTestMode,
         as follows:
           'macPopulate', 'macPurge','p2mpLspPing', 'svcPing'                                        : 1
           'ethCfmTwoWayDelay', 'ethCfmOneWayDelay', 'ethCfmTwoWaySlm', 'ethCfmTwoWayLm'             : 1000
           'icmpPing'                                                                                : 100000
           otherwise                                                                                 : 100

         For the following tnOamPingCtlTestMode values, the value of
         tnOamPingCtlProbeCount does not affect the behavior of the test:
         'mrInfo', 'mtuPing'.

         If tnOamPingCtlTestMode is 'icmpPing', the default probe count value
         is 5.  Otherwise, the DEFVAL applies."
    DEFVAL { 1 }
    ::= { tnOamPingCtlEntry 20 }

tnOamPingCtlInterval  OBJECT-TYPE
    SYNTAX      Unsigned32 (1..90000)
    UNITS       "milliseconds"
    MAX-ACCESS  read-create
    STATUS      current
    DESCRIPTION
        "The value of tnOamPingCtlInterval specifies the time to wait between
         the transmission of one OAM Echo request and the next.

         The applicability, range, and default value of the interval specified
         using the tnOamPingCtlInterval vary with tnOamPingCtlTestMode and
         tnOamIcmpPingCtlRapid, as shown in the following table in seconds.

         tnOamPingCtlTestMode   Supported Values (sec)           Default (sec)
         'ethCfmLoopback'         1, 2, .. 10                           5
         'ethCfmTwoWayDelay'      0.1, 0.2, .. 0.9;  1, 2, .. 10        5
         'ethCfmOneWayDelay'      0.1, 0.2, .. 0.9;  1, 2, .. 10        5
         'ethCfmTwoWaySlm'        0.1, 0.2, .. 0.9;  1, 2, .. 10        5
         'ethCfmTwoWayLm'         0.1, 1, 10                            1
         'icmpPing' with RAPID    0.01, 0.02, .. 100.00                 0.01
         'icmpPing' without RAPID 1, 2, .. 10000                        1
         'p2mpLspPing'            not applicable
         otherwise                1, 2, .. 10                           1

         Following are the allowed value for 1830 TPS:
        {33, 100, 1000} - all values in decimilliseconds
        {1, 10, 60, 600} - all values in seconds."
    DEFVAL { 1000 }
    ::= { tnOamPingCtlEntry 21 }

tnOamPingCtlMaxRows OBJECT-TYPE
    SYNTAX      Unsigned32
    UNITS       "rows"
    MAX-ACCESS  read-create
    STATUS      obsolete
    DESCRIPTION
        "The maximum number of entries allowed in the tnOamPingHistoryTable
         for this OAM ping test.  The agent will remove the oldest entry in
         the tnOamPingHistoryTable to allow the addition of an new entry
         once the number of rows in the tnOamPingHistoryTable reaches this
         value.

         Old entries are not removed when a new test is started.  Entries are
         added to the tnOamPingHistoryTable until tnOamPingCtlMaxRows is
         reached before entries begin to be removed.

         'p2mpLspPing' uses a default value of 400, which is the maximum
         number of leaves per P2MP LSP tree.

         A value of 0 for this object disables creation of
         tnOamPingHistoryTable entries.

         This object was obsoleted in release 6.0R17."
    DEFVAL { 300 }
    ::= { tnOamPingCtlEntry 22 }

tnOamPingCtlTrapGeneration OBJECT-TYPE
    SYNTAX      BITS {
                   probeFailure(0),
                   testFailure(1),
                   testCompletion(2)
                  }
    MAX-ACCESS  read-create
    STATUS      current
    DESCRIPTION
        "The value of tnOamPingCtlTrapGeneration specifies the
         notification(s) to send for a test run.

         Each bit enables the transmission of one notification, as follows.
         'probeFailure(0)':  send one tnOamPingProbeFailedV3 notification if
            at least M successive probes failed during the test run.  M is
            configured using tnOamPingCtlTrapProbeFailureFilter.
         'testFailure(1)':  send one tnOamPingTestFailedV3 notification if at
            least N probes failed during the test run.  N is configured using
            tnOamPingCtlTrapTestFailureFilter.
         'testCompletion(2)':  send one tnOamPingTestCompletedV3 notification
            when the test run is complete."
    DEFVAL { {} }
    ::= { tnOamPingCtlEntry 23 }

tnOamPingCtlTrapProbeFailureFilter OBJECT-TYPE
    SYNTAX      Unsigned32 (0..15)
    MAX-ACCESS  read-create
    STATUS      current
    DESCRIPTION
        "The value of this object is used to determine when
         to generate a tnOamPingProbeFailed NOTIFICATION.

         Setting tnOamPingCtlTrapGeneration
         to 'probeFailure (0)' implies that a tnOamPingProbeFailed
         NOTIFICATION is generated only when the number of
         successive probe failures, as indicated by the
         value of tnOamPingCtlTrapProbeFailureFilter, fail within
         a given ping test."
    DEFVAL { 1 }
    ::= { tnOamPingCtlEntry 24 }

tnOamPingCtlTrapTestFailureFilter OBJECT-TYPE
    SYNTAX      Unsigned32 (0..15)
    MAX-ACCESS  read-create
    STATUS      current
    DESCRIPTION
        "The value of this object is used to determine when
         to generate a tnOamPingTestFailed NOTIFICATION.

         Setting tnOamPingCtlTrapGeneration to 'testFailure (1)'
         implies that a tnOamPingTestFailed NOTIFICATION is
         generated only when the number of ping failures
         within a test exceed the value of
         tnOamPingCtlTrapTestFailureFilter."
    DEFVAL { 1 }
    ::= { tnOamPingCtlEntry 25 }

tnOamPingCtlSAA OBJECT-TYPE
    SYNTAX      TruthValue
    MAX-ACCESS  read-create
    STATUS      current
    DESCRIPTION
        "The value of tnOamPingCtlSAA specifies if this test is an SAA test
         (Service Assurance Agent; 'true'), or an OAM test ('false').  If
         there is a tnOamSaaCtlTable row with the specified index values,
         'true' is returned.  Otherwise, 'false' is returned."
    DEFVAL { false }
    ::= { tnOamPingCtlEntry 26 }

tnOamPingCtlRuns      OBJECT-TYPE
    SYNTAX      Counter32
    MAX-ACCESS  read-only
    STATUS      current
    DESCRIPTION
        "The value of tnOamPingCtlRuns indicates the number of times
         this OAM ping test has been executed."
    ::= { tnOamPingCtlEntry 27 }

tnOamPingCtlFailures  OBJECT-TYPE
    SYNTAX      Counter32
    MAX-ACCESS  read-only
    STATUS      current
    DESCRIPTION
        "The value of tnOamPingCtlFailures indicates the number of times
         this OAM ping test has failed."
    ::= { tnOamPingCtlEntry 28 }

tnOamPingCtlLastRunResult  OBJECT-TYPE
    SYNTAX      TmnxOamTestResult
    MAX-ACCESS  read-only
    STATUS      current
    DESCRIPTION
        "The value of tnOamPingCtlLastRunResult indicates the completion
         status the last time this test was executed.  If this OAM test is
         currently in progress, this object indicates the result of the
         previous test run, if any."
    ::= { tnOamPingCtlEntry 29 }

tnOamPingCtlLastChanged   OBJECT-TYPE
    SYNTAX      TimeStamp
    MAX-ACCESS  read-only
    STATUS      current
    DESCRIPTION
        "The value of tnOamPingCtlLastChanged indicates the time the
         value of a settable object in this row was last changed."
    ::= { tnOamPingCtlEntry 30 }

tnOamPingCtlVRtrID  OBJECT-TYPE
    SYNTAX      TmnxVRtrID
    MAX-ACCESS  read-create
    STATUS      current
    DESCRIPTION
        "The value of tnOamPingCtlVRtrID specifies the virtual router to be
         used for the test.  The value specified must be the index of an active
         row in TIMETRA-VRTR-MIB::vRtrConfTable.

         This object is applicable if tnOamPingCtlTestMode is 'icmpPing' or
         'mrInfo'.

         When directing an 'icmpPing' or 'mrInfo' test to use a virtual router
         associated with a VPRN service, the virtual router can be specified
         using tnOamPingCtlVRtrID (with the VPRN's virtual router number) or
         tnOamPingCtlServiceId (with the VPRN's service number).
         tnOamPingCtlServiceId is preferred, because service numbers are
         constant across an SROS reboot (while virtual routers may be
         renumbered).  If non-default values are specified for both
         tnOamPingCtlVRtrID and tnOamPingCtlServiceId,
         tnOamPingCtlServiceId is used.

         Setting this object is optional."
    DEFVAL { 1 }
    ::= { tnOamPingCtlEntry 31 }

tnOamPingCtlTgtAddrType   OBJECT-TYPE
    SYNTAX      InetAddressType
    MAX-ACCESS  read-create
    STATUS      current
    DESCRIPTION
        "The value of tnOamPingCtlTgtAddrType specifies the address type of
         tnOamPingCtlTgtAddress.

         Values supported depend on tnOamPingCtlTestMode, as follows.
           'cpePing ':              'ipv4(1)'
           'dnsPing' :              'ipv4(1)' 'ipv6(2)'
           'icmpPing':              'ipv4(1)' 'ipv6(2)' 'ipv6z(4)' 'dns(16)'
           'mfibPing':              'ipv4(1)' 'ipv6(2)'
           'mrInfo  ':              'ipv4(1)'                      'dns(16)'
           'svcPing' :              'ipv4(1)'
           'vccvPing': 'unknown(0)' 'ipv4(1)'
           'vprnPing':              'ipv4(1)' 'ipv6(2)'
           otherwise : 'unknown(0)'                                          "
    DEFVAL { unknown }
    ::= { tnOamPingCtlEntry 32 }

tnOamPingCtlTgtAddress OBJECT-TYPE
    SYNTAX      InetAddress
    MAX-ACCESS  read-create
    STATUS      current
    DESCRIPTION
        "The value of tnOamPingCtlTgtAddress specifies the destination IP host
         address to be used when performing an OAM ping operation.  The
         corresponding address type is configured using
         tnOamPingCtlTgtAddrType.

         For 'dnsPing' this is the address of the DNS server host that will be
         asked to resolve a dns name specified by tnOamPingCtlDnsName."
    DEFVAL { ''H }
    ::= { tnOamPingCtlEntry 33 }

tnOamPingCtlSrcAddrType   OBJECT-TYPE
    SYNTAX      InetAddressType
    MAX-ACCESS  read-create
    STATUS      current
    DESCRIPTION
        "The value of tnOamPingCtlSrcAddrType specifies the address type of
         tnOamPingCtlSrcAddress.

         Only 'ipv4' and 'ipv6' address types are supported."
    DEFVAL { unknown }
    ::= { tnOamPingCtlEntry 34 }

tnOamPingCtlSrcAddress OBJECT-TYPE
    SYNTAX      InetAddress  (SIZE(0|4|16))
    MAX-ACCESS  read-create
    STATUS      current
    DESCRIPTION
        "The value of tnOamPingCtlSrcAddress specifies the source IP host
         address to be used when performing an OAM ping operation.  The
         corresponding address type is configured using
         tnOamPingCtlSrcAddrType.

         This is an optional parameter.  It is used when tnOamPingCtlTestMode
         is 'icmpPing', 'dnsPing', 'lspPing', 'p2mpLspPing' (LDP), or
         'vccvPing'."
    DEFVAL { ''H }
    ::= { tnOamPingCtlEntry 35 }

tnOamPingCtlDnsName   OBJECT-TYPE
    SYNTAX      OCTET STRING (SIZE(0..255))
    MAX-ACCESS  read-create
    STATUS      current
    DESCRIPTION
        "The value of tnOamPingCtlDnsName specifies the DNS name to
         be resolved to an IP address.

         This object is required for 'dnsPing'."
    DEFVAL { ''H }
    ::= { tnOamPingCtlEntry 36 }

tnOamPingCtlDNSRecord  OBJECT-TYPE
    SYNTAX      INTEGER {
                    ipv4Arecord    (1),
                    ipv6AAAArecord (2)
                }
    MAX-ACCESS  read-create
    STATUS      current
    DESCRIPTION
        "The value of tnOamPingCtlDNSRecord specifies which DNS record
         is to be retrieved in this test."
    DEFVAL {ipv4Arecord }
    ::= { tnOamPingCtlEntry 37 }

tnOamPingCtlIntervalUnits      OBJECT-TYPE
    SYNTAX      INTEGER {
                    seconds(1),
                    centiseconds(2),
                    decimilliseconds(3)
                }
    MAX-ACCESS  read-create
    STATUS      current
    DESCRIPTION
        "The value of tnOamPingCtlIntervalUnits specifies the units for
         tnOamPingCtlInterval.  For example, if tnOamPingCtlIntervalUnits
         has the value 'centiseconds(2)', and tnOamPingCtlInterval has the
         value 10, the test's interval is 0.1 seconds.

         The supported combinations of tnOamPingCtlIntervalUnits,
         tnOamPingCtlInterval, tnOamPingCtlTestMode, and
         tnOamIcmpPingCtlRapid are specified in the tnOamPingCtlInterval
         DESCRIPTION clause.

         The interaction between this object and tnOamIcmpPingCtlRapid is
         specified in the tnOamIcmpPingCtlRapid DESCRIPTION clause."
    DEFVAL { seconds }
    ::= { tnOamPingCtlEntry 38 }

--
-- Nokia SROS series OAM Ping Results Table
--
tnOamPingResultsTable OBJECT-TYPE
    SYNTAX      SEQUENCE OF TnOamPingResultsEntry
    MAX-ACCESS  not-accessible
    STATUS      current
    DESCRIPTION
        "Defines the OAM Ping Results Table for providing
         the capability of performing OAM ping operations.  The
         results of these operations are stored in the
         tnOamPingResultsTable and the tnOamPingHistoryTable.

         An entry is added to the tnOamPingResultsTable when an
         tnOamPingCtlEntry is started by successful transition
         of its tnOamPingCtlAdminStatus object to enabled(1).

         An entry is removed from the tnOamPingResultsTable when
         its corresponding tnOamPingCtlEntry is deleted."
    ::= { tnOamPingObjs 6 }

tnOamPingResultsEntry OBJECT-TYPE
    SYNTAX      TnOamPingResultsEntry
    MAX-ACCESS  not-accessible
    STATUS      current
    DESCRIPTION
        "Defines an entry in the tnOamPingResultsTable.  The
         tnOamPingResultsTable has the same indexing as the
         tnOamPingCtlTable in order for a tnOamPingResultsEntry to
         correspond to the tnOamPingCtlEntry that caused it to
         be created.

         An entry in this table summarizes results from multiple
         invocations of the test configured by the corresponding
         entry in tnOamPingCtlTable."
    INDEX {
             tnSysSwitchId,
             -- tnOamPingCtlOwnerIndex,
             tnOamPingCtlTestIndex,
             tnOamPingResultsTestRunIndex
          }
    ::= { tnOamPingResultsTable 1 }

TnOamPingResultsEntry ::=
    SEQUENCE {
        tnOamPingResultsOperStatus          INTEGER,
        tnOamPingResultsMinRtt              Unsigned32,
        tnOamPingResultsMaxRtt              Unsigned32,
        tnOamPingResultsAverageRtt          Unsigned32,
        tnOamPingResultsRttSumOfSquares     Unsigned32,
        tnOamPingResultsMtuResponseSize     Unsigned32,
        tnOamPingResultsSvcPing             INTEGER,
        tnOamPingResultsProbeResponses      Unsigned32,
        tnOamPingResultsSentProbes          Unsigned32,
        tnOamPingResultsLastGoodProbe       DateAndTime,
        tnOamPingResultsLastRespHeader      OCTET STRING,
        tnOamPingResultsMinTt               Integer32,
        tnOamPingResultsMaxTt               Integer32,
        tnOamPingResultsAverageTt           Integer32,
        tnOamPingResultsTtSumOfSquares      Unsigned32,
        tnOamPingResultsMinInTt             Integer32,
        tnOamPingResultsMaxInTt             Integer32,
        tnOamPingResultsAverageInTt         Integer32,
        tnOamPingResultsInTtSumOfSqrs       Unsigned32,
        tnOamPingResultsOutJitter           Integer32,
        tnOamPingResultsInJitter            Integer32,
        tnOamPingResultsRtJitter            Integer32,
        tnOamPingResultsProbeTimeouts       Unsigned32,
        tnOamPingResultsProbeFailures       Unsigned32,
        tnOamPingResultsTestRunIndex        Unsigned32,
        tnOamPingResultsRttOFSumSquares     Counter32,
        tnOamPingResultsRttHCSumSquares     Counter64,
        tnOamPingResultsTtOFSumSquares      Counter32,
        tnOamPingResultsTtHCSumSquares      Counter64,
        tnOamPingResultsInTtOFSumSqrs       Counter32,
        tnOamPingResultsInTtHCSumSqrs       Counter64,
        tnOamPingResultsTestRunResult       TmnxOamTestResult
    }

tnOamPingResultsOperStatus OBJECT-TYPE
    SYNTAX      INTEGER {
                          enabled(1),  -- test is in progress
                          disabled(2)  -- test has stopped
                        }
    MAX-ACCESS  read-only
    STATUS      current
    DESCRIPTION
        "Reflects the operational state of a tnOamPingCtlEntry:
           enabled(1)   - Test is active.
           disabled(2)  - Test has stopped."
    ::= { tnOamPingResultsEntry 1 }

tnOamPingResultsMinRtt OBJECT-TYPE
    SYNTAX      Unsigned32
    UNITS       "microseconds"
    MAX-ACCESS  read-only
    STATUS      current
    DESCRIPTION
        "The minimum OAM ping round-trip-time (RTT) received.

         This value is relevant when tnOamPingCtlTestMode has a value of
         'sdpPing', 'ethCfmLoopback', 'ethCfmTwoWayDelay', 'ethCfmOneWayDelay', 'ethCfmTwoWaySlm',
         'ethCfmTwoWayLm'.
         Otherwise, this object contains a value of 0."
    ::= { tnOamPingResultsEntry 4 }

tnOamPingResultsMaxRtt OBJECT-TYPE
    SYNTAX      Unsigned32
    UNITS       "microseconds"
    MAX-ACCESS  read-only
    STATUS      current
    DESCRIPTION
        "The maximum OAM ping round-trip-time (RTT) received.
         A value of 0 for this object implies that no RTT has been received.

         This value is relevant when tnOamPingCtlTestMode has a value of
         'sdpPing', 'ethCfmLoopback', 'ethCfmTwoWayDelay', 'ethCfmOneWayDelay', 'ethCfmTwoWaySlm',
         'ethCfmTwoWayLm'.
         Otherwise, this object contains a value of 0."
    ::= { tnOamPingResultsEntry 5 }

tnOamPingResultsAverageRtt OBJECT-TYPE
    SYNTAX      Unsigned32
    UNITS       "microseconds"
    MAX-ACCESS  read-only
    STATUS      current
    DESCRIPTION
        "The current average OAM ping round-trip-time (RTT).

         This value is relevant when tnOamPingCtlTestMode has a value of
         'sdpPing', 'ethCfmLoopback', 'ethCfmTwoWayDelay', 'ethCfmOneWayDelay', 'ethCfmTwoWaySlm',
         'ethCfmTwoWayLm'.
         Otherwise, this object contains a value of 0."
    ::= { tnOamPingResultsEntry 6 }

tnOamPingResultsRttSumOfSquares OBJECT-TYPE
    SYNTAX      Unsigned32
    UNITS       "microseconds squared"
    MAX-ACCESS  read-only
    STATUS      current
    DESCRIPTION
        "The value of tnOamPingResultsRttSumOfSquares indicates the least
         significant 32 bits of tnOamPingResultsRttHCSumSquares."
    ::= { tnOamPingResultsEntry 7 }

tnOamPingResultsMtuResponseSize      OBJECT-TYPE
    SYNTAX      Unsigned32
    UNITS       "Octets"
    MAX-ACCESS  read-only
    STATUS      current
    DESCRIPTION
        "This object contains the largest size OAM Echo request message
         that received a valid reply.

         The value of this object MUST be reported as 0 when no ping responses
         have been received or an active test has not yet timed out.  When
         tnOamPingCtlTestMode does not have a value of 'mtuPing', this object
         is not relevant and should contain a value of 0."
    ::= { tnOamPingResultsEntry 8 }

tnOamPingResultsSvcPing         OBJECT-TYPE
    SYNTAX      INTEGER {
                    undetermined (0),
                    failed (1),
                    success (2)
                }
    MAX-ACCESS  read-only
    STATUS      current
    DESCRIPTION
        "The object contains the final results of an OAM 'svcPing' test.
         The value of this object MUST be reported as 0 when no ping responses
         have been received or an active test has not yet timed out.  When
         tnOamPingCtlTestMode does not have a value of 'svcPing', this object
         is not relevant and should contain a value of 0."
    ::= { tnOamPingResultsEntry 9 }

tnOamPingResultsProbeResponses OBJECT-TYPE
    SYNTAX      Unsigned32
    UNITS       "responses"
    MAX-ACCESS  read-only
    STATUS      current
    DESCRIPTION
        "Number of responses received for the corresponding
         tnOamPingCtlEntry and tnOamPingResultsEntry.  The value of
         this object MUST be reported as 0 when no probe responses have
         been received."
    ::= { tnOamPingResultsEntry 10 }

tnOamPingResultsSentProbes OBJECT-TYPE
    SYNTAX      Unsigned32
    UNITS       "probes"
    MAX-ACCESS  read-only
    STATUS      current
    DESCRIPTION
        "The value of this object reflects the number of probes sent
         for the corresponding tnOamPingCtlEntry and tnOamPingResultsEntry.
         The value of this object MUST be reported as 0 when no probes
         have been sent."
    ::= { tnOamPingResultsEntry 11 }

tnOamPingResultsLastGoodProbe OBJECT-TYPE
    SYNTAX      DateAndTime
    MAX-ACCESS  read-only
    STATUS      current
    DESCRIPTION
        "Date and time when the last response was received for
         an OAM probe.  If a response has not been received,
         '1970-1-1,0:0:0.0,+0:0' is returned."
    ::= { tnOamPingResultsEntry 12 }

tnOamPingResultsLastRespHeader   OBJECT-TYPE
    SYNTAX      OCTET STRING (SIZE (100))
    MAX-ACCESS  read-only
    STATUS      obsolete
    DESCRIPTION
        "A copy of the OAM header of the last response packet received for
         this OAM ping test.  The value of this object MUST be reported
         as 0 when no probes have been sent.

         This object was obsoleted in release 8.0R1 and replaced with
         tnOamPingHistoryRespHdr in tnOamPingHistoryTable."
    ::= { tnOamPingResultsEntry 13 }

tnOamPingResultsMinTt OBJECT-TYPE
    SYNTAX      Integer32
    UNITS       "microseconds"
    MAX-ACCESS  read-only
    STATUS      current
    DESCRIPTION
        "The minimum OAM ping outbound one-way trip time received.
         A value of 0 for this object implies that no one-way trip time
         measurement is available."
    ::= { tnOamPingResultsEntry 14 }

tnOamPingResultsMaxTt OBJECT-TYPE
    SYNTAX      Integer32
    UNITS       "microseconds"
    MAX-ACCESS  read-only
    STATUS      current
    DESCRIPTION
        "The maximum OAM ping outbound one-way trip time received.
         A value of 0 for this object implies that no one-way trip time
         measurement is available."
    ::= { tnOamPingResultsEntry 15 }

tnOamPingResultsAverageTt OBJECT-TYPE
    SYNTAX      Integer32
    UNITS       "microseconds"
    MAX-ACCESS  read-only
    STATUS      current
    DESCRIPTION
        "The current average OAM ping outbound one-way trip time.
         A value of 0 for this object implies that no one-way trip time
         measurement is available."
    ::= { tnOamPingResultsEntry 16 }

tnOamPingResultsTtSumOfSquares OBJECT-TYPE
    SYNTAX      Unsigned32
    UNITS       "microseconds squared"
    MAX-ACCESS  read-only
    STATUS      current
    DESCRIPTION
        "The value of tnOamPingResultsTtSumOfSquares indicates the least
         significant 32 bits of tnOamPingResultsTtHCSumSquares."
    ::= { tnOamPingResultsEntry 17 }

tnOamPingResultsMinInTt OBJECT-TYPE
    SYNTAX      Integer32
    UNITS       "microseconds"
    MAX-ACCESS  read-only
    STATUS      current
    DESCRIPTION
        "The minimum OAM ping inbound one-way trip time received.

         A value of 0 for this object implies that no one-way trip time
         measurement is available."
    ::= { tnOamPingResultsEntry 18 }

tnOamPingResultsMaxInTt OBJECT-TYPE
    SYNTAX      Integer32
    UNITS       "microseconds"
    MAX-ACCESS  read-only
    STATUS      current
    DESCRIPTION
        "The maximum OAM ping inbound one-way trip time received.

         A value of 0 for this object implies that no one-way trip time
         measurement is available."
    ::= { tnOamPingResultsEntry 19 }

tnOamPingResultsAverageInTt OBJECT-TYPE
    SYNTAX      Integer32
    UNITS       "microseconds"
    MAX-ACCESS  read-only
    STATUS      current
    DESCRIPTION
        "The current average OAM ping inbound one-way trip time.

         A value of 0 for this object implies that no one-way trip time
         measurement is available."
    ::= { tnOamPingResultsEntry 20 }

tnOamPingResultsInTtSumOfSqrs  OBJECT-TYPE
    SYNTAX      Unsigned32
    UNITS       "microseconds squared"
    MAX-ACCESS  read-only
    STATUS      current
    DESCRIPTION
        "The value of tnOamPingResultsInTtSumOfSqrs indicates the least
         significant 32 bits of tnOamPingResultsInTtHCSumSqrs."
    ::= { tnOamPingResultsEntry 21 }

tnOamPingResultsOutJitter      OBJECT-TYPE
    SYNTAX      Integer32
    UNITS       "microseconds"
    MAX-ACCESS  read-only
    STATUS      current
    DESCRIPTION
        "The value of tnOamPingResultsOutJitter indicates the
         amount of one-way trip jitter, expressed in microseconds, for a
         ping probe request packet sent for this OAM test.

         A value of 0 for this object implies that no one-way trip jitter
         measurement is available."
    ::= { tnOamPingResultsEntry 22 }

tnOamPingResultsInJitter      OBJECT-TYPE
    SYNTAX      Integer32
    UNITS       "microseconds"
    MAX-ACCESS  read-only
    STATUS      current
    DESCRIPTION
        "The value of tnOamPingResultsInJitter indicates the
         amount of one-way trip jitter, expressed in microseconds, for a
         ping probe response packet received for this OAM test.

         A value of 0 for this object implies that no one-way trip jitter
         measurement is available."
    ::= { tnOamPingResultsEntry 23 }

tnOamPingResultsRtJitter      OBJECT-TYPE
    SYNTAX      Integer32
    UNITS       "microseconds"
    MAX-ACCESS  read-only
    STATUS      current
    DESCRIPTION
        "The value of tnOamPingResultsRtJitter indicates the
         amount of two-way trip jitter, expressed in microseconds, for a
         ping probe sent for this OAM test.

         A value of 0 for this object implies that no two-way-trip jitter
         measurement is available."
    ::= { tnOamPingResultsEntry 24 }

tnOamPingResultsProbeTimeouts     OBJECT-TYPE
    SYNTAX      Unsigned32
    MAX-ACCESS  read-only
    STATUS      current
    DESCRIPTION
        "The value of tnOamPingResultsProbeTimeouts indicates the number
         of probes timed out without receiving a response."
    ::= { tnOamPingResultsEntry 25 }

tnOamPingResultsProbeFailures     OBJECT-TYPE
    SYNTAX      Unsigned32
    MAX-ACCESS  read-only
    STATUS      current
    DESCRIPTION
        "The value of tnOamPingResultsProbeFailures indicates the total
         number of probes that failed to be transmitted plus the number of
         probes that timed out without receiving a response."
    ::= { tnOamPingResultsEntry 26 }

tnOamPingResultsTestRunIndex      OBJECT-TYPE
    SYNTAX      Unsigned32 (1..4294967295)
    MAX-ACCESS  not-accessible
    STATUS      current
    DESCRIPTION
        "The value of tnOamPingResultsTestRunIndex identifies the
         row entry that reports results for a single OAM test run.

         The agent starts assigning tnOamPingResultsTestRunIndex values
         at 1 and wraps after exceeding the maximum possible value as
         defined by the limit of this object."
    ::= { tnOamPingResultsEntry 27 }

tnOamPingResultsRttOFSumSquares OBJECT-TYPE
    SYNTAX      Counter32
    MAX-ACCESS  read-only
    STATUS      current
    DESCRIPTION
        "The value of tnOamPingResultsRttOFSumSquares indicates the number of
         times tnOamPingResultsRttSumOfSquares overflowed."
    ::= { tnOamPingResultsEntry  28 }

tnOamPingResultsRttHCSumSquares OBJECT-TYPE
    SYNTAX      Counter64
    UNITS       "microseconds squared"
    MAX-ACCESS  read-only
    STATUS      current
    DESCRIPTION
        "The value of tnOamPingResultsRttHCSumSquares indicates the sum of
         squares of the round trip times of the ping test.  Its purpose is to
         enable the standard deviation calculation.

         The value of this object will be reported as 0 when one or more of the
         following conditions apply:
         1.  No round trip time measurement is available.
         2.  The test stopped before completion.
         3.  The test type (i.e. tnOamPingCtlTestMode) is one of the
             following:
             'ancpLoopback',
             'atmPing',
             'macPopulate',
             'macPurge',
             'mfibPing',
             'mrInfo',
             'mtuPing',
             'p2mpLspPing',
             'svcPing."
    ::= { tnOamPingResultsEntry  29 }

tnOamPingResultsTtOFSumSquares OBJECT-TYPE
    SYNTAX      Counter32
    MAX-ACCESS  read-only
    STATUS      current
    DESCRIPTION
        "The value of tnOamPingResultsTtOFSumSquares indicates the number of
         times tnOamPingResultsTtSumOfSquares overflowed."
    ::= { tnOamPingResultsEntry 30 }

tnOamPingResultsTtHCSumSquares OBJECT-TYPE
    SYNTAX      Counter64
    UNITS       "microseconds squared"
    MAX-ACCESS  read-only
    STATUS      current
    DESCRIPTION
        "The value of tnOamPingResultsTtHCSumSquares indicates the sum of
         squares of the outbound one-way trip times of the ping test.  Its
         purpose is to enable the standard deviation calculation.

         The value of this object will be reported as 0 when one or more of the
         following conditions apply:
         1.  No outbound one-way trip time measurement is available.
         2.  The test stopped before completion.
         3.  The test type (i.e. tnOamPingCtlTestMode) is one of the
             following:
             'ancpLoopback',
             'atmPing',
             'cpePing' (sum of squares supported for round trip, not outbound),
             'dnsPing' (sum of squares supported for round trip, not outbound),
             'macPopulate',
             'macPurge',
             'mfibPing',
             'mrInfo',
             'mtuPing',
             'p2mpLspPing',
             'svcPing."
    ::= { tnOamPingResultsEntry 31 }

tnOamPingResultsInTtOFSumSqrs  OBJECT-TYPE
    SYNTAX      Counter32
    MAX-ACCESS  read-only
    STATUS      current
    DESCRIPTION
        "The value of tnOamPingResultsInTtOFSumSqrs indicates the number of
         times tnOamPingResultsInTtSumOfSqrs overflowed."
    ::= { tnOamPingResultsEntry 32 }

tnOamPingResultsInTtHCSumSqrs  OBJECT-TYPE
    SYNTAX      Counter64
    UNITS       "microseconds squared"
    MAX-ACCESS  read-only
    STATUS      current
    DESCRIPTION
        "The value of tnOamPingResultsInTtHCSumSqrs indicates the sum of
         squares of the inbound one-way trip times of the ping test.  Its
         purpose is to enable the standard deviation calculation.

         The value of this object will be reported as 0 when one or more of the
         following conditions apply:
         1.  No inbound one-way trip time measurement is available.
         2.  The test stopped before completion.
         3.  The test type (i.e. tnOamPingCtlTestMode) is one of the
             following:
             'ancpLoopback',
             'atmPing',
             'cpePing' (sum of squares supported for round trip, not inbound),
             'dnsPing' (sum of squares supported for round trip, not inbound),
             'macPopulate',
             'macPurge',
             'mfibPing',
             'mrInfo',
             'mtuPing',
             'p2mpLspPing',
             'svcPing."
    ::= { tnOamPingResultsEntry 33 }

tnOamPingResultsTestRunResult  OBJECT-TYPE
    SYNTAX      TmnxOamTestResult
    MAX-ACCESS  read-only
    STATUS      current
    DESCRIPTION
        "The object contains the overall state of the ping test."
    ::= { tnOamPingResultsEntry 34 }

--
-- Nokia SROS series OAM Ping History Table
--
tnOamPingHistoryTable OBJECT-TYPE
    SYNTAX      SEQUENCE OF TnOamPingHistoryEntry
    MAX-ACCESS  not-accessible
    STATUS      current
    DESCRIPTION
        "Defines a table for storing the results of an OAM ping
         probe operation. The probe results for all OAM ping test types
         are saved in this table except for 'macPing'.  The 'macPing'
         results are saved in the tnOamMacPingHistoryTable.

         For a configured test, this table will hold the results for
         up to 3 runs.

         An entry in this table is created when the result of an OAM ping
         probe is determined.  An entry is removed from this table when
         its corresponding tnOamPingCtlEntry is deleted."
    ::= { tnOamPingObjs 8 }

tnOamPingHistoryEntry OBJECT-TYPE
    SYNTAX      TnOamPingHistoryEntry
    MAX-ACCESS  not-accessible
    STATUS      current
    DESCRIPTION
        "Defines an entry in the tnOamPingHistoryTable.
         The first two index elements identify the tnOamPingCtlEntry
         that a tnOamPingHistoryEntry belongs to.  The third index
         identifies a specific OAM test run.  The fourth index
         element selects a single OAM probe result."
    INDEX {
             tnSysSwitchId,
             -- tnOamPingCtlOwnerIndex,
             tnOamPingCtlTestIndex,
             tnOamPingResultsTestRunIndex,
             tnOamPingHistoryIndex
           }
    ::= { tnOamPingHistoryTable 1 }

TnOamPingHistoryEntry ::=
    SEQUENCE {
        tnOamPingHistoryIndex         Unsigned32,
        tnOamPingHistoryResponse      Unsigned32,
        tnOamPingHistoryOneWayTime    Integer32,
        tnOamPingHistorySize          Unsigned32,
        tnOamPingHistoryStatus        TmnxOamResponseStatus,
        tnOamPingHistoryTime          DateAndTime,
        tnOamPingHistoryReturnCode    Integer32,
        tnOamPingHistorySrcIpAddress  IpAddress,
        tnOamPingHistAddressType      TmnxOamAddressType,
        tnOamPingHistSapId            TmnxStrSapId,
        tnOamPingHistoryVersion       Unsigned32,
        tnOamPingHistoryCpeMacAddr    MacAddress,
        tnOamPingHistoryRespSvcId     TmnxServId,
        tnOamPingHistorySequence      Unsigned32,
        tnOamPingHistoryIfIndex       InterfaceIndexOrZero,
        tnOamPingHistoryDataLen       Unsigned32,
        tnOamPingHistoryRespPlane     TmnxOamTestResponsePlane,
        tnOamPingHistoryReqHdr        OCTET STRING,
        tnOamPingHistoryRespHdr       OCTET STRING,
        tnOamPingHistoryDnsAddrType   InetAddressType,
        tnOamPingHistoryDnsAddress    InetAddress,
        tnOamPingHistorySrcAddrType   InetAddressType,
        tnOamPingHistorySrcAddress    InetAddress,
        tnOamPingHistoryInOneWayTime  Integer32,
        tnOamPingHistoryLspName       TLNamedItemOrEmpty,
        tnOamPingHistNextHopAddrType  InetAddressType,
        tnOamPingHistNextHopAddress   InetAddress,
        tnOamPingHistorySrcGlobalId   TmnxMplsTpGlobalID,
        tnOamPingHistorySrcNodeId     TmnxMplsTpNodeID,
        tnOamPingHistorySdpBindId     TNamedItemOrEmpty,
        tnOamPingHistoryRtrnSubcode   Unsigned32
    }

tnOamPingHistoryIndex OBJECT-TYPE
-- NOTE: The UCD snmpget utility program does not parse this correctly
--   SYNTAX      Unsigned32 (1..'ffffffff'h)
    SYNTAX      Unsigned32 (1..4294967295)
    MAX-ACCESS  not-accessible
    STATUS      current
    DESCRIPTION
        "An entry in this table is created when the result of
         a OAM ping probe is determined.  The initial 2 instance
         identifier index values identify the tnOamPingCtlEntry
         that a OAM probe result (tnOamPingHistoryEntry) belongs
         to.  The tnOamPingHistoryIndex element selects a single OAM
         probe result.
         The agent starts assigning tnOamPingHistoryIndex values at 1
         and wraps after exceeding the maximum possible value as defined by
         the limit of this object ('ffffffff'h)."
    ::= { tnOamPingHistoryEntry 1 }

tnOamPingHistoryResponse OBJECT-TYPE
    SYNTAX      Unsigned32
    UNITS       "microseconds"
    MAX-ACCESS  read-only
    STATUS      current
    DESCRIPTION
        "The amount of time measured in microseconds from when
         a OAM probe was sent to when its response was received or
         when it timed out.  The value of this object is reported
         as 0 when it is not possible to transmit an OAM probe."
    ::= { tnOamPingHistoryEntry 2 }

tnOamPingHistoryOneWayTime OBJECT-TYPE
    SYNTAX      Integer32
    UNITS       "microseconds"
    MAX-ACCESS  read-only
    STATUS      current
    DESCRIPTION
        "The amount of time measured in microseconds from when
         a OAM probe was sent to when it was received by the replier.
         The value of this object is reported as 0 when it is not possible
         to transmit an OAM probe or the information is not available."
    ::= { tnOamPingHistoryEntry 3 }

tnOamPingHistorySize OBJECT-TYPE
    SYNTAX      Unsigned32
    UNITS       "octets"
    MAX-ACCESS  read-only
    STATUS      current
    DESCRIPTION
        "The value of tnOamPingHistorySize indicates the size of the OAM echo
         request transmitted for this OAM probe.  Zero is returned if no probe
         has been transmitted.

         When tnOamPingCtlTestMode is 'ethCfmLoopback', 'ethCfmTwoWayDelay', 'ethCfmOneWayDelay',
         'ethCfmTwoWaySlm', or 'ethCfmTwoWayLm' the size of the trasmitted layer 2 frame
         (including the layer 2 header) is returned.

         For other tnOamPingCtlTestMode values, the size returned is the
         tnOamPingCtlSize value."
    ::= { tnOamPingHistoryEntry 4 }

tnOamPingHistoryStatus OBJECT-TYPE
    SYNTAX      TmnxOamResponseStatus
    MAX-ACCESS  read-only
    STATUS      current
    DESCRIPTION
        "The result of a particular OAM test probe."
    ::= { tnOamPingHistoryEntry 5 }

tnOamPingHistoryTime OBJECT-TYPE
    SYNTAX      DateAndTime
    MAX-ACCESS  read-only
    STATUS      current
    DESCRIPTION
        "Time stamp for when this OAM probe result was determined."
    ::= { tnOamPingHistoryEntry 6 }

tnOamPingHistoryReturnCode    OBJECT-TYPE
    SYNTAX      Integer32
    MAX-ACCESS  read-only
    STATUS      current
    DESCRIPTION
        "The value of tnOamPingHistoryReturnCode is an integer
         that indicates the OAM return code received in the OAM ping response.

         The return codes are test specific and can vary for different types
         of pings.

         LSP-PING and VCCV-PING use return codes values from RFC4379 with
         the following meanings and suggested text descriptions.

         Value    Meaning
          -----    -------
              0    No return code (NoRtnCode)
              1    Malformed echo request received (MalformedReq)
              2    One or more of the TLVs was not understood (UnknownTlv)
              3    Replying router is an egress for the FEC at stack-depth
                   (EgressRtr)
              4    Replying router has no mapping for the FEC at stack-depth
                   (NoFECMapping)
              5    Downstream Mapping Mismatch (DSMappingMismatched)
              6    Upstream Interface Index Unknown (USIntfIdxUnkn)
              7    Reserved (Reserved)
              8    Label switched at stack-depth (DSRtrMatchLabel)
              9    Label switched but no MPLS forwarding at stack-depth
                   (DSNoMplsFwding)
             10    Mapping for this FEC is not the given label at stack-depth
                   (DSRtrUnmatchLabel)
             11    No label entry at stack-depth (DSNoLabelEntry)
             12    Protocol not associated with interface at FEC stack-depth
                   (DSProtoMismatched)
             13    Premature termination of ping due to label stack
                   shrinking to a single label (DSPreTermination)
             14    See DDMap TLV for rc and sub-rc (seeDDMapForRetCodeSubCode)
             15    Label Switched with FEC Stack Change (LabelSwitchedWithFecChange)"
    ::= { tnOamPingHistoryEntry 7 }

tnOamPingHistorySrcIpAddress  OBJECT-TYPE
    SYNTAX      IpAddress
    MAX-ACCESS  read-only
    STATUS      obsolete
    DESCRIPTION
        "Specifies the Ipv4 address of the remote node that generated this
         reply to a OAM probe.

         This object was obsoleted in release 4.0 and replaced with
         InetAddress objects tnOamPingHistorySrcAddrType and
         tnOamPingHistorySrcAddress."
    ::= { tnOamPingHistoryEntry 8 }

tnOamPingHistAddressType     OBJECT-TYPE
    SYNTAX      TmnxOamAddressType
    MAX-ACCESS  read-only
    STATUS      current
    DESCRIPTION
        "The value of tnOamPingHistAddressType specifies the type of
         binding address information returned in response to a 'vprnPing'
         'mfibPing', or 'cpePing' test."
    ::= { tnOamPingHistoryEntry 9 }

tnOamPingHistSapId OBJECT-TYPE
    SYNTAX          TmnxStrSapId
    MAX-ACCESS      read-only
    STATUS          current
    DESCRIPTION
        "The value of tnOamPingHistSapId is the name of the access
         port of the SAP supporting the requests returned in
         response to a 'vprnPing', 'mfibPing' or 'cpePing' probe.

         If the value of tnOamPingHistAddressType is not 'sapId',
         this object is not relevant and MUST have a null string ''."
    ::= { tnOamPingHistoryEntry 10 }

-- Numbering gap:  { tnOamPingHistoryEntry 11 } is not defined.

tnOamPingHistoryVersion OBJECT-TYPE
    SYNTAX      Unsigned32
    MAX-ACCESS  read-only
    STATUS      current
    DESCRIPTION
        "The value of tnOamPingHistoryVersion indicates the protocol
         version for this OAM ping probe reply."
    ::= { tnOamPingHistoryEntry 12 }

tnOamPingHistoryCpeMacAddr OBJECT-TYPE
    SYNTAX      MacAddress
    MAX-ACCESS  read-only
    STATUS      current
    DESCRIPTION
        "tnOamPingHistoryCpeMacAddr is set to 0 except in case of
         a 'cpePing', where it contains the mac address of the replying
         CPE for this OAM ping probe reply."
    ::= { tnOamPingHistoryEntry 13 }

tnOamPingHistoryRespSvcId OBJECT-TYPE
    SYNTAX      TmnxServId
    MAX-ACCESS  read-only
    STATUS      current
    DESCRIPTION
        "The value tnOamPingHistoryRespSvcId indicates for an 'mfibPing'
         the service id to which the SAP responding to the 'mfibPing' probe
         belongs. If the indicated SAP is part of the same service originating
         the probe, this value is set to 0.

         For other types of probes, this value is insignificant and is also
         set to 0."
    ::= { tnOamPingHistoryEntry 14 }

tnOamPingHistorySequence OBJECT-TYPE
    SYNTAX      Unsigned32
    MAX-ACCESS  read-only
    STATUS      current
    DESCRIPTION
        "The value tnOamPingHistorySequence indicates this probe's
         sequence number.  If a probe response was received, this object
         indicates the sequence number of the response."
    ::= { tnOamPingHistoryEntry 15 }

tnOamPingHistoryIfIndex   OBJECT-TYPE
    SYNTAX      InterfaceIndexOrZero
    MAX-ACCESS  read-only
    STATUS      current
    DESCRIPTION
        "The value of tnOamPingHistoryIfIndex indicates the ifIndex of the
         interface that this probe was transmitted from.

         This object applies to 'lspPing' and 'vccvPing' tests.  For other test
         modes, this value is not significant and is set to 0."
    ::= { tnOamPingHistoryEntry 16 }

tnOamPingHistoryDataLen   OBJECT-TYPE
    SYNTAX      Unsigned32
    MAX-ACCESS  read-only
    STATUS      current
    DESCRIPTION
        "The value of tnOamPingHistoryDataLen indicates for an 'lspPing'
         the UDP data length of the echo reply, and for 'icmpPing' normally
         the length starting after the IP header of the echo reply.  For
         'ethCfmLoopback', 'ethCfmTwoWaySlm', or 'ethCfmTwoWayLm' the value is the number of
         octets in the Value field of the Data TLV of the Ethernet CFM loopback
         packet (zero if the packet has no Data TLV).

         For other types of probes, this value is not significant and is
         set to 0."
    ::= { tnOamPingHistoryEntry 17 }

tnOamPingHistoryRespPlane OBJECT-TYPE
    SYNTAX      TmnxOamTestResponsePlane
    MAX-ACCESS  read-only
    STATUS      current
    DESCRIPTION
        "The value of tnOamPingHistoryRespPlane indicates the
         response plane from which this ping response was received."
    ::= { tnOamPingHistoryEntry 18 }

tnOamPingHistoryReqHdr   OBJECT-TYPE
    SYNTAX      OCTET STRING (SIZE (0|1..150))
    MAX-ACCESS  read-only
    STATUS      obsolete
    DESCRIPTION
        "The value of tnOamPingHistoryReqHdr is a copy of the OAM header of
         the request packet sent for this OAM ping test probe.

         The request header is reported only when tnOamPingCtlTestMode has a
         value of 'svcPing', 'sdpPing' 'mtuPing', 'ethCfmLoopback',
         'ethCfmTwoWayDelay', 'ethCfmOneWayDelay', 'ethCfmTwoWaySlm',or 'ethCfmTwoWayLm'.
         Otherwise, a zero length OCTET STRING is returned.

         This object was marked obsolete in SROS release 10.0 R1."
    ::= { tnOamPingHistoryEntry 19 }

tnOamPingHistoryRespHdr   OBJECT-TYPE
    SYNTAX      OCTET STRING (SIZE (0|1..150))
    MAX-ACCESS  read-only
    STATUS      current
    DESCRIPTION
        "The value of tnOamPingHistoryRespHdr is a copy of the OAM
         header of the response packet received for this OAM ping test probe.

         The response header is reported only when tnOamPingCtlTestMode
         has a value of 'svcPing', 'sdpPing', 'mtuPing', 'icmpPing',
         'ethCfmLoopback', 'ethCfmTwoWayDelay', 'ethCfmOneWayDelay', 'ethCfmTwoWaySlm',
         or 'ethCfmTwoWayLm'.
         Otherwise, a zero length OCTET STRING is returned.  For 'icmpPing'
         the value reported is the received ICMP message starting from the IP
         header.

         The value of this object MUST be reported as a zero length
         OCTET STRING when no probe response has been received."
    ::= { tnOamPingHistoryEntry 20 }

tnOamPingHistoryDnsAddrType   OBJECT-TYPE
    SYNTAX      InetAddressType
    MAX-ACCESS  read-only
    STATUS      current
    DESCRIPTION
        "The value of tnOamPingHistoryDnsAddrType indicates the
         Internet address type stored in tnOamPingHistoryDnsAddress.

         If this was not a 'dnsPing' test or the dns name specified
         in tnOamPingCtlDnsName could not be resolved, the value of
         this object will be reported as 'unknown'."
    ::= { tnOamPingHistoryEntry 21 }

tnOamPingHistoryDnsAddress    OBJECT-TYPE
    SYNTAX      InetAddress (SIZE (0|4|16))
    MAX-ACCESS  read-only
    STATUS      current
    DESCRIPTION
        "The value of tnOamPingHistoryDnsAddress indicates the
         Internet address that was resolved from the name specified
         in tnOamPingCtlDnsName by a 'dnsPing' test.

         If this was not a 'dnsPing' test or the dns name specified
         in tnOamPingCtlDnsName could not be resolved, the value of
         this object will be reported as ''H (empty string)."
    ::= { tnOamPingHistoryEntry 22 }

tnOamPingHistorySrcAddrType  OBJECT-TYPE
    SYNTAX      InetAddressType
    MAX-ACCESS  read-only
    STATUS      current
    DESCRIPTION
        "The value of tnOamPingHistorySrcAddrType indicates the Internet
         address type of the address stored in tnOamPingHistorySrcAddress."
    ::= { tnOamPingHistoryEntry 23 }

tnOamPingHistorySrcAddress  OBJECT-TYPE
    SYNTAX      InetAddress (SIZE (0|4|16|20))
    MAX-ACCESS  read-only
    STATUS      current
    DESCRIPTION
        "The value of tnOamPingHistorySrcAddress indicates the Internet
        address of the remote node that generated this reply to a OAM probe."
    ::= { tnOamPingHistoryEntry 24 }

tnOamPingHistoryInOneWayTime OBJECT-TYPE
    SYNTAX      Integer32
    UNITS       "microseconds"
    MAX-ACCESS  read-only
    STATUS      current
    DESCRIPTION
        "The value of tnOamPingHistoryInOneWayTime indicates the amount
         of time measured in microseconds from when an OAM probe reply was
         sent to when it was received by this host (in-bound one-way time).
         The value of this object is reported as 0 when the information is
         not available."
    ::= { tnOamPingHistoryEntry 25 }

tnOamPingHistoryLspName OBJECT-TYPE
    SYNTAX      TLNamedItemOrEmpty
    MAX-ACCESS  read-only
    STATUS      current
    DESCRIPTION
        "The value of tnOamPingHistoryLspName indicates the name of the LSP
         that this probe was transmitted on.

         The empty string is returned when the test mode is not 'vccvPing'.
         The empty string is returned when the transport tunnel is not RSVP."
    ::= { tnOamPingHistoryEntry 26 }

tnOamPingHistNextHopAddrType OBJECT-TYPE
    SYNTAX      InetAddressType
    MAX-ACCESS  read-only
    STATUS      current
    DESCRIPTION
        "The value of tnOamPingHistNextHopAddrType indicates the Internet
         address type of the address stored in tnOamPingHistNextHopAddress.

         The value 'unknown(0)' is returned when the test mode is not
         'vccvPing'."
    ::= { tnOamPingHistoryEntry 27 }

tnOamPingHistNextHopAddress OBJECT-TYPE
    SYNTAX      InetAddress (SIZE (0|4|16|20))
    MAX-ACCESS  read-only
    STATUS      current
    DESCRIPTION
        "The value of tnOamPingHistNextHopAddress indicates the next hop
         Internet address that this probe was transmitted to.

         The empty string is returned when the test mode is not 'vccvPing'."
    ::= { tnOamPingHistoryEntry 28 }

tnOamPingHistorySrcGlobalId    OBJECT-TYPE
    SYNTAX      TmnxMplsTpGlobalID
    MAX-ACCESS  read-only
    STATUS      current
    DESCRIPTION
        "The value of tnOamPingHistorySrcGlobalId indicates the source MPLS-TP
         global identifier of the replying node.  The value is copied from the
         reply's RFC 6426 Source Identifier TLV.  If the TLV is absent, zero is
         returned.

         This value is relevant when tnOamPingCtlTestMode is 'lspPing' or
         'vccvPing'.  Otherwise, zero is returned."
    REFERENCE
        "RFC 6426, 'MPLS On-Demand Connectivity Verification and Route Tracing',
         Section 2.2.2, 'Source Identifier TLV'."
    ::= { tnOamPingHistoryEntry 29 }

tnOamPingHistorySrcNodeId      OBJECT-TYPE
    SYNTAX      TmnxMplsTpNodeID
    MAX-ACCESS  read-only
    STATUS      current
    DESCRIPTION
        "The value of tnOamPingHistorySrcNodeId indicates the source MPLS-TP
         node identifier of the replying node.  The value is copied from the
         reply's RFC 6426 Source Identifier TLV.  If the TLV is absent, zero is
         returned.

         This value is relevant when tnOamPingCtlTestMode is 'lspPing' or
         'vccvPing'.  Otherwise, zero is returned."
    REFERENCE
        "RFC 6426, 'MPLS On-Demand Connectivity Verification and Route Tracing',
         Section 2.2.2, 'Source Identifier TLV'."
    ::= { tnOamPingHistoryEntry 30 }

tnOamPingHistorySdpBindId      OBJECT-TYPE
    SYNTAX          TNamedItemOrEmpty
    MAX-ACCESS      read-only
    STATUS          current
    DESCRIPTION
        "The value of tnOamPingHistorySdpBindId indicates the SDP binding
         provided by the remote system.

         The value of tnOamPingHistorySdpBindId is relevant when
         tnOamPingHistAddressType is 'sdpBindId(9)'."
    ::= { tnOamPingHistoryEntry 31 }

tnOamPingHistoryRtrnSubcode    OBJECT-TYPE
    SYNTAX          Unsigned32
    MAX-ACCESS      read-only
    STATUS          current
    DESCRIPTION
        "The value of tnOamPingHistoryRtrnSubcode indicates the value present
         in an MPLS echo reply's RFC 4379 Return Subcode (RSC) field.

         A valid value is returned when the test has a tnOamPingCtlTestMode
         value of 'lspPing'.  Otherwise, zero is returned."
    REFERENCE
        "RFC 4379, 'Detecting Multi-Protocol Label Switched (MPLS) Data Plane
         Failures', Section 3.1, 'Return Codes'."
    ::= { tnOamPingHistoryEntry 32 }

--
--  Nokia SROS series OAM MAC Ping Control Table
--
--  Sparse Dependent Extension of the tnOamPingCtlTable.
--
--  The same indexes are used for both the base table, tnOamPingCtlTable,
--  and the sparse dependent table, tnOamMacPingCtlTable.
--
--  This in effect extends the tnOamPingCtlTable with additional columns.
--  Rows are created in the tnOamMacPingCtlTable only for those entries
--  in the tnOamPingCtlTable where tnOamPingCtlTestMode has a value of
--  'macPing', 'macPopulate', or 'macPurge'.
--
--  Deletion of a row in the tnOamPingCtlTable results in the
--  same fate for the row in the tnOamMacPingCtlTable.
--

-- tnOamMacPingCtlTable     OBJECT-TYPE
--     SYNTAX      SEQUENCE OF TnOamMacPingCtlEntry
--     MAX-ACCESS  not-accessible
--     STATUS      current
--     DESCRIPTION
--         "Defines the Nokia SROS OAM MAC Ping Control Table for
--          providing, via SNMP, the capability of performing Nokia SROS
--          OAM 'macPing', 'macPopulate', or 'macPurge' test operations.
--          The results of these tests are stored in the tnOamPingResultsTable
--          and the tnOamMacPingHistoryTable.  There will be no entries for
--          these test in the tnOamPingHistoryTable."
--    ::= { tnOamPingObjs 10 }
--
-- tnOamMacPingCtlEntry OBJECT-TYPE
--     SYNTAX      TnOamMacPingCtlEntry
--     MAX-ACCESS  not-accessible
--     STATUS      current
--     DESCRIPTION
--         "Defines an entry in the tnOamMacPingCtlTable.  The first index
--          element, tnOamPingCtlOwnerIndex, is of type SnmpAdminString,
--          a textual convention that allows for use of the SNMPv3
--          View-Based Access Control Model (RFC 2575 [11], VACM)
--          and allows a management application to identify its entries.
--          The second index, tnOamPingCtlTestIndex, enables the same
--          management application to have multiple outstanding requests."
--     INDEX {
--              tnOamPingCtlOwnerIndex,
--              tnOamPingCtlTestIndex
--           }
--     ::= { tnOamMacPingCtlTable 1 }
--
-- TnOamMacPingCtlEntry ::=
--     SEQUENCE {
--         tnOamMacPingCtlTargetMacAddr      MacAddress,
--         tnOamMacPingCtlSourceMacAddr      MacAddress,
--         tnOamMacPingCtlSendControl        TruthValue,
--         tnOamMacPingCtlReplyControl       TruthValue,
--         tnOamMacPingCtlTtl                Unsigned32,
--         tnOamMacPingCtlRegister           TruthValue,
--         tnOamMacPingCtlFlood              TruthValue,
--         tnOamMacPingCtlForce              TruthValue,
--         tnOamMacPingCtlAge                Unsigned32,
--         tnOamMacPingCtlSapPortId          TmnxPortID,
--         tnOamMacPingCtlSapEncapValue      TmnxEncapVal,
--         tnOamMacPingCtlFibEntryName       TNamedItemOrEmpty
--     }
--
-- tnOamMacPingCtlTargetMacAddr OBJECT-TYPE
--     SYNTAX      MacAddress
--     MAX-ACCESS  read-create
--     STATUS      current
--     DESCRIPTION
--         "The value of tnOamMacPingCtlTargetMacAddr is a 6-octet value
--          that specifies the target MAC address to be used in the query
--          request for performing an OAM ping operation.
--
--          This parameter is required."
--     REFERENCE
--         "IEEE 802.3 Subclause 30.7.1.1.9"
--     DEFVAL { '000000000000'H }
--     ::= { tnOamMacPingCtlEntry 1 }
--
-- tnOamMacPingCtlSourceMacAddr OBJECT-TYPE
--     SYNTAX      MacAddress
--     MAX-ACCESS  read-create
--     STATUS      current
--     DESCRIPTION
--         "The value of tnOamMacPingCtlSourceMacAddr is a 6-octet value
--          that  specifies  the  MAC  address to be used as the source in the
--          query request for performing an OAM ping operation.  This object
--          is optional and is not relevant when tnOamPingCtlTestMode has a
--          value other than 'macPing'."
--     REFERENCE
--         "IEEE 802.3 Subclause 30.7.1.1.9"
--     DEFVAL { '000000000000'H }
--     ::= { tnOamMacPingCtlEntry 2 }
--
-- tnOamMacPingCtlSendControl       OBJECT-TYPE
--     SYNTAX      TruthValue
--     MAX-ACCESS  read-create
--     STATUS      current
--     DESCRIPTION
--         "When the value of tnOamMacPingCtlSendControl is 'true', the OAM
--          ping packet is sent directly to the destination IP address via the
--          control plane. If its value is 'false', the packet is sent via the
--          data plane.
--
--          This object is optional and is not relevant when
--          tnOamPingCtlTestMode has a value other than 'macPopulate',
--          'macPurge' or 'macPing'."
--     DEFVAL { false }
--     ::= { tnOamMacPingCtlEntry 3 }
--
-- tnOamMacPingCtlReplyControl      OBJECT-TYPE
--     SYNTAX      TruthValue
--     MAX-ACCESS  read-create
--     STATUS      current
--     DESCRIPTION
--         "When the value of tnOamMacPingCtlReplyControl is 'true', the
--          OAM ping response is returned using the control plane. If its
--          value is 'false', the packet is sent via the data plane. This
--          object is optional and is not relevant when tnOamPingCtlTestMode
--          has a value other than 'macPing'."
--     DEFVAL { false }
--     ::= { tnOamMacPingCtlEntry 4 }
--
-- tnOamMacPingCtlTtl       OBJECT-TYPE
--     SYNTAX      Unsigned32 (1..255)
--     UNITS       "time-to-live value"
--     MAX-ACCESS  read-create
--     STATUS      current
--     DESCRIPTION
--         "Specifies the vc-label time-to-live value.
--
--          This object is optional and is not relevant when
--          tnOamPingCtlTestMode has a value other than 'macPing'.
--
--          While performing the test with a ttl of 1 no responses should ever be
--          expected."
--     DEFVAL { 255 }
--     ::= { tnOamMacPingCtlEntry 5 }
--
-- tnOamMacPingCtlRegister      OBJECT-TYPE
--     SYNTAX      TruthValue
--     MAX-ACCESS  read-create
--     STATUS      current
--     DESCRIPTION
--         "When the value of tnOamMacPingCtlRegister is 'true', the
--          OAM ping request is transmitted that causes each upstream node
--          to delete the MAC address only from its forwarding plane but
--          keep it in its control plane in order to inhibit dynamic learning.
--          If its value is 'false', the MAC address is deleted from both
--          the forwarding and control planes.
--
--          This object is optional and is not relevant when
--          tnOamPingCtlTestMode has a value other than 'macPurge'."
--     DEFVAL { false }
--     ::= { tnOamMacPingCtlEntry 6 }
--
-- tnOamMacPingCtlFlood     OBJECT-TYPE
--     SYNTAX      TruthValue
--     MAX-ACCESS  read-create
--     STATUS      current
--     DESCRIPTION
--         "When the value of tnOamMacPingCtlFlood is 'true', the
--          OAM ping request is transmitted that causes each upstream node
--          to add or delete the MAC address. If its value is 'false', the
--          operation is performed locally.
--
--          This object is optional and is not relevant when
--          tnOamPingCtlTestMode has a value other than 'macPopulate' or
--          'macPurge'."
--     DEFVAL { false }
--     ::= { tnOamMacPingCtlEntry 7 }
--
-- tnOamMacPingCtlForce     OBJECT-TYPE
--     SYNTAX      TruthValue
--     MAX-ACCESS  read-create
--     STATUS      current
--     DESCRIPTION
--         "When the value of tnOamMacPingCtlForce is 'true', the
--          MAC type in the FIB is forced to be labeled OAM type if it already
--          existed as dynamic or static.
--
--          This object is optional and is not relevant when
--          tnOamPingCtlTestMode has a value other than 'macPopulate'."
--     DEFVAL { false }
--     ::= { tnOamMacPingCtlEntry 8 }
--
-- tnOamMacPingCtlAge       OBJECT-TYPE
--     SYNTAX      Unsigned32
--     UNITS       "seconds"
--     MAX-ACCESS  read-create
--     STATUS      current
--     DESCRIPTION
--         "The value of tnOamMacPingCtlAge specifies the number of seconds
--          to age this OAM MAC address in the FIB.
--
--          This object is optional and is not relevant when
--          tnOamPingCtlTestMode has a value other than 'macPopulate'."
--     DEFVAL { 3600 }  --   -- 1 hour
--     ::= { tnOamMacPingCtlEntry 9 }
--
-- tnOamMacPingCtlSapPortId OBJECT-TYPE
--     SYNTAX          TmnxPortID
--     MAX-ACCESS      read-create
--     STATUS          current
--     DESCRIPTION
--         "The value of tnOamMacPingCtlSapPortId is the ID of the access
--          port of the target SAP.
--
--          This object is optional and is not relevant when
--          tnOamPingCtlTestMode has a value other than 'macPopulate'."
--     DEFVAL { 0 }
--     ::= { tnOamMacPingCtlEntry 10 }
--
-- tnOamMacPingCtlSapEncapValue     OBJECT-TYPE
--     SYNTAX          TmnxEncapVal
--     MAX-ACCESS      read-create
--     STATUS          current
--     DESCRIPTION
--         "The value of tnOamMacPingCtlSapEncapValue is the label used to
--          identify the target SAP on the port specified in
--          tnOamMacPingCtlSapPortId.
--
--          This object is optional and is not relevant when
--          tnOamPingCtlTestMode has a value other than 'macPopulate'."
--     DEFVAL { 0 }
--     ::= { tnOamMacPingCtlEntry 11 }
--
-- tnOamMacPingCtlFibEntryName      OBJECT-TYPE
--     SYNTAX          TNamedItemOrEmpty
--     MAX-ACCESS      read-create
--     STATUS          current
--     DESCRIPTION
--         "The value of tnOamMacPingCtlFibEntryName is the fib entry name
--          to associate with the target MAC address.
--
--          This object is optional and is not relevant when
--          tnOamPingCtlTestMode has a value other than 'macPopulate'."
--     DEFVAL { ''H }  -- -- the empty string
--     ::= { tnOamMacPingCtlEntry 12 }

--
-- Nokia SROS series OAM MAC Ping History Table
--
-- tnOamMacPingHistoryTable OBJECT-TYPE
--     SYNTAX      SEQUENCE OF TnOamMacPingHistoryEntry
--     MAX-ACCESS  not-accessible
--     STATUS      current
--     DESCRIPTION
--         "Defines a table for storing the results of an OAM 'macPing' probe
--          operation.  The number of entries in this table for a test
--          is limited to the results of 3 runs.
--
--          An entry in this table is created when the result of an OAM 'macPing'
--          probe is determined.  An entry is removed from this table when its
--          corresponding tnOamPingCtlEntry is deleted."
--    ::= { tnOamPingObjs 12 }
--
-- tnOamMacPingHistoryEntry OBJECT-TYPE
--     SYNTAX      TnOamMacPingHistoryEntry
--     MAX-ACCESS  not-accessible
--     STATUS      current
--     DESCRIPTION
--         "Defines an entry in the tnOamPingHistoryTable.  The first two
--          index elements identify the tnOamPingCtlEntry that a
--          tnOamMacPingHistoryEntry belongs to.  The third index identifies
--          a specific run of the OAM test.  The fourth index element
--          selects the group of responses associated with a specific probe
--          attempt.  The fifth index selects a single OAM 'macPing' reply."
--     INDEX {
--              tnOamPingCtlOwnerIndex,
--              tnOamPingCtlTestIndex,
--              tnOamPingResultsTestRunIndex,
--              tnOamMacPingHistoryIndex,
--              tnOamMacPingReplyIndex
--            }
--     ::= { tnOamMacPingHistoryTable 1 }
--
-- TnOamMacPingHistoryEntry ::=
--     SEQUENCE {
--         tnOamMacPingHistoryIndex              Unsigned32,
--         tnOamMacPingReplyIndex                Unsigned32,
--         tnOamMacPingHistoryResponse           Unsigned32,
--         tnOamMacPingHistoryOneWayTime         Integer32,
--         tnOamMacPingHistoryStatus             TmnxOamResponseStatus,
--         tnOamMacPingHistoryTime               DateAndTime,
--         tnOamMacPingHistoryReturnCode         TmnxOamPingRtnCode,
--         tnOamMacPingHistorySrcIpAddress       IpAddress,
--         tnOamMacPingHistoryAddressType        TmnxOamAddressType,
--         tnOamMacPingHistorySapId              TmnxStrSapId,
--         tnOamMacPingHistorySdpId              SdpId,
--         tnOamMacPingHistoryAdminStatus        TruthValue,
--         tnOamMacPingHistoryOperStatus         TruthValue,
--         tnOamMacPingHistoryResponsePlane      TmnxOamTestResponsePlane,
--         tnOamMacPingHistorySize               Unsigned32,
--         tnOamMacPingHistoryInOneWayTime       Integer32,
--         tnOamMacPingHistorySrcAddrType        InetAddressType,
--         tnOamMacPingHistorySrcAddress         InetAddress
--     }
--
-- tnOamMacPingHistoryIndex OBJECT-TYPE
--  NOTE: The UCD snmpget utility program does not parse this correctly
--    SYNTAX      Unsigned32 (1..'ffffffff'h)
--     SYNTAX      Unsigned32 (1..4294967295)
--     MAX-ACCESS  not-accessible
--     STATUS      current
--     DESCRIPTION
--         "An entry in this table is created when the result of a OAM
--          'macPing' probe is determined.  The initial 2 instance identifier
--          index values identify the tnOamPingCtlEntry that a OAM probe
--          result (tnOamMacPingHistoryEntry) belongs to.  The
--          tnOamMacPingHistoryIndex has the value of the sequence number
--          of the request probe and identifies a group of replies received
--          in response to a specific probe transmission.
--
--          The agent starts assigning tnOamMacPingHistoryIndex values at 1
--          and wraps after exceeding the maximum possible value as defined by
--          the limit of this object ('ffffffff'h)."
--     ::= { tnOamMacPingHistoryEntry 1 }
--
-- tnOamMacPingReplyIndex OBJECT-TYPE
--  NOTE: The UCD snmpget utility program does not parse this correctly
--    SYNTAX      Unsigned32 (1..'ffffffff'h)
--     SYNTAX      Unsigned32 (1..4294967295)
--     MAX-ACCESS  not-accessible
--     STATUS      current
--     DESCRIPTION
--         "The tnOamMacPingReplyIndex is unique within a group of responses
--          received as the result of a OAM 'macPing' probe as specified by
--          having the same value for tnOamMacPingHistoryIndex.
--
--          The agent starts assigning tnOamMacPingReplyIndex values at 1
--          and wraps after exceeding the maximum possible value as defined by
--          the limit of this object ('ffffffff'h)."
--     ::= { tnOamMacPingHistoryEntry 2 }
--
-- tnOamMacPingHistoryResponse OBJECT-TYPE
--     SYNTAX      Unsigned32
--     UNITS       "microseconds"
--     MAX-ACCESS  read-only
--     STATUS      current
--     DESCRIPTION
--         "The amount of time measured in microseconds from when
--          a OAM probe was sent to when its response was received or
--          when it timed out.  The value of this object is reported
--          as 0 when it is not possible to transmit an OAM probe."
--     ::= { tnOamMacPingHistoryEntry 3 }
--
-- tnOamMacPingHistoryOneWayTime OBJECT-TYPE
--     SYNTAX      Integer32
--     UNITS       "microseconds"
--     MAX-ACCESS  read-only
--     STATUS      current
--     DESCRIPTION
--         "The amount of time measured in microseconds from when an
--          OAM probe was sent to when it was received by the replier
--          (out-bound one-way time).  The value of this object is
--          reported as 0 when it is not possible to transmit an OAM
--          probe or the information is not available."
--     ::= { tnOamMacPingHistoryEntry 4 }
--
-- tnOamMacPingHistoryStatus OBJECT-TYPE
--     SYNTAX      TmnxOamResponseStatus
--     MAX-ACCESS  read-only
--     STATUS      current
--     DESCRIPTION
--         "The value of tnOamMacPingHistoryStatus is an enumerated integer
--          that indicates the result of a particular OAM probe."
--     ::= { tnOamMacPingHistoryEntry 5 }
--
-- tnOamMacPingHistoryTime OBJECT-TYPE
--     SYNTAX      DateAndTime
--     MAX-ACCESS  read-only
--     STATUS      current
--     DESCRIPTION
--         "Timestamp for when this OAM probe result was determined."
--     ::= { tnOamMacPingHistoryEntry 6 }
--
-- tnOamMacPingHistoryReturnCode    OBJECT-TYPE
--     SYNTAX      TmnxOamPingRtnCode
--     MAX-ACCESS  read-only
--     STATUS      current
--     DESCRIPTION
--         "The value of tnOamMacPingHistoryReturnCode is an enumerated integer
--          that indicates the return code received in the OAM ping response."
--     ::= { tnOamMacPingHistoryEntry 7 }
--
-- tnOamMacPingHistorySrcIpAddress  OBJECT-TYPE
--     SYNTAX      IpAddress
--     MAX-ACCESS  read-only
--     STATUS      obsolete
--     DESCRIPTION
--         "The value of tnOamMacPingHistorySrcIpAddress specifies the Ipv4
--          address of the remote node that generated this reply to a OAM probe.
--
--          This object was obsoleted in release 4.0 and replaced with
--          InetAddress objects tnOamMacPingHistorySrcAddrType and
--          tnOamMacPingHistorySrcAddress."
--     ::= { tnOamMacPingHistoryEntry 8 }
--
-- tnOamMacPingHistoryAddressType       OBJECT-TYPE
--     SYNTAX      TmnxOamAddressType
--     MAX-ACCESS  read-only
--     STATUS      current
--     DESCRIPTION
--         "The value of tnOamMacPingHistoryAddressType specifies the type of
--          binding address information returned in response to a 'macPing' test."
--     ::= { tnOamMacPingHistoryEntry 9 }
--
-- tnOamMacPingHistorySapId OBJECT-TYPE
--     SYNTAX          TmnxStrSapId
--     MAX-ACCESS      read-only
--     STATUS          current
--     DESCRIPTION
--         "The value of tnOamMacPingHistorySapId is the name of the access
--          port of the SAP supporting the requested MAC address returned in
--          response to a 'macPing' probe.
--
--          If the value of tnOamMacPingHistoryAddressType is not 'sapId',
--          this object is not relevant and MUST have a null string ''."
--     ::= { tnOamMacPingHistoryEntry 10 }
--
-- tnOamMacPingHistorySdpId     OBJECT-TYPE
--     SYNTAX      SdpId
--     MAX-ACCESS  read-only
--     STATUS      current
--     DESCRIPTION
--         "The value of tnOamMacPingHistorySdpId is the ID of the SDP
--          supporting the requested MAC address returned in response to a
--          'macPing' probe.
--
--          If the value of tnOamMacPingHistoryAddressType is not 'sdpId',
--          this object is not relevant and MUST return a value of '0'."
--     ::= { tnOamMacPingHistoryEntry 12 }
--
-- tnOamMacPingHistoryAdminStatus   OBJECT-TYPE
--     SYNTAX      TruthValue
--     MAX-ACCESS  read-only
--     STATUS      current
--     DESCRIPTION
--         "The value of tnOamMacPingHistoryAdminStatus indicates the current
--          administrative state of the SAP or SDP ID returned in response to a
--          'macPing' test.  A value of 'true' indicates the SAP or SDP is
--          administratively 'up'.
--
--          The value of this object MUST be reported as 'false' when no ping
--          responses have been received or an active test has not yet timed out."
--     ::= { tnOamMacPingHistoryEntry 13 }
--
-- tnOamMacPingHistoryOperStatus    OBJECT-TYPE
--     SYNTAX      TruthValue
--     MAX-ACCESS  read-only
--     STATUS      current
--     DESCRIPTION
--         "The value of tnOamMacPingHistoryOperStatus indicates the current
--          operational state of the SAP or SDP ID returned in response to a
--          'macPing' test.  A value of 'true' indicates the SAP or SDP is
--          operationally 'up'.
--
--          The value of this object MUST be reported as 'false' when no ping
--          responses have been received or an active test has not yet timed out."
--     ::= { tnOamMacPingHistoryEntry 14 }
--
-- tnOamMacPingHistoryResponsePlane     OBJECT-TYPE
--     SYNTAX      TmnxOamTestResponsePlane
--     MAX-ACCESS  read-only
--     STATUS      current
--     DESCRIPTION
--         "The value of tnOamMacPingHistoryResponsePlane indicates the
--          response plane from which this ping response was received."
--     ::= { tnOamMacPingHistoryEntry 15 }
--
-- tnOamMacPingHistorySize     OBJECT-TYPE
--     SYNTAX      Unsigned32
--     UNITS       "octets"
--     MAX-ACCESS  read-only
--     STATUS      current
--     DESCRIPTION
--         "The value of tnOamMacPingHistorySize indicates the size in octets
--          of the user payload in a ping request packet.  It does not include
--          the service encapsulation."
--     ::= { tnOamMacPingHistoryEntry 16 }
--
-- tnOamMacPingHistoryInOneWayTime OBJECT-TYPE
--     SYNTAX      Integer32
--     UNITS       "microseconds"
--     MAX-ACCESS  read-only
--     STATUS      current
--     DESCRIPTION
--         "The amount of time measured in microseconds from when an OAM
--          probe reply was sent to when it was received by this host
--          (in-bound one-way time).  The value of this object is reported
--          as 0 when the information is not available."
--     ::= { tnOamMacPingHistoryEntry 17 }
--
-- tnOamMacPingHistorySrcAddrType  OBJECT-TYPE
--     SYNTAX      InetAddressType
--     MAX-ACCESS  read-only
--     STATUS      current
--     DESCRIPTION
--         "The value of tnOamMacPingHistorySrcAddrType indicates the Internet
--          address type stored in tnOamMacPingHistorySrcAddress."
--     ::= { tnOamMacPingHistoryEntry 18 }
--
-- tnOamMacPingHistorySrcAddress  OBJECT-TYPE
--     SYNTAX      InetAddress (SIZE (0|4|16))
--     MAX-ACCESS  read-only
--     STATUS      current
--     DESCRIPTION
--         "The value of tnOamMacPingHistorySrcAddress indicates the Internet
--          address of the remote node that generated this reply to a OAM probe."
--     ::= { tnOamMacPingHistoryEntry 19 }

--
-- Nokia SROS series OAM MAC Ping Label Mapping Table (OBSOLETE)
--
-- tnOamMacPingL2MapTable OBJECT-TYPE
--     SYNTAX      SEQUENCE OF TnOamMacPingL2MapEntry
--     MAX-ACCESS  not-accessible
--     STATUS      obsolete
--     DESCRIPTION
--         "Defines a table for storing the results of an OAM 'macQuery'
--          probe operation where a L2 mapping TLV is returned.  Only one
--          downstream and one upstream L2 mapping entry is returned if the
--          'macQuery' replier has no egress mapping for the requested MAC
--          address but it does have an SDP binding.  Multiple downstream L2
--          mappings that specify the replier's flooding domain may be returned
--          if the replier has no bindings for the MAC address.

--          An entry in this table is created when the result of an OAM
--          'macQuery'probe is determined.

--          An entry is removed from this table when its corresponding
--          tnOamPingCtlEntry is deleted."
--    ::= { tnOamPingObjs 14 }

-- tnOamMacPingL2MapEntry OBJECT-TYPE
--     SYNTAX      TnOamMacPingL2MapEntry
--     MAX-ACCESS  not-accessible
--     STATUS      obsolete
--     DESCRIPTION
--         "Defines an entry in the tnOamMacPingL2MapTable.  The first two
--          index elements identify the tnOamPingCtlEntry that a
--          tnOamMacPingL2MapEntry belongs to.  The third index element
--          identifies a specific OAM test run.  The fourth index element
--          selects the group of responses associated with a specific probe
--          attempt.  The fifth index selects a single OAM 'macQuery' reply.
--          Note that in the case of a successful 'macQuery' reply there will
--          be only two row entries created per test run.  However there may
--          also be one or more error replies.  The sixth index selects a
--          single L2 mapping entry within a specific probe reply."
--     INDEX {
--              tnOamPingCtlOwnerIndex,
--              tnOamPingCtlTestIndex,
--              tnOamPingResultsTestRunIndex,
--              tnOamMacPingHistoryIndex,
--              tnOamMacPingReplyIndex,
--              tnOamMacPingL2MapIndex
--            }
--     ::= { tnOamMacPingL2MapTable 1 }

-- TnOamMacPingL2MapEntry ::=
--     SEQUENCE {
--         tnOamMacPingL2MapIndex        Unsigned32,
--         tnOamMacPingL2MapRouterID     IpAddress,
--         tnOamMacPingL2MapLabel        MplsLabel,
--         tnOamMacPingL2MapProtocol     TmnxOamSignalProtocol,
--         tnOamMacPingL2MapVCType       TmnxOamVcType,
--         tnOamMacPingL2MapVCID         TmnxVcId,
--         tnOamMacPingL2MapDirection    INTEGER
--     }

-- tnOamMacPingL2MapIndex OBJECT-TYPE
--  NOTE: The UCD snmpget utility program does not parse this correctly
--    SYNTAX      Unsigned32 (1..'ffffffff'h)
--     SYNTAX      Unsigned32 (1..4294967295)
--     MAX-ACCESS  not-accessible
--     STATUS      obsolete
--     DESCRIPTION
--         "An entry in this table is created when the result of a OAM
--          'macQuery' probe is determined.  The initial 2 instance identifier
--          index values identify the tnOamPingCtlEntry that a OAM probe result
--          (tnOamMacPingHistoryEntry) belongs to. The tnOamMacPingHistoryIndex
--          identifies a group of replies received in response to a specific
--          probe transmission.  The tnOamMacPingReplyIndex selects a single
--          OAM 'macQuery' reply.

--          The tnOamMacPingL2MapIndex selects a single L2 mapping entry
--          within a specific 'macQuery' probe reply.

--          The agent starts assigning tnOamMacPingL2MapIndex values at 1."
--     ::= { tnOamMacPingL2MapEntry 1 }

-- tnOamMacPingL2MapRouterID    OBJECT-TYPE
--     SYNTAX      IpAddress
--     MAX-ACCESS  read-only
--     STATUS      obsolete
--     DESCRIPTION
--         "The value of tnOamMacPingL2MapRouterID is the router ID for this
--          L2 mapping entry."
--     ::= { tnOamMacPingL2MapEntry 2 }

-- tnOamMacPingL2MapLabel       OBJECT-TYPE
--     SYNTAX      MplsLabel
--     MAX-ACCESS  read-only
--     STATUS      obsolete
--     DESCRIPTION
--         "The value of tnOamMacPingL2MapLabel is the label used by the
--          router for the L2FEC or VC ID specified by this L2 mapping entry."
--     ::= { tnOamMacPingL2MapEntry 3 }

-- tnOamMacPingL2MapProtocol    OBJECT-TYPE
--     SYNTAX      TmnxOamSignalProtocol
--     MAX-ACCESS  read-only
--     STATUS      obsolete
--     DESCRIPTION
--         "The value of tnOamMacPingL2MapProtocol is the signaling protocol
--          used by the router for the L2FEC or VC ID specified by this L2
--          mapping entry."
--     ::= { tnOamMacPingL2MapEntry 4 }

-- tnOamMacPingL2MapVCType       OBJECT-TYPE
--     SYNTAX      TmnxOamVcType
--     MAX-ACCESS  read-only
--     STATUS      obsolete
--     DESCRIPTION
--         "The value of tnOamMacPingL2MapVCType specifies the class of
--          VC ID given in tnOamMacPingL2MapVCID."
--     ::= { tnOamMacPingL2MapEntry 5 }

-- tnOamMacPingL2MapVCID        OBJECT-TYPE
--     SYNTAX      TmnxVcId
--     MAX-ACCESS  read-only
--     STATUS      obsolete
--     DESCRIPTION
--         "The value of tnOamMacPingL2MapVCID is the VC ID associated with
--          the label used by the L2FEC specified by this L2 mapping entry."
--     ::= { tnOamMacPingL2MapEntry 6 }

-- tnOamMacPingL2MapDirection       OBJECT-TYPE
--     SYNTAX      INTEGER {
--                     upstream (1),
--                     downstream (2)
--                 }
--     MAX-ACCESS  read-only
--     STATUS      obsolete
--     DESCRIPTION
--         "The value of tnOamMacPingL2MapDirection specifies the direction
--          that this L2 mapping entry is in relation to the node that returned
--          the 'macQuery' reply."
--     ::= { tnOamMacPingL2MapEntry 7 }



--
--  Nokia SROS series OAM LSP Ping Control Table
--
--
--  Sparse Dependent Extension of the tnOamPingCtlTable.
--
--  The same indexes are used for both the base table, tnOamPingCtlTable,
--  and the sparse dependent table, tnOamLspPingCtlTable.
--
--  This in effect extends the tnOamPingCtlTable with additional columns.
--  Rows are created in the tnOamLspPingCtlTable only for those entries
--  in the tnOamPingCtlTable where tnOamPingCtlTestMode has a value of
--  'lspPing'.
--
--  Deletion of a row in the tnOamPingCtlTable results in the
--  same fate for the row in the tnOamLspPingCtlTable.
--
--
tnOamLspPingCtlTable     OBJECT-TYPE
    SYNTAX      SEQUENCE OF TnOamLspPingCtlEntry
    MAX-ACCESS  not-accessible
    STATUS      current
    DESCRIPTION
        "Defines the Nokis SROS OAM LSP Ping Control Table for
         providing, via SNMP, the capability of performing Nokia
         SROS OAM 'lspPing' test operations.  The results of these
         tests are stored in the tnOamPingResultsTable and the
         tnOamPingHistoryTable."
    ::= { tnOamPingObjs 16 }

tnOamLspPingCtlEntry OBJECT-TYPE
    SYNTAX      TnOamLspPingCtlEntry
    MAX-ACCESS  not-accessible
    STATUS      current
    DESCRIPTION
        "Defines an entry in the tnOamLspPingCtlTable.  The first index
         element, tnOamPingCtlOwnerIndex, is of type SnmpAdminString,
         a textual convention that allows for use of the SNMPv3
         View-Based Access Control Model (RFC 2575 [11], VACM)
         and allows a management application to identify its entries.
         The second index, tnOamPingCtlTestIndex, enables the same
         management application to have multiple outstanding requests."
    INDEX {
             tnSysSwitchId,
             -- tnOamPingCtlOwnerIndex,
             tnOamPingCtlTestIndex
          }
    ::= { tnOamLspPingCtlTable 1 }

TnOamLspPingCtlEntry ::=
    SEQUENCE {
        tnOamLspPingCtlVRtrID          TmnxVRtrID,
        tnOamLspPingCtlLspName         TNamedItemOrEmpty,
        tnOamLspPingCtlReturnLsp       TNamedItemOrEmpty,
        tnOamLspPingCtlTtl             Unsigned32,
        tnOamLspPingCtlPathName        TNamedItemOrEmpty,
        tnOamLspPingCtlLdpIpPrefix     IpAddress,
        tnOamLspPingCtlLdpIpPrefixLen  IpAddressPrefixLength,
        tnOamLspPingCtlLdpPrefixType   InetAddressType,
        tnOamLspPingCtlLdpPrefix       InetAddress,
        tnOamLspPingCtlLdpPrefixLen    InetAddressPrefixLength,
        tnOamLspPingCtlPathDestType    InetAddressType,
        tnOamLspPingCtlPathDest        InetAddress,
        tnOamLspPingCtlNhIntfName      TNamedItemOrEmpty,
        tnOamLspPingCtlNhAddressType   InetAddressType,
        tnOamLspPingCtlNhAddress       InetAddress,
        tnOamLspPingCtlTestSubMode     TmnxOamLspTestSubMode,
        tnOamLspPingCtlMplsTpPathType  TmnxOamMplsTpPathType,
        tnOamLspPingCtlMplsTpGlobalId  TmnxMplsTpGlobalID,
        tnOamLspPingCtlMplsTpNodeId    TmnxMplsTpNodeID,
        tnOamLspPingCtlAssocChannel    TmnxOamLspAssocChannel,
        tnOamLspPingCtlForce           TruthValue
    }

tnOamLspPingCtlVRtrID  OBJECT-TYPE
    SYNTAX      TmnxVRtrID
    MAX-ACCESS  read-create
    STATUS      obsolete
    DESCRIPTION
        "The unique value which identifies this virtual router in the
         Nokia SROS system. The vRtrID value for each virtual router
         must remain constant at least from one re-initialization of the
         system management processor (CPM) to the next.  There will always
         be at least one router entry defined by the agent with vRtrID=1
         which represents the transport router.

         This object was obsoleted in release 6.0R15 and replaced with
         tnOamPingCtlVRtrID in tnOamPingCtlTable."
    DEFVAL { 1 } -- Base router
    ::= { tnOamLspPingCtlEntry 1 }

tnOamLspPingCtlLspName     OBJECT-TYPE
    SYNTAX      TNamedItemOrEmpty
    MAX-ACCESS  read-create
    STATUS      current
    DESCRIPTION
        "Administrative name of the target Labeled Switch Path (LSP) for this
         OAM LSP Ping test.  The LSP name must be unique within the virtual
         router instance specified by tnOamLspPingCtlVRtrID.

         This parameter is mutually exclusive with the IP prefix parameter
         associated with an LDP based LSP (tnOamLspPingCtlLdpIpPrefix).
         Either the LSP name or the LDP IP Prefix must be specified but not
         both."
    DEFVAL { ''H }  -- the empty string
    ::= { tnOamLspPingCtlEntry 2 }

tnOamLspPingCtlReturnLsp     OBJECT-TYPE
    SYNTAX      TNamedItemOrEmpty
    MAX-ACCESS  read-create
    STATUS      obsolete
    DESCRIPTION
        "Administrative name of the Labeled Switch Path (LSP) to use to
         return the response to this OAM LSP Ping test.  The LSP name must
         be unique within the virtual router instance specified by
         tnOamLspPingCtlVRtrID.
         This is an optional parameter."
    DEFVAL { ''H }  -- the empty string
    ::= { tnOamLspPingCtlEntry 3 }

tnOamLspPingCtlTtl       OBJECT-TYPE
    SYNTAX      Unsigned32 (1..255)
    UNITS       "time-to-live value"
    MAX-ACCESS  read-create
    STATUS      current
    DESCRIPTION
        "Specifies the outermost label time-to-live value.  This is an optional
         parameter."
    DEFVAL { 255 }
    ::= { tnOamLspPingCtlEntry 4 }

tnOamLspPingCtlPathName     OBJECT-TYPE
    SYNTAX      TNamedItemOrEmpty
    MAX-ACCESS  read-create
    STATUS      current
    DESCRIPTION
        "Administrative name of the Path (LSP) for this OAM LSP Ping test.
         The Path name must be unique within the virtual router
         instance specified by tnOamLspPingCtlVRtrID.

         This is an optional parameter which can be specified only if the
         LSP Name parameter is specified."
    DEFVAL { ''H }  -- the empty string
    ::= { tnOamLspPingCtlEntry 5 }

tnOamLspPingCtlLdpIpPrefix     OBJECT-TYPE
    SYNTAX      IpAddress
    MAX-ACCESS  read-create
    STATUS      obsolete
    DESCRIPTION
        "The IP prefix for the LDP based LSP for this OAM LSP Ping test.

         This parameter is mutually exclusive with the LSP name parameter
         (tnOamLspPingCtlLspName). Either the LDP IP Prefix or the LSP
         name must be specified but not both.

         This object was obsoleted in release 4.0 and replaced with
         InetAddress objects tnOamLspPingCtlLdpPrefixType and
         tnOamLspPingCtlLdpPrefix."
    DEFVAL { '00000000'H } -- 0.0.0.0
    ::= { tnOamLspPingCtlEntry 6 }

tnOamLspPingCtlLdpIpPrefixLen     OBJECT-TYPE
    SYNTAX      IpAddressPrefixLength
    MAX-ACCESS  read-create
    STATUS      obsolete
    DESCRIPTION
        "The IP prefix length for the LDP based LSP for this OAM LSP
         Ping test.

         The value of this parameter is valid only when LDP IP Prefix
         has been specified.

         This object was obsoleted in release 4.0 and replaced with
         InetAddress object tnOamLspPingCtlLdpPrefixLen."
    DEFVAL { 32 }
    ::= { tnOamLspPingCtlEntry 7 }

tnOamLspPingCtlLdpPrefixType    OBJECT-TYPE
    SYNTAX      InetAddressType
    MAX-ACCESS  read-create
    STATUS      current
    DESCRIPTION
        "The value of tnOamLspPingCtlLdpPrefixType specifies the type
         of Internet address stored in tnOamLspPingCtlLdpPrefix."
    DEFVAL { unknown }
    ::= { tnOamLspPingCtlEntry 8 }

tnOamLspPingCtlLdpPrefix     OBJECT-TYPE
    SYNTAX      InetAddress (SIZE (0|4|16))
    MAX-ACCESS  read-create
    STATUS      current
    DESCRIPTION
        "The value of tnOamLspPingCtlLdpPrefix specifies the Internet
         prefix for the LDP based LSP for this OAM LSP Ping test.

         This parameter is mutually exclusive with the LSP name parameter
         (tnOamLspPingCtlLspName).  Either the LDP IP Prefix or the LSP
         name must be specified but not both."
    DEFVAL { ''H }
    ::= { tnOamLspPingCtlEntry 9 }

tnOamLspPingCtlLdpPrefixLen     OBJECT-TYPE
    SYNTAX      InetAddressPrefixLength
    MAX-ACCESS  read-create
    STATUS      current
    DESCRIPTION
        "The value of tnOamLspPingCtlLdpPrefixLen specifies the Internet
         address prefix length for the LDP based LSP for this OAM LSP
         Ping test.

         The value of this parameter is valid only when LDP IP Prefix
         has been specified."
    DEFVAL { 32 }
    ::= { tnOamLspPingCtlEntry 10 }

tnOamLspPingCtlPathDestType    OBJECT-TYPE
    SYNTAX      InetAddressType
    MAX-ACCESS  read-create
    STATUS      current
    DESCRIPTION
        "The value of tnOamLspPingCtlPathDestType specifies the type
         of Internet address stored in tnOamLspPingCtlPathDest."
    DEFVAL { unknown }
    ::= { tnOamLspPingCtlEntry 11 }

tnOamLspPingCtlPathDest     OBJECT-TYPE
    SYNTAX      InetAddress (SIZE (0|4|16))
    MAX-ACCESS  read-create
    STATUS      current
    DESCRIPTION
        "The value of tnOamLspPingCtlPathDest specifies a unique path
         for this OAM LSP Ping to traverse. This address is used as part of a
         hash key to select the appropriate ECMP path to the destination of
         an OAM LSP Ping test.

         This is an optional parameter. "
    DEFVAL { ''H }
    ::= { tnOamLspPingCtlEntry 12 }

tnOamLspPingCtlNhIntfName     OBJECT-TYPE
    SYNTAX      TNamedItemOrEmpty
    MAX-ACCESS  read-create
    STATUS      current
    DESCRIPTION
        "Administrative name of the next hop interface for this OAM LSP
         Ping test to be sent. The interface name must be unique within
         the virtual router instance specified by tnOamLspPingCtlVRtrID.

         This is an optional parameter which can be specified only if the
         tnOamLspPingCtlPathDest parameter is specified. This parameter
         is mutually exclusive with the tnOamLspPingCtlNhAddress
         parameter. Either the next-hop interface name or next-hop address
         can be specified but not both. An attempt to set this object to a
         non-default value when tnOamLspPingCtlNhAddress has a
         non-default value will result in an 'inconsistentValue' error."
    DEFVAL { ''H }  -- the empty string
    ::= { tnOamLspPingCtlEntry 13 }

tnOamLspPingCtlNhAddressType    OBJECT-TYPE
    SYNTAX      InetAddressType
    MAX-ACCESS  read-create
    STATUS      current
    DESCRIPTION
        "The value of tnOamLspPingCtlNhAddressType specifies the type
         of Internet address stored in tnOamLspPingCtlNhAddress."
    DEFVAL { unknown }
    ::= { tnOamLspPingCtlEntry 14 }

tnOamLspPingCtlNhAddress     OBJECT-TYPE
    SYNTAX      InetAddress (SIZE (0|4|16))
    MAX-ACCESS  read-create
    STATUS      current
    DESCRIPTION
        "The value of tnOamLspPingCtlNhAddress specifies the Interface
         address to the next hop in which this OAM LSP ping test will be
         transmitted.

         This is an optional parameter which can be specified only if the
         tnOamLspPingCtlPathDest parameter is specified. This parameter
         is mutually exclusive with tnOamLspPingCtlNhIntfName parameter.
         Either the next-hop interface name or next-hop address
         can be specified but not both. An attempt to set this object to a
         non-default value when tnOamLspPingCtlNhIntfName has a
         non-default value  will result in an 'inconsistentValue' error."
    DEFVAL { ''H }
    ::= { tnOamLspPingCtlEntry 15 }

tnOamLspPingCtlTestSubMode     OBJECT-TYPE
    SYNTAX      TmnxOamLspTestSubMode
    MAX-ACCESS  read-create
    STATUS      current
    DESCRIPTION
        "The value of tnOamLspPingCtlTestSubMode specifies the type of LSP
         ping test to perform.

         When this object is 'unspecified(1)', the type of LSP ping test to be
         performed is determined when the test is started, from the set of
         tnOamLspPingCtlTable objects configured with non-default values.

         If there is a mismatch between tnOamLspPingCtlTestSubMode and the
         type of the LSP to be tested, the test will fail.  For example, if
         tnOamLspPingCtlTestSubMode is 'static(2)', and
         tnOamLspPingCtlLspName refers to an LSP with
         TIMETRA-MPLS-MIB::vRtrMplsLspType not equal to 'mplsTp(7)', the test
         will fail.

         The supported object combinations for LSP ping tests are listed in the
         tnOamLspPingCtlTable DESCRIPTION clause."
    DEFVAL { unspecified }
    ::= { tnOamLspPingCtlEntry 16 }

tnOamLspPingCtlMplsTpPathType  OBJECT-TYPE
    SYNTAX      TmnxOamMplsTpPathType
    MAX-ACCESS  read-create
    STATUS      current
    DESCRIPTION
        "The value of tnOamLspPingCtlMplsTpPathType specifies the type of the
         MPLS-TP path to be tested.

         The supported object combinations for LSP ping tests are listed in the
         tnOamLspPingCtlTable DESCRIPTION clause."
    DEFVAL { active }
    ::= { tnOamLspPingCtlEntry 17 }

tnOamLspPingCtlMplsTpGlobalId  OBJECT-TYPE
    SYNTAX         TmnxMplsTpGlobalID
    MAX-ACCESS     read-create
    STATUS         current
    DESCRIPTION
        "The value of tnOamLspPingCtlMplsTpGlobalId specifies the target
         MPLS-TP Global Identifier to be used for the test.

         The supported object combinations for LSP ping tests are listed in the
         tnOamLspPingCtlTable DESCRIPTION clause."
    DEFVAL { 0 }
    ::= { tnOamLspPingCtlEntry 18 }

tnOamLspPingCtlMplsTpNodeId    OBJECT-TYPE
    SYNTAX         TmnxMplsTpNodeID
    MAX-ACCESS     read-create
    STATUS         current
    DESCRIPTION
        "The value of tnOamLspPingCtlMplsTpNodeId specifies the target
         MPLS-TP Node Identifier to be used for the test.

         A value of zero indicates that no Node Identifier has been configured.

         The supported object combinations for LSP ping tests are listed in the
         tnOamLspPingCtlTable DESCRIPTION clause."
    DEFVAL { 0 }
    ::= { tnOamLspPingCtlEntry 19 }

tnOamLspPingCtlAssocChannel    OBJECT-TYPE
    SYNTAX      TmnxOamLspAssocChannel
    MAX-ACCESS  read-create
    STATUS      current
    DESCRIPTION
        "The value of tnOamLspPingCtlAssocChannel specifies the launched echo
         request's usage of the Associated Channel (ACH) mechanism, when testing
         an MPLS-TP LSP.

         When tnOamLspPingCtlTestSubMode is 'static(2)', the default value
         for tnOamLspPingCtlAssocChannel is 'nonIp(2)'.

         The supported object combinations for LSP ping tests are listed in the
         tnOamLspPingCtlTable DESCRIPTION clause."
    DEFVAL { notApplicable }
    ::= { tnOamLspPingCtlEntry 20 }

tnOamLspPingCtlForce           OBJECT-TYPE
    SYNTAX      TruthValue
    MAX-ACCESS  read-create
    STATUS      current
    DESCRIPTION
        "The value of tnOamLspPingCtlForce specifies whether or not to force
         the transmission of the 'lspPing' request PDU(s).

         If tnOamLspPingCtlForce is 'true(1)', the test will proceed and
         request PDU(s) will be sent regardless of the local operational status
         of the tested LSP path.

         If tnOamLspPingCtlForce is 'false(2)',  the test will fail
         immediately when the local operational status of the tested LSP path is
         down.

         The supported object combinations for LSP ping tests are listed in the
         tnOamLspPingCtlTable DESCRIPTION clause."
    DEFVAL { false }
    ::= { tnOamLspPingCtlEntry 21 }

--  Nokia SROS series OAM VPRN Ping Control Table
--
--  Sparse Dependent Extension of the tnOamPingCtlTable.
--
--  The same indexes are used for both the base table, tnOamPingCtlTable,
--  and the sparse dependent table, tnOamVprnPingCtlTable.
--
--  This in effect extends the tnOamPingCtlTable with additional columns.
--  Rows are created in the tnOamVprnPingCtlTable only for those entries
--  in the tnOamPingCtlTable where tnOamPingCtlTestMode has a value of
--  'vprnPing'.
--
--  Deletion of a row in the tnOamPingCtlTable results in the
--  same fate for the row in the tnOamVprnPingCtlTable.
--

-- tnOamVprnPingCtlTable     OBJECT-TYPE
--     SYNTAX      SEQUENCE OF TnOamVprnPingCtlEntry
--     MAX-ACCESS  not-accessible
--     STATUS      current
--     DESCRIPTION
--         "Defines the Nokia SROS OAM VPRN Ping Control Table for
--          providing, via SNMP, the capability of performing Nokia
--          SROS OAM 'vprnPing' test operations.
--
--          The results of these tests are stored in the tnOamPingResultsTable
--          and the tnOamTrProbeHistoryTable.  There will be no entries for
--          these test in the tnOamPingHistoryTable."
--    ::= { tnOamPingObjs 18 }
--
-- tnOamVprnPingCtlEntry OBJECT-TYPE
--     SYNTAX      TnOamVprnPingCtlEntry
--     MAX-ACCESS  not-accessible
--     STATUS      current
--     DESCRIPTION
--         "Defines an entry in the tnOamVprnPingCtlTable.  The first index
--          element, tnOamPingCtlOwnerIndex, is of type SnmpAdminString,
--          a textual convention that allows for use of the SNMPv3
--          View-Based Access Control Model (RFC 2575 [11], VACM)
--          and allows a management application to identify its entries.
--          The second index, tnOamPingCtlTestIndex, enables the same
--          management application to have multiple outstanding requests."
--     INDEX {
--              tnOamPingCtlOwnerIndex,
--              tnOamPingCtlTestIndex
--           }
--     ::= { tnOamVprnPingCtlTable 1 }
--
-- TnOamVprnPingCtlEntry ::=
--     SEQUENCE {
--         tnOamVprnPingCtlSourceIpAddr      IpAddress,
--         tnOamVprnPingCtlReplyControl      TruthValue,
--         tnOamVprnPingCtlTtl               Unsigned32,
--         tnOamVprnPingCtlSrcAddrType       InetAddressType,
--         tnOamVprnPingCtlSrcAddress        InetAddress
--     }
--
-- tnOamVprnPingCtlSourceIpAddr     OBJECT-TYPE
--     SYNTAX      IpAddress
--     MAX-ACCESS  read-create
--     STATUS      obsolete
--     DESCRIPTION
--         "Specifies the Ipv4 address to be used as the source for
--          performing an OAM ping operation when tnOamPingCtlTestMode has
--          a value of 'vprnPing'.   This parameter is required.
--
--          This object was obsoleted in release 4.0 and replaced with
--          InetAddress objects tnOamVprnPingCtlSrcAddrType and
--          tnOamVprnPingCtlSrcAddress."
--     DEFVAL { '00000000'h }   --   -- 0.0.0.0
--     ::= { tnOamVprnPingCtlEntry 1 }
--
-- tnOamVprnPingCtlReplyControl     OBJECT-TYPE
--     SYNTAX      TruthValue
--     MAX-ACCESS  read-create
--     STATUS      current
--     DESCRIPTION
--         "When the value of tnOamVprnPingCtlReplyControl is 'true', the
--          OAM ping response is returned using the control plane.  If its value
--          is 'false', the packet is sent via the data plane.
--
--          This object is optional and is not relevant when
--          tnOamPingCtlTestMode has a value other than 'vprnPing'."
--     DEFVAL { false }
--     ::= { tnOamVprnPingCtlEntry 2 }
--
-- tnOamVprnPingCtlTtl      OBJECT-TYPE
--     SYNTAX      Unsigned32 (1..255)
--     UNITS       "time-to-live value"
--     MAX-ACCESS  read-create
--     STATUS      current
--     DESCRIPTION
--         "Specifies the vc-label time-to-live value.
--
--          This object is optional and is not relevant when
--          tnOamPingCtlTestMode has a value other than 'vprnPing'.
--
--          While performing the test with a ttl of 1 no responses should ever be
--          expected."
--     DEFVAL { 255 }
--     ::= { tnOamVprnPingCtlEntry 3 }
--
-- tnOamVprnPingCtlSrcAddrType     OBJECT-TYPE
--     SYNTAX      InetAddressType
--     MAX-ACCESS  read-create
--     STATUS      current
--     DESCRIPTION
--         "The value of tnOamVprnPingCtlSrcAddrType specifies the Internet
--          address type stored in tnOamVprnPingCtlSrcAddress."
--     DEFVAL { unknown }
--     ::= { tnOamVprnPingCtlEntry 4 }
--
-- tnOamVprnPingCtlSrcAddress     OBJECT-TYPE
--     SYNTAX      InetAddress (SIZE (0|4|16))
--     MAX-ACCESS  read-create
--     STATUS      current
--     DESCRIPTION
--         "The value of tnOamVprnPingCtlSrcAddress specifies the Internet
--          address to be used as the source for performing an OAM ping
--          operation when tnOamPingCtlTestMode has a value of 'vprnPing'.
--
--          This parameter is required."
--     DEFVAL { ''H }
--     ::= { tnOamVprnPingCtlEntry 5 }


--
--  Nokia SROS series OAM ATM Ping Control Table
--
--  Sparse Dependent Extension of the tnOamPingCtlTable.
--
--  The same indexes are used for both the base table, tnOamPingCtlTable,
--  and the sparse dependent table, tnOamAtmPingCtlTable.
--
--  This in effect extends the tnOamPingCtlTable with additional columns.
--  Rows are created in the tnOamAtmPingCtlTable only for those entries
--  in the tnOamPingCtlTable where tnOamPingCtlTestMode has a value of
--  'atmPing'.
--
--  Deletion of a row in the tnOamPingCtlTable results in the
--  same fate for the row in the tnOamAtmPingCtlTable.
--
-- tnOamAtmPingCtlTable     OBJECT-TYPE
--     SYNTAX      SEQUENCE OF TnOamAtmPingCtlEntry
--     MAX-ACCESS  not-accessible
--     STATUS      current
--     DESCRIPTION
--         "Defines the Nokia SROS OAM ATM Ping Control Table for providing,
--          via SNMP, the capability of performing Nokia SROS OAM 'atmPing'
--          test operations.

--          The results of these tests are stored in the tnOamPingResultsTable
--          and the tnOamPingHistoryTable."
--    ::= { tnOamPingObjs 20 }

-- tnOamAtmPingCtlEntry OBJECT-TYPE
--     SYNTAX      TnOamAtmPingCtlEntry
--     MAX-ACCESS  not-accessible
--     STATUS      current
--     DESCRIPTION
--         "Defines an entry in the tnOamAtmPingCtlTable.  The first index
--          element, tnOamPingCtlOwnerIndex, is of type SnmpAdminString,
--          a textual convention that allows for use of the SNMPv3
--          View-Based Access Control Model (RFC 2575 [11], VACM)
--          and allows a management application to identify its entries.
--          The second index, tnOamPingCtlTestIndex, enables the same
--          management application to have multiple outstanding requests."
--     INDEX {
--              tnOamPingCtlOwnerIndex,
--              tnOamPingCtlTestIndex
--           }
--     ::= { tnOamAtmPingCtlTable 1 }

-- TnOamAtmPingCtlEntry ::=
--     SEQUENCE {
--         tnOamAtmPingCtlPortId           TmnxPortID,
--         tnOamAtmPingCtlVpi              AtmVpIdentifier,
--         tnOamAtmPingCtlVci              AtmVcIdentifier,
--         tnOamAtmPingCtlLpbkLocation     OCTET STRING,
--         tnOamAtmPingCtlSegment          INTEGER
--     }

-- tnOamAtmPingCtlPortId OBJECT-TYPE
--     SYNTAX          TmnxPortID
--     MAX-ACCESS      read-create
--     STATUS          current
--     DESCRIPTION
--         "The value of tnOamAtmPingCtlPortId is the ID of the access
--          port of the target VC. This parameter is required."
--     DEFVAL { 0 }
--     ::= { tnOamAtmPingCtlEntry 1 }

-- tnOamAtmPingCtlVpi OBJECT-TYPE
--     SYNTAX          AtmVpIdentifier
--     MAX-ACCESS      read-create
--     STATUS          current
--     DESCRIPTION
--         "The value of tnOamAtmPingCtlVpi is the VPI of the VC used to
--          send the OAM ATM ping.  This is a required parameter."
--     DEFVAL { 0 }
--     ::= { tnOamAtmPingCtlEntry 2 }

-- tnOamAtmPingCtlVci OBJECT-TYPE
--     SYNTAX          AtmVcIdentifier
--     MAX-ACCESS      read-create
--     STATUS          current
--     DESCRIPTION
--         "The value of tnOamAtmPingCtlVci is the VCI of the VC used to
--          send the OAM ATM ping.  This is a required parameter."
--     DEFVAL { 0 }
--     ::= { tnOamAtmPingCtlEntry 3 }

-- tnOamAtmPingCtlLpbkLocation OBJECT-TYPE
--     SYNTAX          OCTET STRING (SIZE(16))
--     MAX-ACCESS      read-create
--     STATUS          current
--     DESCRIPTION
--         "The value of tnOamAtmPingCtlLpbkLocation is the Loopback
--          Location ID used in the ATM OAM loopback cell.  If all bits in the
--          Loopback Location ID are '1', the destination of the OAM ATM ping
--          is the far-end destination of the VC.  Otherwise it is destined to
--          a specific ATM node in the ATM network.

--          This is a required parameter."
--     DEFVAL { ''H }  -- -- the empty string
--     ::= { tnOamAtmPingCtlEntry 4 }

-- tnOamAtmPingCtlSegment OBJECT-TYPE
--     SYNTAX          INTEGER {
--                           endToEnd (1),
--                           segment (2)
--                     }
--     MAX-ACCESS      read-create
--     STATUS          current
--     DESCRIPTION
--         "The value of tnOamAtmPingCtlSegment determines if the
--          ATM OAM loopback cell is destined to the first segment going in
--          the line direction or the PVCC's connection endpoint."
--     DEFVAL { endToEnd }
--     ::= { tnOamAtmPingCtlEntry 5 }


--
--  Nokia SROS series OAM MFIB Ping Control Table
--
--
--  Sparse Dependent Extension of the tnOamPingCtlTable.
--
--  The same indexes are used for both the base table, tnOamPingCtlTable,
--  and the sparse dependent table, tnOamMfibPingCtlTable.
--
--  Rows are created in the tnOamMfibPingCtlTable only for those entries
--  in the tnOamPingCtlTable where tnOamPingCtlTestMode has a value of
--  'mfibPing'.
--
--  Deletion of a row in the tnOamPingCtlTable results in the
--  same fate for the row in the tnOamMfibPingCtlTable.
--
-- tnOamMfibPingCtlTable     OBJECT-TYPE
--     SYNTAX      SEQUENCE OF TnOamMfibPingCtlEntry
--     MAX-ACCESS  not-accessible
--     STATUS      current
--     DESCRIPTION
--         "Defines the Nokia SROS OAM  MFIB  Ping Control Table for
--          providing, via SNMP, the capability of performing Nokia SROS
--          OAM 'mfibPing' test operations.
--
--          The results of these tests are stored in the
--          tnOamPingResultsTable and the tnOamPingHistoryTable. Rows are
--          created in the tnOamMfibPingCtlTable only for those entries in
--          the tnOamPingCtlTable where tnOamPingCtlTestMode has a value of
--          'mfibPing'."
--    ::= { tnOamPingObjs 22 }
--
-- tnOamMfibPingCtlEntry     OBJECT-TYPE
--     SYNTAX      TnOamMfibPingCtlEntry
--     MAX-ACCESS  not-accessible
--     STATUS      current
--     DESCRIPTION
--         "Defines an entry in the tnOamMfibPingCtlTable.  The
--          first index element, tnOamPingCtlOwnerIndex, is of
--          type SnmpAdminString, a textual convention that allows
--          for use of the SNMPv3 View-Based Access Control Model
--          (RFC 2575 [11], VACM) and allows a management
--          application to identify its entries. The second index,
--          tnOamPingCtlTestIndex, enables the same management
--          application to have multiple outstanding requests."
--     INDEX {
--              tnOamPingCtlOwnerIndex,
--              tnOamPingCtlTestIndex
--           }
--     ::= { tnOamMfibPingCtlTable 1 }
--
-- TnOamMfibPingCtlEntry ::=
--     SEQUENCE {
--         tnOamMfibPingCtlSourceIpAddr    IpAddress,
--         tnOamMfibPingCtlDestIpAddr      IpAddress,
--         tnOamMfibPingCtlReplyControl    TruthValue,
--         tnOamMfibPingCtlTtl             Unsigned32,
--         tnOamMfibPingCtlSrcAddrType     InetAddressType,
--         tnOamMfibPingCtlSrcAddress      InetAddress,
--         tnOamMfibPingCtlDestAddrType    InetAddressType,
--         tnOamMfibPingCtlDestAddress     InetAddress,
--         tnOamMfibPingCtlDestMacAddr     MacAddress
--     }
--
-- tnOamMfibPingCtlSourceIpAddr     OBJECT-TYPE
--     SYNTAX      IpAddress
--     MAX-ACCESS  read-write
--     STATUS      obsolete
--     DESCRIPTION
--         "Specifies the Ipv4 address to be used as the source for performing
--          an OAM ping operation when tnOamPingCtlTestMode has a value of
--          'mfibPing' in which case this parameter is required.  If
--          tnOamPingCtlTestMode is different from 'mfibPing' this field is
--          ignored.
--
--          This object was obsoleted in release 4.0 and replaced with
--          InetAddress objects tnOamMfibPingCtlSrcAddrType and
--          tnOamMfibPingCtlSrcAddress."
--     DEFVAL { '00000000'h }  --    -- 0.0.0.0
--     ::= { tnOamMfibPingCtlEntry 1 }
--
-- tnOamMfibPingCtlDestIpAddr       OBJECT-TYPE
--     SYNTAX      IpAddress
--     MAX-ACCESS  read-write
--     STATUS      obsolete
--     DESCRIPTION
--         "Specifies the Ipv4 multicast address to be used as the destination
--          for performing an OAM ping operation when tnOamPingCtlTestMode has a
--          value of 'mfibPing' in which case this parameter is required. If
--          tnOamPingCtlTestMode is different from 'mfibPing' this field is
--          ignored.
--
--          This object was obsoleted in release 4.0 and replaced with
--          InetAddress objects tnOamMfibPingCtlDestAddrType and
--          tnOamMfibPingCtlDestAddress."
--     DEFVAL { '00000000'h }  --    -- 0.0.0.0
--     ::= { tnOamMfibPingCtlEntry 2 }
--
-- tnOamMfibPingCtlReplyControl     OBJECT-TYPE
--     SYNTAX      TruthValue
--     MAX-ACCESS  read-write
--     STATUS      current
--     DESCRIPTION
--         "When the value of tnOamMfibPingCtlReplyControl is 'true', the
--          OAM ping response is returned using the control plane. If its value
--          is 'false', the packet is sent via the data plane.
--
--          This object is optional and is not relevant when tnOamPingCtlTestMode
--          has a value other than 'mfibPing'."
--     DEFVAL { false }
--     ::= { tnOamMfibPingCtlEntry 3 }
--
-- tnOamMfibPingCtlTtl              OBJECT-TYPE
--     SYNTAX      Unsigned32 (1..255)
--     UNITS       "time-to-live value"
--     MAX-ACCESS  read-write
--     STATUS      current
--     DESCRIPTION
--         "Specifies the vc-label time-to-live value.
--          This object is optional and is not relevant when
--          tnOamPingCtlTestMode has a value other than 'mfibPing'.
--          While performing the test with a ttl of 1 no responses should ever
--          be expected."
--     DEFVAL { 255 }
--     ::= { tnOamMfibPingCtlEntry 4 }
--
-- tnOamMfibPingCtlSrcAddrType     OBJECT-TYPE
--     SYNTAX      InetAddressType
--     MAX-ACCESS  read-write
--     STATUS      current
--     DESCRIPTION
--         "The value of tnOamMfibPingCtlSrcAddrType specifies the Internet
--          address type stored in tnOamMfibPingCtlSrcAddress."
--     DEFVAL { unknown }
--     ::= { tnOamMfibPingCtlEntry 5 }
--
-- tnOamMfibPingCtlSrcAddress     OBJECT-TYPE
--     SYNTAX      InetAddress (SIZE (0|4|16))
--     MAX-ACCESS  read-write
--     STATUS      current
--     DESCRIPTION
--         "The value of tnOamMfibPingCtlSrcAddress specifies the Internet
--          address to be used as the source for performing an OAM ping
--          operation when tnOamPingCtlTestMode has a value of 'mfibPing'
--          and the value of tnOamMfibPingCtlDestMacAddr is all zeros, in
--          which case this parameter is required.  If tnOamPingCtlTestMode is
--          different from 'mfibPing' this field is ignored."
--     DEFVAL { ''H }
--     ::= { tnOamMfibPingCtlEntry 6 }
--
-- tnOamMfibPingCtlDestAddrType       OBJECT-TYPE
--     SYNTAX      InetAddressType
--     MAX-ACCESS  read-write
--     STATUS      current
--     DESCRIPTION
--         "The value of tnOamMfibPingCtlDestAddrType specifies the Internet
--          multicast address type stored in tnOamMfibPingCtlDestAddress."
--     DEFVAL { unknown }
--     ::= { tnOamMfibPingCtlEntry 7 }
--
-- tnOamMfibPingCtlDestAddress       OBJECT-TYPE
--     SYNTAX      InetAddress (SIZE (0|4|16))
--     MAX-ACCESS  read-write
--     STATUS      current
--     DESCRIPTION
--         "The value of tnOamMfibPingCtlDestAddress specifies the Internet
--          multicast address to be used as the destination for performing an
--          OAM ping operation when tnOamPingCtlTestMode has a value of
--          'mfibPing' and the value of tnOamMfibPingCtlDestMacAddr is all zeros,
--          in which case this parameter is required.  If tnOamPingCtlTestMode is
--          different from 'mfibPing' this field is ignored."
--     DEFVAL { ''H }
--     ::= { tnOamMfibPingCtlEntry 8 }
--
-- tnOamMfibPingCtlDestMacAddr       OBJECT-TYPE
--     SYNTAX      MacAddress
--     MAX-ACCESS  read-write
--     STATUS      current
--     DESCRIPTION
--         "The value of tnOamMfibPingCtlDestMacAddr specifies the IPv6
--          multicast MAC address to be used as the destination for performing an
--          OAM ping operation when tnOamPingCtlTestMode has a value of
--          'mfibPing' and objects tnOamMfibPingCtlSrcAddrType and
--          tnOamMfibPingCtlDestAddrType have a value of 'unknown (0)',
--          in which case this parameter is required.  If tnOamPingCtlTestMode is
--          different from 'mfibPing' this field is ignored."
--     DEFVAL { ''H }
--     ::= { tnOamMfibPingCtlEntry 9 }

--
--  Nokia SROS series OAM CPE Ping Control Table
--
--
--  Sparse Dependent Extension of the tnOamPingCtlTable.
--
--  The same indexes are used for both the base table, tnOamPingCtlTable,
--  and the sparse dependent table, tnOamCpePingCtlTable.
--
--  Rows are created in the tnOamCpePingCtlTable only for those entries
--  in the tnOamPingCtlTable where tnOamPingCtlTestMode has a value of
--  'cpePing'.
--
--  Deletion of a row in the tnOamPingCtlTable results in the
--  same fate for the row in the tnOamCpePingCtlTable.
--
-- tnOamCpePingCtlTable     OBJECT-TYPE
--     SYNTAX      SEQUENCE OF TnOamCpePingCtlEntry
--     MAX-ACCESS  not-accessible
--     STATUS      current
--     DESCRIPTION
--         "Defines the Nokia SROS OAM CPE Ping Control Table for
--          providing,  via  SNMP, the capability of performing Nokia SROS
--          OAM 'cpePing' test operations.
--
--          The results of these tests are stored in the
--          tnOamPingResultsTable  and  the tnOamPingHistoryTable. Rows are
--          created in the tnOamCpePingCtlTable only for those entries in the
--          tnOamPingCtlTable where tnOamPingCtlTestMode has a value of
--          'cpePing'."
--    ::= { tnOamPingObjs 24 }
--
-- tnOamCpePingCtlEntry     OBJECT-TYPE
--     SYNTAX      TnOamCpePingCtlEntry
--     MAX-ACCESS  not-accessible
--     STATUS      current
--     DESCRIPTION
--         "Defines an entry in the tnOamCpePingCtlTable. The first index
--          element, tnOamPingCtlOwnerIndex, is of type SnmpAdminString, a
--          textual convention that allows for use of the SNMPv3 View-Based
--          Access Control Model (RFC 2575 [11], VACM) and allows a management
--          application to identify its entries.  The second index,
--          tnOamPingCtlTestIndex, enables the same management application to
--          have multiple outstanding requests."
--     INDEX {
--              tnOamPingCtlOwnerIndex,
--              tnOamPingCtlTestIndex
--           }
--     ::= { tnOamCpePingCtlTable 1 }
--
-- TnOamCpePingCtlEntry ::=
--     SEQUENCE {
--         tnOamCpePingCtlSourceIpAddr    IpAddress,
--         tnOamCpePingCtlSendControl     TruthValue,
--         tnOamCpePingCtlReplyControl    TruthValue,
--         tnOamCpePingCtlTtl             Unsigned32,
--         tnOamCpePingCtlSrceMacAddr     MacAddress,
--         tnOamCpePingCtlSrcAddrType     InetAddressType,
--         tnOamCpePingCtlSrcAddress      InetAddress
--     }
--
-- tnOamCpePingCtlSourceIpAddr     OBJECT-TYPE
--     SYNTAX      IpAddress
--     MAX-ACCESS  read-write
--     STATUS      obsolete
--     DESCRIPTION
--         "Specifies the Ipv4 address to be used as the source for performing
--          an CPE ping operation when tnOamPingCtlTestMode has a value of
--          'cpePing'.  This parameter is required for 'cpePing' and ignored in
--          all other cases.
--
--          This object was obsoleted in release 4.0 and replaced with
--          InetAddress objects tnOamCpePingCtlSrcAddrType and
--          tnOamCpePingCtlSrcAddress."
--     DEFVAL { '00000000'h }   --   -- 0.0.0.0
--     ::= { tnOamCpePingCtlEntry 1 }
--
-- tnOamCpePingCtlSendControl      OBJECT-TYPE
--     SYNTAX      TruthValue
--     MAX-ACCESS  read-write
--     STATUS      current
--     DESCRIPTION
--         "When the value of tnOamCpePingCtlSendControl is 'true', the OAM
--          ping packet is sent via the control plane.  If its value is 'false',
--          the packet is sent via the data plane.
--          This object is optional and is not relevant when tnOamPingCtlTestMode
--          has a value other than 'cpePing'."
--     DEFVAL { false }
--     ::= { tnOamCpePingCtlEntry 2 }
--
-- tnOamCpePingCtlReplyControl     OBJECT-TYPE
--     SYNTAX      TruthValue
--     MAX-ACCESS  read-write
--     STATUS      current
--     DESCRIPTION
--         "When the value of tnOamCpePingCtlReplyControl is 'true', the OAM
--          ping response is returned using the control plane. If its value is
--          'false', the packet is sent via the data plane.
--          This object is optional and is not relevant when
--          tnOamPingCtlTestMode has a value other than 'cpePing'."
--     DEFVAL { false }
--     ::= { tnOamCpePingCtlEntry 3 }
--
-- tnOamCpePingCtlTtl              OBJECT-TYPE
--     SYNTAX      Unsigned32 (1..255)
--     UNITS       "time-to-live value"
--     MAX-ACCESS  read-write
--     STATUS      current
--     DESCRIPTION
--         "Specifies the vc-label time-to-live value. This object is optional
--          and is not relevant when tnOamPingCtlTestMode has a value other
--          than 'cpePing'. When performing the test with a ttl=1, the cpe-ping
--          is only done to the local SAP(s)."
--     DEFVAL { 255 }
--     ::= { tnOamCpePingCtlEntry 4 }
--
-- tnOamCpePingCtlSrceMacAddr      OBJECT-TYPE
--     SYNTAX      MacAddress
--     MAX-ACCESS  read-write
--     STATUS      current
--     DESCRIPTION
--         "When set to a non zero value, the system will use the value as
--          source mac address in the ARP request that will be sent to the CPE.
--          If set to 0, the MAC address configured for the CPM is used. This
--          object is optional and is not relevant when tnOamPingCtlTestMode
--          has a value other than 'cpePing'."
--     DEFVAL { '000000000000'H }
--     ::= { tnOamCpePingCtlEntry 5 }
--
-- tnOamCpePingCtlSrcAddrType     OBJECT-TYPE
--     SYNTAX      InetAddressType
--     MAX-ACCESS  read-write
--     STATUS      current
--     DESCRIPTION
--         "The value of tnOamCpePingCtlSrcAddrType specifies the Internet
--          address type stored in tnOamCpePingCtlSrcAddress."
--     DEFVAL { unknown }
--     ::= { tnOamCpePingCtlEntry 6 }
--
-- tnOamCpePingCtlSrcAddress     OBJECT-TYPE
--     SYNTAX      InetAddress (SIZE (0|4|16))
--     MAX-ACCESS  read-write
--     STATUS      current
--     DESCRIPTION
--         "The value of tnOamCpePingCtlSrcAddress specifies the Internet
--          address to be used as the source for performing a CPE ping operation
--          when tnOamPingCtlTestMode has a value of 'cpePing'.  This parameter
--          is required for 'cpePing' and ignored in all other cases."
--     DEFVAL { ''H }
--     ::= { tnOamCpePingCtlEntry 7 }


--
-- Nokia SROS series OAM Multicast Router Information Response Table
--
-- tnOamMRInfoRespTable     OBJECT-TYPE
--     SYNTAX      SEQUENCE OF TnOamMRInfoRespEntry
--     MAX-ACCESS  not-accessible
--     STATUS      current
--     DESCRIPTION
--         "Defines the Nokia SROS OAM Multicast Router Information
--          Response Table for providing, via SNMP, the capability of performing
--          Nokia SROS OAM 'mrinfo' test operations. The results of these
--          tests are stored in the tnOamPingResultsTable, the
--          tnOamPingHistoryTable and the tnOamMRInfoRespTable."
--    ::= { tnOamPingObjs 26 }
--
-- tnOamMRInfoRespEntry OBJECT-TYPE
--     SYNTAX      TnOamMRInfoRespEntry
--     MAX-ACCESS  not-accessible
--     STATUS      current
--     DESCRIPTION
--         "Defines an entry in the tnOamMRInfoRespTable.  The first index
--          element, tnOamPingCtlOwnerIndex, is of type SnmpAdminString,
--          a textual convention that allows for use of the SNMPv3
--          View-Based Access Control Model (RFC 2575 [11], VACM)
--          and allows a management application to identify its entries.
--          The second index, tnOamPingCtlTestIndex, enables the same
--          management application to have multiple outstanding requests."
--     INDEX {
--              tnOamPingCtlOwnerIndex,
--              tnOamPingCtlTestIndex,
--              tnOamPingResultsTestRunIndex,
--              tnOamPingHistoryIndex
--           }
--     ::= { tnOamMRInfoRespTable 1 }
--
-- TnOamMRInfoRespEntry ::=
--     SEQUENCE {
--         tnOamMRInfoRespCapabilities   BITS,
--         tnOamMRInfoRespMinorVersion   Unsigned32,
--         tnOamMRInfoRespMajorVersion   Unsigned32,
--         tnOamMRInfoRespNumInterfaces  Unsigned32
--     }
--
-- tnOamMRInfoRespCapabilities    OBJECT-TYPE
--     SYNTAX      BITS {
--                     leaf(0),
--                     prune(1),
--                     genid(2),
--                     mtrace(3),
--                     snmp(4)
--                 }
--     MAX-ACCESS  read-only
--     STATUS      current
--     DESCRIPTION
--         "tnOamMRInfoRespCapabilities indicates the capabilities of the router
--          responding to the mrinfo request:
--             leaf(0)     This is a leaf router
--             prune(1)    This router understands pruning
--             genid(2)    This router sends Generation Id's
--             mtrace(3)   This router handles Mtrace requests
--             snmp(4)     This router supports the DVMRP MIB
--         "
--     ::= { tnOamMRInfoRespEntry 1 }
--
-- tnOamMRInfoRespMinorVersion    OBJECT-TYPE
--     SYNTAX      Unsigned32
--     MAX-ACCESS  read-only
--     STATUS      current
--     DESCRIPTION
--         "tnOamMRInfoRespMinorVersion indicates the minor software version
--          on the router responding to the mrinfo request."
--     ::= { tnOamMRInfoRespEntry 2 }
--
-- tnOamMRInfoRespMajorVersion    OBJECT-TYPE
--     SYNTAX      Unsigned32
--     MAX-ACCESS  read-only
--     STATUS      current
--     DESCRIPTION
--         "tnOamMRInfoRespMajorVersion indicates the major software version
--          on the router responding to the mrinfo request."
--     ::= { tnOamMRInfoRespEntry 3 }
--
-- tnOamMRInfoRespNumInterfaces    OBJECT-TYPE
--     SYNTAX      Unsigned32
--     MAX-ACCESS  read-only
--     STATUS      current
--     DESCRIPTION
--         "tnOamMRInfoRespNumInterfaces indicates the number of interfaces
--          in the mrinfo response packet. These interfaces are listed in the
--          tnOamMRInfoRespIfTable."
--     ::= { tnOamMRInfoRespEntry 4 }


--
-- Nokia SROS series OAM Multicast Router Information Interface Table
--
-- tnOamMRInfoRespIfTable     OBJECT-TYPE
--     SYNTAX      SEQUENCE OF TnOamMRInfoRespIfEntry
--     MAX-ACCESS  not-accessible
--     STATUS      current
--     DESCRIPTION
--         "Defines the Nokia SROS OAM Multicast Router Information
--          Interface Table for providing, via SNMP, the capability of performing
--          Nokia SROS OAM 'mrinfo' test operation. The results of
--          these tests are stored in the tnOamPingResultsTable, the
--          tnOamPingHistoryTable and the tnOamMRInfoRespIfTable."
--    ::= { tnOamPingObjs 28 }
--
-- tnOamMRInfoRespIfEntry OBJECT-TYPE
--     SYNTAX      TnOamMRInfoRespIfEntry
--     MAX-ACCESS  not-accessible
--     STATUS      current
--     DESCRIPTION
--         "Defines an entry in the tnOamMRInfoRespIfTable.  The first index
--          element, tnOamPingCtlOwnerIndex, is of type SnmpAdminString,
--          a textual convention that allows for use of the SNMPv3
--          View-Based Access Control Model (RFC 2575 [11], VACM)
--          and allows a management application to identify its entries.
--          The second index, tnOamPingCtlTestIndex, enables the same
--          management application to have multiple outstanding requests."
--     INDEX {
--              tnOamPingCtlOwnerIndex,
--              tnOamPingCtlTestIndex,
--              tnOamPingResultsTestRunIndex,
--              tnOamPingHistoryIndex,
--              tnOamMRInfoRespIfIndex
--           }
--     ::= { tnOamMRInfoRespIfTable 1 }
--
-- TnOamMRInfoRespIfEntry ::=
--     SEQUENCE {
--         tnOamMRInfoRespIfIndex        Unsigned32,
--         tnOamMRInfoRespIfAddress      IpAddress,
--         tnOamMRInfoRespIfMetric       Unsigned32,
--         tnOamMRInfoRespIfThreshold    Unsigned32,
--         tnOamMRInfoRespIfFlags        BITS,
--         tnOamMRInfoRespIfNbrCount     Unsigned32,
--         tnOamMRInfoRespIfAddrType     InetAddressType,
--         tnOamMRInfoRespIfAddr         InetAddress
--     }
--
-- tnOamMRInfoRespIfIndex    OBJECT-TYPE
--     SYNTAX      Unsigned32
--     MAX-ACCESS  not-accessible
--     STATUS      current
--     DESCRIPTION
--         "tnOamMRInfoRespIfIndex is the index into the
--          tnOamMRInfoRespIfTable.  The mrinfo response packet has
--          the router's interfaces on which multicast is enabled.
--          tnOamMRInfoRespIfIndex is used to identify those interfaces."
--     ::= { tnOamMRInfoRespIfEntry 1 }
--
-- tnOamMRInfoRespIfAddress    OBJECT-TYPE
--     SYNTAX      IpAddress
--     MAX-ACCESS  read-only
--     STATUS      obsolete
--     DESCRIPTION
--         "tnOamMRInfoRespIfAddress indicates the interface address on the
--          router responding to the mrinfo request.
--
--          This object was obsoleted in release 4.0 and replaced with
--          InetAddress objects tnOamMRInfoRespIfAddrType and
--          tnOamMRInfoRespIfAddr."
--     ::= { tnOamMRInfoRespIfEntry 2 }
--
-- tnOamMRInfoRespIfMetric    OBJECT-TYPE
--     SYNTAX      Unsigned32
--     MAX-ACCESS  read-only
--     STATUS      current
--     DESCRIPTION
--         "tnOamMRInfoRespIfMetric indicates the metric on the interface."
--     ::= { tnOamMRInfoRespIfEntry 3 }
--
-- tnOamMRInfoRespIfThreshold    OBJECT-TYPE
--     SYNTAX      Unsigned32
--     MAX-ACCESS  read-only
--     STATUS      current
--     DESCRIPTION
--         "tnOamMRInfoRespIfThreshold indicates the threshold on the
--          interface."
--     ::= { tnOamMRInfoRespIfEntry 4 }
--
-- tnOamMRInfoRespIfFlags    OBJECT-TYPE
--     SYNTAX      BITS {
--                     tunnel(0),
--                     srcrt(1),
--                     reserved1(2),
--                     reserved2(3),
--                     down(4),
--                     disabled(5),
--                     querier(6),
--                     leaf(7)
--                 }
--     MAX-ACCESS  read-only
--     STATUS      current
--     DESCRIPTION
--         "tnOamMRInfoRespIfFlags indicates the flags associated with
--          an interface:
--
--          tunnel(0)         Neighbor reached via tunnel
--          srcrt(1)          Tunnel uses IP source routing
--          reserved1(2)      No longer used
--          reserved2(3)      No longer used
--          down(4)           Operational status down
--          disabled(5)       Administrative status down
--          querier(6)        Querier for interface
--          leaf(7)           No downstream neighbors on interface
--         "
--     ::= { tnOamMRInfoRespIfEntry 5 }
--
-- tnOamMRInfoRespIfNbrCount    OBJECT-TYPE
--     SYNTAX      Unsigned32
--     MAX-ACCESS  read-only
--     STATUS      current
--     DESCRIPTION
--         "tnOamMRInfoRespIfNbrCount indicates the number of multicast neighbors
--          on the interface. The neighbors are listed in the
--          tnOamMRInfoRespIfNbrTable."
--     ::= { tnOamMRInfoRespIfEntry 6 }
--
-- tnOamMRInfoRespIfAddrType    OBJECT-TYPE
--     SYNTAX      InetAddressType
--     MAX-ACCESS  read-only
--     STATUS      current
--     DESCRIPTION
--         "tnOamMRInfoRespIfAddrType indicates the Internet address type
--          stored in tnOamMRInfoRespIfAddr."
--     ::= { tnOamMRInfoRespIfEntry 7 }
--
-- tnOamMRInfoRespIfAddr    OBJECT-TYPE
--     SYNTAX      InetAddress (SIZE (0|4|16))
--     MAX-ACCESS  read-only
--     STATUS      current
--     DESCRIPTION
--         "tnOamMRInfoRespIfAddr indicates the Internet address of the
--          interface on the router responding to the mrinfo request."
--     ::= { tnOamMRInfoRespIfEntry 8 }


--
-- Nokia SROS series OAM Multicast Router Information If Neighbor Table
--

-- tnOamMRInfoRespIfNbrTable     OBJECT-TYPE
--     SYNTAX      SEQUENCE OF TnOamMRInfoRespIfNbrEntry
--     MAX-ACCESS  not-accessible
--     STATUS      current
--     DESCRIPTION
--         "Defines the Nokia SROS OAM Multicast Router Information
--          Interface Neighbor Table for providing, via SNMP, the capability of
--          performing Nokia SROS OAM 'mrInfo' test operation. This table
--          contains entries for neighbors on an interface. The results of the
--          mrinfo test are stored in the tnOamPingResultsTable, the
--          tnOamPingHistoryTable, the tnOamMRInfoRespTable,
--          the tnOamMRInfoRespIfTable and the tnOamMRInfoRespIfNbrTable."
--    ::= { tnOamPingObjs 30 }
--
-- tnOamMRInfoRespIfNbrEntry OBJECT-TYPE
--     SYNTAX      TnOamMRInfoRespIfNbrEntry
--     MAX-ACCESS  not-accessible
--     STATUS      current
--     DESCRIPTION
--         "Defines an entry in the tnOamMRInfoRespIfNbrTable.  The first index
--         element, tnOamPingCtlOwnerIndex, is of type SnmpAdminString,
--         a textual convention that allows for use of the SNMPv3
--         View-Based Access Control Model (RFC 2575 [11], VACM)
--         and allows a management application to identify its entries.
--         The second index, tnOamPingCtlTestIndex, enables the same
--         management application to have multiple outstanding requests."
--     INDEX {
--             tnOamPingCtlOwnerIndex,
--             tnOamPingCtlTestIndex,
--             tnOamPingResultsTestRunIndex,
--             tnOamPingHistoryIndex,
--             tnOamMRInfoRespIfIndex,
--             tnOamMRInfoRespIfNbrIndex
--           }
--     ::= { tnOamMRInfoRespIfNbrTable 1 }
--
-- TnOamMRInfoRespIfNbrEntry ::=
--     SEQUENCE {
--        tnOamMRInfoRespIfNbrIndex     Unsigned32,
--        tnOamMRInfoRespIfNbrAddress   IpAddress,
--        tnOamMRInfoRespIfNbrAddrType  InetAddressType,
--        tnOamMRInfoRespIfNbrAddr      InetAddress
--     }
--
-- tnOamMRInfoRespIfNbrIndex    OBJECT-TYPE
--     SYNTAX      Unsigned32
--     MAX-ACCESS  not-accessible
--     STATUS      current
--     DESCRIPTION
--         "tnOamMRInfoRespIfNbrIndex is used to identify the multicast neighbor
--          on the interface tnOamMRInfoRespIfIndex."
--     ::= { tnOamMRInfoRespIfNbrEntry 1 }
--
-- tnOamMRInfoRespIfNbrAddress    OBJECT-TYPE
--     SYNTAX      IpAddress
--     MAX-ACCESS  read-only
--     STATUS      obsolete
--     DESCRIPTION
--         "tnOamMRInfoRespIfNbrAddress indicates the address of the neighbor
--          on the interface.
--
--          This object was obsoleted in release 4.0 and replaced with
--          InetAddress objects tnOamMRInfoRespIfNbrAddrType and
--          tnOamMRInfoRespIfNbrAddr."
--     ::= { tnOamMRInfoRespIfNbrEntry 2 }
--
-- tnOamMRInfoRespIfNbrAddrType    OBJECT-TYPE
--     SYNTAX      InetAddressType
--     MAX-ACCESS  read-only
--     STATUS      current
--     DESCRIPTION
--         "tnOamMRInfoRespIfNbrAddrType indicates the Internet address type
--          stored in tnOamMRInfoRespIfNbrAddr."
--     ::= { tnOamMRInfoRespIfNbrEntry 3 }
--
-- tnOamMRInfoRespIfNbrAddr    OBJECT-TYPE
--     SYNTAX      InetAddress (SIZE (0|4|16))
--     MAX-ACCESS  read-only
--     STATUS      current
--     DESCRIPTION
--         "tnOamMRInfoRespIfNbrAddr indicates the Internet address of the
--          neighbor on the interface."
--     ::= { tnOamMRInfoRespIfNbrEntry 4 }


--
--  Nokia SROS series OAM VCCV Ping Control Table
--
--  Sparse Dependent Extension of the tnOamPingCtlTable.
--
--  The same indexes are used for both the base table, tnOamPingCtlTable,
--  and the sparse dependent table, tnOamVccvPingCtlTable.
--
--  This in effect extends the tnOamPingCtlTable with additional columns.
--  Rows are created in the tnOamVccvPingCtlTable only for those entries
--  in the tnOamPingCtlTable where tnOamPingCtlTestMode has a value of
--  'vccvPing'.
--
--  Deletion of a row in the tnOamPingCtlTable results in the
--  deletion of the row in the tnOamVccvPingCtlTable.
--
tnOamVccvPingCtlTable     OBJECT-TYPE
    SYNTAX      SEQUENCE OF TnOamVccvPingCtlEntry
    MAX-ACCESS  not-accessible
    STATUS      current
    DESCRIPTION
        "Defines the Nokia SROS OAM VCCV Ping Control Table for
         providing, via SNMP, the capability of performing Nokia
         SROS OAM 'vccvPing' test operations.
         The results of these tests are stored in the tnOamPingResultsTable
         and the tnOamPingHistoryTable."
   ::= { tnOamPingObjs 32 }

tnOamVccvPingCtlEntry OBJECT-TYPE
    SYNTAX      TnOamVccvPingCtlEntry
    MAX-ACCESS  not-accessible
    STATUS      current
    DESCRIPTION
        "Defines an entry in the tnOamVccvPingCtlTable.  The first index
         element, tnOamPingCtlOwnerIndex, is of type SnmpAdminString,
         a textual convention that allows for use of the SNMPv3
         View-Based Access Control Model (RFC 2575 [11], VACM)
         and allows a management application to identify its entries.
         The second index, tnOamPingCtlTestIndex, enables the same
         management application to have multiple outstanding requests."
    INDEX {
             tnSysSwitchId,
             -- tnOamPingCtlOwnerIndex,
             tnOamPingCtlTestIndex
          }
    ::= { tnOamVccvPingCtlTable 1 }

TnOamVccvPingCtlEntry ::=
    SEQUENCE {
        tnOamVccvPingCtlSdpIdVcId      SdpBindId,
        tnOamVccvPingCtlReplyMode      INTEGER,
        tnOamVccvPingCtlPwId           TmnxVcIdOrNone,
        tnOamVccvPingCtlTtl            Unsigned32,
        tnOamVccvPingCtlSpokeSdpId     TmnxSpokeSdpIdOrZero,
        tnOamVccvPingCtlSaiiGlobalId   TmnxPwGlobalIdOrZero,
        tnOamVccvPingCtlSaiiPrefix     Unsigned32,
        tnOamVccvPingCtlSaiiAcId       Unsigned32,
        tnOamVccvPingCtlTaiiGlobalId   TmnxPwGlobalIdOrZero,
        tnOamVccvPingCtlTaiiPrefix     Unsigned32,
        tnOamVccvPingCtlTaiiAcId       Unsigned32,
        tnOamVccvPingCtlMplsTpGlobalId TmnxMplsTpGlobalID,
        tnOamVccvPingCtlMplsTpNodeId   TmnxMplsTpNodeID,
        tnOamVccvPingCtlTestSubMode    TmnxOamVccvTestSubMode,
        tnOamVccvPingCtlAssocChannel   TmnxOamVccvAssocChannel
    }

tnOamVccvPingCtlSdpIdVcId    OBJECT-TYPE
    SYNTAX      SdpBindId
    MAX-ACCESS  read-create
    STATUS      current
    DESCRIPTION
        "The value of tnOamVccvPingCtlSdpIdVcId specifies the SDP binding of
         the FEC 128 pseudowire to be used when performing a vccv-ping
         operation.  A non-zero value is mandatory when testing a FEC 128
         pseudowire.

         The all-zeros value indicates an unused SDP binding.

         If tnOamVccvPingCtlSdpIdVcId is set to a non-default value, the
         following objects must be default:  tnOamVccvPingCtlSpokeSdpId,
         tnOamVccvPingCtlSaiiGlobalId, tnOamVccvPingCtlSaiiPrefix,
         tnOamVccvPingCtlSaiiAcId, tnOamVccvPingCtlTaiiGlobalId,
         tnOamVccvPingCtlTaiiPrefix, and tnOamVccvPingCtlTaiiAcId.

         If the value of tnOamVccvPingCtlSdpIdVcId is non-zero and invalid, or
         the pseudowire is administratively down, or unavailable, the OAM Echo
         request message probe is not sent and an appropriate error value is
         written to tnOamPingHistoryStatus for that probe entry.  Once the
         interval timer expires, the next probe attempt will be made if
         required."
    DEFVAL { '0000000000000000'h }
    ::= { tnOamVccvPingCtlEntry 1 }

tnOamVccvPingCtlReplyMode OBJECT-TYPE
    SYNTAX          INTEGER {
                        ip(2),
                        controlChannel(4)
                    }
    MAX-ACCESS      read-create
    STATUS          current
    DESCRIPTION
        "The value of tnOamVccvPingCtlReplyMode as specified in
         draft-ietf-mpls-lsp-ping-10.txt sets the method of reply
         due to the vccv-ping request message.

             ip(2)                 out-of-band reply
             controlChannel(4)     inband reply

         This parameter is optional for vccv-ping."
    DEFVAL { controlChannel }
    ::= { tnOamVccvPingCtlEntry 2 }

tnOamVccvPingCtlPwId    OBJECT-TYPE
    SYNTAX          TmnxVcIdOrNone
    MAX-ACCESS      read-create
    STATUS          current
    DESCRIPTION
        "The value of tnOamVccvPingCtlPwId specifies the pseudowire identifier
         to be used when performing a vccv-ping operation on a FEC 128
         pseudowire. The pseudowire Id is a non-zero 32-bit connection ID
         required by FEC 128, as defined in RFC 4379.  This object is only valid
         when used in conjunction with valid tnOamPingCtlTgtAddress and
         tnOamPingCtlSrcAddress.  A value of zero indicates that no pseudowire
         Id has been configured."
    DEFVAL { 0 }
    ::= { tnOamVccvPingCtlEntry 3 }

tnOamVccvPingCtlTtl    OBJECT-TYPE
    SYNTAX      Unsigned32 (1..255)
    UNITS       "time-to-live value"
    MAX-ACCESS  read-create
    STATUS      current
    DESCRIPTION
        "The value of tnOamVccvPingCtlTtl specifies the time-to-live value
         for the vc-label of the echo request message. The outer label TTL is
         still set to the default of 255 regardless of this value."
    DEFVAL { 1 }
    ::= { tnOamVccvPingCtlEntry 4 }

tnOamVccvPingCtlSpokeSdpId     OBJECT-TYPE
    SYNTAX         TmnxSpokeSdpIdOrZero
    MAX-ACCESS     read-create
    STATUS         current
    DESCRIPTION
        "The value of tnOamVccvPingCtlSpokeSdpId specifies the spoke SDP
         identifier to be used when performing a vccv-ping test on a FEC 129
         pseudowire.  This object is optional.

         At most one of tnOamVccvPingCtlSdpIdVcId and
         tnOamVccvPingCtlSpokeSdpId can be set to a non-default value on a
         particular row.

         A value of zero indicates that no spoke SDP identifier has been
         configured."
    DEFVAL { 0 }
    ::= { tnOamVccvPingCtlEntry 5 }

tnOamVccvPingCtlSaiiGlobalId   OBJECT-TYPE
    SYNTAX         TmnxPwGlobalIdOrZero
    MAX-ACCESS     read-create
    STATUS         current
    DESCRIPTION
        "The value of tnOamVccvPingCtlSaiiGlobalId specifies the global
         identifier of the Source Attachment Individual Identifier (SAII)
         to be used when testing a FEC 129 AII Type 2 pseudowire.

         tnOamVccvPingCtlSaiiGlobalId, tnOamVccvPingCtlSaiiPrefix,
         tnOamVccvPingCtlSaiiAcId, tnOamVccvPingCtlTaiiGlobalId,
         tnOamVccvPingCtlTaiiPrefix, and tnOamVccvPingCtlTaiiAcId can be
         used (together) to identify a FEC 129 AII Type 2 pseudowire.

         At most one of tnOamVccvPingCtlSdpIdVcId and
         tnOamVccvPingCtlSaiiGlobalId can be set to a non-default value on a
         particular row.

         A value of zero indicates that no global identifier has been
         configured."
    REFERENCE
        "RFC 5003 Section 3.2"
    DEFVAL { 0 }
    ::= { tnOamVccvPingCtlEntry 6 }

tnOamVccvPingCtlSaiiPrefix     OBJECT-TYPE
    SYNTAX         Unsigned32
    MAX-ACCESS     read-create
    STATUS         current
    DESCRIPTION
        "The value of tnOamVccvPingCtlSaiiPrefix specifies the prefix of the
         Source Attachment Individual Identifier (SAII) to be used when testing
         a FEC 129 AII Type 2 pseudowire.

         At most one of tnOamVccvPingCtlSdpIdVcId and
         tnOamVccvPingCtlSaiiPrefix can be set to a non-default value on a
         particular row.

         A value of zero indicates that no prefix has been configured."
    REFERENCE
        "RFC 5003 Section 3.2"
    DEFVAL { 0 }
    ::= { tnOamVccvPingCtlEntry 7 }

tnOamVccvPingCtlSaiiAcId       OBJECT-TYPE
    SYNTAX         Unsigned32
    MAX-ACCESS     read-create
    STATUS         current
    DESCRIPTION
        "The value of tnOamVccvPingCtlSaiiAcId specifies the attachment
         circuit identifier of the Source Attachment Individual Identifier
         (SAII) to be used when testing a FEC 129 AII Type 2 pseudowire.

         At most one of tnOamVccvPingCtlSdpIdVcId and
         tnOamVccvPingCtlSaiiAcId can be set to a non-default value on a
         particular row.

         A value of zero indicates that no attachment circuit identifier has
         been configured."
    REFERENCE
        "RFC 5003 Section 3.2"
    DEFVAL { 0 }
    ::= { tnOamVccvPingCtlEntry 8 }

tnOamVccvPingCtlTaiiGlobalId   OBJECT-TYPE
    SYNTAX         TmnxPwGlobalIdOrZero
    MAX-ACCESS     read-create
    STATUS         current
    DESCRIPTION
        "The value of tnOamVccvPingCtlTaiiGlobalId specifies the global
         identifier of the Target Attachment Individual Identifier (TAII)
         to be used when testing a FEC 129 AII Type 2 pseudowire.

         At most one of tnOamVccvPingCtlSdpIdVcId and
         tnOamVccvPingCtlTaiiGlobalId can be set to a non-default value on a
         particular row.

         A value of zero indicates that no global identifier has been
         configured."
    REFERENCE
        "RFC 5003 Section 3.2"
    DEFVAL { 0 }
    ::= { tnOamVccvPingCtlEntry 9 }

tnOamVccvPingCtlTaiiPrefix     OBJECT-TYPE
    SYNTAX         Unsigned32
    MAX-ACCESS     read-create
    STATUS         current
    DESCRIPTION
        "The value of tnOamVccvPingCtlTaiiPrefix specifies the prefix of the
         Target Attachment Individual Identifier (TAII) to be used when testing
         a FEC 129 AII Type 2 pseudowire.

         At most one of tnOamVccvPingCtlSdpIdVcId and
         tnOamVccvPingCtlTaiiPrefix can be set to a non-default value on a
         particular row.

         A value of zero indicates that no prefix has been configured."
    REFERENCE
        "RFC 5003 Section 3.2"
    DEFVAL { 0 }
    ::= { tnOamVccvPingCtlEntry 10 }

tnOamVccvPingCtlTaiiAcId       OBJECT-TYPE
    SYNTAX         Unsigned32
    MAX-ACCESS     read-create
    STATUS         current
    DESCRIPTION
        "The value of tnOamVccvPingCtlTaiiAcId specifies the attachment
         circuit identifier of the Target Attachment Individual Identifier
         (TAII) to be used when testing a FEC 129 AII Type 2 pseudowire.

         At most one of tnOamVccvPingCtlSdpIdVcId and
         tnOamVccvPingCtlTaiiAcId can be set to a non-default value on a
         particular row.

         A value of zero indicates that no attachment circuit identifier has
         been configured."
    REFERENCE
        "RFC 5003 Section 3.2"
    DEFVAL { 0 }
    ::= { tnOamVccvPingCtlEntry 11 }

tnOamVccvPingCtlMplsTpGlobalId OBJECT-TYPE
    SYNTAX         TmnxMplsTpGlobalID
    MAX-ACCESS     read-create
    STATUS         current
    DESCRIPTION
        "The value of tnOamVccvPingCtlMplsTpGlobalId specifies the target
         MPLS-TP Global Identifier to be used for the test.

         The supported object combinations for VCCV ping tests are listed in the
         tnOamVccvPingCtlTable DESCRIPTION clause."
    DEFVAL { 0 }
    ::= { tnOamVccvPingCtlEntry 12 }

tnOamVccvPingCtlMplsTpNodeId   OBJECT-TYPE
    SYNTAX         TmnxMplsTpNodeID
    MAX-ACCESS     read-create
    STATUS         current
    DESCRIPTION
        "The value of tnOamVccvPingCtlMplsTpNodeId specifies the target
         MPLS-TP Node Identifier to be used for the test.

         A value of zero indicates that no Node Identifier has been configured.

         The supported object combinations for VCCV ping tests are listed in the
         tnOamVccvPingCtlTable DESCRIPTION clause."
    DEFVAL { 0 }
    ::= { tnOamVccvPingCtlEntry 13 }

tnOamVccvPingCtlTestSubMode    OBJECT-TYPE
    SYNTAX      TmnxOamVccvTestSubMode
    MAX-ACCESS  read-create
    STATUS      current
    DESCRIPTION
        "The value of tnOamVccvPingCtlTestSubMode specifies the type of VCCV
         ping test to perform.

         When this object is 'unspecified(1)', the type of VCCV ping test to be
         performed is determined when the test is started, from the set of
         tnOamVccvPingCtlTable objects configured with non-default values.

         If there is a mismatch between tnOamVccvPingCtlTestSubMode and the
         type of the pseudowire to be tested, the test will fail.  For example,
         if tnOamVccvPingCtlTestSubMode is 'static(2)', and
         tnOamVccvPingCtlSdpIdVcId refers to an SDP binding with
         TIMETRA-SDP-MIB::sdpDelivery not equal to 'mplsTp(3)', the test will
         fail.

         The supported object combinations for VCCV ping tests are listed in the
         tnOamVccvPingCtlTable DESCRIPTION clause."
    DEFVAL { unspecified }
    ::= { tnOamVccvPingCtlEntry 14 }

tnOamVccvPingCtlAssocChannel   OBJECT-TYPE
    SYNTAX      TmnxOamVccvAssocChannel
    MAX-ACCESS  read-create
    STATUS      current
    DESCRIPTION
        "The value of tnOamVccvPingCtlAssocChannel specifies the launched echo
         request's usage of the Associated Channel (ACH) mechanism, when
         performing an MPLS-TP VCCV ping test.

         When tnOamVccvPingCtlTestSubMode is 'static(2)', the default value
         for tnOamVccvPingCtlAssocChannel is 'nonIp(2)'.

         The supported object combinations for VCCV ping tests are listed in the
         tnOamVccvPingCtlTable DESCRIPTION clause."
    DEFVAL { notApplicable }
    ::= { tnOamVccvPingCtlEntry 15 }
--
--  Nokia SROS series OAM ICMP Ping Control Table
--
--  Sparse Dependent Extension of the tnOamPingCtlTable.
--
--  The same indexes are used for both the base table, tnOamPingCtlTable,
--  and the sparse dependent table, tnOamIcmpPingCtlTable.
--
--  This in effect extends the tnOamPingCtlTable with additional columns.
--  Rows are created in the tnOamIcmpPingCtlTable only for those entries
--  in the tnOamPingCtlTable where tnOamPingCtlTestMode has a value of
--  'icmpPing'.
--
--  Deletion of a row in the tnOamPingCtlTable results in the
--  deletion of the row in the tnOamIcmpPingCtlTable.
--
-- tnOamIcmpPingCtlTable     OBJECT-TYPE
--     SYNTAX      SEQUENCE OF TnOamIcmpPingCtlEntry
--     MAX-ACCESS  not-accessible
--     STATUS      current
--     DESCRIPTION
--         "Defines the Nokia SROS OAM ICMP Ping Control Table for
--          providing, via SNMP, the capability of performing Nokia
--          SROS OAM 'icmpPing' test operations.
--
--          The results of these tests are stored in the tnOamPingResultsTable
--          and the tnOamPingHistoryTable."
--    ::= { tnOamPingObjs 34 }
--
-- tnOamIcmpPingCtlEntry OBJECT-TYPE
--     SYNTAX      TnOamIcmpPingCtlEntry
--     MAX-ACCESS  not-accessible
--     STATUS      current
--     DESCRIPTION
--         "Defines an entry in the tnOamIcmpPingCtlTable.  The first index
--          element, tnOamPingCtlOwnerIndex, is of type SnmpAdminString,
--          a textual convention that allows for use of the SNMPv3
--          View-Based Access Control Model (RFC 2575 [11], VACM)
--          and allows a management application to identify its entries.
--          The second index, tnOamPingCtlTestIndex, enables the same
--          management application to have multiple outstanding requests."
--     INDEX {
--              tnOamPingCtlOwnerIndex,
--              tnOamPingCtlTestIndex
--           }
--     ::= { tnOamIcmpPingCtlTable 1 }
--
-- TnOamIcmpPingCtlEntry ::=
--     SEQUENCE {
--         tnOamIcmpPingCtlRapid             TruthValue,
--         tnOamIcmpPingCtlTtl               Unsigned32,
--         tnOamIcmpPingCtlDSField           Unsigned32,
--         tnOamIcmpPingCtlPattern           Integer32,
--         tnOamIcmpPingCtlNhAddrType        InetAddressType,
--         tnOamIcmpPingCtlNhAddress         InetAddress,
--         tnOamIcmpPingCtlEgrIfIndex        InterfaceIndexOrZero,
--         tnOamIcmpPingCtlBypassRouting     TruthValue,
--         tnOamIcmpPingCtlDoNotFragment     TruthValue,
--         tnOamIcmpPingCtlEgrIfName         TNamedItemOrEmpty
--     }
--
-- tnOamIcmpPingCtlRapid    OBJECT-TYPE
--     SYNTAX      TruthValue
--     MAX-ACCESS  read-create
--     STATUS      current
--     DESCRIPTION
--         "The value of tnOamIcmpPingCtlRapid specifies whether or
--          not to send ICMP ping probes in rapid sequence.
--
--          When tnOamIcmpPingCtlRapid has the value 'true', the UNITS
--          value for tnOamPingCtlInterval is changed from 'seconds' to
--          '10 milliseconds'."
--     DEFVAL { false }
--     ::= { tnOamIcmpPingCtlEntry 1 }
--
-- tnOamIcmpPingCtlTtl   OBJECT-TYPE
--     SYNTAX          Unsigned32 (1..128)
--     MAX-ACCESS      read-create
--     STATUS          current
--     DESCRIPTION
--         "The value of tnOamIcmpPingCtlTtl specifies the initial
--          time-to-live value for the ICMP ping packets."
--     DEFVAL { 64 }
--     ::= { tnOamIcmpPingCtlEntry 2 }
--
-- tnOamIcmpPingCtlDSField   OBJECT-TYPE
--     SYNTAX          Unsigned32 (0..255)
--     MAX-ACCESS      read-create
--     STATUS          current
--     DESCRIPTION
--         "The value of tnOamIcmpPingCtlDSField specifies the value to store
--          in the Differentiated Services (DS) Field in the IP packet used
--          to encapsulate the Nokia SROS OAM ping probe.  The DS Field
--          is defined as the Type of Service (TOS) octet in a IPv4 header or
--          as the Traffic Class octet in a IPv6 header.
--
--          The value of this object must be a decimal integer in the range
--          from 0 to 255.  This option can be used to determine what effect
--          an explicit DS Field setting has on a OAM ping response.  Not
--          all values are legal or meaningful.  DS Field usage is often not
--          supported by IP implementations.  A value of 0 means that the
--          function represented by this option is not supported.  Well known
--          TOS octet values are '16' (low delay) and '8' (high throughput)."
--     REFERENCE
--         "Refer to RFC 2474 for the definition of the Differentiated Services
--          Field and to RFC 1812 Section 5.3.2 for Type of Service (TOS)."
--     DEFVAL { 0 }
--     ::= { tnOamIcmpPingCtlEntry 3 }
--
-- tnOamIcmpPingCtlPattern   OBJECT-TYPE
--     SYNTAX      Integer32 (-1|0..65535)
--     MAX-ACCESS  read-create
--     STATUS      current
--     DESCRIPTION
--         "The value of tnOamIcmpPingCtlPattern specifies a pattern to
--          be repeated to fill the data field of the ICMP ping packet.
--          When the value -1 is specified, the data field will be filled
--          with positional values."
--     DEFVAL { -1 }
--     ::= { tnOamIcmpPingCtlEntry 4 }
--
-- tnOamIcmpPingCtlNhAddrType    OBJECT-TYPE
--     SYNTAX      InetAddressType
--     MAX-ACCESS  read-create
--     STATUS      current
--     DESCRIPTION
--         "The value of tnOamIcmpPingCtlNhAddrType specifies the address type
--          of the tnOamIcmpPingCtlNhAddress Internet address."
--     DEFVAL { unknown }
--     ::= { tnOamIcmpPingCtlEntry 5 }
--
-- tnOamIcmpPingCtlNhAddress    OBJECT-TYPE
--     SYNTAX      InetAddress (SIZE (0|4|16))
--     MAX-ACCESS  read-create
--     STATUS      current
--     DESCRIPTION
--         "The value of tnOamIcmpPingCtlNhAddress specifies the Internet
--          address of the next-hop.
--
--          Only one of tnOamIcmpPingCtlNhAddress, tnOamIcmpPingCtlEgrIfIndex,
--          tnOamIcmpPingCtlEgrIfName, or tnOamIcmpPingCtlBypassRouting may be
--          set to a non-default value.  Otherwise, 'inconsistentValue' is
--          returned."
--     DEFVAL { ''H }
--     ::= { tnOamIcmpPingCtlEntry 6 }
--
-- tnOamIcmpPingCtlEgrIfIndex    OBJECT-TYPE
--     SYNTAX      InterfaceIndexOrZero
--     MAX-ACCESS  read-create
--     STATUS      current
--     DESCRIPTION
--         "The value of tnOamIcmpPingCtlEgrIfIndex specifies the ifIndex of the
--          interface to use to transmit the ICMP ping packets.
--
--          If a non-zero value is Set, it must be a known ifIndex.  The value
--          stored is the corresponding interface name string.  When
--          tnOamIcmpPingCtlEgrIfIndex is read, the stored interface name string
--          is converted to an ifIndex (zero, if the interface no longer exists),
--          and the ifIndex is returned.  When tnOamIcmpPingCtlEgrIfName is read,
--          the stored interface name string is returned.
--
--          If zero is Set, the empty string is stored in the interface name
--          string.  When tnOamIcmpPingCtlEgrIfIndex is read, zero is returned.
--          When tnOamIcmpPingCtlEgrIfName is read, the empty string is returned.
--
--          Only one of tnOamIcmpPingCtlNhAddress, tnOamIcmpPingCtlEgrIfIndex,
--          tnOamIcmpPingCtlEgrIfName, or tnOamIcmpPingCtlBypassRouting may be
--          set to a non-default value.  Otherwise, 'inconsistentValue' is
--          returned.
--
--          Managers are encouraged to use tnOamIcmpPingCtlEgrIfName (instead of
--          tnOamIcmpPingCtlEgrIfIndex) because tnOamIcmpPingCtlEgrIfIndex
--          will be deleted in a future release."
--     DEFVAL { 0 }
--     ::= { tnOamIcmpPingCtlEntry 7 }
--
-- tnOamIcmpPingCtlBypassRouting     OBJECT-TYPE
--     SYNTAX      TruthValue
--     MAX-ACCESS  read-create
--     STATUS      current
--     DESCRIPTION
--         "The value of tnOamIcmpPingCtlBypassRouting specifies whether
--          to send the ping request to a host on a directly attached network,
--          bypassing the routing table.
--
--          Only one of tnOamIcmpPingCtlNhAddress, tnOamIcmpPingCtlEgrIfIndex,
--          tnOamIcmpPingCtlEgrIfName, or tnOamIcmpPingCtlBypassRouting may be
--          set to a non-default value.  Otherwise, 'inconsistentValue' is
--          returned."
--     DEFVAL { false }
--     ::= { tnOamIcmpPingCtlEntry 8 }
--
-- tnOamIcmpPingCtlDoNotFragment     OBJECT-TYPE
--     SYNTAX      TruthValue
--     MAX-ACCESS  read-create
--     STATUS      current
--     DESCRIPTION
--         "The value of tnOamIcmpPingCtlDoNotFragment specifies whether or
--          not the 'DF' (Don't Fragment) bit is set in the ICMP ping packet.
--
--          When tnOamIcmpPingCtlDoNotFragment has the value 'false',
--          the 'DF' bit is not set."
--     DEFVAL { false }
--     ::= { tnOamIcmpPingCtlEntry 9 }
--
-- tnOamIcmpPingCtlEgrIfName    OBJECT-TYPE
--     SYNTAX     TNamedItemOrEmpty
--     MAX-ACCESS  read-create
--     STATUS      current
--     DESCRIPTION
--         "The value of tnOamIcmpPingCtlEgrIfName specifies the name of the
--          interface to use to transmit the ICMP ping packets.  The value
--          provided is accepted whether or not it is a known interface name
--          (validation is done as part of executing the test).
--
--          When tnOamIcmpPingCtlEgrIfName is Set, the given interface name
--          string is stored.  When tnOamIcmpPingCtlEgrIfName is read, the
--          interface name string is returned.  When tnOamIcmpPingCtlEgrIfIndex
--          is read, the interface name string is converted to an ifIndex (zero if
--          the interface name string is the empty string, or cannot be converted
--          to an ifIndex), and the ifIndex is returned.
--
--          Only one of tnOamIcmpPingCtlNhAddress, tnOamIcmpPingCtlEgrIfIndex,
--          tnOamIcmpPingCtlEgrIfName, or tnOamIcmpPingCtlBypassRouting may be
--          set to a non-default value.  Otherwise, 'inconsistentValue' is
--          returned."
--     DEFVAL { ''H }  -- -- empty string
--     ::= { tnOamIcmpPingCtlEntry 10 }


--  Nokia SROS series OAM ANCP Control Table
--
--  Sparse Dependent Extension of the tnOamPingCtlTable.
--
--  The same indexes are used for both the base table, tnOamPingCtlTable,
--  and the sparse dependent table, tnOamAncpTestCtlTable.
--
--  This in effect extends the tnOamPingCtlTable with additional columns.
--  Rows are created in the tnOamAncpTestCtlTable only for those entries
--  in the tnOamPingCtlTable where tnOamPingCtlTestMode has a value of
--  'ancpLoopback'.
--
--  Deletion of a row in the tnOamPingCtlTable results in the
--  deletion of the row in the tnOamAncpTestCtlTable.
--
-- tnOamAncpTestCtlTable     OBJECT-TYPE
--     SYNTAX      SEQUENCE OF TnOamAncpTestCtlEntry
--     MAX-ACCESS  not-accessible
--     STATUS      current
--     DESCRIPTION
--         "Defines the Nokia SROS OAM ANCP Control Table for providing,
--          via SNMP, the capability of performing Nokia SROS OAM
--          'ANCP loopback' test operations.
--          The results of these tests are stored in the tnOamPingResultsTable
--          and the tnOamAncpTestHistoryTable.  There will be no entries for
--          these tests in the tnOamPingHistoryTable."
--    ::= { tnOamPingObjs 36 }
--
-- tnOamAncpTestCtlEntry OBJECT-TYPE
--     SYNTAX      TnOamAncpTestCtlEntry
--     MAX-ACCESS  not-accessible
--     STATUS      current
--     DESCRIPTION
--         "Defines an entry in the tnOamAncpTestCtlTable.  The first index
--          element, tnOamPingCtlOwnerIndex, is of type SnmpAdminString,
--          a textual convention that allows for use of the SNMPv3
--          View-Based Access Control Model (RFC 2575 [11], VACM)
--          and allows a management application to identify its entries.
--          The second index, tnOamPingCtlTestIndex, enables the same
--          management application to have multiple outstanding requests."
--     INDEX {
--              tnOamPingCtlOwnerIndex,
--              tnOamPingCtlTestIndex
--           }
--     ::= { tnOamAncpTestCtlTable 1 }
--
-- TnOamAncpTestCtlEntry ::=
--     SEQUENCE {
--         tnOamAncpTestTarget     INTEGER,
--         tnOamAncpTestTargetId   DisplayString,
--         tnOamAncpTestcount      INTEGER,
--         tnOamAncpTestTimeout    INTEGER
--     }
--
-- tnOamAncpTestTarget  OBJECT-TYPE
--     SYNTAX      INTEGER {
--                     none         (0),
--                     subscriberId (1),
--                     ancpString   (2)
--                 }
--     MAX-ACCESS  read-create
--     STATUS      current
--     DESCRIPTION
--         "The object tnOamAncpTestTarget specifies how to interpret the
--          value of the object tnOamAncpTestTargetId.
--          If set to 'subscriberId', the object tnOamAncpTestTargetId
--          is a printable character string which contains the subscriber-id.
--          If set to 'ancpString', the object tnOamAncpTestTargetId
--          is a printable character string which contains the ancp-string.
--          If set to 'none', no value is specified, the object
--          tnOamAncpTestTargetId is an empty string, and no ancp-loopback test
--          can be performed."
--     DEFVAL { none }
--     ::= { tnOamAncpTestCtlEntry 1 }
--
-- tnOamAncpTestTargetId  OBJECT-TYPE
--     SYNTAX      DisplayString (SIZE (0..63))
--     MAX-ACCESS  read-create
--     STATUS      current
--     DESCRIPTION
--         "The object tnOamAncpTestTargetId contains the ID of the subscriber
--          for which the ANCP loopback test must be performed. The content of the
--          field is interpreted as being a subscriber-id of max 32 chars
--          (in case the object tnOamAncpTestTarget is set to 'subscriberId'),
--          or as being an acnp-string of max 63 chars (in case the object
--          tnOamAncpTestTarget is set to 'ancpString')."
--     DEFVAL { "" }
--     ::= { tnOamAncpTestCtlEntry 2 }
--
-- tnOamAncpTestcount  OBJECT-TYPE
--     SYNTAX      INTEGER (0 .. 32)
--     MAX-ACCESS  read-create
--     STATUS      current
--     DESCRIPTION
--         "The value of tnOamAncpTestcount specifies the number of messages the
--          access node will use to test the circuit.
--          If set to 0, the number of messages will be determined by the
--          access node. Following settings are allowed:
--          tnOamAncpTestcount   tnOamAncpTestTimeout
--                 0                   0
--                 1..32               0
--                 1..32               1..255
--         "
--     DEFVAL { 0 }
--     ::= { tnOamAncpTestCtlEntry 3 }
--
-- tnOamAncpTestTimeout  OBJECT-TYPE
--     SYNTAX      INTEGER (0 .. 255)
--     UNITS       "seconds"
--     MAX-ACCESS  read-create
--     STATUS      current
--     DESCRIPTION
--         "The value of tnOamAncpTestTimeout specifies the number of seconds
--           the controlling node will wait for a reply. This timeout value
--           is also sent to the access node. If set to 0, the access node will
--           pick a default value, while the control node will assume a value
--           of 255 seconds.
--
--           Following settings are allowed:
--           tnOamAncpTestcount   tnOamAncpTestTimeout
--                 0                   0
--                 1..32               0
--                 1..32               1..255
--         "
--     DEFVAL { 0 }
--     ::= { tnOamAncpTestCtlEntry 4 }

--
-- Nokia SROS series OAM ANCP History Table
--
-- tnOamAncpTestHistoryTable  OBJECT-TYPE
--     SYNTAX      SEQUENCE OF TnOamAncpTestHistoryEntry
--     MAX-ACCESS  not-accessible
--     STATUS      current
--     DESCRIPTION
--         "Defines a table for storing the results of an OAM ANCP test.
--          The number of entries in this table for a test is limited
--          to the results of 3 runs.
--
--          An entry in this table is created when the result of an OAM
--          ANCP test is determined.  An entry  is removed from this table when
--          its corresponding tnOamPingCtlEntry is deleted."
--    ::= { tnOamPingObjs 38 }
--
-- tnOamAncpTestHistoryEntry  OBJECT-TYPE
--     SYNTAX      TnOamAncpTestHistoryEntry
--     MAX-ACCESS  not-accessible
--     STATUS      current
--     DESCRIPTION
--         "Defines an entry in the tnOamAncpTestHistoryTable. The first two
--          index elements identify the tnOamPingCtlEntry that a
--          tnOamAncpTestHistoryTable belongs to. The third index identifies
--          a specific run of the OAM test. The fourth index element selects a
--          single OAM ANCP test result."
--     INDEX {
--              tnOamPingCtlOwnerIndex,
--              tnOamPingCtlTestIndex,
--              tnOamPingResultsTestRunIndex,
--              tnOamAncpHistoryIndex
--            }
--     ::= { tnOamAncpTestHistoryTable 1 }
--
-- TnOamAncpTestHistoryEntry ::=
--     SEQUENCE {
--         tnOamAncpHistoryIndex         Unsigned32,
--         tnOamAncpHistoryAncpString    DisplayString,
--         tnOamAncpHistoryAccNodeCode   Unsigned32,
--         tnOamAncpHistoryAccNodeResult Unsigned32,
--         tnOamAncpHistoryAccNodeRspStr DisplayString
--     }
--
-- tnOamAncpHistoryIndex OBJECT-TYPE
--     SYNTAX      Unsigned32 (1..4294967295)
--     MAX-ACCESS  not-accessible
--     STATUS      current
--     DESCRIPTION
--         "An entry in this table is created when the result of a OAM
--          ANCP test is determined. The initial 2 instance
--          identifier index values identify the tnOamPingCtlEntry
--          that This ANCP test result belongs
--          to.  The tnOamAncpHistoryIndex element selects a single OAM
--          probe result.
--
--          The agent starts assigning tnOamAncpHistoryIndex values at 1
--          and wraps after exceeding the maximum possible value as defined by
--          the limit of this object ('ffffffff'h)."
--     ::= { tnOamAncpTestHistoryEntry 1 }
--
-- tnOamAncpHistoryAncpString  OBJECT-TYPE
--     SYNTAX      DisplayString (SIZE (0..63))
--     MAX-ACCESS  read-only
--     STATUS      current
--     DESCRIPTION
--         "The object tnOamAncpHistoryAncpString indicates the value of the
--          ancp-string used while running this ANCP test."
--     ::= { tnOamAncpTestHistoryEntry 2 }
--
-- tnOamAncpHistoryAccNodeCode  OBJECT-TYPE
--     SYNTAX      Unsigned32
--     MAX-ACCESS  read-only
--     STATUS      current
--     DESCRIPTION
--         "The object tnOamAncpHistoryAccNodeCode indicates, if different
--          from 0, the return code received from the ANCP access node.
--          The value of this field corresponds to the errorcodes defined in the
--          draft-wadhwa-gsmp-l2control-configuration-01:
--          - 0x500 Specified access line does not exist
--          - 0x501 Loopback test timed out
--          - 0x502 Reserved
--          - 0x503 DSL line status showtime
--          - 0x504 DSL line status idle
--          - 0x505 DSL line status silent
--          - 0x506 DSL line status training
--          - 0x507 DSL line integrity error
--          - 0x508 DSLAM resource not available
--          - 0x509 Invalid test parameter"
--     ::= { tnOamAncpTestHistoryEntry 3 }
--
-- tnOamAncpHistoryAccNodeResult  OBJECT-TYPE
--     SYNTAX      Unsigned32
--     MAX-ACCESS  read-only
--     STATUS      current
--     DESCRIPTION
--         "The object tnOamAncpHistoryAccNodeResult indicates, if different
--          from 0, the return result received from the ANCP access node.
--          The value of this field corresponds to the result codes defined in the
--          draft-wadhwa-gsmp-l2control-configuration-01:
--          {
--          - 1: NoSuccessAck
--          - 2: AckAll
--          - 3: Success
--          - 4: Failure
--          - 5: More
--          - 6: ReturnReceipt
--          }"
--     ::= { tnOamAncpTestHistoryEntry 4 }
--
-- tnOamAncpHistoryAccNodeRspStr  OBJECT-TYPE
--     SYNTAX      DisplayString
--     MAX-ACCESS  read-only
--     STATUS      current
--     DESCRIPTION
--         "The object tnOamAncpHistoryAccNodeRspStr indicates, if different
--          from the empty string, the OAM-loopback-Test-Response-String received
--          from the access node, as reply to the requested test."
--     ::= { tnOamAncpTestHistoryEntry 5 }


--
--  Nokia SROS series OAM LSP P2MP Ping Control Table
--
--
--  Sparse Dependent Extension of the tnOamPingCtlTable.
--
--  The same indexes are used for both the base table, tnOamPingCtlTable,
--  and the sparse dependent table, tnOamP2mpLspPingCtlTable.
--
--  This in effect extends the tnOamPingCtlTable with additional columns.
--  Rows are created in the tnOamP2mpLspPingCtlTable only for those entries
--  in the tnOamPingCtlTable where tnOamPingCtlTestMode has a value of
--  'p2mpLspPing'.
--
--  Deletion of a row in the tnOamPingCtlTable results in the
--  same fate for the row in the tnOamP2mpLspPingCtlTable.
--
-- tnOamP2mpLspPingCtlTable     OBJECT-TYPE
--     SYNTAX      SEQUENCE OF TnOamP2mpLspPingCtlEntry
--     MAX-ACCESS  not-accessible
--     STATUS      current
--     DESCRIPTION
--         "Defines the Nokia SROS OAM P2MP LSP ping Control Table for
--          providing, via SNMP, the capability of performing Nokia
--          SROS OAM 'p2mpLspPing' test operations.  The results of these
--          tests are stored in the tnOamPingResultsTable and the
--          tnOamPingHistoryTable. OAM 'p2mpLspPing' test operation is
--          based on IETF draft-ietf-mpls-p2mp-lsp-ping-06"
--     ::= { tnOamPingObjs 40 }
--
-- tnOamP2mpLspPingCtlEntry OBJECT-TYPE
--     SYNTAX      TnOamP2mpLspPingCtlEntry
--     MAX-ACCESS  not-accessible
--     STATUS      current
--     DESCRIPTION
--         "Defines an entry in the tnOamP2mpLspPingCtlTable.  The first index
--          element, tnOamPingCtlOwnerIndex, is of type SnmpAdminString,
--          a textual convention that allows for use of the SNMPv3
--          View-Based Access Control Model (RFC 2575 [11], VACM)
--          and allows a management application to identify its entries.
--          The second index, tnOamPingCtlTestIndex, enables the same
--          management application to have multiple outstanding requests."
--     INDEX {
--              tnOamPingCtlOwnerIndex,
--              tnOamPingCtlTestIndex
--           }
--     ::= { tnOamP2mpLspPingCtlTable 1 }
--
-- TnOamP2mpLspPingCtlEntry ::=
--     SEQUENCE {
--         tnOamP2mpLspPingCtlLspName         TLNamedItemOrEmpty,
--         tnOamP2mpLspPingCtlInstName        TNamedItemOrEmpty,
--         tnOamP2mpLspPingCtlTtl             Unsigned32,
--         tnOamP2mpLspPingCtlP2MPId          Unsigned32,
--         tnOamP2mpLspPingCtlSrcAddrType     InetAddressType,
--         tnOamP2mpLspPingCtlSrcAddr         InetAddress,
--         tnOamP2mpLspPingCtlGrpAddrType     InetAddressType,
--         tnOamP2mpLspPingCtlGrpAddr         InetAddress
--     }
--
-- tnOamP2mpLspPingCtlLspName     OBJECT-TYPE
--     SYNTAX      TLNamedItemOrEmpty
--     MAX-ACCESS  read-write
--     STATUS      current
--     DESCRIPTION
--         "The value of tnOamP2mpLspPingCtlLspName specifies the administrative
--          name of the target RSVP P2MP Labeled Switch Path (LSP) for this
--          OAM P2MP LSP Ping test. The LSP name must be unique within the base
--          router instance.
--
--          The objects tnOamP2mpLspPingCtlLspName and
--          tnOamP2mpLspPingCtlP2MPId are mutually exclusive.
--
--          An 'inconsistentValue' error is returned when attempting to set
--          the value of the tnOamP2mpLspPingCtlLspName object to a non default
--          value while the value of the tnOamP2mpLspPingCtlP2MPId object is
--          already set to non default value.
--
--          An 'inconsistentValue' error is returned when the value of
--          tnOamPingCtlAdminStatus is set to 'enabled' if both the value of
--          tnOamP2mpLspPingCtlLspName and the value of
--          tnOamP2mpLspPingCtlP2MPId objects are set to default values."
--     DEFVAL { ''H }  -- -- the empty string
--     ::= { tnOamP2mpLspPingCtlEntry 1 }
--
-- tnOamP2mpLspPingCtlInstName       OBJECT-TYPE
--     SYNTAX      TNamedItemOrEmpty
--     MAX-ACCESS  read-write
--     STATUS      current
--     DESCRIPTION
--         "This parameter identifies an instance of a P2MP LSP, either a primary
--          or secondary instance of a RSVP P2MP LSP Tree."
--     DEFVAL { ''H }  -- -- the empty string
--     ::= { tnOamP2mpLspPingCtlEntry 2 }
--
-- tnOamP2mpLspPingCtlTtl       OBJECT-TYPE
--     SYNTAX      Unsigned32 (1..255)
--     UNITS       "time-to-live value"
--     MAX-ACCESS  read-write
--     STATUS      current
--     DESCRIPTION
--         "Specifies the outermost label time-to-live value.  This is an optional
--          parameter for RSVP P2MP LSP. This parameter is not applicable for LDP
--          P2MP LSP"
--     DEFVAL { 255 }
--     ::= { tnOamP2mpLspPingCtlEntry 3 }
--
-- tnOamP2mpLspPingCtlP2MPId     OBJECT-TYPE
--     SYNTAX      Unsigned32 (0 | 1..4294967295)
--     MAX-ACCESS  read-write
--     STATUS      current
--     DESCRIPTION
--         "The value of tnOamP2mpLspPingCtlP2MPId specifies the identifier
--          of a Point to Multipoint (LDP P2MP) Label Switch Path (LSP) for this
--          OAM P2MP LSP ping test.
--
--          The objects tnOamP2mpLspPingCtlP2MPId  and
--          tnOamP2mpLspPingCtlLspName are mutually exclusive.
--
--          An 'inconsistentValue' error is returned when attempting to set
--          the value of the tnOamP2mpLspPingCtlP2MPId object to a non default
--          value while the value of the tnOamP2mpLspPingCtlLspName object is
--          already set to non default value.
--
--          An 'inconsistentValue' error is returned when the value of
--          tnOamPingCtlAdminStatus is set to 'enabled' if both the value of
--          tnOamP2mpLspPingCtlP2MPId and the value of
--          tnOamP2mpLspPingCtlLspName objects are set to default values."
--     DEFVAL { 0 }  -- -- invalid P2mp-Id
--     ::= { tnOamP2mpLspPingCtlEntry 4 }
--
-- tnOamP2mpLspPingCtlSrcAddrType       OBJECT-TYPE
--     SYNTAX      InetAddressType
--     MAX-ACCESS  read-write
--     STATUS      current
--     DESCRIPTION
--         "The value of tnOamP2mpLspPingCtlSrcAddrType specifies the address
--          type of tnOamP2mpLspPingCtlSrcAddr.
--
--          When tnOamPingCtlAdminStatus is to set to 'enable', objects
--          tnOamP2mpLspPingCtlSrcAddrType, tnOamP2mpLspPingCtlSrcAddr,
--          tnOamP2mpLspPingCtlGrpAddrType, and tnOamP2mpLspPingCtlGrpAddr
--          should all have default values or should all have non-default values."
--     DEFVAL { unknown }
--     ::= { tnOamP2mpLspPingCtlEntry 5 }
--
-- tnOamP2mpLspPingCtlSrcAddr       OBJECT-TYPE
--     SYNTAX      InetAddress (SIZE(0|4|16))
--     MAX-ACCESS  read-write
--     STATUS      current
--     DESCRIPTION
--         "The value of tnOamP2mpLspPingCtlSrcAddr specifies the source address
--          of a Point to Multipoint (LDP P2MP) Label Switch Path (LSP) for this
--          OAM P2MP LSP ping test. This IP address must be valid unicast address.
--
--          The objects tnOamP2mpLspPingCtlSrcAddr and tnOamP2mpLspPingCtlP2MPId
--          are mutually exclusive.
--
--          When tnOamPingCtlAdminStatus is to set to 'enable', objects
--          tnOamP2mpLspPingCtlSrcAddrType, tnOamP2mpLspPingCtlSrcAddr,
--          tnOamP2mpLspPingCtlGrpAddrType, and tnOamP2mpLspPingCtlGrpAddr
--          should all have default values or should all have non-default values."
--     DEFVAL { ''H }
--     ::= { tnOamP2mpLspPingCtlEntry 6 }
--
-- tnOamP2mpLspPingCtlGrpAddrType       OBJECT-TYPE
--     SYNTAX      InetAddressType
--     MAX-ACCESS  read-write
--     STATUS      current
--     DESCRIPTION
--         "The value of tnOamP2mpLspPingCtlGrpAddrType specifies the address
--          type of tnOamP2mpLspPingCtlGrpAddr.
--
--          When tnOamPingCtlAdminStatus is to set to 'enable', objects
--          tnOamP2mpLspPingCtlSrcAddrType, tnOamP2mpLspPingCtlSrcAddr,
--          tnOamP2mpLspPingCtlGrpAddrType, and tnOamP2mpLspPingCtlGrpAddr
--          should all have default values or should all have non-default values."
--     DEFVAL { unknown }
--     ::= { tnOamP2mpLspPingCtlEntry 7 }
--
-- tnOamP2mpLspPingCtlGrpAddr       OBJECT-TYPE
--     SYNTAX      InetAddress (SIZE(0|4|16))
--     MAX-ACCESS  read-write
--     STATUS      current
--     DESCRIPTION
--         "The value of tnOamP2mpLspPingCtlGrpAddr specifies the group address
--          of a Point to Multipoint (LDP P2MP) Label Switch Path (LSP) for this
--          OAM P2MP LSP ping test. This IP address must be valid multicast
--          address.
--
--          The objects tnOamP2mpLspPingCtlGrpAddr and
--          tnOamP2mpLspPingCtlP2MPId are mutually exclusive.
--
--          When tnOamPingCtlAdminStatus is to set to 'enable', objects
--          tnOamP2mpLspPingCtlSrcAddrType, tnOamP2mpLspPingCtlSrcAddr,
--          tnOamP2mpLspPingCtlGrpAddrType, and tnOamP2mpLspPingCtlGrpAddr
--          should all have default values or should all have non-default values."
--     DEFVAL { ''H }
--     ::= { tnOamP2mpLspPingCtlEntry 8 }

--
--  Nokia SROS series OAM LSP P2MP Ping IP Address Control Table
--
--
--  Dependent Extension of the tnOamP2mpLspPingCtlTable.
--
--  The first two indexes are used for both the base table,
--  tnOamP2mpLspPingCtlTable, and the dependent table,
--  tnOamP2mpLspPingIPAddressTable.
--
--  Deletion of a row in the tnOamP2mpLspPingCtlTable results in the
--  same fate for all the rows in the tnOamP2mpLspPingIPAddressTable
--  using the same indices.
--
-- tnOamP2mpLspPingIPAddressTable OBJECT-TYPE
--     SYNTAX      SEQUENCE OF TnOamP2mpLspPingIPAddressEntry
--     MAX-ACCESS  not-accessible
--     STATUS      current
--     DESCRIPTION
--         "Defines the Nokia SROS OAM P2MP LSP ping IP Address Table for
--          providing, via SNMP, the capability of performing Nokia
--          SROS OAM 'p2mpLspPing' test operations.
--
--          This table provides the ability to add multiple IP Address
--          destinations for the 'p2mpLspPing' test.
--
--          The results of these tests are stored in the tnOamPingResultsTable
--          and the tnOamPingHistoryTable."
--     ::= { tnOamPingObjs 42 }
--
-- tnOamP2mpLspPingIPAddressEntry OBJECT-TYPE
--     SYNTAX      TnOamP2mpLspPingIPAddressEntry
--     MAX-ACCESS  not-accessible
--     STATUS      current
--     DESCRIPTION
--         "Defines an entry in the tnOamP2mpLspPingIPAddressTable.
--          The first index element, tnOamPingCtlOwnerIndex, is of type
--          SnmpAdminString, a textual convention that allows for use of
--          the SNMPv3 View-Based Access Control Model (RFC 2575 [11], VACM)
--          and allows a management application to identify its entries.
--          The second index, tnOamPingCtlTestIndex, enables the same
--          management application to have multiple outstanding requests.
--          The third and fourth index, tnOamP2mpLspPingCtlIpAddrType and
--          tnOamP2mpLspPingCtlIpAddr enables the same management application
--          to have multiple IP address destinations."
--     INDEX {
--              tnOamPingCtlOwnerIndex,
--              tnOamPingCtlTestIndex,
--              tnOamP2mpLspPingCtlIpAddrIndex
--           }
--     ::= { tnOamP2mpLspPingIPAddressTable 1 }
--
-- TnOamP2mpLspPingIPAddressEntry ::= SEQUENCE {
--              tnOamP2mpLspPingCtlIpAddrIndex  Unsigned32,
--              tnOamP2mpLspPingCtlIpRowStatus  RowStatus,
--              tnOamP2mpLspPingCtlIpAddrType   InetAddressType,
--              tnOamP2mpLspPingCtlIpAddr       InetAddress
--     }
--
-- tnOamP2mpLspPingCtlIpAddrIndex OBJECT-TYPE
--     SYNTAX      Unsigned32 (1..5)
--     MAX-ACCESS  not-accessible
--     STATUS      current
--     DESCRIPTION
--         "The object tnOamP2mpLspPingCtlIpAddrIndex specifies the numerical
--          row-order in the table."
--     ::= { tnOamP2mpLspPingIPAddressEntry 1 }
--
-- tnOamP2mpLspPingCtlIpRowStatus OBJECT-TYPE
--     SYNTAX      RowStatus
--     MAX-ACCESS  read-create
--     STATUS      current
--     DESCRIPTION
--         "The object tnOamP2mpLspPingCtlIpRowStatus allows for the creation
--          and deletion of rows in the tnOamP2mpLspPingIPAddressTable."
--     ::= { tnOamP2mpLspPingIPAddressEntry 2 }
--
-- tnOamP2mpLspPingCtlIpAddrType  OBJECT-TYPE
--     SYNTAX      InetAddressType
--     MAX-ACCESS  read-create
--     STATUS      current
--     DESCRIPTION
--         "The value of tnOamP2mpLspPingCtlIpAddrType specifies the type
--          of Internet address stored in tnOamP2mpLspPingCtlIpAddr."
--     ::= { tnOamP2mpLspPingIPAddressEntry 3 }
--
-- tnOamP2mpLspPingCtlIpAddr      OBJECT-TYPE
--     SYNTAX      InetAddress (SIZE (0|4|16))
--     MAX-ACCESS  read-create
--     STATUS      current
--     DESCRIPTION
--         "The value of tnOamP2mpLspPingCtlIpAddr specifies a remote Internet
--          address to send P2MP LSP Ping packets for a particular test."
--     ::= { tnOamP2mpLspPingIPAddressEntry 4 }

--
--  Nokia SROS series OAM Ethernet Connectivity Fault Management Ping
--  Control Table
--
tnOamEthCfmPingCtlTable OBJECT-TYPE
    SYNTAX      SEQUENCE OF TnOamEthCfmPingCtlEntry
    MAX-ACCESS  not-accessible
    STATUS      current
    DESCRIPTION
        "tnOamEthCfmPingCtlTable contains Ethernet CFM-specific configuration
         information for 'ethCfmLoopback', 'ethCfmTwoWayDelay', 'ethCfmOneWayDelay',
         'ethCfmTwoWaySlm' and 'ethCfmTwoWayLm' tests.

         This table extends the tnOamPingCtlTable.  A row is automatically
         created in this table when a row is created in tnOamPingCtlTable with
         tnOamPingCtlTestMode set to 'ethCfmLoopback', 'ethCfmTwoWayDelay', 'ethCfmOneWayDelay',
         'ethCfmTwoWaySlm', or 'ethCfmTwoWayLm'.  Deleting a row in tnOamPingCtlTable automatically
         deletes the row (if any) with the same index values in
         tnOamEthCfmPingCtlTable.

         Test results are stored in tnOamPingResultsTable and
         tnOamPingHistoryTable."
    ::= { tnOamPingObjs 44 }

tnOamEthCfmPingCtlEntry OBJECT-TYPE
    SYNTAX      TnOamEthCfmPingCtlEntry
    MAX-ACCESS  not-accessible
    STATUS      current
    DESCRIPTION
        "tnOamEthCfmPingCtlEntry defines an entry in the
         tnOamEthCfmPingCtlTable.  Each index is an object in
         tnOamPingCtlTable."
    AUGMENTS        { tnOamPingCtlEntry }
    ::= { tnOamEthCfmPingCtlTable 1 }

TnOamEthCfmPingCtlEntry ::= SEQUENCE {
          tnOamEthCfmPingCtlTgtMacAddr    MacAddress,
          tnOamEthCfmPingCtlSrcMdIndex    Unsigned32,
          tnOamEthCfmPingCtlSrcMaIndex    Unsigned32,
          tnOamEthCfmPingCtlSrcMepId      Dot1agCfmMepIdOrZero
    }

tnOamEthCfmPingCtlTgtMacAddr OBJECT-TYPE
    SYNTAX      MacAddress
    MAX-ACCESS  read-create
    STATUS      current
    DESCRIPTION
       "The value of tnOamEthCfmPingCtlTgtMacAddr specifies the target MAC
        address for the test."
    DEFVAL { '000000000000'H }  -- 00:00:00:00:00:00
    ::= { tnOamEthCfmPingCtlEntry 1 }

tnOamEthCfmPingCtlSrcMdIndex OBJECT-TYPE
    SYNTAX      Unsigned32
    MAX-ACCESS  read-create
    STATUS      current
    DESCRIPTION
        "The value of tnOamEthCfmPingCtlSrcMdIndex specifies the source CFM
         maintenance domain index for the test.  Zero is the null CFM
         maintenance domain index."
    DEFVAL { 0 }
    ::= { tnOamEthCfmPingCtlEntry 2 }

tnOamEthCfmPingCtlSrcMaIndex OBJECT-TYPE
    SYNTAX      Unsigned32
    MAX-ACCESS  read-create
    STATUS      current
    DESCRIPTION
        "The value of tnOamEthCfmPingCtlSrcMaIndex specifies the source CFM
         maintenance association index for the test.  Zero is the null CFM
         maintenance association index."
    DEFVAL { 0 }
    ::= { tnOamEthCfmPingCtlEntry 3 }

tnOamEthCfmPingCtlSrcMepId OBJECT-TYPE
    SYNTAX      Dot1agCfmMepIdOrZero
    MAX-ACCESS  read-create
    STATUS      current
    DESCRIPTION
        "The value of tnOamEthCfmPingCtlSrcMepId specifies the source
         Maintenance association End Point Identifier (MEP ID) for the test.
         Zero is the null MEP ID."
    DEFVAL { 0 }
    ::= { tnOamEthCfmPingCtlEntry 4 }

--
-- Notification Definition section
--
--
-- tnOamPingProbeFailed NOTIFICATION-TYPE
--     OBJECTS {
--       tnOamPingCtlTargetAddressType,
--       tnOamPingCtlTargetAddress,
--        tnOamPingCtlTargetIpAddress,
--        tnOamPingResultsOperStatus,
--        tnOamPingResultsMinRtt,
--        tnOamPingResultsMaxRtt,
--        tnOamPingResultsAverageRtt,
--        tnOamPingResultsRttSumOfSquares,
--        tnOamPingResultsMtuResponseSize,
--        tnOamPingResultsSvcPing,
--        tnOamPingResultsProbeResponses,
--        tnOamPingResultsSentProbes,
--        tnOamPingResultsLastGoodProbe
--     }
--     STATUS  obsolete
--     DESCRIPTION
--         "Generated when a probe failure is detected when the
--          corresponding tnOamPingCtlTrapGeneration object is set to
--          probeFailure(0) subject to the value of
--          tnOamPingCtlTrapProbeFailureFilter.  The object
--          tnOamPingCtlTrapProbeFailureFilter can be used to specify the
--          number of successive probe failures that are required
--          before this notification can be generated."
--     ::= { tnOamPingNotifications 1 }
--
-- tnOamPingTestFailed NOTIFICATION-TYPE
--     OBJECTS {
--       tnOamPingCtlTargetAddressType,
--       tnOamPingCtlTargetAddress,
--         tnOamPingCtlTargetIpAddress,
--         tnOamPingResultsOperStatus,
--         tnOamPingResultsMinRtt,
--         tnOamPingResultsMaxRtt,
--         tnOamPingResultsAverageRtt,
--         tnOamPingResultsRttSumOfSquares,
--         tnOamPingResultsMtuResponseSize,
--         tnOamPingResultsSvcPing,
--         tnOamPingResultsProbeResponses,
--         tnOamPingResultsSentProbes,
--         tnOamPingResultsLastGoodProbe
--       }
--     STATUS  obsolete
--     DESCRIPTION
--         "Generated when a ping test is determined to have failed
--          when the corresponding tnOamPingCtlTrapGeneration object is
--          set to testFailure(1).  In this instance
--          tnOamPingCtlTrapTestFailureFilter should specify the number of
--          probes in a test required to have failed in order to
--          consider the test as failed."
--     ::= { tnOamPingNotifications 2 }
--
-- tnOamPingTestCompleted NOTIFICATION-TYPE
--     OBJECTS {
--       tnOamPingCtlTargetAddressType,
--       tnOamPingCtlTargetAddress,
--      tnOamPingCtlTargetIpAddress,
--      tnOamPingResultsOperStatus,
--      tnOamPingResultsMinRtt,
--      tnOamPingResultsMaxRtt,
--      tnOamPingResultsAverageRtt,
--      tnOamPingResultsRttSumOfSquares,
--      tnOamPingResultsMtuResponseSize,
--      tnOamPingResultsSvcPing,
--      tnOamPingResultsProbeResponses,
--      tnOamPingResultsSentProbes,
--      tnOamPingResultsLastGoodProbe
--     }
--     STATUS  obsolete
--     DESCRIPTION
--         "Generated at the completion of a ping test when the
--          corresponding tnOamPingCtlTrapGeneration object is set to
--          testCompletion(2)."
--     ::= { tnOamPingNotifications 3 }
--
-- tnOamPingProbeFailedV2 NOTIFICATION-TYPE
--     OBJECTS {
--        tnOamPingCtlTgtAddrType,
--        tnOamPingCtlTgtAddress,
--        tnOamPingResultsOperStatus,
--        tnOamPingResultsMinRtt,
--        tnOamPingResultsMaxRtt,
--        tnOamPingResultsAverageRtt,
--        tnOamPingResultsRttSumOfSquares,
--        tnOamPingResultsMtuResponseSize,
--        tnOamPingResultsSvcPing,
--        tnOamPingResultsProbeResponses,
--        tnOamPingResultsSentProbes,
--        tnOamPingResultsLastGoodProbe
--     }
--     STATUS  obsolete
--     DESCRIPTION
--         "Generated when a probe failure is detected when the
--          corresponding tnOamPingCtlTrapGeneration object is set to
--          probeFailure(0) subject to the value of
--          tnOamPingCtlTrapProbeFailureFilter.  The object
--          tnOamPingCtlTrapProbeFailureFilter can be used to specify the
--          number of successive probe failures that are required
--          before this notification can be generated."
--     ::= { tnOamPingNotifications 4 }
--
-- tnOamPingTestFailedV2 NOTIFICATION-TYPE
--     OBJECTS {
--         tnOamPingCtlTgtAddrType,
--         tnOamPingCtlTgtAddress,
--         tnOamPingResultsOperStatus,
--         tnOamPingResultsMinRtt,
--         tnOamPingResultsMaxRtt,
--         tnOamPingResultsAverageRtt,
--         tnOamPingResultsRttSumOfSquares,
--         tnOamPingResultsMtuResponseSize,
--         tnOamPingResultsSvcPing,
--         tnOamPingResultsProbeResponses,
--         tnOamPingResultsSentProbes,
--         tnOamPingResultsLastGoodProbe
--       }
--     STATUS  obsolete
--     DESCRIPTION
--         "Generated when a ping test is determined to have failed
--          when the corresponding tnOamPingCtlTrapGeneration object is
--          set to testFailure(1).  In this instance
--          tnOamPingCtlTrapTestFailureFilter should specify the number of
--          probes in a test required to have failed in order to
--          consider the test as failed."
--     ::= { tnOamPingNotifications 5 }
--
-- tnOamPingTestCompletedV2 NOTIFICATION-TYPE
--     OBJECTS {
--      tnOamPingCtlTgtAddrType,
--      tnOamPingCtlTgtAddress,
--      tnOamPingResultsOperStatus,
--      tnOamPingResultsMinRtt,
--      tnOamPingResultsMaxRtt,
--      tnOamPingResultsAverageRtt,
--      tnOamPingResultsRttSumOfSquares,
--      tnOamPingResultsMtuResponseSize,
--      tnOamPingResultsSvcPing,
--      tnOamPingResultsProbeResponses,
--      tnOamPingResultsSentProbes,
--      tnOamPingResultsLastGoodProbe
--     }
--     STATUS  obsolete
--     DESCRIPTION
--         "Generated at the completion of a ping test when the
--          corresponding tnOamPingCtlTrapGeneration object is set to
--          testCompletion(2)."
--     ::= { tnOamPingNotifications 6 }
--
-- tnAncpLoopbackTestCompleted NOTIFICATION-TYPE
--    OBJECTS {
--        tnOamAncpHistoryAncpString
--    }
--    STATUS  current
--    DESCRIPTION
--        "This Notification is sent whenever a ANCP loopback
--         is finished for which a notification was explictly requested."
--    ::= { tnOamPingNotifications 7 }
--
-- tnOamPingProbeFailedV3 NOTIFICATION-TYPE
--     OBJECTS {
--        tnOamPingCtlTgtAddrType,
--        tnOamPingCtlTgtAddress,
--        tnOamPingResultsOperStatus,
--        tnOamPingResultsMinRtt,
--        tnOamPingResultsMaxRtt,
--        tnOamPingResultsAverageRtt,
--        tnOamPingResultsRttSumOfSquares,
--        tnOamPingResultsRttOFSumSquares,
--        tnOamPingResultsMtuResponseSize,
--        tnOamPingResultsSvcPing,
--        tnOamPingResultsProbeResponses,
--        tnOamPingResultsSentProbes,
--        tnOamPingResultsLastGoodProbe
--     }
--     STATUS  current
--     DESCRIPTION
--         "Generated when a probe failure is detected when the
--          corresponding tnOamPingCtlTrapGeneration object is set to
--          probeFailure(0) subject to the value of
--          tnOamPingCtlTrapProbeFailureFilter.  The object
--          tnOamPingCtlTrapProbeFailureFilter can be used to specify the
--          number of successive probe failures that are required
--          before this notification can be generated."
--     ::= { tnOamPingNotifications 8 }
--
-- tnOamPingTestFailedV3 NOTIFICATION-TYPE
--     OBJECTS {
--         tnOamPingCtlTgtAddrType,
--         tnOamPingCtlTgtAddress,
--         tnOamPingResultsOperStatus,
--         tnOamPingResultsMinRtt,
--         tnOamPingResultsMaxRtt,
--         tnOamPingResultsAverageRtt,
--         tnOamPingResultsRttSumOfSquares,
--         tnOamPingResultsRttOFSumSquares,
--         tnOamPingResultsMtuResponseSize,
--         tnOamPingResultsSvcPing,
--         tnOamPingResultsProbeResponses,
--         tnOamPingResultsSentProbes,
--         tnOamPingResultsLastGoodProbe
--     }
--     STATUS  current
--     DESCRIPTION
--         "Generated when a ping test is determined to have failed
--          when the corresponding tnOamPingCtlTrapGeneration object is
--          set to testFailure(1).  In this instance
--          tnOamPingCtlTrapTestFailureFilter should specify the number of
--          probes in a test required to have failed in order to
--          consider the test as failed."
--     ::= { tnOamPingNotifications 9 }
--
-- tnOamPingTestCompletedV3 NOTIFICATION-TYPE
--     OBJECTS {
--         tnOamPingCtlTgtAddrType,
--         tnOamPingCtlTgtAddress,
--         tnOamPingResultsOperStatus,
--         tnOamPingResultsMinRtt,
--         tnOamPingResultsMaxRtt,
--         tnOamPingResultsAverageRtt,
--         tnOamPingResultsRttSumOfSquares,
--         tnOamPingResultsRttOFSumSquares,
--         tnOamPingResultsMtuResponseSize,
--         tnOamPingResultsSvcPing,
--         tnOamPingResultsProbeResponses,
--         tnOamPingResultsSentProbes,
--         tnOamPingResultsLastGoodProbe
--     }
--     STATUS  current
--     DESCRIPTION
--         "Generated at the completion of a ping test when the
--          corresponding tnOamPingCtlTrapGeneration object is set to
--          testCompletion(2)."
--     ::= { tnOamPingNotifications 10 }

--
-- Nokia SROS series OAM Trace Route Simple Object Definitions
--
--
-- tnOamTrMaxConcurrentRequests OBJECT-TYPE
--     SYNTAX      Unsigned32
--     UNITS       "requests"
--     MAX-ACCESS  read-write
--     STATUS      current
--     DESCRIPTION
--        "The maximum number of concurrent active trace route requests
--         that are allowed within an agent implementation.  A value
--         of 0 for this object implies that there is no limit for
--         the number of concurrent active requests in effect."
--     DEFVAL { 0 }
--     ::= { tnOamTraceRouteObjs 2 }
--
--
-- Nokia SROS series OAM Traceroute Control Table
--
tnOamTrCtlTable OBJECT-TYPE
    SYNTAX      SEQUENCE OF TnOamTrCtlEntry
    MAX-ACCESS  not-accessible
    STATUS      current
    DESCRIPTION
        "Defines the Nokia SROS OAM Trace Route Control Table for
         providing the capability of invoking OAM trace route tests from
         SNMP.  The results of trace route operations can be stored in
         the tnOamTrResultsTable, tnOamTrProbeHistoryTable, and
         the tnOamTrHopsTable."
   ::= { tnOamTraceRouteObjs 3 }

tnOamTrCtlEntry OBJECT-TYPE
    SYNTAX      TnOamTrCtlEntry
    MAX-ACCESS  not-accessible
    STATUS      current
    DESCRIPTION
        "Defines an entry in the tnOamTrCtlTable.  The first
         index element, tnOamTrCtlOwnerIndex, is of type
         SnmpAdminString, a textual convention that allows for
         use of the SNMPv3 View-Based Access Control Model
         (RFC 2575 [11], VACM) and allows an management
         application to identify its entries.  The second index,
         tnOamTrCtlTestIndex (also an SnmpAdminString),
         enables the same management application to have
         multiple requests outstanding."
    INDEX {
           tnSysSwitchId,
           -- tnOamTrCtlOwnerIndex,
           tnOamTrCtlTestIndex
          }
    ::= { tnOamTrCtlTable 1 }

TnOamTrCtlEntry ::=
    SEQUENCE {
     -- tnOamTrCtlOwnerIndex         SnmpAdminString,
     tnOamTrCtlTestIndex          SnmpAdminString,
     tnOamTrCtlRowStatus          RowStatus,
     tnOamTrCtlStorageType        StorageType,
     tnOamTrCtlDescr              SnmpAdminString,
     tnOamTrCtlTestMode           INTEGER,
     tnOamTrCtlAdminStatus        INTEGER,
     tnOamTrCtlFcName             TFCName,
     tnOamTrCtlProfile            TProfile,
     tnOamTrCtlTargetIpAddress    IpAddress,
     tnOamTrCtlServiceId          TmnxServId,
     tnOamTrCtlDataSize           Unsigned32,
     tnOamTrCtlTimeOut            Unsigned32,
     tnOamTrCtlProbesPerHop       Unsigned32,
     tnOamTrCtlMaxTtl             Unsigned32,
     tnOamTrCtlInitialTtl         Unsigned32,
     tnOamTrCtlDSField            Unsigned32,
     tnOamTrCtlMaxFailures        Unsigned32,
     tnOamTrCtlInterval           Unsigned32,
     tnOamTrCtlMaxRows            Unsigned32,
     tnOamTrCtlTrapGeneration     BITS,
     tnOamTrCtlCreateHopsEntries  TruthValue,
     tnOamTrCtlSAA                TruthValue,
     tnOamTrCtlRuns               Counter32,
     tnOamTrCtlFailures           Counter32,
     tnOamTrCtlLastRunResult      TmnxOamTestResult,
     tnOamTrCtlLastChanged        TimeStamp,
     tnOamTrCtlVRtrID             TmnxVRtrID,
     tnOamTrCtlTgtAddrType        InetAddressType,
     tnOamTrCtlTgtAddress         InetAddress,
     tnOamTrCtlSrcAddrType        InetAddressType,
     tnOamTrCtlSrcAddress         InetAddress,
     tnOamTrCtlWaitMilliSec       Unsigned32
    }

-- tnOamTrCtlOwnerIndex OBJECT-TYPE
--     SYNTAX      SnmpAdminString (SIZE(1..32))
--    MAX-ACCESS  not-accessible
--    STATUS      current
--    DESCRIPTION
--       "To facilitate the provisioning of access control by a
--        security administrator using the View-Based Access
--        Control Model (RFC 2575, VACM) for tables in which
--        multiple users may need to independently create or
--        modify entries, the initial index is used as an 'owner
--        index'.  Such an initial index has a syntax of
--        SnmpAdminString, and can thus be trivially mapped to a
--        security name or group name as defined in VACM, in
--        accordance with a security policy.
--
--        When used in conjunction with such a security policy
--        all entries in the table belonging to a particular user
--        (or group) will have the same value for this initial
--        index.  For a given user's entries in a particular
--        table, the object identifiers for the information in
--        these entries will have the same subidentifiers (except
--        for the 'column' subidentifier) up to the end of the
--        encoded owner index. To configure VACM to permit access
--        to this portion of the table, one would create
--        vacmViewTreeFamilyTable entries with the value of
--        vacmViewTreeFamilySubtree including the owner index
--        portion, and vacmViewTreeFamilyMask 'wildcarding' the
--        column subidentifier.  More elaborate configurations
--        are possible."
--    ::= { tnOamTrCtlEntry 1 }

tnOamTrCtlTestIndex OBJECT-TYPE
    SYNTAX      SnmpAdminString (SIZE(1..32))
    MAX-ACCESS  not-accessible
    STATUS      current
    DESCRIPTION
        "The test name index of a Nokia SROS OAM Trace Route test.
         This is locally unique, within the scope of a tnOamTrCtlOwnerIndex."
    ::= { tnOamTrCtlEntry 2 }

tnOamTrCtlRowStatus OBJECT-TYPE
    SYNTAX      RowStatus
    MAX-ACCESS  read-create
    STATUS      current
    DESCRIPTION
        "This object allows entries to be created and deleted
         in the tnOamTrCtlTable.  Deletion of an entry in
         this table results in all corresponding (same
         tnOamTrCtlOwnerIndex and tnOamTrCtlTestIndex
         index values) tnOamTrResultsTable,
         tnOamTrProbeHistoryTable, and tnOamTrHopsTable
         entries being deleted.

         The values for configuration objects required for the type of
         test specified in tnOamTrCtlTestMode MUST be specified
         prior to a transition to active(1) state being
         accepted.

         Activation of an Nokia SROS OAM Trace Route operation is
         controlled via tnOamTrCtlAdminStatus and not
         by transitioning of this object's value to active(1).

         Transitions in and out of active(1) state are not
         allowed while an entry's tnOamTrResultsOperStatus
         is active(1) with the exception that deletion of
         an entry in this table by setting its RowStatus
         object to destroy(6) will stop an active Nokia
         SROS OAM Trace Route operation.

         The operational state of an Nokia SROS OAM Trace Route
         operation can be determined by examination of the corresponding
         tnOamTrResultsOperStatus object."
    REFERENCE
        "See definition of RowStatus in RFC 2579, 'Textual
        Conventions for SMIv2.'"
    ::= { tnOamTrCtlEntry 3 }

tnOamTrCtlStorageType OBJECT-TYPE
    SYNTAX      StorageType
    MAX-ACCESS  read-create
    STATUS      current
    DESCRIPTION
        "The storage type for this conceptual row.
         Conceptual rows having the value 'permanent' need not
         allow write-access to any columnar objects in the row."
    DEFVAL { volatile }
    ::= { tnOamTrCtlEntry 4 }

tnOamTrCtlDescr OBJECT-TYPE
    SYNTAX      SnmpAdminString
    MAX-ACCESS  read-create
    STATUS      current
    DESCRIPTION
        "The purpose of this object is to provide a descriptive name of
         the Nokia SROS OAM Trace Route test."
    DEFVAL { '00'H }
    ::= { tnOamTrCtlEntry 5 }

tnOamTrCtlTestMode     OBJECT-TYPE
    SYNTAX      INTEGER {
                    none (0),
                    macTraceRoute (1),
                    lspTraceRoute (2),
                    vprnTraceRoute (3),
                    mcastTraceRoute (4),
                    icmpTraceRoute (5),
                    ldpTreeTrace (6),
                    vccvTraceRoute (7),
                    p2mpLspTrace (8),
                    ethCfmLinkTrace (9)
                }
    MAX-ACCESS  read-create
    STATUS      current
    DESCRIPTION
        "Specifies the type of Nokia SROS OAM Trace Route test defined
         by this entry.  The configuration parameters unique to a specific
         test type are to be found in a sparsely dependent extension table
         for that test type.

         p2mpLspTrace is supported for non-SAA tests only.
         ethCfmLinkTrace is supported for SAA tests only.

         This is a required parameter."
    DEFVAL { none }
    ::= { tnOamTrCtlEntry 6 }

tnOamTrCtlAdminStatus OBJECT-TYPE
    SYNTAX      INTEGER {
                          enabled(1), -- operation should be started
                          disabled(2) -- operation should be stopped
                        }
    MAX-ACCESS  read-create
    STATUS      current
    DESCRIPTION
        "Reflects the desired state that a tnOamTrCtlEntry
         should be in:
           enabled(1)  - Attempt to activate the test as defined by
                         this tnOamTrCtlEntry.
           disabled(2) - Deactivate the test as defined by this
                         tnOamTrCtlEntry.

         If tnOamTrCtlSAA has the value 'true' and tnOamSaaCtlAdminStatus
         has the value 'outOfService', an attempt to set this object to
         'enabled' will fail with an inconsistentValue error.

         Refer to the corresponding tnOamTrResultsOperStatus to
         determine the operational state of the test defined by
         this entry."
     DEFVAL { disabled }
    ::= { tnOamTrCtlEntry 7 }

tnOamTrCtlFcName       OBJECT-TYPE
    SYNTAX      TFCName
    MAX-ACCESS  read-create
    STATUS      current
    DESCRIPTION
        "The value of tnOamTrCtlFcName specifies the forwarding class to be
         used when launching the probe(s).  The forwarding class name must be
         present in the index column of TIMETRA-QOS-MIB::tFCNameTable.  This
         object is optional.

         As shown in the following table
         a) this object is applicable to a subset of the test types, and
         b) the default forwarding class depends on the test type.

         tnOamTrCtlTestMode   Applicable?   Default
         --------------------   -----------   -------
         ethCfmLinkTrace        yes           'nc'
         ldpTreeTrace           yes           'be'
         lspTraceRoute          yes           'be'
         macTraceRoute          yes           'be'
         p2mpLspTrace           yes           'be'
         vccvTraceRoute         yes           'be'
         vprnTraceRoute         yes           'be'
         otherwise              no            N/A

         For 'ethCfmLinkTrace', the forwarding class depends on whether the
         request is configured to egress on a network port or an access port.
         In the network port case, the forwarding class is the forwarding class
         of the pseudowire.  In the access port case, the forwarding class is
         that of the SAP's egress encapsulation policy.

         For 'lspTraceRoute' this is the forwarding class of the LSP tunnel.

         For 'macTraceRoute' this is the forwarding class of the SDP
         encapsulation.

         For 'p2mpLspTrace' this is the forwarding class of the P2MP LSP tree.

         If forwarding classes are mapped by the applicable QoS policy, the
         probe(s) may be launched using a different forwarding class than the
         forwarding class specified by this object."
    DEFVAL { "be" }
    ::= { tnOamTrCtlEntry 8 }

tnOamTrCtlProfile      OBJECT-TYPE
    SYNTAX      TProfile
    MAX-ACCESS  read-create
    STATUS      current
    DESCRIPTION
        "The value of tnOamTrCtlProfile specifies the profile to be used
         with the forwarding class specified in tnOamTrCtlFcName.  This
         object is optional.

         As shown in the following table
         a) this object is applicable to a subset of the test types, and
         b) the default profile value depends on the test type.

         tnOamTrCtlTestMode   Applicable?   Default
         --------------------   -----------   -------
         ethCfmLinkTrace        yes           'in(1)'
         ldpTreeTrace           yes           'out(2)'
         lspTraceRoute          yes           'out(2)'
         macTraceRoute          yes           'out(2)'
         p2mpLspTrace           yes           'out(2)'
         vccvTraceRoute         yes           'out(2)'
         vprnTraceRoute         yes           'out(2)'
         otherwise              no            N/A"
     DEFVAL { out }
     ::= { tnOamTrCtlEntry 9 }

tnOamTrCtlTargetIpAddress  OBJECT-TYPE
    SYNTAX      IpAddress
    MAX-ACCESS  read-create
    STATUS      obsolete
    DESCRIPTION
        "Specifies the Ipv4 address to be used as the destination for
         performing an OAM Trace Route operation.  This parameter is
         not used by 'macTraceRoute' or 'lspTraceRoute' or 'mcastTraceRoute'.
         This parameter is required by 'vprnTraceRoute'.

         This object was obsoleted in release 4.0 and replaced with
         InetAddress objects tnOamTrCtlTgtAddrType and
         tnOamTrCtlTgtAddress."
    DEFVAL { '00000000'h }      -- 0.0.0.0
    ::= { tnOamTrCtlEntry 10 }

tnOamTrCtlServiceId            OBJECT-TYPE
    SYNTAX      TmnxServId (0..2147483647)
    MAX-ACCESS  read-create
    STATUS      current
    DESCRIPTION
        "The value of tnOamTrCtlServiceId specifies the service ID of the
         service being tested.

         The applicability of tnOamTrCtlServiceId varies with the test type,
         as shown in the following table.

         tnOamTrCtlTestMode   Applicability    Related Virtual Router Object
         --------------------   -------------    -----------------------------
         'icmpTraceRoute'       optional         tnOamTrCtlVRtrID
         'macTraceRoute'        mandatory        none
         'mcastTraceRoute'      optional         tnOamMcastTrCtlVRtrID
         'vprnTraceRoute'       mandatory        none
         otherwise              not applicable   none

         When tnOamTrCtlServiceId is mandatory, a non-zero value must be
         provided.

         When tnOamTrCtlServiceId is optional, it is used to specify a VPRN
         service.  The test must use the VPRN service's virtual router.

         When a related virtual router object is shown, the interaction is
         described in the DESCRIPTION clause of the listed object.

         Service IDs larger than 2147483647 are internal, so they are excluded
         from the range.

         The default value is the null service ID."
    DEFVAL { 0 }
    ::= { tnOamTrCtlEntry 11 }

tnOamTrCtlDataSize OBJECT-TYPE
    SYNTAX      Unsigned32 (1..9198)
    UNITS       "octets"
    MAX-ACCESS  read-create
    STATUS      current
    DESCRIPTION
        "The value of tnOamTrCtlDataSize specifies the size of the data
         portion of the Trace Route request, in octets.  The size of the message
         does not include the SDP encapsulation, VC-Label (if applied) or any
         DLC headers or trailers.  This parameter is optional.

         When the OAM message is encapsulated in an IP/GRE SDP, the
         IP 'DF' (Don't Fragment) bit is set.  If any segment of the path
         between the sender and receiver cannot handle the message size,
         the message is discarded.  MPLS LSPs are not expected to fragment
         the message either, as the message contained in the LSP is not an
         IP packet.

         When the data size is specified as 1, it is interpreted as the minumum
         valid data size for the trace type.

         The minimum data size (in octets) varies with tnOamTrCtlTestMode, as
         follows:
           'lspTraceRoute' with multipath DSMap   140
           'lspTraceRoute' otherwise              104
           'macTraceRoute'                          1
           'p2mpLspTrace'                         132
           'vccvTraceRoute', FEC 128 pseudowire    88
           'vccvTraceRoute', FEC 129 pseudowire   120
           'vprnTraceRoute'                         1

         This parameter is not used by 'ethCfmLinkTrace', 'icmpTraceRoute',
         'ldpTreeTrace', or 'mcastTraceRoute'."
    DEFVAL { 1 }
    ::= { tnOamTrCtlEntry 12 }

tnOamTrCtlTimeOut OBJECT-TYPE
    SYNTAX      Unsigned32 (1..60)
    UNITS       "seconds"
    MAX-ACCESS  read-create
    STATUS      current
    DESCRIPTION
        "Specifies the time-out value, in seconds, for an Nokia SROS
         OAM Trace Route request.  This parameter is optional.

         For 'ethCfmLinkTrace', this is the time out for the whole test.

         The minimum, maximum, and default values of this object vary with
         tnOamTrCtlTestMode, as follows:
           'icmpTraceRoute' :  N/A N/A N/A
           'ethCfmLinkTrace':    1  10   5
            otherwise       :    1  60   3

        If tnOamTrCtlTestMode is 'ethCfmLinkTrace', the value of
        tnOamTrCtlTimeOut must be less than or equal to the value of
        tnOamTrCtlInterval."
    DEFVAL { 3 }
    ::= { tnOamTrCtlEntry 13 }

tnOamTrCtlProbesPerHop OBJECT-TYPE
    SYNTAX      Unsigned32 (1..10)
    UNITS       "probes"
    MAX-ACCESS  read-create
    STATUS      current
    DESCRIPTION
        "Specifies the number of times to reissue an Nokia SROS OAM
         Trace Route request with the same time-to-live (TTL) value.
         This parameter is optional.

         This parameter is not configurable for 'icmpTraceRoute';
         a default value of 3 is used."
    DEFVAL { 1 }
    ::= { tnOamTrCtlEntry 14 }

tnOamTrCtlMaxTtl OBJECT-TYPE
    SYNTAX      Unsigned32 (1..255)
    UNITS       "time-to-live value"
    MAX-ACCESS  read-create
    STATUS      current
    DESCRIPTION
        "The value of tnOamTrCtlMaxTtl specifies the maximum time-to-live
        value.  This parameter is optional.

        When tnOamTrCtlMaxTtl is not explicitly specified, the agent
        defaults the value based on the 'tnOamTrCtlTestMode'.

        In the case of 'lspTraceRoute' the default is set to 30.
        In the case of 'icmpTraceRoute' the default is set to 30.
        In the case of 'ldpTreeTrace' the default is set to 30.
        In the case of 'vccvTraceRoute' the default is set to 8.
        In the case of 'p2mplspTrace' the default is set to 30.
        In the case of 'ethCfmLinkTrace' the default is set to 64.
        Otherwise the default is set to 4."
    DEFVAL { 4 }
    ::= { tnOamTrCtlEntry 15 }

tnOamTrCtlInitialTtl OBJECT-TYPE
    SYNTAX         Unsigned32 (1..255)
    MAX-ACCESS     read-create
    STATUS         current
    DESCRIPTION
        "The value of tnOamTrCtlInitialTtl specifies the initial TTL
        value to use.  This enables bypassing the initial (often well known)
        portion of a path.  This parameter is optional.

        This parameter is not configurable for 'icmpTraceRoute'; the
        default value 1 is used.  This parameter is not used with
        'ethCfmLinkTrace'."
    DEFVAL { 1 }
    ::= { tnOamTrCtlEntry 16 }

tnOamTrCtlDSField OBJECT-TYPE
    SYNTAX      Unsigned32 (0..255)
    MAX-ACCESS  read-create
    STATUS      current
    DESCRIPTION
        "The value of tnOamTrCtlDSField specifies the value to load in the
         Type of Service (TOS) octet or the Traffic Class (TC) octet of the
         launched ICMP echo request(s).  The TOS octet is a field in the IPv4
         packet header.  The TC octet is a field in the IPv6 packet header.

         The value in the TOS or TC octet may influence the route, latency,
         and/or probability of loss for the echo request (and, by inference, for
         the associated data flow).

         This object is supported when tnOamTrCtlTestMode is 'icmpTraceRoute'.
         Otherwise, it is ignored.

         This object is optional."
    REFERENCE
        "RFC  791, 'Internet Protocol', section 3.1.
         RFC 1812, 'Requirements for IP Version 4 Routers', section 5.3.2.
         RFC 2460, 'Internet Protocol, Version 6 (IPv6) Specification',
         section 7.
         RFC 2474, 'Definition of the Differentiated Services Field (DS Field)
         in the IPv4 and IPv6 Headers'."
    DEFVAL { 0 }
    ::= { tnOamTrCtlEntry 17 }

tnOamTrCtlMaxFailures OBJECT-TYPE
    SYNTAX      Unsigned32 (1..255)
    UNITS       "timeouts"
    MAX-ACCESS  read-create
    STATUS      current
    DESCRIPTION
        "The value of tnOamTrCtlMaxFailures specifies the maximum number of
         consecutive timeouts allowed before terminating a trace route test.
         This object is optional.

         As shown in the following table
         a) this object is applicable to a subset of the test types, and
         b) the default value and upper bound depend on the test type.

         tnOamTrCtlTestMode   Applicable?   Default   Upper Bound
         --------------------   -----------   -------   -----------
         'icmpTraceRoute'       yes            90        90
         'lspTraceRoute'        yes             5       255
         'p2mpLspTrace'         yes             5        10
         'vccvTraceRoute'       yes             5       255
         otherwise              no            N/A       N/A

         In the 'icmpTraceRoute' case, changing the tnOamTrCtlMaxFailures
         value away from the default is not supported."
    DEFVAL { 5 }
    ::= { tnOamTrCtlEntry 18 }

tnOamTrCtlInterval  OBJECT-TYPE
    SYNTAX      Unsigned32
    UNITS       "seconds"
    MAX-ACCESS  read-create
    STATUS      current
    DESCRIPTION
        "The value of tnOamTrCtlInterval specifies the number of seconds
         to wait before repeating an Nokia SROS OAM Trace Route test as
         defined by the value of the various objects in the corresponding row.
         This parameter is optional.

         The number of hops in a single Nokia SROS OAM Trace Route test
         is determined by the value of the corresponding
         tnOamTrCtlProbesPerHop object.  After a single test completes,
         the number of seconds as defined by the value of tnOamTrCtlInterval
         MUST elapse before the next Nokia SROS OAM Trace Route test is
         started.

         The applicability, range, and default value of this object vary with
         tnOamTrCtlTestMode, as shown in the following table.

           tnOamTrCtlTestMode   Min Max Default
           'ethCfmLinkTrace'        1  10       5
           'icmpTraceRoute'        not applicable
           'vccvTraceRoute'         1 255       1
           otherwise                1  10       1"
    DEFVAL { 1 }
    ::= { tnOamTrCtlEntry 19 }

tnOamTrCtlMaxRows OBJECT-TYPE
    SYNTAX      Unsigned32
    UNITS       "rows"
    MAX-ACCESS  read-create
    STATUS      obsolete
    DESCRIPTION
        "The value of tnOamTrCtlMaxRows specifies the maximum number of
         entries allowed in the tnOamTrProbeHistoryTable.  The oldest entry
         in the tnOamTrProbeHistoryTable is removed to allow the addition
         of an new entry once the number of rows in the
         tnOamTrProbeHistoryTable reaches this value.

         Old entries are not removed when a new test is started.  Entries are
         added to the tnOamTrProbeHistoryTable until tnOamTrCtlMaxRows
         is reached before entries begin to be removed.

         A value of 0 for this object disables creation of
         tnOamTrProbeHistoryTable entries.

         This object was obsoleted in release 6.0R17."
    DEFVAL      { 300 }
    ::= { tnOamTrCtlEntry 20 }

tnOamTrCtlTrapGeneration OBJECT-TYPE
    SYNTAX      BITS {
                  pathChange(0),
                  testFailure(1),
                  testCompletion(2)
                }
    MAX-ACCESS  read-create
    STATUS      current
    DESCRIPTION
        "The value of tnOamTrCtlTrapGeneration specifies when and if to
         generate a notification for this entry:
         pathChange(0)     - Generate a tnOamTrPathChange
             notification when the current path varies from a previously
             determined path.
         testFailure(1)    - Generate a tnOamTrTestFailed notification when
             the full path to a target can't be determined.
         testCompletion(2) - Generate a tnOamTrTestCompleted notification
             when the test is completed."
    DEFVAL { {} }
    ::= { tnOamTrCtlEntry 21 }

tnOamTrCtlCreateHopsEntries OBJECT-TYPE
    SYNTAX      TruthValue
    MAX-ACCESS  read-create
    STATUS      obsolete
    DESCRIPTION
        "The value of tnOamTrCtlCreateHopsEntries specifies whether or not
         the current path for an Nokia SROS OAM Trace Route test is kept
         in the tnOamTrHopsTable on a per hop basis.

         tnOamTrHopsTable provides a current path topology based on the
         results of the OAM Trace Route tests.  If this feature is not
         supported tnOamTrCtlCreateHopsEntries will always be set to false(2)
         and any attempt to change its value to true(1) will be denied."
    DEFVAL { false }
    ::= { tnOamTrCtlEntry 22 }

tnOamTrCtlSAA OBJECT-TYPE
    SYNTAX      TruthValue
    MAX-ACCESS  read-create
    STATUS      current
    DESCRIPTION
        "The value of tnOamTrCtlSAA specifies if this test is an SAA test
         (Service Assurance Agent; 'true'), or an OAM test ('false').  If
         there is a tnOamSaaCtlTable row with the specified index values,
         'true' is returned.  Otherwise, 'false' is returned."
    DEFVAL { false }
    ::= { tnOamTrCtlEntry 23 }

tnOamTrCtlRuns      OBJECT-TYPE
    SYNTAX      Counter32
    MAX-ACCESS  read-only
    STATUS      current
    DESCRIPTION
        "The value of tnOamTrCtlRuns indicates the number of times
         this OAM trace route test has been executed."
    ::= { tnOamTrCtlEntry 24 }

tnOamTrCtlFailures  OBJECT-TYPE
    SYNTAX      Counter32
    MAX-ACCESS  read-only
    STATUS      current
    DESCRIPTION
        "The value of tnOamTrCtlFailures indicates the number of times
         this OAM trace route test has failed."
    ::= { tnOamTrCtlEntry 25 }

tnOamTrCtlLastRunResult  OBJECT-TYPE
    SYNTAX      TmnxOamTestResult
    MAX-ACCESS  read-only
    STATUS      current
    DESCRIPTION
        "The value of tnOamTrCtlLastRunResult indicates the completion
         status the last time this test was executed.  If this OAM test is
         currently in progress, this object indicates the result of the
         previous test run, if any."
    ::= { tnOamTrCtlEntry 26 }

tnOamTrCtlLastChanged   OBJECT-TYPE
    SYNTAX      TimeStamp
    MAX-ACCESS  read-only
    STATUS      current
    DESCRIPTION
        "The value of tnOamTrCtlLastChanged indicates the time the
         value of a settable object in this row was last changed."
    ::= { tnOamTrCtlEntry 27 }

tnOamTrCtlVRtrID  OBJECT-TYPE
    SYNTAX      TmnxVRtrID
    MAX-ACCESS  read-create
    STATUS      current
    DESCRIPTION
        "The value of tnOamTrCtlVRtrID specifies the virtual router to be
         used for the test.  The value specified must be the index of an active
         row in TIMETRA-VRTR-MIB::vRtrConfTable.

         This object is applicable if tnOamTrCtlTestMode is 'icmpTraceRoute'.

         When directing an 'icmpTraceRoute' test to use a virtual router
         associated with a VPRN service, the virtual router can be specified
         using tnOamTrCtlVRtrID (with the VPRN's virtual router number) or
         tnOamTrCtlServiceId (with the VPRN's service number).
         tnOamTrCtlServiceId is preferred, because service numbers are
         constant across an SROS reboot (while virtual routers may be
         renumbered).  If non-default values are specified for both
         tnOamTrCtlVRtrID and tnOamTrCtlServiceId,
         tnOamTrCtlServiceId is used.

         Setting this object is optional."
    DEFVAL { 1 }
    ::= { tnOamTrCtlEntry 28 }

tnOamTrCtlTgtAddrType   OBJECT-TYPE
    SYNTAX      InetAddressType
    MAX-ACCESS  read-create
    STATUS      current
    DESCRIPTION
        "The value of tnOamTrCtlTgtAddrType specifies the type of host
         address to be used as the destination for performing a OAM Trace
         Route operation. Only 'ipv4', 'ipv6' and 'dns' address types are
         supported.

         This object indicates the type of address stored in the
         corresponding tnOamTrCtlTgtAddress object.

         The 'dns' address type is valid only for 'icmpTraceRoute'."
    DEFVAL { unknown }
    ::= { tnOamTrCtlEntry 29 }

tnOamTrCtlTgtAddress OBJECT-TYPE
    SYNTAX      InetAddress
    MAX-ACCESS  read-create
    STATUS      current
    DESCRIPTION
        "The value of tnOamTrCtlTgtAddress specifies the IP host address to
         be used as the destination for performing an OAM Trace Route
         operation. The host address type is determined by the value of the
         corresponding tnOamTrCtlTgtAddrType object.

         This parameter is required by 'vprnTraceRoute' and 'icmpTraceRoute'.
         This parameter is not used by 'macTraceRoute', 'lspTraceRoute',
         'mcastTraceRoute', 'vccvTraceRoute', 'p2mpLspPing', or
         'ethCfmLinkTrace'. "
    DEFVAL { ''H }
    ::= { tnOamTrCtlEntry 30 }

tnOamTrCtlSrcAddrType   OBJECT-TYPE
    SYNTAX      InetAddressType
    MAX-ACCESS  read-create
    STATUS      current
    DESCRIPTION
        "The value of tnOamTrCtlSrcAddrType specifies the type of host
         address to be used as the source for performing an OAM traceroute
         operation. This object indicates the type of address stored in the
         corresponding tnOamTrCtlSrcAddress object. Only 'ipv4' and 'ipv6'
         address types are supported.

         This object is valid only when the tnOamTrCtlTestMode has a
         value of 'icmpTraceRoute' or 'lspTraceRoute'."
    DEFVAL { unknown }
    ::= { tnOamTrCtlEntry 31 }

tnOamTrCtlSrcAddress OBJECT-TYPE
    SYNTAX      InetAddress  (SIZE(0|4|16))
    MAX-ACCESS  read-create
    STATUS      current
    DESCRIPTION
        "The value of tnOamTrCtlSrcAddress specifies the IP host address to
         be used as the source for performing an OAM Trace Route operation.
         The host address type is determined by the value of the corresponding
         tnOamTrCtlSrcAddrType object. This is an optional parameter.

         This object is valid only when the tnOamTrCtlTestMode has a
         value of 'icmpTraceRoute' or 'lspTraceRoute'."
    DEFVAL { ''H }
    ::= { tnOamTrCtlEntry 32 }

tnOamTrCtlWaitMilliSec OBJECT-TYPE
    SYNTAX      Unsigned32 (10..60000)
    UNITS       "milliseconds"
    MAX-ACCESS  read-create
    STATUS      current
    DESCRIPTION
        "The value of tnOamTrCtlWaitMilliSec specifies the time in
         milliseconds to wait for a response before sending the next
         probe.

         This object is valid only for 'icmpTraceRoute' tests."
    DEFVAL { 5000 }  -- 5 seconds
    ::= { tnOamTrCtlEntry 33 }
--
-- Nokia SROS series OAM Trace Route Test Results Table
--
tnOamTrResultsTable OBJECT-TYPE
    SYNTAX      SEQUENCE OF TnOamTrResultsEntry
    MAX-ACCESS  not-accessible
    STATUS      current
    DESCRIPTION
        "Defines the Nokia SROS OAM Trace Route Test Results
         Table for keeping track of the status of a tnOamTrCtlEntry.

         An entry is added to the tnOamTrResultsTable when an
         tnOamTrCtlEntry is started by successful transition
         of its tnOamTrCtlAdminStatus object to enabled(1).
         An entry is removed from the tnOamTrResultsTable when
         its corresponding tnOamTrCtlEntry is deleted."
   ::= { tnOamTraceRouteObjs 4 }

tnOamTrResultsEntry OBJECT-TYPE
    SYNTAX      TnOamTrResultsEntry
    MAX-ACCESS  not-accessible
    STATUS      current
    DESCRIPTION
        "Defines an entry in the tnOamTrResultsTable.  The
         first two indexes of the tnOamTrResultsTable are the
         same as the tnOamTrCtlTable in order for a tnOamTrResultsEntry
         to correspond to the tnOamTrCtlEntry that caused it to
         be created.  The third index allows a history of test runs
         to be stored."
    INDEX {
           tnSysSwitchId,
           -- tnOamTrCtlOwnerIndex,
           tnOamTrCtlTestIndex,
           tnOamTrResultsTestRunIndex
          }
    ::= { tnOamTrResultsTable 1 }

 TnOamTrResultsEntry ::=
    SEQUENCE {
     tnOamTrResultsOperStatus       INTEGER,
     tnOamTrResultsCurHopCount      Gauge32,
     tnOamTrResultsCurProbeCount    Gauge32,
     tnOamTrResultsIpTgtAddr        IpAddress,
     tnOamTrResultsTestAttempts     Unsigned32,
     tnOamTrResultsTestSuccesses    Unsigned32,
     tnOamTrResultsLastGoodPath     DateAndTime,
     tnOamTrResultsTestRunIndex     Unsigned32,
     tnOamTrResultsTgtAddrType      InetAddressType,
     tnOamTrResultsTgtAddress       InetAddress,
     tnOamTrResultsTestRunResult    TmnxOamTestResult
    }

tnOamTrResultsOperStatus OBJECT-TYPE
    SYNTAX      INTEGER {
                          enabled(1), -- test is in progress
                          disabled(2) -- test has stopped
                        }
    MAX-ACCESS  read-only
    STATUS      current
    DESCRIPTION
        "Reflects the operational state of a tnOamTrCtlEntry:

           enabled(1)  - Test is active.
           disabled(2) - Test has stopped."
    ::= { tnOamTrResultsEntry 1 }

tnOamTrResultsCurHopCount OBJECT-TYPE
    SYNTAX      Gauge32
    UNITS       "hops"
    MAX-ACCESS  read-only
    STATUS      current
    DESCRIPTION
        "Reflects the current TTL value (range from 0 to
         255) for an Nokia SROS OAM Trace Route operation.
         Maximum TTL value is determined by tnOamTrCtlMaxTtl.

         Zero is returned only in the case of an aborted 'ethCfmLinkTrace'
         test."
    ::= { tnOamTrResultsEntry 2 }

tnOamTrResultsCurProbeCount OBJECT-TYPE
    SYNTAX      Gauge32
    UNITS       "probes"
    MAX-ACCESS  read-only
    STATUS      current
    DESCRIPTION
        "Reflects the current probe count (1..10) for an Nokia
         SROS OAM Trace Route operation. The maximum probe count is
         determined by tnOamTrCtlProbesPerHop."
    ::= { tnOamTrResultsEntry 3 }

tnOamTrResultsIpTgtAddr OBJECT-TYPE
    SYNTAX      IpAddress
    MAX-ACCESS  read-only
    STATUS      obsolete
    DESCRIPTION
        "This objects reports the IP address associated
         with a tnOamTrCtlTargetIpAddress value when the
         destination address is specified as a DNS name.
         The value of this object should be a zero length
         octet string when a DNS name is not specified or
         when a specified DNS name fails to resolve.

         This object was obsoleted in release 4.0 and replaced with
         InetAddress objects tnOamTrResultsTgtAddrType and
         tnOamTrResultsTgtAddress."
    ::= { tnOamTrResultsEntry 4 }

tnOamTrResultsTestAttempts OBJECT-TYPE
    SYNTAX      Unsigned32
    UNITS       "tests"
    MAX-ACCESS  read-only
    STATUS      obsolete
    DESCRIPTION
        "The current number of attempts to determine a path
         to a target.  The value of this object MUST be started
         at 0.

         This object was made obsolete in the 3.0 release.  Originally
         this table was used to report a summary of the results of all
         traceroute test for the configured test.  An additional index,
         tnOamTrResultsTestRunIndex, has been added to this table and
         a row in this table now represents the results of a single
         traceroute test run.  The new object tnOamTrCtlRuns in the
         tnOamTrCtlTable indicates the number of times this traceroute
         test has been run."
    ::= { tnOamTrResultsEntry 5 }

tnOamTrResultsTestSuccesses OBJECT-TYPE
    SYNTAX      Unsigned32
    UNITS       "tests"
    MAX-ACCESS  read-only
    STATUS      obsolete
    DESCRIPTION
        "The current number of attempts to determine a path
         to a target that have succeeded.  The value of this
         object MUST be reported as 0 when no attempts have
         succeeded.

         This object was made obsolete in the 3.0 release.  Originally
         this table was used to report a summary of the results of all
         traceroute test for the configured test.  An additional index,
         tnOamTrResultsTestRunIndex, has been added to this table and
         a row in this table now represents the results of a single
         traceroute test run.  The new object tnOamTrCtlFailures in the
         tnOamTrCtlTable indicates the number of times an attempt to run
         this traceroute test has failed.  The number of successful runs
         can be calclated as (tnOamTrCtlRuns - tnOamTrCtlFailures)."
    ::= { tnOamTrResultsEntry 6 }

tnOamTrResultsLastGoodPath OBJECT-TYPE
    SYNTAX      DateAndTime
    MAX-ACCESS  read-only
    STATUS      current
    DESCRIPTION
        "The date and time when the last complete path
         was determined."
    ::= { tnOamTrResultsEntry 7 }

tnOamTrResultsTestRunIndex      OBJECT-TYPE
    SYNTAX      Unsigned32 (1..4294967295)
    MAX-ACCESS  not-accessible
    STATUS      current
    DESCRIPTION
        "The value of tnOamTrResultsTestRunIndex identifies the
         row entry that reports results for a single OAM trace
         route test run.

         The agent starts assigning tnOamTrResultsTestRunIndex values
         at 1 and wraps after exceeding the maximum possible value as
         defined by the limit of this object."
    ::= { tnOamTrResultsEntry 8 }

tnOamTrResultsTgtAddrType OBJECT-TYPE
    SYNTAX      InetAddressType
    MAX-ACCESS  read-only
    STATUS      current
    DESCRIPTION
        "The value of tnOamTrResultsTgtAddrType indicates the Internet
         address type stored in tnOamTrResultsTgtAddress."
    ::= { tnOamTrResultsEntry 9 }

tnOamTrResultsTgtAddress OBJECT-TYPE
    SYNTAX      InetAddress (SIZE (0|4|16))
    MAX-ACCESS  read-only
    STATUS      current
    DESCRIPTION
        "The value of tnOamTrResultsTgtAddress indicates the Internet
         address associated with a tnOamTrCtlTgtAddress value when the
         destination address is specified as a DNS name.  The value of this
         object should be a zero length octet string when a DNS name is not
         specified or when a specified DNS name fails to resolve."
    ::= { tnOamTrResultsEntry 10 }

tnOamTrResultsTestRunResult  OBJECT-TYPE
    SYNTAX      TmnxOamTestResult
    MAX-ACCESS  read-only
    STATUS      current
    DESCRIPTION
        "The object contains the overall state of the trace test."
    ::= { tnOamTrResultsEntry 11 }

--
-- Trace Route Probe History Table
--
tnOamTrProbeHistoryTable OBJECT-TYPE
    SYNTAX      SEQUENCE OF TnOamTrProbeHistoryEntry
    MAX-ACCESS  not-accessible
    STATUS      current
    DESCRIPTION
        "tnOamTrProbeHistoryTable contains per-probe results for trace route
         tests.

         The number of rows in this table for a test is limited to the results
         of 3 runs.

         This table is not used for tests which have tnOamTrCtlTestMode set to
         'ldpTreeTrace'."
   ::= { tnOamTraceRouteObjs 5 }

tnOamTrProbeHistoryEntry OBJECT-TYPE
    SYNTAX      TnOamTrProbeHistoryEntry
    MAX-ACCESS  not-accessible
    STATUS      current
    DESCRIPTION
        "A tnOamTrProbeHistoryEntry is created by the system when the result
         of a trace route probe launch is determined.

         A tnOamTrProbeHistoryEntry is destroyed when the corresponding
         tnOamTrCtlEntry is destroyed.

         The first two indices identify the parent tnOamTrCtlEntry.  The third
         index identifies a trace route test run.  Each subsequent index is
         described in its DESCRIPTION clause, below."
    INDEX {
            tnSysSwitchId,
            -- tnOamTrCtlOwnerIndex,
            tnOamTrCtlTestIndex,
            tnOamTrResultsTestRunIndex,
            tnOamTrProbeHistoryIndex,
            tnOamTrProbeHistoryHopIndex,
            tnOamTrProbeHistoryProbeIndex
          }
    ::= { tnOamTrProbeHistoryTable 1 }

 TnOamTrProbeHistoryEntry ::=
    SEQUENCE {
     tnOamTrProbeHistoryIndex         Unsigned32,
     tnOamTrProbeHistoryHopIndex      Unsigned32,
     tnOamTrProbeHistoryProbeIndex    Unsigned32,
     tnOamTrProbeHistoryIpAddr        IpAddress,
     tnOamTrProbeHistoryResponse      Unsigned32,
     tnOamTrProbeHistoryOneWayTime    Integer32,
     tnOamTrProbeHistoryStatus        TmnxOamResponseStatus,
     tnOamTrProbeHistoryLastRC        Integer32,
     tnOamTrProbeHistoryTime          DateAndTime,
     tnOamTrProbeHistoryResponsePlane TmnxOamTestResponsePlane,
     tnOamTrProbeHistoryAddressType   TmnxOamAddressType,
     tnOamTrProbeHistorySapId         TmnxStrSapId,
     tnOamTrProbeHistoryVersion       Unsigned32,
     tnOamTrProbeHistoryRouterID      RouterID,
     tnOamTrProbeHistoryIfIndex       InterfaceIndexOrZero,
     tnOamTrProbeHistoryDataLen       Unsigned32,
     tnOamTrProbeHistorySize          Unsigned32,
     tnOamTrProbeHistoryInOneWayTime  Integer32,
     tnOamTrProbeHistoryAddrType      InetAddressType,
     tnOamTrProbeHistoryAddress       InetAddress,
     tnOamTrProbeHistorySrcGlobalId   TmnxMplsTpGlobalID,
     tnOamTrProbeHistorySrcNodeId     TmnxMplsTpNodeID
    }

tnOamTrProbeHistoryIndex OBJECT-TYPE
    SYNTAX      Unsigned32 (1..4294967295)
    MAX-ACCESS  not-accessible
    STATUS      current
    DESCRIPTION
        "The value of tnOamTrProbeHistoryIndex specifies the entries belonging
         to a single OAM Trace Route test instance.

         The tnOamTrProbeHistoryIndex values are assigned starting at 1
         and wrap on exceeding the upper bound."
    ::= { tnOamTrProbeHistoryEntry 1 }

tnOamTrProbeHistoryHopIndex OBJECT-TYPE
    SYNTAX      Unsigned32 (1..255)
    MAX-ACCESS  not-accessible
    STATUS      current
    DESCRIPTION
       "Indicates which hop in an Nokia SROS OAM Trace Route path that
        the probe's results are for.  The value of this object is initially
        determined by the value of tnOamTrCtlInitialTtl."
    ::= { tnOamTrProbeHistoryEntry 2 }

tnOamTrProbeHistoryProbeIndex OBJECT-TYPE
    SYNTAX      Unsigned32 (1..10)
    MAX-ACCESS  not-accessible
    STATUS      current
    DESCRIPTION
       "Indicates the index of a probe for a particular hop in an Nokia
        SROS OAM Trace Route path.  The number of probes per hop is
        determined by the value of the corresponding tnOamTrCtlProbesPerHop
        object."
    ::= { tnOamTrProbeHistoryEntry 3 }

tnOamTrProbeHistoryIpAddr OBJECT-TYPE
    SYNTAX      IpAddress
    MAX-ACCESS  read-only
    STATUS      obsolete
    DESCRIPTION
        "The IP address of a hop in an Nokia SROS OAM Trace Route path.
         The value of tnOamTrProbeHistoryIpAddr specifies the Ipv4
         address of the remote node that generated this reply to a OAM
         Trace Route probe.

         This object was obsoleted in release 4.0 and replaced with
         InetAddress objects tnOamTrProbeHistoryAddrType and
         tnOamTrProbeHistoryAddress."
    ::= { tnOamTrProbeHistoryEntry 4 }

tnOamTrProbeHistoryResponse OBJECT-TYPE
    SYNTAX      Unsigned32
    UNITS       "microseconds"
    MAX-ACCESS  read-only
    STATUS      current
    DESCRIPTION
        "The amount of time measured in microseconds from when
         a probe was sent to when its response was received, two-way
         time, or when it timed out.

         The value of this object is reported as 0 when it is not
         possible to transmit a probe."
    ::= { tnOamTrProbeHistoryEntry 5 }

tnOamTrProbeHistoryOneWayTime OBJECT-TYPE
    SYNTAX      Integer32
    UNITS       "microseconds"
    MAX-ACCESS  read-only
    STATUS      current
    DESCRIPTION
        "The amount of time measured in microseconds from when
         a OAM probe was sent to when it was received by the replier,
         out-bound one-way time.

         The value of this object is reported as 0 when it is not possible
         to transmit an OAM probe or the information is not available."
    ::= { tnOamTrProbeHistoryEntry 6 }

tnOamTrProbeHistoryStatus OBJECT-TYPE
    SYNTAX      TmnxOamResponseStatus
    MAX-ACCESS  read-only
    STATUS      current
    DESCRIPTION
        "The result of an Nokia SROS OAM Trace Route operation made
         by a remote node to a particular probe."
    ::= { tnOamTrProbeHistoryEntry 7 }

tnOamTrProbeHistoryLastRC OBJECT-TYPE
    SYNTAX      Integer32
    MAX-ACCESS  read-only
    STATUS      current
    DESCRIPTION
        "The last implementation method specific reply code received.

         The Nokia SROS OAM Trace Route is usually implemented by
         transmitting a series of probe packets with increasing time-to-live
         values.  A probe packet is a UDP datagram encapsulated into an
         IP packet.  Each hop in a path to the target (destination) host
         rejects the probe packets (probe's TTL too small, ICMP reply) until
         either the maximum TTL is exceeded or the target host is
         received. For icmpTraceRoute, both icmp packet type and code
         are included."
    ::= { tnOamTrProbeHistoryEntry 8 }

tnOamTrProbeHistoryTime OBJECT-TYPE
    SYNTAX      DateAndTime
    MAX-ACCESS  read-only
    STATUS      current
    DESCRIPTION
        "Timestamp for when this probe results were determined."
    ::= { tnOamTrProbeHistoryEntry 9 }

tnOamTrProbeHistoryResponsePlane OBJECT-TYPE
    SYNTAX      TmnxOamTestResponsePlane
    MAX-ACCESS  read-only
    STATUS      current
    DESCRIPTION
        "The value of tnOamTrProbeHistoryResponsePlane indicates the
         type of response plane this trace route response was received on."
    ::= { tnOamTrProbeHistoryEntry 10 }

tnOamTrProbeHistoryAddressType       OBJECT-TYPE
    SYNTAX      TmnxOamAddressType
    MAX-ACCESS  read-only
    STATUS      current
    DESCRIPTION
        "The value of tnOamTrProbeHistoryAddressType indicates the type of
         binding address information returned in response to a test.

         When the test has the tnOamTrCtlTestMode value 'ethCfmLinkTrace',
         'unknown' is returned.

         For 'macTraceRoute', three types of address are applicable - 'sapId',
         'localCpu', and 'sdpId'.  Address type of 'sdpId' is a special case
         used specifically to indicate that the probe was traversing a b-vpls
         node in a PBB network (but where destination MAC is not necessarily
         known to the b-vpls node)."
    ::= { tnOamTrProbeHistoryEntry 11 }

tnOamTrProbeHistorySapId OBJECT-TYPE
    SYNTAX          TmnxStrSapId
    MAX-ACCESS      read-only
    STATUS          current
    DESCRIPTION
        "The value of tnOamTrProbeHistorySapId is the name of the access
         port of the SAP supporting the requested IP address returned in
         response to a 'vprnTraceRoute' probe.

         If the value of tnOamTrProbeHistoryAddressType is not 'sapId',
         this object is not relevant and MUST have a null string ''."
    ::= { tnOamTrProbeHistoryEntry 12 }

tnOamTrProbeHistoryVersion       OBJECT-TYPE
    SYNTAX      Unsigned32
    MAX-ACCESS  read-only
    STATUS      current
    DESCRIPTION
        "The value of tnOamTrProbeHistoryVersion indicates the protocol
         version for this OAM ping reply."
    ::= { tnOamTrProbeHistoryEntry 14 }

tnOamTrProbeHistoryRouterID       OBJECT-TYPE
    SYNTAX      RouterID
    MAX-ACCESS  read-only
    STATUS      current
    DESCRIPTION
        "The value tnOamTrProbeHistoryRouterID indicates the downstream
         router ID of the node that provided this ping reply.  This object
         is valid only when tnOamTrCtlTestMode has a value of
         'lspTraceRoute'."
    ::= { tnOamTrProbeHistoryEntry 15 }

tnOamTrProbeHistoryIfIndex   OBJECT-TYPE
    SYNTAX      InterfaceIndexOrZero
    MAX-ACCESS  read-only
    STATUS      current
    DESCRIPTION
        "The value of tnOamTrProbeHistoryIfIndex indicates for a
         'lspTraceRoute' or 'vccvTraceRoute' probe the ifIndex value of the
         interface that this probe was transmitted from.

         For other types of probes, this value is not significant and zero is
         returned."
    ::= { tnOamTrProbeHistoryEntry 16 }

tnOamTrProbeHistoryDataLen   OBJECT-TYPE
    SYNTAX      Unsigned32
    UNITS       "octets"
    MAX-ACCESS  read-only
    STATUS      current
    DESCRIPTION
        "The value of tnOamTrProbeHistoryDataLen indicates the UDP data length
         of the echo reply.

         A valid value is returned when the test has a tnOamTrCtlTestMode
         value of 'icmpTraceRoute', 'lspTraceRoute', 'p2mpLspTrace', or
         'vccvTraceRoute'.  Otherwise, this value is not significant and zero is
         returned."
    ::= { tnOamTrProbeHistoryEntry 17 }

tnOamTrProbeHistorySize   OBJECT-TYPE
    SYNTAX      Unsigned32
    UNITS       "octets"
    MAX-ACCESS  read-only
    STATUS      current
    DESCRIPTION
        "The value of tnOamTrProbeHistorySize indicates the size in octets
         of the user payload in the probe request packet.  It does not
         include the service encapsulation."
    ::= { tnOamTrProbeHistoryEntry 18 }

tnOamTrProbeHistoryInOneWayTime OBJECT-TYPE
    SYNTAX      Integer32
    UNITS       "microseconds"
    MAX-ACCESS  read-only
    STATUS      current
    DESCRIPTION
        "The amount of time measured in microseconds from when
         a OAM probe reply was sent to when it was received,
         in-bound one-way time.

         The value of this object is reported as 0 when the information
         is not available."
    ::= { tnOamTrProbeHistoryEntry 19 }

tnOamTrProbeHistoryAddrType OBJECT-TYPE
    SYNTAX      InetAddressType
    MAX-ACCESS  read-only
    STATUS      current
    DESCRIPTION
       "The value of tnOamTrProbeHistoryAddrType indicates the Internet
        address type stored in tnOamTrProbeHistoryAddress."
    ::= { tnOamTrProbeHistoryEntry 20 }

tnOamTrProbeHistoryAddress OBJECT-TYPE
    SYNTAX      InetAddress (SIZE (0|4|16))
    MAX-ACCESS  read-only
    STATUS      current
    DESCRIPTION
       "The value of tnOamTrProbeHistoryAddress indicates the Internet
        address of a hop in an Nokia SROS OAM Trace Route path."
    ::= { tnOamTrProbeHistoryEntry 21 }

tnOamTrProbeHistorySrcGlobalId OBJECT-TYPE
    SYNTAX      TmnxMplsTpGlobalID
    MAX-ACCESS  read-only
    STATUS      current
    DESCRIPTION
        "The value of tnOamTrProbeHistorySrcGlobalId indicates the source
         MPLS-TP global identifier of the replying node.  The value is copied
         from the reply's RFC 6426 Source Identifier TLV.  If the TLV is absent,
         zero is returned.

         This value is relevant when tnOamTrCtlTestMode is 'lspTraceRoute' or
         'vccvTraceRoute'.  Otherwise, zero is returned."
    REFERENCE
        "RFC 6426, 'MPLS On-Demand Connectivity Verification and Route Tracing',
         Section 2.2.2, 'Source Identifier TLV'."
    ::= { tnOamTrProbeHistoryEntry 22 }

tnOamTrProbeHistorySrcNodeId   OBJECT-TYPE
    SYNTAX      TmnxMplsTpNodeID
    MAX-ACCESS  read-only
    STATUS      current
    DESCRIPTION
        "The value of tnOamTrProbeHistorySrcNodeId indicates the source
         MPLS-TP node identifier of the replying node.  The value is copied from
         the reply's RFC 6426 Source Identifier TLV.  If the TLV is absent, zero
         is returned.

         This value is relevant when tnOamTrCtlTestMode is 'lspTraceRoute' or
         'vccvTraceRoute'.  Otherwise, zero is returned."
    REFERENCE
        "RFC 6426, 'MPLS On-Demand Connectivity Verification and Route Tracing',
         Section 2.2.2, 'Source Identifier TLV'."
    ::= { tnOamTrProbeHistoryEntry 23 }

--
-- Nokia SROS series OAM Trace Route Test Hop Results Table
--
-- NOTE: This table provides a current path topology based on the results
--       of the OAM Trace Route tests.
--
-- tnOamTrHopsTable OBJECT-TYPE
--     SYNTAX      SEQUENCE OF TnOamTrHopsEntry
--     MAX-ACCESS  not-accessible
--     STATUS      current
--     DESCRIPTION
--         "Defines the Nokia SROS OAM Trace Route Hop Table for keeping
--          track of the results of an Nokia SROS OAM Trace Route test
--          on a per hop basis."
--     ::= { tnOamTraceRouteObjs 6 }
--
-- tnOamTrHopsEntry OBJECT-TYPE
--     SYNTAX      TnOamTrHopsEntry
--     MAX-ACCESS  not-accessible
--     STATUS      current
--     DESCRIPTION
--         "Defines an entry in the tnOamTrHopsTable.
--          The first two index elements identify the tnOamTrCtlEntry
--          that a tnOamTrHopsEntry belongs to.  The third index element
--          identifies a OAM trace route test run.  The fourth index element,
--          tnOamTrHopsHopIndex, selects a hop in an Nokia SROS OAM
--          Trace Route path."
--     INDEX {
--            tnOamTrCtlOwnerIndex,
--            tnOamTrCtlTestIndex,
--            tnOamTrResultsTestRunIndex,
--            tnOamTrHopsHopIndex
--           }
--     ::= { tnOamTrHopsTable 1 }
--
--  TnOamTrHopsEntry ::=
--     SEQUENCE {
--        tnOamTrHopsHopIndex         Unsigned32,
--        tnOamTrHopsIpTgtAddress     IpAddress,
--        tnOamTrHopsMinRtt           Unsigned32,
--        tnOamTrHopsMaxRtt           Unsigned32,
--        tnOamTrHopsAverageRtt       Unsigned32,
--        tnOamTrHopsRttSumOfSquares  Unsigned32,
--        tnOamTrHopsMinTt            Integer32,
--        tnOamTrHopsMaxTt            Integer32,
--        tnOamTrHopsAverageTt        Integer32,
--        tnOamTrHopsTtSumOfSquares   Unsigned32,
--        tnOamTrHopsSentProbes       Unsigned32,
--        tnOamTrHopsProbeResponses   Unsigned32,
--        tnOamTrHopsLastGoodProbe    DateAndTime,
--        tnOamTrHopsMinInTt          Integer32,
--        tnOamTrHopsMaxInTt          Integer32,
--        tnOamTrHopsAverageInTt      Integer32,
--        tnOamTrHopsInTtSumOfSqrs    Unsigned32,
--        tnOamTrHopsOutJitter        Integer32,
--        tnOamTrHopsInJitter         Integer32,
--        tnOamTrHopsRtJitter         Integer32,
--        tnOamTrHopsProbeTimeouts    Unsigned32,
--        tnOamTrHopsProbeFailures    Unsigned32,
--        tnOamTrHopsTgtAddrType      InetAddressType,
--        tnOamTrHopsTgtAddress       InetAddress,
--        tnOamTrHopsRttOFSumSquares  Counter32,
--        tnOamTrHopsRttHCSumSquares  Counter64,
--        tnOamTrHopsTtOFSumSquares   Counter32,
--        tnOamTrHopsTtHCSumSquares   Counter64,
--        tnOamTrHopsInTtOFSumSqrs    Counter32,
--        tnOamTrHopsInTtHCSumSqrs    Counter64
--       }
--
-- tnOamTrHopsHopIndex OBJECT-TYPE
--     SYNTAX      Unsigned32
--     MAX-ACCESS  not-accessible
--     STATUS      current
--     DESCRIPTION
--         "Specifies the hop index for an Nokia SROS OAM Trace Route
--          hop.  Values for this object with respect to the same
--          tnOamTrCtlOwnerIndex and tnOamTrCtlTestIndex MUST start at 1
--          and increase monotonically.
--
--          The tnOamTrHopsTable keeps the current Nokia SROS OAM Trace
--          Route path per tnOamTrCtlEntry.
--
--          All hops (tnOamTrHopsTable entries) in an Nokia SROS OAM
--          Trace Route path MUST be updated at the same time when an
--          Nokia SROS OAM Trace Route operation completes.  Care needs
--          to be applied when either a path changes or can't be determined.
--          The initial portion of the path, up to the first hop change, MUST
--          retain the same tnOamTrHopsHopIndex values.  The remaining portion
--          of the path SHOULD be assigned new tnOamTrHopsHopIndex values."
--     ::= { tnOamTrHopsEntry 1 }
--
-- tnOamTrHopsIpTgtAddress OBJECT-TYPE
--     SYNTAX      IpAddress
--     MAX-ACCESS  read-only
--     STATUS      obsolete
--     DESCRIPTION
--         "This object reports the IP address associated with
--          the hop.  A value for this object should be reported
--          as a numeric IP address and not as a DNS name.
--
--          This value of this object is not significant when
--          tnOamTrCtlTestMode has a value of 'macTraceRoute'.
--
--          This object was obsoleted in release 4.0 and replaced with
--          InetAddress objects tnOamTrHopsTgtAddrType and
--          tnOamTrHopsTgtAddrType."
--     ::= { tnOamTrHopsEntry 2 }
--
-- tnOamTrHopsMinRtt OBJECT-TYPE
--     SYNTAX      Unsigned32
--     UNITS       "microseconds"
--     MAX-ACCESS  read-only
--     STATUS      current
--     DESCRIPTION
--         "The minimum Nokia SROS OAM Trace Route round-trip-time (RTT)
--          received for this hop.  A value of 0 for this object implies that no
--          RTT has been received."
--     ::= { tnOamTrHopsEntry 3 }
--
-- tnOamTrHopsMaxRtt OBJECT-TYPE
--     SYNTAX      Unsigned32
--     UNITS       "microseconds"
--     MAX-ACCESS  read-only
--     STATUS      current
--     DESCRIPTION
--         "The maximum Nokia SROS OAM Trace Route round-trip-time (RTT)
--          received for this hop.  A value of 0 for this object implies that no
--          RTT has been received."
--     ::= { tnOamTrHopsEntry 4 }
--
-- tnOamTrHopsAverageRtt OBJECT-TYPE
--     SYNTAX      Unsigned32
--     UNITS       "microseconds"
--     MAX-ACCESS  read-only
--     STATUS      current
--     DESCRIPTION
--         "The current average Nokia SROS OAM Trace Route round-trip-time
--         (RTT) for this hop."
--     ::= { tnOamTrHopsEntry 5 }
--
-- tnOamTrHopsRttSumOfSquares OBJECT-TYPE
--     SYNTAX      Unsigned32
--     UNITS       "microseconds squared"
--     MAX-ACCESS  read-only
--     STATUS      current
--     DESCRIPTION
--         "The value of tnOamTrHopsRttSumOfSquares indicates the sum of squares
--          of the received response times of the OAM trace route for this hop.
--          Its purpose is to enable standard deviation calculation."
--     ::= { tnOamTrHopsEntry 6 }
--
-- tnOamTrHopsMinTt OBJECT-TYPE
--     SYNTAX      Integer32
--     UNITS       "microseconds"
--     MAX-ACCESS  read-only
--     STATUS      current
--     DESCRIPTION
--         "The minimum Nokia SROS OAM Trace Route outbound one-way trip
--          time received for this hop.  A value of 0 for this object implies
--          that no one-way trip time has been received."
--     ::= { tnOamTrHopsEntry 7 }
--
-- tnOamTrHopsMaxTt OBJECT-TYPE
--     SYNTAX      Integer32
--     UNITS       "microseconds"
--     MAX-ACCESS  read-only
--     STATUS      current
--     DESCRIPTION
--         "The maximum Nokia SROS OAM Trace Route outbound one-way trip
--          time received for this hop.  A value of 0 for this object implies
--          that no one-way trip time has been received."
--     ::= { tnOamTrHopsEntry 8 }
--
-- tnOamTrHopsAverageTt OBJECT-TYPE
--     SYNTAX      Integer32
--     UNITS       "microseconds"
--     MAX-ACCESS  read-only
--     STATUS      current
--     DESCRIPTION
--         "The current average Nokia SROS OAM Trace Route outbound
--          one-way trip time for this hop."
--     ::= { tnOamTrHopsEntry 9 }
--
-- tnOamTrHopsTtSumOfSquares OBJECT-TYPE
--     SYNTAX      Unsigned32
--     UNITS       "microseconds squared"
--     MAX-ACCESS  read-only
--     STATUS      current
--     DESCRIPTION
--         "The value of tnOamTrHopsTtSumOfSquares indicates the sum of squares
--          of the outbound one-way trip times of the OAM trace route for
--          this hop.  Its purpose is to enable standard deviation calculation."
--     ::= { tnOamTrHopsEntry 10 }
--
-- tnOamTrHopsSentProbes OBJECT-TYPE
--     SYNTAX      Unsigned32
--     MAX-ACCESS  read-only
--     STATUS      current
--     DESCRIPTION
--         "The value of this object reflects the number of probes sent
--          for this hop during this Nokia SROS OAM Trace Route test.
--          The value of this object should start at 0."
--     ::= { tnOamTrHopsEntry 11 }
--
-- tnOamTrHopsProbeResponses OBJECT-TYPE
--     SYNTAX      Unsigned32
--     MAX-ACCESS  read-only
--     STATUS      current
--     DESCRIPTION
--         "Number of responses received for this hop during this Nokia
--          SROS OAM Trace Route test.  This value of this object should
--          start at 0."
--     ::= { tnOamTrHopsEntry 12 }
--
-- tnOamTrHopsLastGoodProbe OBJECT-TYPE
--     SYNTAX      DateAndTime
--     MAX-ACCESS  read-only
--     STATUS      current
--     DESCRIPTION
--         "Date and time when the last response was received for a probe
--          for this hop during this Nokia SROS OAM Trace Route test."
--     ::= { tnOamTrHopsEntry 13 }
--
-- tnOamTrHopsMinInTt OBJECT-TYPE
--     SYNTAX      Integer32
--     UNITS       "microseconds"
--     MAX-ACCESS  read-only
--     STATUS      current
--     DESCRIPTION
--         "The minimum OAM trace route inbound one-way trip time received.
--          A value of 0 for this object implies that no one-way trip time
--          measurement is available."
--     ::= { tnOamTrHopsEntry 18 }
--
-- tnOamTrHopsMaxInTt OBJECT-TYPE
--     SYNTAX      Integer32
--     UNITS       "microseconds"
--     MAX-ACCESS  read-only
--     STATUS      current
--     DESCRIPTION
--         "The maximum OAM trace route inbound one-way trip time received.
--          A value of 0 for this object implies that no one-way trip time
--          measurement is available."
--     ::= { tnOamTrHopsEntry 19 }
--
-- tnOamTrHopsAverageInTt OBJECT-TYPE
--     SYNTAX      Integer32
--     UNITS       "microseconds"
--     MAX-ACCESS  read-only
--     STATUS      current
--     DESCRIPTION
--         "The current average OAM inbound inbound one-way trip time.
--          A value of 0 for this object implies that no one-way trip time
--          measurement is available."
--     ::= { tnOamTrHopsEntry 20 }
--
-- tnOamTrHopsInTtSumOfSqrs OBJECT-TYPE
--     SYNTAX      Unsigned32
--     UNITS       "microseconds squared"
--     MAX-ACCESS  read-only
--     STATUS      current
--     DESCRIPTION
--         "The value of tnOamTrHopsInTtSumOfSqrs indicates the sum of squares
--          of the inbound one-way trip times of the OAM trace route for this hop.
--          Its purpose is to enable standard deviation calculation.
--
--          The value of this object will be reported as 0 when no one-way trip
--          time measurement is available."
--     ::= { tnOamTrHopsEntry 21 }
--
-- tnOamTrHopsOutJitter      OBJECT-TYPE
--     SYNTAX      Integer32
--     UNITS       "microseconds"
--     MAX-ACCESS  read-only
--     STATUS      current
--     DESCRIPTION
--         "The value of tnOamTrHopsOutJitter indicates the
--          amount of outbound one-way trip jitter, expressed in microseconds,
--          for a trace route probe request packet sent for this OAM test.
--
--          A value of 0 for this object implies that no one-way trip jitter
--          measurement is available."
--     ::= { tnOamTrHopsEntry 22 }
--
-- tnOamTrHopsInJitter      OBJECT-TYPE
--     SYNTAX      Integer32
--     UNITS       "microseconds"
--     MAX-ACCESS  read-only
--     STATUS      current
--     DESCRIPTION
--         "The value of tnOamTrHopsInJitter indicates the
--          amount of inbound one-way trip jitter, expressed in microseconds,
--          for a trace route probe response packet received for this OAM test.
--
--          A value of 0 for this object implies that no one-way trip jitter
--          measurement is available."
--     ::= { tnOamTrHopsEntry 23 }
--
-- tnOamTrHopsRtJitter      OBJECT-TYPE
--     SYNTAX      Integer32
--     UNITS       "microseconds"
--     MAX-ACCESS  read-only
--     STATUS      current
--     DESCRIPTION
--         "The value of tnOamTrHopsRtJitter indicates the
--          amount of two-way trip jitter, expressed in microseconds, for a
--          trace route probe sent for this OAM test.
--
--          A value of 0 for this object implies that no two-way-trip jitter
--          measurement is available."
--     ::= { tnOamTrHopsEntry 24 }
--
-- tnOamTrHopsProbeTimeouts     OBJECT-TYPE
--     SYNTAX      Unsigned32
--     MAX-ACCESS  read-only
--     STATUS      current
--     DESCRIPTION
--         "The value of tnOamTrHopsProbeTimeouts indicates the number
--          of probes that timed out without receiving a response."
--     ::= { tnOamTrHopsEntry 25 }
--
-- tnOamTrHopsProbeFailures     OBJECT-TYPE
--     SYNTAX      Unsigned32
--     MAX-ACCESS  read-only
--     STATUS      current
--     DESCRIPTION
--         "The value of tnOamTrHopsProbeFailures indicates the total
--          number of probes that failed to be transmitted plus the number of
--          probes that timed out without receiving a response."
--     ::= { tnOamTrHopsEntry 26 }
--
-- tnOamTrHopsTgtAddrType OBJECT-TYPE
--     SYNTAX      InetAddressType
--     MAX-ACCESS  read-only
--     STATUS      current
--     DESCRIPTION
--         "The value of tnOamTrHopsTgtAddrType indicates the Internet
--          address type stored in tnOamTrHopsTgtAddress."
--     ::= { tnOamTrHopsEntry 27 }
--
-- tnOamTrHopsTgtAddress OBJECT-TYPE
--     SYNTAX      InetAddress (SIZE (0|4|16))
--     MAX-ACCESS  read-only
--     STATUS      current
--     DESCRIPTION
--         "The value of tnOamTrHopsTgtAddress indicates the Internet
--          address associated with the hop.  A value for this object should
--          be reported as a numeric IP address and not as a DNS name.
--
--          This value of this object is not significant when
--          tnOamTrCtlTestMode has a value of 'macTraceRoute' or
--          'ethCfmLinkTrace'."
--     ::= { tnOamTrHopsEntry 28 }
--
-- tnOamTrHopsRttOFSumSquares OBJECT-TYPE
--     SYNTAX      Counter32
--     MAX-ACCESS  read-only
--     STATUS      current
--     DESCRIPTION
--         "This object contains a count of the number of times
--          tnOamTrHopsRttSumOfSquares overflowed."
--     ::= { tnOamTrHopsEntry 29 }
--
-- tnOamTrHopsRttHCSumSquares OBJECT-TYPE
--     SYNTAX      Counter64
--     UNITS       "microseconds squared"
--     MAX-ACCESS  read-only
--     STATUS      current
--     DESCRIPTION
--         "The value of tnOamTrHopsRttHCSumSquares indicates the high counter
--          for the sum of squares of the received response times of the OAM
--          trace route for this hop. Its purpose is to enable standard deviation
--          calculation."
--     ::= { tnOamTrHopsEntry 30 }
--
-- tnOamTrHopsTtOFSumSquares OBJECT-TYPE
--     SYNTAX      Counter32
--     MAX-ACCESS  read-only
--     STATUS      current
--     DESCRIPTION
--         "This object contains a count of the number of times
--          tnOamTrHopsTtSumOfSquares overflowed."
--     ::= { tnOamTrHopsEntry 31 }
--
-- tnOamTrHopsTtHCSumSquares OBJECT-TYPE
--     SYNTAX      Counter64
--     UNITS       "microseconds squared"
--     MAX-ACCESS  read-only
--     STATUS      current
--     DESCRIPTION
--         "The value of tnOamTrHopsTtHCSumSquares indicates the high counter
--          for the sum of squares of the outbound one-way trip times for the
--          OAM trace route for this hop. Its purpose is to enable standard
--          deviation calculation."
--     ::= { tnOamTrHopsEntry 32 }
--
-- tnOamTrHopsInTtOFSumSqrs OBJECT-TYPE
--     SYNTAX      Counter32
--     MAX-ACCESS  read-only
--     STATUS      current
--     DESCRIPTION
--         "This object contains a count of the number of times
--          tnOamTrHopsInTtSumOfSqrs overflowed."
--     ::= { tnOamTrHopsEntry 33 }
--
-- tnOamTrHopsInTtHCSumSqrs OBJECT-TYPE
--     SYNTAX      Counter64
--     UNITS       "microseconds squared"
--     MAX-ACCESS  read-only
--     STATUS      current
--     DESCRIPTION
--         "The value of tnOamTrHopsInTtHCSumSqrs indicates the high counter
--          for the sum of squares of the inbound one-way trip times of the OAM
--          trace route for this hop. Its purpose is to enable standard deviation
--          calculation.
--
--          The value of this object will be reported as 0 when no one-way trip
--          time measurement is available."
--     ::= { tnOamTrHopsEntry 34 }

--
--  Nokia SROS OAM MAC Trace Route Control Table
--
--
--  Sparsely dependent extension of the tnOamTrCtlTable.
--
--  The same indexes are used for both the base table, tnOamTrCtlTable,
--  and the sparse dependent table, tnOamMacTrCtlTable.
--
--  This in effect extends the tnOamTrCtlTable with additional columns.
--  Rows are created in the tnOamMacTrCtlTable only for those entries
--  in the tnOamTrCtlTable where tnOamTrCtlTestMode has a value of
--  'macTraceRoute'.
--
--  Deletion of a row in the tnOamTrCtlTable results in the
--  same fate for the row in the tnOamMacTrCtlTable.
--
-- tnOamMacTrCtlTable     OBJECT-TYPE
--     SYNTAX      SEQUENCE OF TnOamMacTrCtlEntry
--     MAX-ACCESS  not-accessible
--     STATUS      current
--     DESCRIPTION
--         "Defines the Nokia SROS OAM MAC Trace Route Control Table for
--          providing, via SNMP, the capability of performing Nokia SROS
--          OAM 'macTraceRoute' test operations.  The results of these tests
--          are stored in the tnOamTrResultsTable, tnOamTrProbeHistoryTable
--          and the tnOamMacTrL2MapTable."
--    ::= { tnOamTraceRouteObjs 7 }
--
-- tnOamMacTrCtlEntry OBJECT-TYPE
--     SYNTAX      TnOamMacTrCtlEntry
--     MAX-ACCESS  not-accessible
--     STATUS      current
--     DESCRIPTION
--         "Defines an entry in the tnOamMacTrCtlTable.  The first index
--          element, tnOamTrCtlOwnerIndex, is of type SnmpAdminString,
--          a textual convention that allows for use of the SNMPv3
--          View-Based Access Control Model (RFC 2575 [11], VACM)
--          and allows a management application to identify its entries.
--          The second index, tnOamTrCtlTestIndex, enables the same
--          management application to have multiple outstanding requests."
--     INDEX {
--            tnOamTrCtlOwnerIndex,
--            tnOamTrCtlTestIndex
--           }
--     ::= { tnOamMacTrCtlTable 1 }
--
--  TnOamMacTrCtlEntry ::=
--     SEQUENCE {
--        tnOamMacTrCtlTargetMacAddr    MacAddress,
--        tnOamMacTrCtlSourceMacAddr    MacAddress,
--        tnOamMacTrCtlSendControl      TruthValue,
--        tnOamMacTrCtlReplyControl     TruthValue
--     }
--
-- tnOamMacTrCtlTargetMacAddr   OBJECT-TYPE
--     SYNTAX      MacAddress
--     MAX-ACCESS  read-create
--     STATUS      current
--     DESCRIPTION
--         "The value of tnOamMacTrCtlTargetMacAddr is a 6-octet value
--          that specifies the target MAC address to be used in the query
--          request for performing an OAM Mac Trace Route operation when
--          tnOamTrCtlTestMode has a value of 'macTraceRoute'. "
--     REFERENCE
--         "IEEE 802.3 Subclause 30.7.1.1.9"
--     DEFVAL { '000000000000'H }
--     ::= { tnOamMacTrCtlEntry 1 }
--
-- tnOamMacTrCtlSourceMacAddr   OBJECT-TYPE
--     SYNTAX      MacAddress
--     MAX-ACCESS  read-create
--     STATUS      current
--     DESCRIPTION
--         "The value of tnOamMacTrCtlSourceMacAddr is a 6-octet value
--          that specifies the MAC address to be used as the source in the
--          query request for performing an OAM MAC Trace Route operation when
--          tnOamTrCtlTestMode has a value of 'macTraceRoute'. "
--     REFERENCE
--         "IEEE 802.3 Subclause 30.7.1.1.9"
--     DEFVAL { '000000000000'H }
--     ::= { tnOamMacTrCtlEntry 2 }
--
-- tnOamMacTrCtlSendControl     OBJECT-TYPE
--     SYNTAX      TruthValue
--     MAX-ACCESS  read-create
--     STATUS      current
--     DESCRIPTION
--         "When the value of tnOamMacTrCtlSendControl is 'true', the OAM
--         MAC Trace Route packet is sent directly to the destination IP address
--         via the control plane.  If its value is 'false', the packet is sent
--         via the data plane."
--     DEFVAL { false }
--     ::= { tnOamMacTrCtlEntry 3 }
--
-- tnOamMacTrCtlReplyControl        OBJECT-TYPE
--     SYNTAX      TruthValue
--     MAX-ACCESS  read-create
--     STATUS      current
--     DESCRIPTION
--         "When the value of tnOamMacTrCtlReplyControl is 'true', the
--         OAM Mac Trace Route response is returned using the control plane.
--         If its value is 'false', the packet is sent via the data plane."
--     DEFVAL { false }
--     ::= { tnOamMacTrCtlEntry 4 }

--
-- Nokia SROS series OAM MAC Trace Route Label Mapping Table
--
-- tnOamMacTrL2MapTable OBJECT-TYPE
--     SYNTAX      SEQUENCE OF TnOamMacTrL2MapEntry
--     MAX-ACCESS  not-accessible
--     STATUS      current
--     DESCRIPTION
--         "Defines a table for storing the results of an OAM 'macTraceRoute'
--          probe operation when a L2 Mapping TLV was returned.  Each row
--          represents a single L2FEC TLV within the L2 Mapping TLV. A single
--          L2 mapping entry is returned if the 'macTraceRoute' replier knows
--          the requested VPN ID and has a binding for the requested MAC
--          address.  Multiple downstream L2 mappings that specify
--          the replier's flooding domain may be returned if the replier has
--          no bindings for the MAC address.

--          An entry in this table is created when the result of an OAM
--          'macTraceRoute' probe is determined.  An entry is removed from
--          this table when its corresponding tnOamTrCtlEntry is deleted."
--    ::= { tnOamTraceRouteObjs 8 }

-- tnOamMacTrL2MapEntry OBJECT-TYPE
--     SYNTAX      TnOamMacTrL2MapEntry
--     MAX-ACCESS  not-accessible
--     STATUS      current
--     DESCRIPTION
--         "Defines an entry in the tnOamMacTrL2MapTable.  The first two
--          index elements identify the tnOamTrCtlEntry that a
--          tnOamMacTrL2MapEntry belongs to.  The third index element
--          identifies a particular OAM trace route test run.  The fourth
--          index element selects the group of responses associated with a
--          specific probe attempt.  The fifth and sixth indexes select the
--          hop and the probe at that hop for a particular Nokia SROS
--          OAM Trace Route operation.  Note that in the case of a successful
--          'macTraceRoute' reply there will be only one row entry created.
--          However there may also be one or more error replies.  The seventh
--          index selects a single L2 mapping entry within a specific
--          probe reply."
--     INDEX {
--             tnOamTrCtlOwnerIndex,
--             tnOamTrCtlTestIndex,
--             tnOamTrResultsTestRunIndex,
--             tnOamTrProbeHistoryIndex,
--             tnOamTrProbeHistoryHopIndex,
--             tnOamTrProbeHistoryProbeIndex,
--             tnOamMacTrL2MapIndex
--            }
--     ::= { tnOamMacTrL2MapTable 1 }

--  TnOamMacTrL2MapEntry ::=
--     SEQUENCE {
--        tnOamMacTrL2MapIndex        Unsigned32,
--        tnOamMacTrL2MapRouterID     IpAddress,
--        tnOamMacTrL2MapLabel        MplsLabel,
--        tnOamMacTrL2MapProtocol     TmnxOamSignalProtocol,
--        tnOamMacTrL2MapVCType       TmnxOamVcType,
--        tnOamMacTrL2MapVCID         TmnxVcId,
--        tnOamMacTrL2MapDirection    INTEGER,
--        tnOamMacTrL2MapSdpId        SdpId,
--        tnOamMacTrL2MapSapName      TNamedItemOrEmpty
--     }

-- tnOamMacTrL2MapIndex OBJECT-TYPE
--  NOTE: The UCD snmpget utility program does not parse this correctly
--    SYNTAX      Unsigned32 (1..'ffffffff'h)
--     SYNTAX      Unsigned32 (1..4294967295)
--     MAX-ACCESS  not-accessible
--     STATUS      current
--     DESCRIPTION
--         "The tnOamMacTrL2MapIndex selects a single L2 mapping entry
--          within a specific 'macTraceRoute' probe reply.

--          The agent starts assigning tnOamMacTrL2MapIndex values at 1."
--     ::= { tnOamMacTrL2MapEntry 1 }

-- tnOamMacTrL2MapRouterID    OBJECT-TYPE
--     SYNTAX      IpAddress
--     MAX-ACCESS  read-only
--     STATUS      current
--     DESCRIPTION
--         "The value of tnOamMacTrL2MapRouterID is the router ID for this
--          L2 mapping entry."
--     ::= { tnOamMacTrL2MapEntry 2 }

-- tnOamMacTrL2MapLabel       OBJECT-TYPE
--     SYNTAX      MplsLabel
--     MAX-ACCESS  read-only
--     STATUS      current
--     DESCRIPTION
--         "The value of tnOamMacTrL2MapLabel is the label used by the
--          router for the L2FEC or VC ID specified by this L2 mapping entry."
--     ::= { tnOamMacTrL2MapEntry 3 }

-- tnOamMacTrL2MapProtocol    OBJECT-TYPE
--     SYNTAX      TmnxOamSignalProtocol
--     MAX-ACCESS  read-only
--     STATUS      current
--     DESCRIPTION
--         "The value of tnOamMacTrL2MapProtocol is the signaling protocol
--          used by the router for the L2FEC or VC ID specified by this L2
--          mapping entry."
--     ::= { tnOamMacTrL2MapEntry 4 }

-- tnOamMacTrL2MapVCType       OBJECT-TYPE
--     SYNTAX      TmnxOamVcType
--     MAX-ACCESS  read-only
--     STATUS      current
--     DESCRIPTION
--         "The value of tnOamMacTrL2MapVCType specifies the class of
--          VC ID given in tnOamMacTrL2MapVCID."
--     ::= { tnOamMacTrL2MapEntry 5 }

-- tnOamMacTrL2MapVCID        OBJECT-TYPE
--     SYNTAX      TmnxVcId
--     MAX-ACCESS  read-only
--     STATUS      current
--     DESCRIPTION
--         "The value of tnOamMacTrL2MapVCID is the VC ID associated with
--          the label used by the L2FEC specified by this L2 mapping entry."
--     ::= { tnOamMacTrL2MapEntry 6 }

-- tnOamMacTrL2MapDirection       OBJECT-TYPE
--     SYNTAX      INTEGER {
--                     upstream (1),
--                     downstream (2)
--                 }
--     MAX-ACCESS  read-only
--     STATUS      current
--     DESCRIPTION
--         "The value of tnOamMacTrL2MapDirection specifies the direction
--          that this L2 mapping entry is in relation to the node that returned
--          the 'macTraceRoute' reply."
--     ::= { tnOamMacTrL2MapEntry 7 }

-- tnOamMacTrL2MapSdpId     OBJECT-TYPE
--     SYNTAX      SdpId
--     MAX-ACCESS  read-only
--     STATUS      current
--     DESCRIPTION
--         "The value of tnOamMacTrL2MapSdpId specifies the ID of the SDP
--          supporting the L2 mapping entry that returned the reply.

--          If this mapping is not a SDP, this object is not relevant and
--          MUST return a value of '0'."
--     ::= { tnOamMacTrL2MapEntry 8 }

-- tnOamMacTrL2MapSapName    OBJECT-TYPE
--     SYNTAX      TNamedItemOrEmpty
--     MAX-ACCESS  read-only
--     STATUS      current
--     DESCRIPTION
--         "The value of tnOamMacTrL2MapSapName specifies the SAP name
--          when the downstream of the responder is a SAP.

--          If the downstream responder is not a SAP, this object is not
--          relevant and MUST return a zero length empty string."
--     ::= { tnOamMacTrL2MapEntry 9 }


--
--  Nokia SROS series OAM LSP Trace Route Control Table
--
--
--  Sparsely dependent extension of the tnOamTrCtlTable.
--
--  The same indexes are used for both the base table, tnOamTrCtlTable,
--  and the sparse dependent table, tnOamLspTrCtlTable.
--
--  This in effect extends the tnOamTrCtlTable with additional columns.
--  Rows are created in the tnOamLspTrCtlTable only for those entries
--  in the tnOamTrCtlTable where tnOamTrCtlTestMode has a value of
--  'lspTraceRoute'.
--
--  Deletion of a row in the tnOamTrCtlTable results in the
--  same fate for the row in the tnOamLspTrCtlTable.
--

tnOamLspTrCtlTable     OBJECT-TYPE
    SYNTAX      SEQUENCE OF TnOamLspTrCtlEntry
    MAX-ACCESS  not-accessible
    STATUS      current
    DESCRIPTION
        "Defines the Nokia SROS OAM LSP Trace Route Control Table
         for providing, via SNMP, the capability of performing Nokia
         SROS OAM 'lspTraceRoute' test operations.  The results of
         these tests are stored in the tnOamTrResultsTable and the
         tnOamTrProbeHistoryTable."
   ::= { tnOamTraceRouteObjs 9 }

tnOamLspTrCtlEntry OBJECT-TYPE
    SYNTAX      TnOamLspTrCtlEntry
    MAX-ACCESS  not-accessible
    STATUS      current
    DESCRIPTION
        "Defines an entry in the tnOamLspTrCtlTable.  The first index
         element, tnOamTrCtlOwnerIndex, is of type SnmpAdminString,
         a textual convention that allows for use of the SNMPv3
         View-Based Access Control Model (RFC 2575 [11], VACM)
         and allows a management application to identify its entries.
         The second index, tnOamTrCtlTestIndex, enables the same
         management application to have multiple outstanding requests."
    INDEX {
           tnSysSwitchId,
           -- tnOamTrCtlOwnerIndex,
           tnOamTrCtlTestIndex
          }
    ::= { tnOamLspTrCtlTable 1 }

TnOamLspTrCtlEntry ::=
    SEQUENCE {
       tnOamLspTrCtlVRtrID           TmnxVRtrID,
       tnOamLspTrCtlLspName          TNamedItemOrEmpty,
       tnOamLspTrCtlPathName         TNamedItemOrEmpty,
       tnOamLspTrCtlLdpIpPrefix      IpAddress,
       tnOamLspTrCtlLdpIpPrefixLen   IpAddressPrefixLength,
       tnOamLspTrCtlLdpPrefixType    InetAddressType,
       tnOamLspTrCtlLdpPrefix        InetAddress,
       tnOamLspTrCtlLdpPrefixLen     InetAddressPrefixLength,
       tnOamLspTrCtlPathDestType     InetAddressType,
       tnOamLspTrCtlPathDest         InetAddress,
       tnOamLspTrCtlNhIntfName       TNamedItemOrEmpty,
       tnOamLspTrCtlNhAddressType    InetAddressType,
       tnOamLspTrCtlNhAddress        InetAddress,
       tnOamLspTrCtlDownstreamMapTlv  TmnxOamMplsEchoDownMapTlvOrNone,
       tnOamLspTrCtlTestSubMode       TmnxOamLspTestSubMode,
       tnOamLspTrCtlMplsTpPathType    TmnxOamMplsTpPathType,
       tnOamLspTrCtlAssocChannel      TmnxOamLspAssocChannel,
       tnOamLspTrCtlForce             TruthValue
    }

tnOamLspTrCtlVRtrID  OBJECT-TYPE
    SYNTAX      TmnxVRtrID
    MAX-ACCESS  read-create
    STATUS      obsolete
    DESCRIPTION
        "The unique value which identifies this virtual router in the
         Nokia SROS system. The vRtrID value for each virtual router
         must remain constant at least from one re-initialization of the
         system management processor (CPM) to the next.  There will always
         be at least one router entry defined by the agent with vRtrID=1
         which represents the base transport router.

         This object was obsoleted in release 6.0R15 and replaced with
         tnOamTrCtlVRtrID in tnOamTrCtlTable."
    DEFVAL { 1 }
    ::= { tnOamLspTrCtlEntry 1 }

tnOamLspTrCtlLspName     OBJECT-TYPE
    SYNTAX      TNamedItemOrEmpty
    MAX-ACCESS  read-create
    STATUS      current
    DESCRIPTION
        "Administrative name of the target Labeled Switch Path (LSP) for this
         OAM LSP Trace Route test.  The LSP name must be unique within the
         virtual router instance specified by tnOamLspTrCtlVRtrID.

         This parameter is mutually exclusive with the IP prefix parameter
         associated with an LDP based LSP (tnOamLspTrCtlLdpIpPrefix). Either
         the LSP name or the LDP IP Prefix must be specified but not both."
    DEFVAL { ''H }  -- the empty string
    ::= { tnOamLspTrCtlEntry 2 }

tnOamLspTrCtlPathName     OBJECT-TYPE
    SYNTAX      TNamedItemOrEmpty
    MAX-ACCESS  read-create
    STATUS      current
    DESCRIPTION
        "Administrative name of the Path (LSP) for this OAM LSP Trace Route
         test. The Path name must be unique within the virtual router
         instance specified by tnOamLspTrCtlVRtrID.

         This is an optional parameter which can be specified only if the
         LSP Name parameter is specified."
    DEFVAL { ''H }  -- the empty string
    ::= { tnOamLspTrCtlEntry 3 }

tnOamLspTrCtlLdpIpPrefix     OBJECT-TYPE
    SYNTAX      IpAddress
    MAX-ACCESS  read-create
    STATUS      obsolete
    DESCRIPTION
        "The IP prefix for the LDP based LSP for this OAM LSP Trace Route
         test.

         This parameter is mutually exclusive with the LSP name parameter
         (tnOamLspTrCtlLspName). Either the LDP IP Prefix or the LSP name
         must be specified but not both.

         This object was obsoleted in release 4.0 and replaced with
         InetAddress objects tnOamLspTrCtlLdpPrefixType and
         tnOamLspTrCtlLdpPrefix."
    DEFVAL { '00000000'H } -- 0.0.0.0
    ::= { tnOamLspTrCtlEntry 4 }

tnOamLspTrCtlLdpIpPrefixLen     OBJECT-TYPE
    SYNTAX      IpAddressPrefixLength
    MAX-ACCESS  read-create
    STATUS      obsolete
    DESCRIPTION
        "The IP prefix length for the LDP based LSP for this OAM LSP Trace
         Route test.

         The value of this parameter is valid only when LDP IP Prefix
         has been specified.

         This object was obsoleted in release 4.0 and replaced with
         InetAddress object tnOamLspTrCtlLdpPrefixLen."
    DEFVAL { 32 }
    ::= { tnOamLspTrCtlEntry 5 }

tnOamLspTrCtlLdpPrefixType     OBJECT-TYPE
    SYNTAX      InetAddressType
    MAX-ACCESS  read-create
    STATUS      current
    DESCRIPTION
        "The value of tnOamLspTrCtlLdpPrefixType specifies the type of
         Internet address stored in tnOamLspTrCtlLdpPrefix."
    DEFVAL { unknown }
    ::= { tnOamLspTrCtlEntry 6 }

tnOamLspTrCtlLdpPrefix     OBJECT-TYPE
    SYNTAX      InetAddress (SIZE (0|4|16))
    MAX-ACCESS  read-create
    STATUS      current
    DESCRIPTION
        "The value of tnOamLspTrCtlLdpPrefix specifies the Internet address
         prefix for the LDP based LSP for this OAM LSP Trace Route
         test.

         This parameter is mutually exclusive with the LSP name parameter
         (tnOamLspTrCtlLspName). Either the LDP IP Prefix or the LSP name
         must be specified but not both."
    DEFVAL { ''H }
    ::= { tnOamLspTrCtlEntry 7 }

tnOamLspTrCtlLdpPrefixLen     OBJECT-TYPE
    SYNTAX      InetAddressPrefixLength
    MAX-ACCESS  read-create
    STATUS      current
    DESCRIPTION
        "The value of tnOamLspTrCtlLdpPrefixLen specifies the Internet
         address prefix length for the LDP based LSP for this OAM LSP Trace
         Route test.

         The value of this parameter is valid only when LDP IP Prefix
         has been specified."
    DEFVAL { 32 }
    ::= { tnOamLspTrCtlEntry 8 }

tnOamLspTrCtlPathDestType    OBJECT-TYPE
    SYNTAX      InetAddressType
    MAX-ACCESS  read-create
    STATUS      current
    DESCRIPTION
        "The value of tnOamLspTrCtlPathDestType specifies the type
         of Internet address stored in tnOamLspTrCtlPathDest."
    DEFVAL { unknown }
    ::= { tnOamLspTrCtlEntry 9 }

tnOamLspTrCtlPathDest     OBJECT-TYPE
    SYNTAX      InetAddress (SIZE (0|4|16))
    MAX-ACCESS  read-create
    STATUS      current
    DESCRIPTION
        "The value of tnOamLspTrCtlPathDest specifies a unique path
         in a multipath setup for this OAM LSP Trace Route to traverse.
         This address is used as part of a hash key to select the
         appropriate ECMP to the destination of an OAM LSP Trace test.

         This is an optional parameter. "
    DEFVAL { ''H }
    ::= { tnOamLspTrCtlEntry 10 }

tnOamLspTrCtlNhIntfName     OBJECT-TYPE
    SYNTAX      TNamedItemOrEmpty
    MAX-ACCESS  read-create
    STATUS      current
    DESCRIPTION
        "Administrative name of the next hop interface for this OAM LSP
         Trace Route test to be sent. The interface name must be unique
         within the virtual router instance specified by
         tnOamLspTrCtlVRtrID.

         This is an optional parameter which can be specified only if the
         tnOamLspTrCtlPathDest parameter is specified. This parameter
         is mutually exclusive with the tnOamLspTrCtlNhAddress
         parameter. Either the next-hop interface name or next-hop address
         can be specified but not both. An attempt to set this object to a
         non-default value when tnOamLspTrCtlNhAddress has a
         non-default value will result in an 'inconsistentValue' error."

    DEFVAL { ''H }  -- the empty string
    ::= { tnOamLspTrCtlEntry 11 }

tnOamLspTrCtlNhAddressType    OBJECT-TYPE
    SYNTAX      InetAddressType
    MAX-ACCESS  read-create
    STATUS      current
    DESCRIPTION
        "The value of tnOamLspTrCtlNhAddressType specifies the type
         of Internet address stored in tnOamLspTrCtlNhAddress."
    DEFVAL { unknown }
    ::= { tnOamLspTrCtlEntry 12 }

tnOamLspTrCtlNhAddress     OBJECT-TYPE
    SYNTAX      InetAddress (SIZE (0|4|16))
    MAX-ACCESS  read-create
    STATUS      current
    DESCRIPTION
        "The value of tnOamLspTrCtlNhAddress specifies the Interface
         address to the next hop through which this OAM LSP Trace Route
         test is to be transmitted.

         This is an optional parameter which can be specified only if the
         tnOamLspTrCtlPathDest parameter is specified. This parameter
         is mutually exclusive with tnOamLspTrCtlNhIntfName parameter.
         Either the next-hop interface name or next-hop address
         can be specified but not both. An attempt to set this object to a
         non-default value when tnOamLspTrCtlNhIntfName has a
         non-default value will result in an 'inconsistentValue' error."
    DEFVAL { ''H }
    ::= { tnOamLspTrCtlEntry 13 }

tnOamLspTrCtlDownstreamMapTlv  OBJECT-TYPE
    SYNTAX      TmnxOamMplsEchoDownMapTlvOrNone
    MAX-ACCESS  read-create
    STATUS      current
    DESCRIPTION
        "The value of tnOamLspTrCtlDownstreamMapTlv specifies the type of
         downstream mapping TLV to insert in the MPLS echo request PDU when
         launching the test.


         When an LSP trace route test is created, the value of this object
         defaults to the value of the global configuration object
         tnOamMplsEchoDownstreamMapTlv.

         The supported object combinations for LSP trace route tests are listed
         in the tnOamLspTrCtlTable DESCRIPTION clause."

    DEFVAL { dsmap }

    ::= { tnOamLspTrCtlEntry 14 }

tnOamLspTrCtlTestSubMode       OBJECT-TYPE
    SYNTAX      TmnxOamLspTestSubMode
    MAX-ACCESS  read-create
    STATUS      current
    DESCRIPTION
        "The value of tnOamLspTrCtlTestSubMode specifies the type of LSP
         trace route test to perform.

         When this object is 'unspecified(1)', the type of LSP trace route test
         to be performed is determined when the test is started, from the set of
         tnOamLspTrCtlTable objects configured with non-default values.

         If there is a mismatch between tnOamLspTrCtlTestSubMode and the
         type of the LSP to be tested, the test will fail.  For example, if
         tnOamLspTrCtlTestSubMode is 'static(2)', and
         tnOamLspTrCtlLspName refers to an LSP with
         TIMETRA-MPLS-MIB::vRtrMplsLspType not equal to 'mplsTp(7)', the test
         will fail.

         The supported object combinations for LSP trace route tests are listed
         in the tnOamLspTrCtlTable DESCRIPTION clause."
    DEFVAL { unspecified }
    ::= { tnOamLspTrCtlEntry 15 }

tnOamLspTrCtlMplsTpPathType    OBJECT-TYPE
    SYNTAX      TmnxOamMplsTpPathType
    MAX-ACCESS  read-create
    STATUS      current
    DESCRIPTION
        "The value of tnOamLspTrCtlMplsTpPathType specifies the type of the
         MPLS-TP path to be tested.

         The supported object combinations for LSP trace route tests are listed
         in the tnOamLspTrCtlTable DESCRIPTION clause."
    DEFVAL { active }
    ::= { tnOamLspTrCtlEntry 16 }

tnOamLspTrCtlAssocChannel      OBJECT-TYPE
    SYNTAX      TmnxOamLspAssocChannel
    MAX-ACCESS  read-create
    STATUS      current
    DESCRIPTION
        "The value of tnOamLspTrCtlAssocChannel specifies the launched echo
         request's usage of the Associated Channel (ACH) mechanism, when testing
         an MPLS-TP LSP.

         When tnOamLspTrCtlTestSubMode is 'static(2)', the default value for
         tnOamLspTrCtlAssocChannel is 'nonIp(2)'.

         The supported object combinations for LSP trace route tests are listed
         in the tnOamLspTrCtlTable DESCRIPTION clause."
    DEFVAL { notApplicable }
    ::= { tnOamLspTrCtlEntry 17 }

tnOamLspTrCtlForce             OBJECT-TYPE
    SYNTAX      TruthValue
    MAX-ACCESS  read-create
    STATUS      current
    DESCRIPTION
        "The value of tnOamLspTrCtlForce specifies whether or not to force
         the transmission of the 'lspTraceRoute' request PDU(s).

         If tnOamLspTrCtlForce is 'true(1)', the test will proceed and request
         PDU(s) will be sent regardless of the local operational status of the
         tested LSP path.

         If tnOamLspTrCtlForce is 'false(2)',  the test will fail
         immediately when the local operational status of the tested LSP path is
         down.

         The supported object combinations for LSP trace route tests are listed
         in the tnOamLspTrCtlTable DESCRIPTION clause."
    DEFVAL { false }
    ::= { tnOamLspTrCtlEntry 18 }

--
-- Nokia SROS series OAM Lsp Trace Route Downstream L2 Mapping Table
--

tnOamLspTrMapTable OBJECT-TYPE
    SYNTAX      SEQUENCE OF TnOamLspTrMapEntry
    MAX-ACCESS  not-accessible
    STATUS      current
    DESCRIPTION
        "Defines a table for storing the results of an OAM 'lspTraceRoute'
         probe operation when a Downstream Mapping TLV was returned.  Each row
         represents a single label map within the returned downstream mapping
         TLV.

         An entry in this table is created when the result of an OAM
         'lspTraceRoute' or 'p2mpLspTrace' probe is determined.

         An entry is removed from this table when its corresponding
         tnOamTrCtlEntry is deleted."
   ::= { tnOamTraceRouteObjs 10 }

tnOamLspTrMapEntry OBJECT-TYPE
    SYNTAX      TnOamLspTrMapEntry
    MAX-ACCESS  not-accessible
    STATUS      current
    DESCRIPTION
        "Defines an entry in the tnOamLspTrMapTable.  The first two
         index elements identify the tnOamTrCtlEntry that a
         tnOamLspTrMapEntry belongs to.  The third index element
         identifies an OAM trace route test run.  The fourth index element
         selects the group of responses associated with a specific
         probe attempt. The fifth and sixth indexes select the hop and
         the probe at that hop for a particular Nokia SROS OAM
         Trace Route operation. The seventh index selects a single downstream
         L2 map entry within the specific probe reply."
    INDEX {
            tnSysSwitchId,
            -- tnOamTrCtlOwnerIndex,
            tnOamTrCtlTestIndex,
            tnOamTrResultsTestRunIndex,
            tnOamTrProbeHistoryIndex,
            tnOamTrProbeHistoryHopIndex,
            tnOamTrProbeHistoryProbeIndex,
            tnOamLspTrMapIndex
           }
    ::= { tnOamLspTrMapTable 1 }

 TnOamLspTrMapEntry ::=
    SEQUENCE {
       tnOamLspTrMapIndex         Unsigned32,
       tnOamLspTrMapDSIPv4Addr    IpAddress,
       tnOamLspTrMapAddrType      TmnxOamAddressType,
       tnOamLspTrMapDSIfAddr      Unsigned32,
       tnOamLspTrMapMTU           Unsigned32,
       tnOamLspTrMapDSIndex       Unsigned32
    }

tnOamLspTrMapIndex OBJECT-TYPE
-- NOTE: The UCD snmpget utility program does not parse this correctly
--   SYNTAX      Unsigned32 (1..'ffffffff'h)
    SYNTAX      Unsigned32 (1..4294967295)
    MAX-ACCESS  not-accessible
    STATUS      current
    DESCRIPTION
        "An entry in this table is created when the result of a OAM
         'lspTraceRoute' probe is determined.  The initial 2
         instance identifier index values identify the tnOamTrCtlEntry
         that a OAM probe result (tnOamTrProbeHistoryEntry) belongs
         to.  The tnOamTrProbeHistoryIndex identifies a group of replies
         received in response to a specific probe transmission. The fourth
         and fifth indexes select the hop and the probe at that hop for a
         particular Nokia SROS OAM Trace Route operation.

         The tnOamLspTrMapIndex selects a single L2 mapping entry
         within a specific 'lspTraceRoute' probe reply.

         The agent starts assigning tnOamLspTrMapIndex values at 1."
    ::= { tnOamLspTrMapEntry 1 }

tnOamLspTrMapDSIPv4Addr    OBJECT-TYPE
    SYNTAX      IpAddress
    MAX-ACCESS  read-only
    STATUS      current
    DESCRIPTION
        "The value of tnOamLspTrMapDSIPv4Addr indicates the IPv4 address
         of the downstream LSR that this entry in the tnOamLspTrMapTable
         describes.  If the interface to the downstream LSR is numbered,
         then the tnOamLspTrMapDSIPv4Addr can either be the downstream
         LSR's Router ID or the interface address of the downstream LSR.

         If the interface to the downstream LSR is unnumbered, the value
         of tnOamLspTrMapDSIPv4Addr indicates the downstream LSR's Router
         ID."
    ::= { tnOamLspTrMapEntry 2 }

tnOamLspTrMapAddrType        OBJECT-TYPE
    SYNTAX      TmnxOamAddressType
    MAX-ACCESS  read-only
    STATUS      current
    DESCRIPTION
        "The value of tnOamLspTrMapAddrType indicates the type of
         downstream interface address specified by tnOamLspTrMapDSIfAddr.
         The only valid values for tnOamLspTrMapAddrType are
         'ipv4Address', 'ipv4Unnumbered', 'ipv6Address' and 'ipv6Unnumbered'."
    ::= { tnOamLspTrMapEntry 3 }

tnOamLspTrMapDSIfAddr        OBJECT-TYPE
    SYNTAX      Unsigned32
    MAX-ACCESS  read-only
    STATUS      current
    DESCRIPTION
        "When tnOamLspTrMapAddrType has a value of 'ipv4Address'
         tnOamLspTrMapDSIfAddr indicates the downstream LSR's
         interface address.  When tnOamLspTrMapAddrType has a value
         of 'unnumbered', tnOamLspTrMapDSIfAddr indicates the index
         assigned by the upstream LSR to the interface."
    ::= { tnOamLspTrMapEntry 4 }

tnOamLspTrMapMTU     OBJECT-TYPE
    SYNTAX      Unsigned32 (0..65535)
    MAX-ACCESS  read-only
    STATUS      current
    DESCRIPTION
        "The value of tnOamLspTrMapMTU indicates the largest MPLS frame
         (including the label stack) that fits on the interface to the
         downstream LSR."
    ::= { tnOamLspTrMapEntry 5 }

tnOamLspTrMapDSIndex     OBJECT-TYPE
    SYNTAX      Unsigned32 (0..255)
    MAX-ACCESS  read-only
    STATUS      obsolete
    DESCRIPTION
        "The value of tnOamLspTrMapDSIndex indicates the unique index
         assigned to the pair of downstream router and interface addresses
         represented by this row in the tnOamLspTrMapTable.

         tnOamLspTrMapDSIndex object was obsolete in release 5.0"
    ::= { tnOamLspTrMapEntry 6 }

--
--  Nokia SROS series OAM VPRN Trace Route Control Table
--
--
--  Sparse Dependent Extension of the tnOamTrCtlTable.
--
--  The same indexes are used for both the base table, tnOamTrCtlTable,
--  and the sparse dependent table, tnOamVprnTrCtlTable.
--
--  This in effect extends the tnOamTrCtlTable with additional columns.
--  Rows are created in the tnOamVprnTrCtlTable only for those entries
--  in the tnOamTrCtlTable where tnOamTrCtlTestMode has a value of
--  'vprnTraceRoute'.
--
--  Deletion of a row in the tnOamTrCtlTable results in the
--  same fate for the row in the tnOamVprnTrCtlTable.
--
-- tnOamVprnTrCtlTable     OBJECT-TYPE
--     SYNTAX      SEQUENCE OF TnOamVprnTrCtlEntry
--     MAX-ACCESS  not-accessible
--     STATUS      current
--     DESCRIPTION
--         "Defines the Nokia SROS OAM VPRN Trace Route Control Table for
--          providing, via SNMP, the capability of performing Nokia SROS
--          OAM 'vprnTraceRoute' test operations.  The results of these tests
--          are stored in the tnOamTrResultsTable, the
--          tnOamTrProbeHistoryTable, the tnOamVprnTrRTTable and the
--          tnOamVprnTrNextHopTable."
--    ::= { tnOamTraceRouteObjs 11 }

-- tnOamVprnTrCtlEntry OBJECT-TYPE
--     SYNTAX      TnOamVprnTrCtlEntry
--     MAX-ACCESS  not-accessible
--     STATUS      current
--     DESCRIPTION
--         "Defines an entry in the tnOamVprnTrCtlTable.  The first index
--          element, tnOamTrCtlOwnerIndex, is of type SnmpAdminString,
--          a textual convention that allows for use of the SNMPv3
--          View-Based Access Control Model (RFC 2575 [11], VACM)
--          and allows a management application to identify its entries.
--          The second index, tnOamTrCtlTestIndex, enables the same
--          management application to have multiple outstanding requests."
--     INDEX {
--             tnOamTrCtlOwnerIndex,
--             tnOamTrCtlTestIndex
--           }
--     ::= { tnOamVprnTrCtlTable 1 }

--  TnOamVprnTrCtlEntry ::=
--     SEQUENCE {
--        tnOamVprnTrCtlSourceIpAddr        IpAddress,
--        tnOamVprnTrCtlReplyControl        TruthValue,
--        tnOamVprnTrCtlSrcAddrType         InetAddressType,
--        tnOamVprnTrCtlSrcAddress          InetAddress
--     }

-- tnOamVprnTrCtlSourceIpAddr       OBJECT-TYPE
--     SYNTAX      IpAddress
--     MAX-ACCESS  read-create
--     STATUS      obsolete
--     DESCRIPTION
--         "Specifies the Ipv4 address to be used as the source for
--          performing an OAM 'vprnTraceRoute' operation when tnOamTrCtlTestMode
--          has a value of 'vprnTraceRoute'.   This parameter is required.

--          This object was obsoleted in release 4.0 and replaced with
--          InetAddress objects tnOamVprnTrCtlSrcAddrType and
--          tnOamVprnTrCtlSrcAddress."
--     DEFVAL { '00000000'h }   --   -- 0.0.0.0
--     ::= { tnOamVprnTrCtlEntry 1 }

-- tnOamVprnTrCtlReplyControl       OBJECT-TYPE
--     SYNTAX      TruthValue
--     MAX-ACCESS  read-create
--     STATUS      current
--     DESCRIPTION
--         "When the value of tnOamVprnTrCtlReplyControl is 'true', the
--          OAM 'vprnTraceRoute' response is returned using the control plane.
--          If its value is 'false', the packet is sent via the data plane.

--          This object is optional and is not relevant when tnOamTrCtlTestMode
--          has a value other than 'vprnTraceRoute'."
--     DEFVAL { false }
--     ::= { tnOamVprnTrCtlEntry 2 }

-- tnOamVprnTrCtlSrcAddrType       OBJECT-TYPE
--     SYNTAX      InetAddressType
--     MAX-ACCESS  read-create
--     STATUS      current
--     DESCRIPTION
--         "The value of tnOamVprnTrCtlSrcAddrType specifies the type of
--          Internet address stored in tnOamVprnTrCtlSrcAddress."
--     DEFVAL { unknown }
--     ::= { tnOamVprnTrCtlEntry 3 }

-- tnOamVprnTrCtlSrcAddress       OBJECT-TYPE
--     SYNTAX      InetAddress (SIZE (0|4|16))
--     MAX-ACCESS  read-create
--     STATUS      current
--     DESCRIPTION
--         "The value of tnOamVprnTrCtlSrcAddress specifies the Internet
--          address to be used as the source for performing an OAM
--          'vprnTraceRoute' operation when tnOamTrCtlTestMode has a value of
--          'vprnTraceRoute'.   This parameter is required."
--     DEFVAL { ''H }
--     ::= { tnOamVprnTrCtlEntry 4 }

--
-- Nokia SROS series OAM VPRN Trace Route L3 Map Table
--
-- tnOamVprnTrL3MapTable OBJECT-TYPE
--     SYNTAX      SEQUENCE OF TnOamVprnTrL3MapEntry
--     MAX-ACCESS  not-accessible
--     STATUS      current
--     DESCRIPTION
--         "Defines a table for storing the results of an OAM 'vprnTraceRoute'
--          probe operation.  The number of entries for a test in this table
--          is limited to the results of 3 runs.
--
--          An entry in this table is created when the result of an OAM
--          'vprnTraceRoute' probe is determined.  An entry is removed from
--          this table when its corresponding tnOamTrCtlEntry is deleted."
--    ::= { tnOamTraceRouteObjs 12 }

-- tnOamVprnTrL3MapEntry OBJECT-TYPE
--     SYNTAX      TnOamVprnTrL3MapEntry
--     MAX-ACCESS  not-accessible
--     STATUS      current
--     DESCRIPTION
--         "Defines an entry in the tnOamVprnTrL3MapTable.  The first
--          two index elements identify the tnOamTrCtlEntry that a
--          tnOamVprnTrL3MapEntry belongs to.  The third index element
--          identifies an OAM trace route test run.  The fourth index element
--          selects a single Nokia SROS OAM 'vprnTraceRoute' operation
--          result.  The fifth and sixth indexes select the hop and the
--          probe at that hop for a particular Nokia SROS OAM
--          'vprnTraceRoute' operation.  The seventh index selects either the
--          requestor's or responder's L3 route information."
--     INDEX {
--             tnOamTrCtlOwnerIndex,
--             tnOamTrCtlTestIndex,
--             tnOamTrResultsTestRunIndex,
--             tnOamTrProbeHistoryIndex,
--             tnOamTrProbeHistoryHopIndex,
--             tnOamTrProbeHistoryProbeIndex,
--             tnOamVprnTrL3MapReporter
--           }
--     ::= { tnOamVprnTrL3MapTable 1 }

--  TnOamVprnTrL3MapEntry ::=
--     SEQUENCE {
--        tnOamVprnTrL3MapReporter          INTEGER,
--        tnOamVprnTrL3MapRouterID          RouterID,
--        tnOamVprnTrL3MapRteDestAddr       IpAddress,
--        tnOamVprnTrL3MapRteDestMask       Unsigned32,
--        tnOamVprnTrL3MapRteVprnLabel      MplsLabel,
--        tnOamVprnTrL3MapRteMetrics        Unsigned32,
--        tnOamVprnTrL3MapRteLastUp         DateAndTime,
--        tnOamVprnTrL3MapRteOwner          INTEGER,
--        tnOamVprnTrL3MapRtePref           Unsigned32,
--        tnOamVprnTrL3MapRteDist           TmnxVPNRouteDistinguisher,
--        tnOamVprnTrL3MapNumNextHops       Unsigned32,
--        tnOamVprnTrL3MapNumRteTargets     Unsigned32,
--        tnOamVprnTrL3MapDestAddrType      InetAddressType,
--        tnOamVprnTrL3MapDestAddress       InetAddress,
--        tnOamVprnTrL3MapDestMaskLen       InetAddressPrefixLength
--     }

-- tnOamVprnTrL3MapReporter        OBJECT-TYPE
--     SYNTAX      INTEGER {
--                     requestor (1),
--                     responder (2)
--                 }
--     MAX-ACCESS  not-accessible
--     STATUS      current
--     DESCRIPTION
--         "The value of tnOamVprnTrL3MapReporter specifies who reported
--          the route information in this row entry.  It may have come from
--          the 'vprnTraceRoute' requestor's local information or it may be
--           from the remote 'vprnTraceRoute' responder."
--     ::= { tnOamVprnTrL3MapEntry 1 }

-- tnOamVprnTrL3MapRouterID     OBJECT-TYPE
--     SYNTAX      RouterID
--     MAX-ACCESS  read-only
--     STATUS      current
--     DESCRIPTION
--         "The value of tnOamVprnTrL3MapRouterID indicates the router ID
--          of the node, requestor or responder, that provided this route
--          information."
--     ::= { tnOamVprnTrL3MapEntry 2 }

-- tnOamVprnTrL3MapRteDestAddr      OBJECT-TYPE
--     SYNTAX      IpAddress
--     MAX-ACCESS  read-only
--     STATUS      obsolete
--     DESCRIPTION
--         "The value of tnOamVprnTrL3MapRteDestAddr indicates the IP
--          address to be advertised for the route information returned by
--          this 'vprnTraceRoute' reply.  When used together with the values
--          in tnOamVprnTrL3MapRteDestMask and tnOamVprnTrL3MapRteVprnLabel
--          a customer route can be identified.

--          This object was obsoleted in release 4.0 and replaced with
--          InetAddress objects tnOamVprnTrL3MapDestAddrType and
--          tnOamVprnTrL3MapDestAddrType."
--     ::= { tnOamVprnTrL3MapEntry 3 }

-- tnOamVprnTrL3MapRteDestMask      OBJECT-TYPE
--     SYNTAX      Unsigned32
--     MAX-ACCESS  read-only
--     STATUS      obsolete
--     DESCRIPTION
--         "The value of tnOamVprnTrL3MapRteDestMask indicates the number
--          of prefix bits (prefix width) to be &-ed with IP address in
--          tnOamVprnTrL3MapRteDestAddr.

--          This object was obsoleted in release 4.0 and replaced with
--          InetAddress object tnOamVprnTrL3MapDestMaskLen."
--     ::= { tnOamVprnTrL3MapEntry 4 }

-- tnOamVprnTrL3MapRteVprnLabel OBJECT-TYPE
--     SYNTAX      MplsLabel
--     MAX-ACCESS  read-only
--     STATUS      current
--     DESCRIPTION
--         "The value of tnOamVprnTrL3MapRteVprnLabel indicates the VPRN
--          label associated with the route information returned in this
--          'vprnTraceRoute' reply."
--     ::= { tnOamVprnTrL3MapEntry 5 }

-- tnOamVprnTrL3MapRteMetrics       OBJECT-TYPE
--     SYNTAX      Unsigned32
--     MAX-ACCESS  read-only
--     STATUS      current
--     DESCRIPTION
--         "The value of tnOamVprnTrL3MapRteMetrics indicates the metrics
--          to be used with this vprnTraceRoute route."
--     ::= { tnOamVprnTrL3MapEntry 6 }

-- tnOamVprnTrL3MapRteLastUp        OBJECT-TYPE
--     SYNTAX      DateAndTime
--     MAX-ACCESS  read-only
--     STATUS      current
--     DESCRIPTION
--         "The value of tnOamVprnTrL3MapRteLastUp indicates the time
--          this route was last added or modified by the protocol."
--     ::= { tnOamVprnTrL3MapEntry 7 }

-- tnOamVprnTrL3MapRteOwner         OBJECT-TYPE
--     SYNTAX      INTEGER {
--                     invalid (0),
--                     local   (1),
--                     static  (2),
--                     rip     (3),
--                     ospf    (4),
--                     isis    (5),
--                     bgp     (6),
--                     bgpVpn  (7),
--                     ldp     (8),
--                     aggregate (9),
--                     any     (10)
--                 }
--     MAX-ACCESS  read-only
--     STATUS      current
--     DESCRIPTION
--         "The value of tnOamVprnTrL3MapRteOwner indicates the protocol
--          that owns this route.  It may be a local or remote route."
--     ::= { tnOamVprnTrL3MapEntry 8 }

-- tnOamVprnTrL3MapRtePref          OBJECT-TYPE
--     SYNTAX      Unsigned32
--     MAX-ACCESS  read-only
--     STATUS      current
--     DESCRIPTION
--         "The value of tnOamVprnTrL3MapRtePref indicates the route
--          preference value for this route."
--     ::= { tnOamVprnTrL3MapEntry 9 }

-- tnOamVprnTrL3MapRteDist          OBJECT-TYPE
--     SYNTAX      TmnxVPNRouteDistinguisher
--     MAX-ACCESS  read-only
--     STATUS      current
--     DESCRIPTION
--         "The value of tnOamVprnTrL3MapRteDist is the route distinguisher
--          associated with the route information returned in this 'vprnTraceRoute'
--          reply."
--     ::= { tnOamVprnTrL3MapEntry 10 }

-- tnOamVprnTrL3MapNumNextHops      OBJECT-TYPE
--     SYNTAX      Unsigned32
--     MAX-ACCESS  read-only
--     STATUS      current
--     DESCRIPTION
--         "The value of tnOamVprnTrL3MapNumNextHops indicates the number
--          of entries in the tnOamVprnTrNextHopTable for this route."
--     ::= { tnOamVprnTrL3MapEntry 11 }

-- tnOamVprnTrL3MapNumRteTargets    OBJECT-TYPE
--     SYNTAX      Unsigned32
--     MAX-ACCESS  read-only
--     STATUS      current
--     DESCRIPTION
--         "The value of tnOamVprnTrL3MapNumRteTargets indicates the number
--          of entries in the tnOamVprnTrRTTable for this route."
--     ::= { tnOamVprnTrL3MapEntry 12 }

-- tnOamVprnTrL3MapDestAddrType      OBJECT-TYPE
--     SYNTAX      InetAddressType
--     MAX-ACCESS  read-only
--     STATUS      current
--     DESCRIPTION
--         "The value of tnOamVprnTrL3MapDestAddrType indicates the type
--          of internet address stored in tnOamVprnTrL3MapDestAddress."
--     ::= { tnOamVprnTrL3MapEntry 13 }

-- tnOamVprnTrL3MapDestAddress      OBJECT-TYPE
--     SYNTAX      InetAddress (SIZE (0|4|16))
--     MAX-ACCESS  read-only
--     STATUS      current
--     DESCRIPTION
--         "The value of tnOamVprnTrL3MapDestAddress indicates the Internet
--          address to be advertised for the route information returned by
--          this 'vprnTraceRoute' reply.  When used together with the values
--          in tnOamVprnTrL3MapRteDestMask and tnOamVprnTrL3MapRteVprnLabel
--          a customer route can be identified."
--     ::= { tnOamVprnTrL3MapEntry 14 }

-- tnOamVprnTrL3MapDestMaskLen      OBJECT-TYPE
--     SYNTAX      InetAddressPrefixLength
--     MAX-ACCESS  read-only
--     STATUS      current
--     DESCRIPTION
--         "The value of tnOamVprnTrL3MapDestMaskLen indicates the number
--          of prefix bits (prefix width) to be &-ed with the IP address in
--          tnOamVprnTrL3MapDestAddress."
--     ::= { tnOamVprnTrL3MapEntry 15 }


--
-- Nokia SROS OAM VPRN TraceRoute L3 Route Information Next Hop Table
--
-- tnOamVprnTrNextHopTable OBJECT-TYPE
--     SYNTAX      SEQUENCE OF TnOamVprnTrNextHopEntry
--     MAX-ACCESS  not-accessible
--     STATUS      current
--     DESCRIPTION
--         "Defines a table for storing the results of an OAM 'vprnTraceRoute'
--          probe operation where a L3 route next hop list is returned.

--          An entry in this table is created when the result of an OAM
--          'vprnTraceRoute' probe is determined.
--          An entry is removed from this table when its corresponding
--          tnOamTrCtlEntry is deleted."
--    ::= { tnOamTraceRouteObjs 13 }

-- tnOamVprnTrNextHopEntry OBJECT-TYPE
--     SYNTAX      TnOamVprnTrNextHopEntry
--     MAX-ACCESS  not-accessible
--     STATUS      current
--     DESCRIPTION
--         "Defines an entry in the tnOamVprnTrNextHopTable.  The first two
--          index elements identify the tnOamTrCtlEntry that a
--          tnOamVprnTrNextHopEntry belongs to.  The third index element
--          identifies an OAM trace route test run.  The fourth, fifth and sixth
--          index elements select a single OAM 'vprnTraceRoute' reply.  The
--          seventh index selects either the requestor's or responder's route
--          information. The eighth index selects a single L3 next hop entry
--          within a specific 'vprnTraceRoute' probe reply route information."
--     INDEX {
--             tnOamTrCtlOwnerIndex,
--             tnOamTrCtlTestIndex,
--             tnOamTrResultsTestRunIndex,
--             tnOamTrProbeHistoryIndex,
--             tnOamTrProbeHistoryHopIndex,
--             tnOamTrProbeHistoryProbeIndex,
--             tnOamVprnTrL3MapReporter,
--             tnOamVprnTrNextHopIndex
--            }
--     ::= { tnOamVprnTrNextHopTable 1 }

--  TnOamVprnTrNextHopEntry ::=
--     SEQUENCE {
--        tnOamVprnTrNextHopIndex      Unsigned32,
--        tnOamVprnTrNextHopRtrID      RouterID,
--        tnOamVprnTrNextHopType       INTEGER,
--        tnOamVprnTrNextHopTunnelID   TmnxTunnelID,
--        tnOamVprnTrNextHopTunnelType TmnxTunnelType,
--        tnOamVprnTrNextHopIfIndex    InterfaceIndex,
--        tnOamVprnTrNextHopAddrType   InetAddressType,
--        tnOamVprnTrNextHopAddress    InetAddress
--     }

-- tnOamVprnTrNextHopIndex OBJECT-TYPE
--  NOTE: The UCD snmpget utility program does not parse this correctly
--    SYNTAX      Unsigned32 (1..'ffffffff'h)
--     SYNTAX      Unsigned32 (1..4294967295)
--     MAX-ACCESS  not-accessible
--     STATUS      current
--     DESCRIPTION
--         "The tnOamVprnTrNextHopIndex selects a single L3 next hop entry
--          associated with the router information returned within a specific
--          'vprnTraceRoute' probe reply.

--          The agent starts assigning tnOamVprnTrNextHopIndex values at 1."
--     ::= { tnOamVprnTrNextHopEntry 1 }

-- tnOamVprnTrNextHopRtrID    OBJECT-TYPE
--     SYNTAX      RouterID
--     MAX-ACCESS  read-only
--     STATUS      obsolete
--     DESCRIPTION
--         "The value of tnOamVprnTrNextHopRtrID is the router ID for this
--          L3 next hop entry.

--          This object was obsoleted in release 6.0 and replaced with
--          InetAddress objects tnOamVprnTrNextHopAddrType and
--          tnOamVprnTrNextHopAddress."
--     ::= { tnOamVprnTrNextHopEntry 2 }

-- tnOamVprnTrNextHopType       OBJECT-TYPE
--     SYNTAX      INTEGER {
--                     local (1),
--                     remote (2)
--                 }
--     MAX-ACCESS  read-only
--     STATUS      current
--     DESCRIPTION
--         "The value of tnOamVprnTrNextHopType indicates whether the
--          route owner is a local route or a remote, BGP-VPRN, route."
--     ::= { tnOamVprnTrNextHopEntry 3 }

-- tnOamVprnTrNextHopTunnelID       OBJECT-TYPE
--     SYNTAX      TmnxTunnelID
--     MAX-ACCESS  read-only
--     STATUS      current
--     DESCRIPTION
--         "When the value of tnOamVprnTrNextHopType is 'remote' the
--          value of tnOamVprnTrNextHopTunnelID indicates the tunnel ID
--          used to reach this BGP next hop."
--     ::= { tnOamVprnTrNextHopEntry 4 }

-- tnOamVprnTrNextHopTunnelType     OBJECT-TYPE
--     SYNTAX      TmnxTunnelType
--     MAX-ACCESS  read-only
--     STATUS      current
--     DESCRIPTION
--         "When the value of tnOamVprnTrNextHopType is 'remote' the
--          value of tnOamVprnTrNextHopTunnelType indicates the type of
--          tunnel used to reach this BGP next hop."
--     ::= { tnOamVprnTrNextHopEntry 5 }

-- tnOamVprnTrNextHopIfIndex        OBJECT-TYPE
--     SYNTAX      InterfaceIndex
--     MAX-ACCESS  read-only
--     STATUS      current
--     DESCRIPTION
--         "When the value of tnOamVprnTrNextHopType is 'local' the
--          value of tnOamVprnTrNextHopIfIndex indicates the interface
--          used to reach this ECMP next hop."
--     ::= { tnOamVprnTrNextHopEntry 6 }

-- tnOamVprnTrNextHopAddrType    OBJECT-TYPE
--     SYNTAX      InetAddressType
--     MAX-ACCESS  read-only
--     STATUS      current
--     DESCRIPTION
--         "tnOamVprnTrNextHopAddrType indicates the type of Internet address
--          stored in tnOamVprnTrNextHopAddress.  Address types 'unknown(0)',
--          'ipv4(1)', 'ipv6(2)', and 'ipv6z(4)' are supported."
--     ::= { tnOamVprnTrNextHopEntry 7 }

-- tnOamVprnTrNextHopAddress    OBJECT-TYPE
--     SYNTAX      InetAddress (SIZE (0|4|16|20))
--     MAX-ACCESS  read-only
--     STATUS      current
--     DESCRIPTION
--         "The value of tnOamVprnTrNextHopAddress is the Internet address
--          for this L3 next hop entry."
--     ::= { tnOamVprnTrNextHopEntry 8 }

--
--  Nokia SROS series OAM VPRN Trace Route Returned Route
--  Information Target Table
--

-- tnOamVprnTrRTTable OBJECT-TYPE
--     SYNTAX      SEQUENCE OF TnOamVprnTrRTEntry
--     MAX-ACCESS  not-accessible
--     STATUS      current
--     DESCRIPTION
--         "Defines a table for storing the results of an OAM 'vprnTraceRoute'
--          probe operation where a L3 route target list is returned.

--          An entry in this table is created when the result of an OAM
--          'vprnTraceRoute' probe is determined.
--          An entry is removed from this table when its corresponding
--          tnOamTrCtlEntry is deleted."
--    ::= { tnOamTraceRouteObjs 14 }

-- tnOamVprnTrRTEntry OBJECT-TYPE
--     SYNTAX      TnOamVprnTrRTEntry
--     MAX-ACCESS  not-accessible
--     STATUS      current
--     DESCRIPTION
--         "Defines an entry in the tnOamVprnTrRTTable.  The first two
--          index elements identify the tnOamTrCtlEntry that a
--          tnOamVprnTrRTEntry belongs to.  The third index element
--          identifies an OAM trace route test run.  The fouth, fifth and sixth
--          index elements select a single OAM 'vprnTraceRoute' reply.
--          The seventh index selects either the probe requestor's or
--          probe replier's route information.  The eighth index selects
--          successive L3 route target entries contained in a specific
--          'vprnTraceRoute' requestor or probe reply route information."
--     INDEX {
--             tnOamTrCtlOwnerIndex,
--             tnOamTrCtlTestIndex,
--             tnOamTrResultsTestRunIndex,
--             tnOamTrProbeHistoryIndex,
--             tnOamTrProbeHistoryHopIndex,
--             tnOamTrProbeHistoryProbeIndex,
--             tnOamVprnTrL3MapReporter,
--             tnOamVprnTrRTIndex
--            }
--     ::= { tnOamVprnTrRTTable 1 }

--  TnOamVprnTrRTEntry ::=
--     SEQUENCE {
--        tnOamVprnTrRTIndex        Unsigned32,
--        tnOamVprnTrRouteTarget    TmnxBgpRouteTarget
--     }

-- tnOamVprnTrRTIndex OBJECT-TYPE
--  NOTE: The UCD snmpget utility program does not parse this correctly
--    SYNTAX      Unsigned32 (1..'ffffffff'h)
--     SYNTAX      Unsigned32 (1..4294967295)
--     MAX-ACCESS  not-accessible
--     STATUS      current
--     DESCRIPTION
--         "The tnOamVprnTrRTIndex selects a single L3 route target entry
--          associated with the router information returned within a specific
--          'vprnTraceRoute' probe reply.

--          The agent starts assigning tnOamVprnTrRTIndex values at 1."
--     ::= { tnOamVprnTrRTEntry 1 }

-- tnOamVprnTrRouteTarget    OBJECT-TYPE
--     SYNTAX      TmnxBgpRouteTarget
--     MAX-ACCESS  read-only
--     STATUS      current
--     DESCRIPTION
--         "The value of tnOamVprnTrRouteTarget is the route target ID
--          for this L3 route target entry."
--     ::= { tnOamVprnTrRTEntry 2 }

--
-- Nokia SROS series OAM Lsp Trace Route Downstream Label Mapping Table
--
--
-- tnOamLspTrDSLabelTable OBJECT-TYPE
--     SYNTAX      SEQUENCE OF TnOamLspTrDSLabelEntry
--     MAX-ACCESS  not-accessible
--     STATUS      current
--     DESCRIPTION
--         "Defines a table for storing the results of an OAM 'lspTraceRoute' or
--          'p2mpLspTrace' probe operation when a Downstream Mapping TLV was
--          returned.  Each row represents a single downstream label within a
--          returned downstream L2 mapping TLV.
--
--          An entry in this table is created when the result of an OAM
--          'lspTraceRoute' or 'p2mpLspTrace' probe is determined.
--          An entry is removed from this table when its corresponding
--          tnOamTrCtlEntry is deleted."
--    ::= { tnOamTraceRouteObjs 15 }

-- tnOamLspTrDSLabelEntry OBJECT-TYPE
--     SYNTAX      TnOamLspTrDSLabelEntry
--     MAX-ACCESS  not-accessible
--     STATUS      current
--     DESCRIPTION
--         "Defines an entry in the tnOamLspTrDSLabelTable.  The first
--          two index elements identify the tnOamTrCtlEntry that a
--          tnOamLspTrMapEntry belongs to.  The third index element
--          identifies a OAM trace route test run. The fourth index element
--          selects the group of responses associated with a specific
--          probe attempt. The fifth and sixth indexes select the hop and
--          the probe at that hop for a particular Nokia SROS OAM
--          Trace Route operation. The seventh index selects a single downstream
--          L2 map entry within the specific probe reply.  The eigth index
--          selects seccessive downstream L2 label entries contained in a
--          specific probe reply."
--     INDEX {
--             tnOamTrCtlOwnerIndex,
--             tnOamTrCtlTestIndex,
--             tnOamTrResultsTestRunIndex,
--             tnOamTrProbeHistoryIndex,
--             tnOamTrProbeHistoryHopIndex,
--             tnOamTrProbeHistoryProbeIndex,
--             tnOamLspTrMapIndex,
--             tnOamLspTrDSLabelIndex
--            }
--     ::= { tnOamLspTrDSLabelTable 1 }

--  TnOamLspTrDSLabelEntry ::=
--     SEQUENCE {
--        tnOamLspTrDSLabelIndex        Unsigned32,
--        tnOamLspTrDSLabelLabel        MplsLabel,
--        tnOamLspTrDSLabelProtocol     TmnxOamSignalProtocol
--     }

-- tnOamLspTrDSLabelIndex OBJECT-TYPE
--  NOTE: The UCD snmpget utility program does not parse this correctly
--    SYNTAX      Unsigned32 (1..'ffffffff'h)
--     SYNTAX      Unsigned32 (1..4294967295)
--     MAX-ACCESS  not-accessible
--     STATUS      current
--     DESCRIPTION
--         "The tnOamLspTrDSLabelIndex selects a single downstream L2 label
--          entry within a specific L2 mapping entry reply.

--          The agent starts assigning tnOamLspTrDSLabelIndex values at 1."
--     ::= { tnOamLspTrDSLabelEntry 1 }

-- tnOamLspTrDSLabelLabel       OBJECT-TYPE
--     SYNTAX      MplsLabel
--     MAX-ACCESS  read-only
--     STATUS      current
--     DESCRIPTION
--         "The value of tnOamLspTrDSLabelLabel is the label used by the
--          downstream router specified by this downstream L2 label entry."
--     ::= { tnOamLspTrDSLabelEntry 2 }

-- tnOamLspTrDSLabelProtocol    OBJECT-TYPE
--     SYNTAX      TmnxOamSignalProtocol
--     MAX-ACCESS  read-only
--     STATUS      current
--     DESCRIPTION
--         "The value of tnOamLspTrDSLabelProtocol is the signaling protocol
--          used by the router for the label specified by this downstream
--          L2 label entry."
--     ::= { tnOamLspTrDSLabelEntry 3 }

--
--  Nokia SROS series OAM Multicast Trace Route Control Table
--
--
--  Sparse Dependent Extension of the tnOamTrCtlTable.
--
--  The same indexes are used for both the base table, tnOamTrCtlTable,
--  and the sparse dependent table, tnOamMcastTrCtlTable.
--
--  This in effect extends the tnOamTrCtlTable with additional columns.
--  Rows are created in the tnOamMcastTrCtlTable only for those entries
--  in the tnOamTrCtlTable where tnOamTrCtlTestMode has a value of
--  'mcastTraceRoute'.
--
--  Deletion of a row in the tnOamTrCtlTable results in the
--  same fate for the row in the tnOamMcastTrCtlTable.
--
-- tnOamMcastTrCtlTable     OBJECT-TYPE
--     SYNTAX      SEQUENCE OF TnOamMcastTrCtlEntry
--     MAX-ACCESS  not-accessible
--     STATUS      current
--     DESCRIPTION
--         "Defines the Nokia SROS OAM Multicast Trace Route Control Table
--          for providing, via SNMP, the capability of performing Nokia
--          SROS OAM 'mcastTraceRoute' test operations.  The results of these
--          tests are stored in the tnOamTrResultsTable, the
--          tnOamTrProbeHistoryTable and the tnOamMcastTrRespTable."
--    ::= { tnOamTraceRouteObjs 16 }
--
-- tnOamMcastTrCtlEntry OBJECT-TYPE
--     SYNTAX      TnOamMcastTrCtlEntry
--     MAX-ACCESS  not-accessible
--     STATUS      current
--     DESCRIPTION
--         "Defines an entry in the tnOamMcastTrCtlTable.  The first index
--          element, tnOamTrCtlOwnerIndex, is of type SnmpAdminString,
--          a textual convention that allows for use of the SNMPv3
--          View-Based Access Control Model (RFC 2575 [11], VACM)
--          and allows a management application to identify its entries.
--          The second index, tnOamTrCtlTestIndex, enables the same
--          management application to have multiple outstanding requests."
--     INDEX {
--             tnOamTrCtlOwnerIndex,
--             tnOamTrCtlTestIndex
--           }
--     ::= { tnOamMcastTrCtlTable 1 }
--
--  TnOamMcastTrCtlEntry ::=
--     SEQUENCE {
--        tnOamMcastTrCtlVRtrID              TmnxVRtrID,
--        tnOamMcastTrCtlSrcIpAddr           IpAddress,
--        tnOamMcastTrCtlDestIpAddr          IpAddress,
--        tnOamMcastTrCtlRespIpAddr          IpAddress,
--        tnOamMcastTrCtlGrpIpAddr           IpAddress,
--        tnOamMcastTrCtlHops                Unsigned32,
--        tnOamMcastTrQueryId                Unsigned32,
--        tnOamMcastTrCtlSrcAddrType         InetAddressType,
--        tnOamMcastTrCtlSrcAddress          InetAddress,
--        tnOamMcastTrCtlDestAddrType        InetAddressType,
--        tnOamMcastTrCtlDestAddress         InetAddress,
--        tnOamMcastTrCtlRespAddrType        InetAddressType,
--        tnOamMcastTrCtlRespAddress         InetAddress,
--        tnOamMcastTrCtlGrpAddrType         InetAddressType,
--        tnOamMcastTrCtlGrpAddress          InetAddress
--     }
--
-- tnOamMcastTrCtlVRtrID  OBJECT-TYPE
--     SYNTAX      TmnxVRtrID
--     MAX-ACCESS  read-create
--     STATUS      current
--     DESCRIPTION
--         "The unique value which identifies this virtual router in the
--          Nokia SROS system. The vRtrID value for each virtual router
--          must remain constant at least from one re-initialization of the
--          system management processor (CPM) to the next.  There will always
--          be at least one router entry defined by the agent with vRtrID=1
--          which represents the base transport router.
--
--          When using the tnOamTrCtlServiceId parameter to direct mtrace
--          to use a virtual router associated with a VPRN service, setting
--          the tnOamMcastTrCtlVRtrID parameter is ignored.
--
--          tnOamTrCtlVRtrID is irrelevant when doing an mtrace."
--     DEFVAL { 1 }
--     ::= { tnOamMcastTrCtlEntry 1 }
--
-- tnOamMcastTrCtlSrcIpAddr    OBJECT-TYPE
--     SYNTAX      IpAddress
--     MAX-ACCESS  read-create
--     STATUS      obsolete
--     DESCRIPTION
--         "tnOamMcastTrCtlSrcIpAddr is used to specify the Ipv4 address to
--          be used as the source for performing an OAM 'mcastTraceRoute'
--          operation when tnOamTrCtlTestMode has a value of 'mcastTraceRoute'.
--          This is a required parameter to initiate a multicast trace.
--
--          This object was obsoleted in release 4.0 and replaced with
--          InetAddress objects tnOamMcastTrCtlSrcAddrType and
--          tnOamMcastTrCtlSrcAddress."
--     ::= { tnOamMcastTrCtlEntry 2 }
--
-- tnOamMcastTrCtlDestIpAddr    OBJECT-TYPE
--     SYNTAX      IpAddress
--     MAX-ACCESS  read-create
--     STATUS      obsolete
--     DESCRIPTION
--         "tnOamMcastTrCtlDestIpAddr is used to specify the Ipv4 address to
--          be used as the destination address for performing an OAM
--          'mcastTraceRoute' operation when tnOamTrCtlTestMode has a value
--          of 'mcastTraceRoute'. The multicast trace query is sent to
--          this destination address. If this object is not set, the multicast
--          trace starts from this router. This is not a required parameter.
--
--          This object was obsoleted in release 4.0 and replaced with
--          InetAddress objects tnOamMcastTrCtlDestAddrType and
--          tnOamMcastTrCtlDestAddress."
--     DEFVAL { '00000000'h }   --   -- 0.0.0.0
--     ::= { tnOamMcastTrCtlEntry 3 }
--
-- tnOamMcastTrCtlRespIpAddr    OBJECT-TYPE
--     SYNTAX      IpAddress
--     MAX-ACCESS  read-create
--     STATUS      obsolete
--     DESCRIPTION
--         "tnOamMcastTrCtlRespIpAddr is used to specify the Ipv4 address
--          to be used as the response address for performing an OAM
--          'mcastTraceRoute' operation. If this object is not set, then
--          the system ip address is used as the response address. This is
--          not a required parameter.
--
--          This object was obsoleted in release 4.0 and replaced with
--          InetAddress objects tnOamMcastTrCtlRespAddrType and
--          tnOamMcastTrCtlRespAddress."
--     ::= { tnOamMcastTrCtlEntry 4 }
--
-- tnOamMcastTrCtlGrpIpAddr    OBJECT-TYPE
--     SYNTAX      IpAddress
--     MAX-ACCESS  read-create
--     STATUS      obsolete
--     DESCRIPTION
--         "tnOamMcastTrCtlGrpIpAddr is used to specify the Ipv4 multicast
--          group address for doing a 'mcastTraceRoute'  operation. This is
--          a required parameter to initiate a multicast trace.
--
--          This object was obsoleted in release 4.0 and replaced with
--          InetAddress objects tnOamMcastTrCtlGrpAddrType and
--          tnOamMcastTrCtlGrpAddress."
--     ::= { tnOamMcastTrCtlEntry 5 }
--
-- tnOamMcastTrCtlHops    OBJECT-TYPE
--     SYNTAX      Unsigned32 (1..255)
--     MAX-ACCESS  read-create
--     STATUS      current
--     DESCRIPTION
--         "tnOamMcastTrCtlHops is used to specify the maximum number of hops
--          that will be traced along the path to the source. This is not a
--          required parameter."
--     DEFVAL { 32 }
--     ::= { tnOamMcastTrCtlEntry 6 }
--
-- tnOamMcastTrQueryId    OBJECT-TYPE
--     SYNTAX      Unsigned32
--     MAX-ACCESS  read-only
--     STATUS      current
--     DESCRIPTION
--         "tnOamMcastTrQueryId is the 24 bit random number that uniquely
--          identifies the multicast trace query. When the router receives the
--          response back from the first hop router, it maps the response to the
--          query by looking at the query id in the packet."
--     ::= { tnOamMcastTrCtlEntry 7 }
--
-- tnOamMcastTrCtlSrcAddrType    OBJECT-TYPE
--     SYNTAX      InetAddressType
--     MAX-ACCESS  read-create
--     STATUS      current
--     DESCRIPTION
--         "tnOamMcastTrCtlSrcAddrType specifies the type of Internet
--          address stored in tnOamMcastTrCtlSrcAddress."
--     DEFVAL { unknown }
--     ::= { tnOamMcastTrCtlEntry 8 }
--
-- tnOamMcastTrCtlSrcAddress    OBJECT-TYPE
--     SYNTAX      InetAddress (SIZE (0|4|16))
--     MAX-ACCESS  read-create
--     STATUS      current
--     DESCRIPTION
--         "tnOamMcastTrCtlSrcAddress specifies the Internet address to
--          be used as the source for performing an OAM 'mcastTraceRoute'
--          operation when tnOamTrCtlTestMode has a value of 'mcastTraceRoute'.
--
--          This is a required parameter to initiate a multicast trace."
--     DEFVAL { ''H }
--     ::= { tnOamMcastTrCtlEntry 9 }
--
-- tnOamMcastTrCtlDestAddrType    OBJECT-TYPE
--     SYNTAX      InetAddressType
--     MAX-ACCESS  read-create
--     STATUS      current
--     DESCRIPTION
--         "tnOamMcastTrCtlDestAddrType specifies the type of Internet
--          address stored in tnOamMcastTrCtlDestAddress."
--     DEFVAL { unknown }
--     ::= { tnOamMcastTrCtlEntry 10 }
--
-- tnOamMcastTrCtlDestAddress    OBJECT-TYPE
--     SYNTAX      InetAddress (SIZE (0|4|16))
--     MAX-ACCESS  read-create
--     STATUS      current
--     DESCRIPTION
--         "tnOamMcastTrCtlDestAddress specifies the Internet address to
--          be used as the destination address for performing an OAM
--          'mcastTraceRoute' operation when tnOamTrCtlTestMode has a value
--          of 'mcastTraceRoute'. The multicast trace query is sent to
--          this destination address. If this object is not set, the multicast
--          trace starts from this router. This is not a required parameter."
--     DEFVAL { ''H }
--     ::= { tnOamMcastTrCtlEntry 11 }
--
-- tnOamMcastTrCtlRespAddrType    OBJECT-TYPE
--     SYNTAX      InetAddressType
--     MAX-ACCESS  read-create
--     STATUS      current
--     DESCRIPTION
--         "tnOamMcastTrCtlRespAddrType specifies the type of Internet
--          address stored in tnOamMcastTrCtlRespAddress."
--     DEFVAL { unknown }
--     ::= { tnOamMcastTrCtlEntry 12 }
--
-- tnOamMcastTrCtlRespAddress    OBJECT-TYPE
--     SYNTAX      InetAddress (SIZE (0|4|16))
--     MAX-ACCESS  read-create
--     STATUS      current
--     DESCRIPTION
--         "tnOamMcastTrCtlRespAddress is used to specify the Internet
--          address to be used as the response address for performing an OAM
--          'mcastTraceRoute' operation. If this object is not set, then
--          the system ip address is used as the response address. This is
--          not a required parameter."
--     DEFVAL { ''H }
--     ::= { tnOamMcastTrCtlEntry 13 }
--
-- tnOamMcastTrCtlGrpAddrType    OBJECT-TYPE
--     SYNTAX      InetAddressType
--     MAX-ACCESS  read-create
--     STATUS      current
--     DESCRIPTION
--         "tnOamMcastTrCtlGrpAddrType specifies the type of Internet
--          address stored in tnOamMcastTrCtlGrpAddress."
--     DEFVAL { unknown }
--     ::= { tnOamMcastTrCtlEntry 14 }
--
-- tnOamMcastTrCtlGrpAddress    OBJECT-TYPE
--     SYNTAX      InetAddress (SIZE (0|4|16))
--     MAX-ACCESS  read-create
--     STATUS      current
--     DESCRIPTION
--         "tnOamMcastTrCtlGrpAddress specifies the Internet multicast
--          group address for doing a 'mcastTraceRoute'  operation. This is
--          a required parameter to initiate a multicast trace."
--     DEFVAL { ''H }
--     ::= { tnOamMcastTrCtlEntry 15 }



-- Multicast Trace Response Table

-- tnOamMcastTrRespTable     OBJECT-TYPE
--     SYNTAX      SEQUENCE OF TnOamMcastTrRespEntry
--     MAX-ACCESS  not-accessible
--     STATUS      current
--     DESCRIPTION
--         "Defines the Nokia SROS OAM Multicast Trace Route Response
--          Table for providing, via SNMP, the result of OAM 'mcastTraceRoute' test
--          operation.  The results of these tests are stored in the
--          tnOamTrResultsTable, the tnOamTrProbeHistoryTable and
--          the tnOamMcastTrRespTable."
--    ::= { tnOamTraceRouteObjs 17 }

-- tnOamMcastTrRespEntry OBJECT-TYPE
--     SYNTAX      TnOamMcastTrRespEntry
--     MAX-ACCESS  not-accessible
--     STATUS      current
--     DESCRIPTION
--         "Defines an entry in the tnOamMcastTrRespTable.
--          The first two index elements identify the tnOamTrCtlEntry that
--          a tnOamMcastTrRespEntry belongs to.  The third index element
--          selects an OAM trace route test run.  The fourth index element
--          selects a single Nokia SROS OAM Trace Route operation result.
--          The fifth and sixth indexes select the hop and the probe at that
--          hop for a particular Nokia SROS OAM Trace Route operation."
--     INDEX {
--             tnOamTrCtlOwnerIndex,
--             tnOamTrCtlTestIndex,
--             tnOamTrResultsTestRunIndex,
--             tnOamTrProbeHistoryIndex,
--             tnOamTrProbeHistoryHopIndex,
--             tnOamTrProbeHistoryProbeIndex
--           }
--     ::= { tnOamMcastTrRespTable 1 }

--  TnOamMcastTrRespEntry ::=
--     SEQUENCE {
--        tnOamMcastTrRespQueryArrivalTime     Unsigned32,
--        tnOamMcastTrRespInIfAddr             IpAddress,
--        tnOamMcastTrRespOutIfAddr            IpAddress,
--        tnOamMcastTrRespPrevHopRtrAddr       IpAddress,
--        tnOamMcastTrRespInPktCount           Counter32,
--        tnOamMcastTrRespOutPktCount          Counter32,
--        tnOamMcastTrRespSGPktCount           Counter32,
--        tnOamMcastTrRespRtgProtocol          INTEGER,
--        tnOamMcastTrRespFwdTtl               Unsigned32,
--        tnOamMcastTrRespMBZBit               Unsigned32,
--        tnOamMcastTrRespSrcBit               Unsigned32,
--        tnOamMcastTrRespSrcMask              Unsigned32,
--        tnOamMcastTrRespFwdCode              INTEGER,
--        tnOamMcastTrRespInIfAddrType         InetAddressType,
--        tnOamMcastTrRespInIfAddress          InetAddress,
--        tnOamMcastTrRespOutIfAddrType        InetAddressType,
--        tnOamMcastTrRespOutIfAddress         InetAddress,
--        tnOamMcastTrRespPhRtrAddrType        InetAddressType,
--        tnOamMcastTrRespPhRtrAddress         InetAddress
--     }

-- tnOamMcastTrRespQueryArrivalTime    OBJECT-TYPE
--     SYNTAX      Unsigned32
--     MAX-ACCESS  read-only
--     STATUS      current
--     DESCRIPTION
--         "tnOamMcastTrRespQueryArrivalTime specifies the 32 bit NTP timestamp.
--          It is the time at which a particular hop received the Multicast
--          Trace query/request."
--     ::= { tnOamMcastTrRespEntry 1 }

-- tnOamMcastTrRespInIfAddr    OBJECT-TYPE
--     SYNTAX      IpAddress
--     MAX-ACCESS  read-only
--     STATUS      obsolete
--     DESCRIPTION
--         "tnOamMcastTrRespInIfAddr specifies the address of the interface on
--          which packets from this source and group are expected to arrive.

--          This object was obsoleted in release 4.0 and replaced with
--          InetAddress objects tnOamMcastTrRespInIfAddrType and
--          tnOamMcastTrRespInIfAddress."
--     ::= { tnOamMcastTrRespEntry 2 }

-- tnOamMcastTrRespOutIfAddr    OBJECT-TYPE
--     SYNTAX      IpAddress
--     MAX-ACCESS  read-only
--     STATUS      obsolete
--     DESCRIPTION
--         "tnOamMcastTrRespOutIfAddr specifies the address of the interface on
--          which packets from this source and group flow to the specified
--          destination.

--          This object was obsoleted in release 4.0 and replaced with
--          InetAddress objects tnOamMcastTrRespOutIfAddrType and
--          tnOamMcastTrRespOutIfAddress."
--     ::= { tnOamMcastTrRespEntry 3 }

-- tnOamMcastTrRespPrevHopRtrAddr    OBJECT-TYPE
--     SYNTAX      IpAddress
--     MAX-ACCESS  read-only
--     STATUS      obsolete
--     DESCRIPTION
--         "tnOamMcastTrRespPrevHopRtrAddr specifies the router from which this
--          router expects packets from this source.  This may be a multicast
--          group (e.g. ALL-[protocol]-ROUTERS.MCAST.NET) if the previous hop is
--          not known because of the workings of the multicast routing protocol.

--          This object was obsoleted in release 4.0 and replaced with
--          InetAddress objects tnOamMcastTrRespPhRtrAddrType and
--          tnOamMcastTrRespPhRtrAddress."
--     ::= { tnOamMcastTrRespEntry 4 }

-- tnOamMcastTrRespInPktCount    OBJECT-TYPE
--     SYNTAX      Counter32
--     MAX-ACCESS  read-only
--     STATUS      current
--     DESCRIPTION
--         "tnOamMcastTrRespInPktCount contains the number of multicast packets
--          received for all groups and sources on the incoming interface, or
--          0xffffffff if no count can be reported.  This counter should have the
--          same value as ifInMulticastPkts from the IF-MIB for this interface."
--     ::= { tnOamMcastTrRespEntry 5 }

-- tnOamMcastTrRespOutPktCount    OBJECT-TYPE
--     SYNTAX      Counter32
--     MAX-ACCESS  read-only
--     STATUS      current
--     DESCRIPTION
--         "tnOamMcastTrRespOutPktCount contains the number of multicast packets
--          that have been transmitted or queued for transmission for all groups
--          and sources on the outgoing interface, or 0xffffffff if no count can
--          be reported.  This counter should have the same value as
--          ifOutMulticastPkts from the IF-MIB for this interface."
--     ::= { tnOamMcastTrRespEntry 6 }

-- tnOamMcastTrRespSGPktCount    OBJECT-TYPE
--     SYNTAX      Counter32
--     MAX-ACCESS  read-only
--     STATUS      current
--     DESCRIPTION
--         "tnOamMcastTrRespSGPktCount counts the number of packets from the
--          specified source forwarded by this router to the specified group,
--          or 0xffffffff if no count can be reported. If the value of
--          tnOamMcastTrRespSrcBit is set to one, the count is for the source
--          network, as specified by tnOamMcastTrRespSrcMask.
--          If the S bit is set and the Src Mask field is 63, indicating no
--          source-specific state, the count is for all sources sending to
--          this group."
--     ::= { tnOamMcastTrRespEntry 7 }

-- tnOamMcastTrRespRtgProtocol    OBJECT-TYPE
--     SYNTAX      INTEGER {
--                     unknown(0),
--                     dvmrp(1),
--                     mospf(2),
--                     pim(3),
--                     cbt(4),
--                     pimSpecial(5),
--                     pimStatic(6),
--                     dvmrpStatic(7),
--                     bgp4Plus(8),
--                     cbtSpecial(9),
--                     cbtStatic(10),
--                     pimAssert(11)
--                 }
--     MAX-ACCESS  read-only
--     STATUS      current
--     DESCRIPTION
--         "tnOamMcastTrRespRtgProtocol describes the routing protocol in use
--          between this router and the previous-hop router."
--     ::= { tnOamMcastTrRespEntry 8 }

-- tnOamMcastTrRespFwdTtl    OBJECT-TYPE
--     SYNTAX      Unsigned32
--     MAX-ACCESS  read-only
--     STATUS      current
--     DESCRIPTION
--         "tnOamMcastTrRespFwdTtl contains the TTL that a packet is required
--          to have before it will be forwarded over the outgoing interface."
--     ::= { tnOamMcastTrRespEntry 9 }

-- tnOamMcastTrRespMBZBit    OBJECT-TYPE
--     SYNTAX      Unsigned32
--     MAX-ACCESS  read-only
--     STATUS      current
--     DESCRIPTION
--         "tnOamMcastTrRespMBZBit is zeroed on transmission and ignored on
--          reception."
--     ::= { tnOamMcastTrRespEntry 10 }

-- tnOamMcastTrRespSrcBit    OBJECT-TYPE
--     SYNTAX      Unsigned32
--     MAX-ACCESS  read-only
--     STATUS      current
--     DESCRIPTION
--         "If the value of tnOamMcastTrRespSrcBit is 1, it indicates that the
--          packet count for the source-group pair is for the source network, as
--          determined by masking the source address with
--          the tnOamMcastTrRespSrcMask field."
--     ::= { tnOamMcastTrRespEntry 11 }

-- tnOamMcastTrRespSrcMask    OBJECT-TYPE
--     SYNTAX      Unsigned32
--     MAX-ACCESS  read-only
--     STATUS      current
--     DESCRIPTION
--         "tnOamMcastTrRespSrcMask contains the number of 1's in the netmask
--          this router has for the source (i.e. a value of 24 means the netmask is
--          0xffffff00).  If the router is forwarding solely on group state,
--          this field is set to 63 (0x3f)."
--     ::= { tnOamMcastTrRespEntry 12 }

-- tnOamMcastTrRespFwdCode    OBJECT-TYPE
--     SYNTAX      INTEGER {
--                     noError(0),
--                     wrongIf(1),
--                     pruneSent(2),
--                     pruneRecvd(3),
--                     scoped(4),
--                     noRoute(5),
--                     wrongLastHop(6),
--                     notForwarding(7),
--                     reachedRP(8),
--                     rpfIf(9),
--                     noMulticast(10),
--                     infoHidden(11),
--                     fatalError(128),
--                     noSpace(129),
--                     oldRouter(130),
--                     adminProhib(131),
--                     unknown(132)
--                 }
--     MAX-ACCESS  read-only
--     STATUS      current
--     DESCRIPTION
--         "tnOamMcastTrRespFwdCode contains a forwarding information/error
--          code:
--          noError(0)    - No error
--          wrongIf(1)    - Traceroute request arrived on an interface to
--                          which this router would not forward for this
--                          source,group,destination.
--          pruneSent(2)  - This router has sent a prune upstream which
--                          applies to the source and group in the traceroute
--                          request.
--          pruneRecvd(3) - This router has stopped forwarding for this
--                          source and group in response to a request from
--                          the next hop router.
--          scoped(4)     - The group is subject to administrative scoping
--                           at this hop.
--          noRoute(5)    - This router has no route for the source or
--                          group and no way to determine a potential route.
--          wrongLastHop(6)  - This router is not the proper last-hop router.
--          notForwarding(7) - This router is not forwarding this
--                             source,group out the outgoing interface for an
--                             unspecified reason.
--          reachedRP(8) - Reached Rendez-vous Point or Core
--          rpfIf(9)     - Traceroute request arrived on the expected RPF
--                           interface for this source,group.
--          noMulticast(10) - Traceroute request arrived on an interface
--                           which is not enabled for multicast.
--          infoHidden(11)  - One or more hops have been hidden from this trace.
--          fatalError(12)  - Router may know the previous hop but cannot forward
--                            the message to it.
--          noSpace(129)    - There was not enough room to insert another
--                           response data block in the packet.
--          oldRouter(130)  - The previous hop router does not understand
--                            traceroute requests
--          adminProhib(131) - Traceroute is administratively prohibited.
--          unknown(132)     - Unknown forwarding code received."
--     ::= { tnOamMcastTrRespEntry 13 }

-- tnOamMcastTrRespInIfAddrType    OBJECT-TYPE
--     SYNTAX      InetAddressType
--     MAX-ACCESS  read-only
--     STATUS      current
--     DESCRIPTION
--         "tnOamMcastTrRespInIfAddrType specifies the type of Internet
--          address stored at tnOamMcastTrRespInIfAddress."
--     ::= { tnOamMcastTrRespEntry 14 }

-- tnOamMcastTrRespInIfAddress    OBJECT-TYPE
--     SYNTAX      InetAddress (SIZE (0|4|16))
--     MAX-ACCESS  read-only
--     STATUS      current
--     DESCRIPTION
--         "tnOamMcastTrRespInIfAddress specifies the Internet address of
--          the interface on which packets from this source and group are
--          expected to arrive."
--     ::= { tnOamMcastTrRespEntry 15 }

-- tnOamMcastTrRespOutIfAddrType    OBJECT-TYPE
--     SYNTAX      InetAddressType
--     MAX-ACCESS  read-only
--     STATUS      current
--     DESCRIPTION
--         "tnOamMcastTrRespOutIfAddrType specifies the type of Internet
--          address stored in tnOamMcastTrRespOutIfAddress."
--     ::= { tnOamMcastTrRespEntry 16 }

-- tnOamMcastTrRespOutIfAddress    OBJECT-TYPE
--     SYNTAX      InetAddress (SIZE (0|4|16))
--     MAX-ACCESS  read-only
--     STATUS      current
--     DESCRIPTION
--         "tnOamMcastTrRespOutIfAddress specifies the Inetenet address
--          of the interface on which packets from this source and group
--          flow to the specified  destination."
--     ::= { tnOamMcastTrRespEntry 17 }

-- tnOamMcastTrRespPhRtrAddrType    OBJECT-TYPE
--     SYNTAX      InetAddressType
--     MAX-ACCESS  read-only
--     STATUS      current
--     DESCRIPTION
--         "tnOamMcastTrRespPhRtrAddrType specifies the type of internet
--          address stored in tnOamMcastTrRespPhRtrAddress."
--     ::= { tnOamMcastTrRespEntry 18 }

-- tnOamMcastTrRespPhRtrAddress    OBJECT-TYPE
--     SYNTAX      InetAddress (SIZE (0|4|16))
--     MAX-ACCESS  read-only
--     STATUS      current
--     DESCRIPTION
--         "tnOamMcastTrRespPhRtrAddress specifies the Internet address of
--          the router from which this router expects packets for this source.
--          This may be a multicast group (e.g. ALL-[protocol]-ROUTERS.MCAST.NET)
--          if the previous hop is not known because of the workings of the
--          multicast routing protocol."
--     ::= { tnOamMcastTrRespEntry 19 }


--
-- Notification Definition section
--
-- tnOamTrPathChange NOTIFICATION-TYPE
--       OBJECTS {
--           tnOamTrCtlTestMode,
--           tnOamTrCtlLastRunResult,
--           tnOamTrResultsOperStatus
--       }
--       STATUS  current
--       DESCRIPTION
--           "The path to a target has changed."
--       ::= { tnOamTraceRouteNotifications 1 }

-- tnOamTrTestFailed NOTIFICATION-TYPE
--       OBJECTS {
--           tnOamTrCtlTestMode,
--           tnOamTrCtlLastRunResult,
--           tnOamTrResultsOperStatus
--       }
--       STATUS  current
--       DESCRIPTION
--           "The OAM trace route test failed to complete successfully."
--       ::= { tnOamTraceRouteNotifications 2 }

-- tnOamTrTestCompleted NOTIFICATION-TYPE
--       OBJECTS {
--           tnOamTrCtlTestMode,
--           tnOamTrCtlLastRunResult,
--           tnOamTrResultsOperStatus
--       }
--       STATUS  current
--       DESCRIPTION
--           "The OAM trace route test has just been completed."
--       ::= { tnOamTraceRouteNotifications 3 }

--
--  Nokia SROS series OAM Service Assurance Agent Test Control Table Scalar
--
tnOamSaaCtlAttributeTotal OBJECT-TYPE
   SYNTAX         Integer32
   MAX-ACCESS     read-only
   STATUS         current
   DESCRIPTION    "."
   ::= { tnOamSaaObjs 3 }

--
--  Nokia SROS series OAM Service Assurance Agent Test Control Table
--
tnOamSaaCtlTable     OBJECT-TYPE
    SYNTAX      SEQUENCE OF TnOamSaaCtlEntry
    MAX-ACCESS  not-accessible
    STATUS      current
    DESCRIPTION
        "Defines the Nokia SROS OAM SAA Control Table for providing,
         via SNMP, the capability of performing Nokia SROS OAM SAA test
         operations.  The results of these tests are stored in the
         ping or trace route results tables."
   ::= { tnOamSaaObjs 4 }

tnOamSaaCtlEntry OBJECT-TYPE
    SYNTAX      TnOamSaaCtlEntry
    MAX-ACCESS  not-accessible
    STATUS      current
    DESCRIPTION
        "Defines an entry in the tnOamSaaCtlTable.  The first index
         element, tnOamSaaCtlOwnerIndex, is of type SnmpAdminString,
         a textual convention that allows for use of the SNMPv3
         View-Based Access Control Model (RFC 2575 [11], VACM)
         and allows a management application to identify its entries.
         The second index, tnOamSaaCtlTestIndex, enables the same
         management application to have multiple outstanding requests."
    INDEX {
             tnSysSwitchId,
             -- tnOamSaaCtlOwnerIndex,
             tnOamSaaCtlTestIndex
          }
    ::= { tnOamSaaCtlTable 1 }

TnOamSaaCtlEntry ::=
    SEQUENCE {
        -- tnOamSaaCtlOwnerIndex         SnmpAdminString,
        tnOamSaaCtlTestIndex           SnmpAdminString,
        tnOamSaaCtlRowStatus           RowStatus,
        tnOamSaaCtlStorageType         StorageType,
        tnOamSaaCtlLastChanged         TimeStamp,
        tnOamSaaCtlAdminStatus         TmnxAdminState,
        tnOamSaaCtlDescr               TItemDescription,
        tnOamSaaCtlTestMode            TmnxOamTestMode,
        tnOamSaaCtlRuns                Counter32,
        tnOamSaaCtlFailures            Counter32,
        tnOamSaaCtlLastRunResult       TmnxOamTestResult,
        tnOamSaaCtlAcctPolicyId        Integer32,
        tnOamSaaCtlSuppressAccounting  TruthValue,
        tnOamSaaCtlContinuous          TruthValue,
        tnOamSaaCtlKeepProbeHistoryAdm INTEGER,
        tnOamSaaCtlKeepProbeHistoryOpr INTEGER,
        tnOamSaaCtlAlmProfName         OCTET STRING
    }

-- tnOamSaaCtlOwnerIndex OBJECT-TYPE
--     SYNTAX      SnmpAdminString (SIZE(1..32))
--     MAX-ACCESS  not-accessible
--     STATUS      current
--     DESCRIPTION
--        "To facilitate the provisioning of access control by a
--         security administrator using the View-Based Access
--         Control Model (RFC 2575, VACM) for tables in which
--         multiple users may need to independently create or
--         modify entries, the initial index is used as an 'owner
--         index'.  Such an initial index has a syntax of
--         SnmpAdminString, and can thus be trivially mapped to a
--         security name or group name as defined in VACM, in
--         accordance with a security policy.

--         When used in conjunction with such a security policy all
--         entries in the table belonging to a particular user (or
--         group) will have the same value for this initial index.
--         For a given user's entries in a particular table, the
--         object identifiers for the information in these entries
--         will have the same subidentifiers (except for the 'column'
--         subidentifier) up to the end of the encoded owner index.
--         To configure VACM to permit access to this portion of the
--         table, one would create vacmViewTreeFamilyTable entries
--         with the value of vacmViewTreeFamilySubtree including
--         the owner index portion, and vacmViewTreeFamilyMask
--         'wildcarding' the column subidentifier.  More elaborate
--         configurations are possible."
--     ::= { tnOamSaaCtlEntry 1 }

tnOamSaaCtlTestIndex OBJECT-TYPE
    SYNTAX      SnmpAdminString (SIZE(1..32))
    MAX-ACCESS  not-accessible
    STATUS      current
    DESCRIPTION
        "The test name index of the Nokia SROS OAM Service Assurance
         Agent, SAA, test.  This is locally unique, within the scope of an
         tnOamSaaCtlOwnerIndex."
    ::= { tnOamSaaCtlEntry 1 }

tnOamSaaCtlRowStatus OBJECT-TYPE
    SYNTAX      RowStatus
    MAX-ACCESS  read-create
    STATUS      current
    DESCRIPTION
        "This object allows entries to be created and deleted
         in the tnOamSaaCtlTable.  Deletion of an entry in this
         table results in all corresponding control and results entries
         in either the ping or traceroute tables.

         Activation of a Nokia SROS OAM ping or trace route operation
         is controlled via tnOamPingCtlAdminStatus or
         tnOamTrCtlAdminStatus and not by changing this object's value
         to 'active (1)'.

         An attempt to delete an entry in this table by setting this object's
         value to 'destroy (6)' will fail with an inconsistentValue error
         if the associated ping or traceroute test is in progress.

         An attempt to delete an entry in this table by setting this object's
         value to 'destroy (6)' will fail with an inconsistentValue error
         if the value of tnOamSaaCtlAdminStatus is not 'outOfService'.

         The operational state of an Nokia SROS OAM SAA test operation
         can be determined by examination of its associated
         tnOamPingResultsOperStatus or tnOamTrResultsOperStatus object."
    REFERENCE
        "See definition of RowStatus in RFC 2579, 'Textual
        Conventions for SMIv2.'"
    ::= { tnOamSaaCtlEntry 2 }

tnOamSaaCtlStorageType OBJECT-TYPE
    SYNTAX      StorageType
    MAX-ACCESS  read-create
    STATUS      current
    DESCRIPTION
        "The storage type for this conceptual row.
         Conceptual rows having the value 'permanent' need not
         allow write-access to any columnar objects in the row."
    DEFVAL { nonVolatile }
    ::= { tnOamSaaCtlEntry 3 }

tnOamSaaCtlLastChanged   OBJECT-TYPE
    SYNTAX      TimeStamp
    MAX-ACCESS  read-only
    STATUS      current
    DESCRIPTION
        "The value of tnOamSaaCtlLastChanged indicates the time the
         value of a settable object in this row was last changed."
    ::= { tnOamSaaCtlEntry 4 }

tnOamSaaCtlAdminStatus OBJECT-TYPE
    SYNTAX      TmnxAdminState
    MAX-ACCESS  read-create
    STATUS      current
    DESCRIPTION
        "The value of tnOamSaaCtlAdminStatus indicates the desired
         administrative state of the Service Assurance Agent, SAA,
         test.

         When the value of tnOamSaaCtlAdminStatus is 'outOfService',
         an attempt to start this SAA test by setting its associated
         tnOamPingCtlAdminStatus or tnOamTrCtlAdminStatus to
         'enabled (1)' will fail with an inconsistentValue error.

         When the value of tnOamSaaCtlAdminStatus is 'inService' attempts
         to modify any other object in the associated tnOamPingCtlTable,
         tnOamTrCtlTable or the control table for the specific OAM test
         type will fail with an inconsistentValue error."
    DEFVAL { outOfService }
    ::= { tnOamSaaCtlEntry 5 }

tnOamSaaCtlDescr OBJECT-TYPE
    SYNTAX      TItemDescription
    MAX-ACCESS  read-create
    STATUS      current
    DESCRIPTION
        "The value of tnOamSaaCtlDescr specifies a user provided description
         string for this SAA test.  It can consist of any printable,
         seven-bit ASCII characters up to 80 characters in length."
    DEFVAL { ''H }  -- empty string
    ::= { tnOamSaaCtlEntry 6 }

tnOamSaaCtlTestMode OBJECT-TYPE
    SYNTAX      TmnxOamTestMode
    MAX-ACCESS  read-only
    STATUS      current
    DESCRIPTION
        "The value of tnOamSaaCtlTestMode indicates the type of
         Service Assurance Agent, SAA, test to be performed.

         When the value of this object is 'notConfigured', no associated
         entry exists in either the tnOamPingCtlTable or tnOamTrCtlTable.

         When the value of this object is 'ping', an associated test entry
         is configured in the tnOamPingCtlTable.

         When the value of this object is 'traceroute', an associated test
         entry is configured in the tnOamTrCtlTable."
    DEFVAL { notConfigured }
    ::= { tnOamSaaCtlEntry 7 }

tnOamSaaCtlRuns      OBJECT-TYPE
    SYNTAX      Counter32
    MAX-ACCESS  read-only
    STATUS      current
    DESCRIPTION
        "The value of tnOamSaaCtlRuns indicates the number of times
         this OAM SAA test has been executed."
    ::= { tnOamSaaCtlEntry 8 }

tnOamSaaCtlFailures  OBJECT-TYPE
    SYNTAX      Counter32
    MAX-ACCESS  read-only
    STATUS      current
    DESCRIPTION
        "The value of tnOamSaaCtlFailures indicates the number of times
         this OAM SAA test has failed."
    ::= { tnOamSaaCtlEntry 9 }

tnOamSaaCtlLastRunResult  OBJECT-TYPE
    SYNTAX      TmnxOamTestResult
    MAX-ACCESS  read-only
    STATUS      current
    DESCRIPTION
        "The value of tnOamSaaCtlLastRunResult indicates the completion
         status the last time this test was executed.  If this OAM test is
         currently in progress, this object indicates the result of the
         previous test run, if any."
    ::= { tnOamSaaCtlEntry 10 }

tnOamSaaCtlAcctPolicyId       OBJECT-TYPE
    SYNTAX      Integer32 (0..99)
    MAX-ACCESS  read-create
    STATUS      current
    DESCRIPTION
        "The value of tnOamSaaCtlAcctPolicyId specifies the accounting
         policy used to record the information obtained from the results
         tables. A value of zero (0) specifies no accounting policy."
    DEFVAL { 0 }
    ::= { tnOamSaaCtlEntry 11 }

tnOamSaaCtlSuppressAccounting OBJECT-TYPE
    SYNTAX      TruthValue
    MAX-ACCESS  read-create
    STATUS      current
    DESCRIPTION
        "The value of tnOamSaaCtlSuppressAccounting specifies whether or
         not the updating of accounting files is suppressed. The value of
         'true (1)' is applicable only when an accounting policy has been
         specified by tnOamSaaCtlAcctPolicyId.

         Upon completion of a test, this object is reset to its default value."
    DEFVAL { false }
    ::= { tnOamSaaCtlEntry 12 }

tnOamSaaCtlContinuous OBJECT-TYPE
    SYNTAX      TruthValue
    MAX-ACCESS  read-create
    STATUS      current
    DESCRIPTION
        "The value of tnOamSaaCtlContinuous specifies whether or not
         the OAM SAA test is to be executed indefinitely."
   DEFVAL { false }
   ::= { tnOamSaaCtlEntry 13 }

tnOamSaaCtlKeepProbeHistoryAdm OBJECT-TYPE
    SYNTAX      INTEGER {
                    keep(1),
                    drop(2),
                    auto(3)
                }
    MAX-ACCESS  read-create
    STATUS      current
    DESCRIPTION
        "The value of tnOamSaaCtlKeepProbeHistoryAdm specifies whether or not
         per-probe history table rows will be created for this test.  A test
         without per-probe history table rows consumes less CPM RAM.

         tnOamSaaCtlKeepProbeHistoryOpr is a read-only operational value
         derived from tnOamSaaCtlKeepProbeHistoryAdm.  The bulk of the
         tnOamSaaCtlKeepProbeHistoryAdm semantics are described in the
         tnOamSaaCtlKeepProbeHistoryOpr DESCRIPTION clause.

         An attempt to set tnOamSaaCtlKeepProbeHistoryAdm to 'drop(2)' when
         tnOamSaaCtlTestMode is not 'ping(1)' returns an 'inconsistentValue'
         error to the manager.

         When the SAA test's test mode is deconfigured (i.e.
         tnOamSaaCtlTestMode becomes 'notConfigured(0)'),
         tnOamSaaCtlKeepProbeHistoryAdm returns to its default value."
    DEFVAL { auto }
    ::= { tnOamSaaCtlEntry 15 }

tnOamSaaCtlKeepProbeHistoryOpr OBJECT-TYPE
    SYNTAX      INTEGER {
                    keep(1),
                    drop(2)
                }
    MAX-ACCESS  read-only
    STATUS      current
    DESCRIPTION
        "The value of tnOamSaaCtlKeepProbeHistoryOpr indicates whether or not
         per-probe history table rows will be created for this test.  A test
         without per-probe history table rows consumes less CPM RAM.

         The value of tnOamSaaCtlKeepProbeHistoryOpr is derived from the value
         of`tnOamSaaCtlKeepProbeHistoryAdm, as shown in the following table.

         tnOamSaaCtlKeepProbeHistoryAdm tnOamSaaCtlKeepProbeHistoryOpr
         -------------------------------- --------------------------------------
         'keep(1)'                        'keep(1)'
         'drop(2)'                        'drop(2)'
         'auto(3)'                        'keep(1)' or 'drop(2)', chosen by SROS

         The history table rows created for the combinations of
         tnOamSaaCtlKeepProbeHistoryOpr and tnOamSaaCtlTestMode values
         are shown in the following table.

         Configuration Options           History Table Rows Created
         --------------------------      --------------------------
         'keep(1)', 'ping(1)'            tnOamPingHistoryTable or
                                         tnOamMacPingHistoryTable
         'keep(1)', 'traceroute(2)'      tnOamTrProbeHistoryTable
         'drop(2)', 'ping(1)'            none
         'drop(2)', 'traceroute(2)'      unsupported combination.

         If tnOamSaaCtlTestMode is 'notConfigured(0)', the value of
         tnOamSaaCtlKeepProbeHistoryOpr is insignificant, since a test without
         a test mode cannot be started.  When a Get is performed on
         tnOamSaaCtlKeepProbeHistoryOpr in this case, 'keep(1)' is returned.

         If tnOamSaaCtlKeepProbeHistoryAdm is 'auto(3)':
           1.  tnOamSaaCtlKeepProbeHistoryOpr is 'drop(2)' if
               a) the test's probe count is greater than 100, OR
               b) the test's interval is less than one second, OR
               c) tnOamSaaCtlTestMode is 'ping(1)' AND the test is continuous
                  (i.e. tnOamSaaCtlContinuous is 'true') AND an accounting
                  policy is specified (i.e. tnOamSaaCtlAcctPolicyId is non-
                  zero).
           2.  Otherwise,  tnOamSaaCtlKeepProbeHistoryOpr is 'keep(1)'."
    ::= { tnOamSaaCtlEntry 16 }

tnOamSaaCtlAlmProfName OBJECT-TYPE
    SYNTAX      OCTET STRING (SIZE(1..40))
    MAX-ACCESS  read-create
    STATUS      current
    DESCRIPTION
        "Alarm profile for OAM proactive test."
    ::= { tnOamSaaCtlEntry 17}

--
--  Nokia SROS series OAM SAA Test Thresholds Table
--

-- tnOamSaaThresholdTable     OBJECT-TYPE
--     SYNTAX      SEQUENCE OF TnOamSaaThresholdEntry
--     MAX-ACCESS  not-accessible
--     STATUS      current
--     DESCRIPTION
--         "Defines the Nokia SROS OAM ping thresholds table for
--          providing, via SNMP, the capability of setting rising and falling
--          thresholds on metrics resulting from Nokia SROS SAA OAM
--          trace route test operations.  The results of the ping tests are
--          stored in the tnOamTrResultsTable and the
--          tnOamTrProbeHistoryTable."
--    ::= { tnOamSaaObjs 6 }
--
-- tnOamSaaThresholdEntry OBJECT-TYPE
--     SYNTAX      TnOamSaaThresholdEntry
--     MAX-ACCESS  not-accessible
--     STATUS      current
--     DESCRIPTION
--         "Defines an entry in the tnOamSaaThresholdTable.  The first index
--          element, tnOamSaaCtlOwnerIndex, is of type SnmpAdminString,
--          a textual convention that allows for use of the SNMPv3
--          View-Based Access Control Model (RFC 2575 [11], VACM)
--          and allows a management application to identify its entries.
--          The second index, tnOamSaaCtlTestIndex, enables the same
--          management application to have multiple outstanding requests.
--          The third index element identifies the type of statistic to be
--          monitored for threshold crossing.  The fourth index element
--          identifies which direction, rising or falling, to monitor."
--     INDEX { tnOamSaaCtlOwnerIndex,
--             tnOamSaaCtlTestIndex,
--             tnOamSaaTType,
--             tnOamSaaTDirection
--           }
--     ::= { tnOamSaaThresholdTable 1 }
--
-- TnOamSaaThresholdEntry ::=
--     SEQUENCE {
--         tnOamSaaTType                    TmnxOamSaaThreshold,
--         tnOamSaaTDirection               INTEGER,
--         tnOamSaaTRowStatus               RowStatus,
--         tnOamSaaTLastChanged             TimeStamp,
--         tnOamSaaTThreshold               Unsigned32,
--         tnOamSaaTValue                   Integer32,
--         tnOamSaaTLastSent                TimeStamp,
--         tnOamSaaTTestMode                TmnxOamTestMode,
--         tnOamSaaTTestRunIndex            Unsigned32
--     }
--
-- tnOamSaaTType        OBJECT-TYPE
--     SYNTAX      TmnxOamSaaThreshold
--     MAX-ACCESS  not-accessible
--     STATUS      current
--     DESCRIPTION
--         "The value of tnOamSaaTType specifies the OAM trace route test
--          statistic to be monitored to determine if a tnOamSaaThreshold
--          notification should be generated at the completion of an
--          SAA test run."
--     ::= { tnOamSaaThresholdEntry 1 }
--
-- tnOamSaaTDirection   OBJECT-TYPE
--     SYNTAX      INTEGER {
--                     rising (1),
--                     falling (2)
--                 }
--     MAX-ACCESS  not-accessible
--     STATUS      current
--     DESCRIPTION
--         "The value of tnOamSaaTDirection specifies whether to
--          monitor this threshold for crossing in the rising or falling
--          direction."
--     ::= { tnOamSaaThresholdEntry 2 }
--
-- tnOamSaaTRowStatus   OBJECT-TYPE
--     SYNTAX      RowStatus
--     MAX-ACCESS  read-create
--     STATUS      current
--     DESCRIPTION
--         "The value of tnOamSaaTRowStatus controls creation and deletion
--          of row entries in the tnOamSaaThresholdTable.
--
--          When a row in this table is created, tnOamSaaTThreshold must
--          also be set or the row creation will fail with an inconsistentValue
--          error."
--     ::= { tnOamSaaThresholdEntry 3 }
--
-- tnOamSaaTLastChanged OBJECT-TYPE
--     SYNTAX      TimeStamp
--     MAX-ACCESS  read-only
--     STATUS      current
--     DESCRIPTION
--         "The value of tnOamSaaTLastChanged indicates the last
--          time the value of tnOamSaaTThreshold was modified."
--     ::= { tnOamSaaThresholdEntry 4 }
--
-- tnOamSaaTThreshold   OBJECT-TYPE
--     SYNTAX      Unsigned32 (0..2147483647)
--     MAX-ACCESS  read-create
--     STATUS      current
--     DESCRIPTION
--         "The value of tnOamSaaTThreshold specifies the threshold
--          value to monitor to determine when to generate a tnOamSaaThreshold
--          notification.
--
--          A threshold value must be set when the row entry is created."
--     ::= { tnOamSaaThresholdEntry 5 }
--
-- tnOamSaaTValue       OBJECT-TYPE
--     SYNTAX      Integer32
--     MAX-ACCESS  read-only
--     STATUS      current
--     DESCRIPTION
--         "The value of tnOamSaaTValue indicates the value of the
--          statistic that last caused a tnOamSaaThreshold notification
--          to be generated."
--     ::= { tnOamSaaThresholdEntry 6 }
--
-- tnOamSaaTLastSent OBJECT-TYPE
--     SYNTAX      TimeStamp
--     MAX-ACCESS  read-only
--     STATUS      current
--     DESCRIPTION
--         "The value of tnOamSaaTLastSent indicates the last time
--          a tnOamSaaThreshold notification was generated as a result
--          of crossing the threshold specified by the value of
--          tnOamSaaTThreshold."
--     ::= { tnOamSaaThresholdEntry 7 }
--
-- tnOamSaaTTestMode OBJECT-TYPE
--     SYNTAX      TmnxOamTestMode
--     MAX-ACCESS  read-only
--     STATUS      current
--     DESCRIPTION
--         "The value of tnOamSaaTTestMode indicates the type of
--          Service Assurance Agent, SAA, test for which a tnOamSaaThreshold
--          notification was generated as a result of crossing the threshold
--          specified by the value of tnOamSaaTThreshold.
--
--          When the value of this object is 'notConfigured', no associated
--          entry exists in either the tnOamPingCtlTable or tnOamTrCtlTable.
--
--          When the value of this object is 'ping', an associated test entry
--          is configured in the tnOamPingCtlTable.
--
--          When the value of this object is 'traceroute', an associated test
--          entry is configured in the tnOamTrCtlTable."
--     ::= { tnOamSaaThresholdEntry 8 }
--
-- tnOamSaaTTestRunIndex OBJECT-TYPE
--     SYNTAX      Unsigned32
--     MAX-ACCESS  read-only
--     STATUS      current
--     DESCRIPTION
--         "The value of tnOamSaaTTestRunIndex indicates the test run index
--          of the Service Assurance Agent, SAA, test for which the last
--          tnOamSaaThreshold notification was generated as a result of
--          crossing the threshold specified by the value of tnOamSaaTThreshold.
--
--          When the value of tnOamSaaTTestMode is 'ping', the value of
--          this object is the value of the tnOamPingResultsTestRunIndex
--          that identifies entries for the ping test results of the test run
--          that generated the last tnOamSaaThreshold notification.
--
--          When the value of tnOamSaaTTestMode is 'traceroute', the value of
--          this object is the value of the tnOamTrResultsTestRunIndex
--          that identifies entries for the traceroute test results of the
--          test run that generated the last tnOamSaaThreshold notification.
--
--          When the value of tnOamSaaTTestMode is 'notConfigured', the value of
--          this object is zero."
--     ::= { tnOamSaaThresholdEntry 9 }

--
-- Notification Definition section
--
-- tnOamSaaThreshold NOTIFICATION-TYPE
--     OBJECTS {
--         tnOamSaaTThreshold,
--         tnOamSaaTValue,
--         tnOamSaaCtlTestMode,
--         tnOamSaaCtlLastRunResult,
--         tnOamSaaTTestRunIndex
--     }
--     STATUS  current
--     DESCRIPTION
--         "Generated at the completion of an SAA OAM trace route
--          test when a threshold has been crossed for a results
--          statistic."
--     ::= { tnOamSaaNotifications 1 }

--
--  Nokia SROS series LDP ECMP OAM (TREE TRACE) Discovery Control Table
--
--
--  Sparsely dependent extension of the tnOamTrCtlTable.
--
--  The same indexes are used for both the base table, tnOamTrCtlTable,
--  and the sparsely dependent table, tnOamLTtraceCtlTable.
--
--  This in effect extends the tnOamTrCtlTable with additional columns.
--  Rows are created in the tnOamLTtraceCtlTable only for those entries
--  in the tnOamTrCtlTable where tnOamTrCtlTestMode has a value of
--  'ldpTreeTrace'.
--
--  Deletion of a row in the tnOamTrCtlTable results in the
--  same fate for the row in the tnOamLTtraceCtlTable.
--

-- tnOamLTtraceCtlTable     OBJECT-TYPE
--     SYNTAX      SEQUENCE OF TnOamLTtraceCtlEntry
--     MAX-ACCESS  not-accessible
--     STATUS      current
--     DESCRIPTION
--         "tnOamLTtraceCtlTable defines the Nokia SROS OAM LDP
--          Tree Trace Control Table for providing, via SNMP, the
--          capability of performing Nokia SROS OAM 'ldpTreeTrace'
--          manual test operations. The results of these tests are stored
--          in the tnOamLTtraceResultsTable and the
--          tnOamLTtraceHopInfoTable."
--    ::= { tnOamTraceRouteObjs 18 }
--
-- tnOamLTtraceCtlEntry OBJECT-TYPE
--     SYNTAX      TnOamLTtraceCtlEntry
--     MAX-ACCESS  not-accessible
--     STATUS      current
--     DESCRIPTION
--         "tnOamLTtraceCtlEntry represents a row in the
--          tnOamLTtraceCtlTable.  The first index element,
--          tnOamTrCtlOwnerIndex, is of type SnmpAdminString,
--          a textual convention that allows for use of the
--          SNMPv3 View-Based Access Control Model (RFC 2575 [11], VACM)
--          and allows a management application to identify its entries.
--          The second index, tnOamTrCtlTestIndex, enables the same
--          management application to have multiple outstanding requests."
--     INDEX {
--            tnOamTrCtlOwnerIndex,
--            tnOamTrCtlTestIndex
--           }
--     ::= { tnOamLTtraceCtlTable 1 }
--
-- TnOamLTtraceCtlEntry ::=
--     SEQUENCE {
--         tnOamLTtraceCtlLdpPrefixType      InetAddressType,
--         tnOamLTtraceCtlLdpPrefix          InetAddress,
--         tnOamLTtraceCtlLdpPrefixLen       InetAddressPrefixLength,
--         tnOamLTtraceCtlMaxPath            Unsigned32,
--         tnOamLTtraceCtlDownstreamMpTlv    TmnxOamMplsEchoDownMapTlv
--     }
--
-- tnOamLTtraceCtlLdpPrefixType     OBJECT-TYPE
--     SYNTAX      InetAddressType
--     MAX-ACCESS  read-create
--     STATUS      current
--     DESCRIPTION
--         "The value of tnOamLTtraceCtlLdpPrefixType specifies the
--          type of Internet address stored in tnOamLTtraceCtlLdpPrefix."
--     DEFVAL { unknown }
--     ::= { tnOamLTtraceCtlEntry 2 }
--
-- tnOamLTtraceCtlLdpPrefix     OBJECT-TYPE
--     SYNTAX      InetAddress (SIZE (0|4|16))
--     MAX-ACCESS  read-create
--     STATUS      current
--     DESCRIPTION
--         "The value of tnOamLTtraceCtlLdpPrefix specifies the
--          Internet address prefix for the LDP based LSP for this
--          OAM LDP Tree discovery test."
--     DEFVAL { ''H }
--     ::= { tnOamLTtraceCtlEntry 3 }
--
-- tnOamLTtraceCtlLdpPrefixLen     OBJECT-TYPE
--     SYNTAX      InetAddressPrefixLength
--     MAX-ACCESS  read-create
--     STATUS      current
--     DESCRIPTION
--         "The value of tnOamLTtraceCtlLdpPrefixLen specifies the Internet
--          address prefix length for the LDP based LSP for this OAM LDP Tree
--          discovery test.
--
--          The value of this parameter is valid only when LDP IP Prefix
--          has been specified."
--     DEFVAL { 32 }
--     ::= { tnOamLTtraceCtlEntry 4 }
--
-- tnOamLTtraceCtlMaxPath OBJECT-TYPE
--     SYNTAX      Unsigned32 (1..255)
--     MAX-ACCESS  read-create
--     STATUS      current
--     DESCRIPTION
--         "The value of tnOamLTtraceCtlMaxPath specifies the maximum number
--          of paths that can be discovered for the given LDP Prefix
--          (tnOamLTtraceCtlLdpPrefix)."
--     DEFVAL { 128 }
--     ::= { tnOamLTtraceCtlEntry 5 }
--
-- tnOamLTtraceCtlDownstreamMpTlv OBJECT-TYPE
--   SYNTAX      TmnxOamMplsEchoDownMapTlv
--     MAX-ACCESS  read-create
--     STATUS      current
--     DESCRIPTION
--         "The value of tnOamLTtraceCtlDownstreamMpTlv specifies the type of
--          downstream mapping TLV to insert in the MPLS echo request PDUs when
--          launching the test.
--
--          When an LDP tree trace test is created, the value of this object
--          defaults to the value of the global configuration object
--          tnOamMplsEchoDownstreamMapTlv."
--     ::= { tnOamLTtraceCtlEntry 6 }

--
-- Nokia SROS series LDP ECMP OAM (TREE TRACE) Manual Discovery Test
-- Simple Object Definitions
--
-- tnOamLTtraceMaxConRequests OBJECT-TYPE
--     SYNTAX      Unsigned32
--     UNITS       "requests"
--     MAX-ACCESS  read-only
--     STATUS      current
--     DESCRIPTION
--        "The value of tnOamLTtraceMaxConRequests indicates the
--         maximum number of concurrent Ldp Tree Trace manual discovery
--         sessions that are allowed within an agent implementation."
--     ::= { tnOamTraceRouteObjs 19 }

--
-- Nokia SROS series LDP ECMP OAM (TREE TRACE) Manual Discovery Test
-- Results Table
--
-- tnOamLTtraceResultsTable OBJECT-TYPE
--     SYNTAX      SEQUENCE OF TnOamLTtraceResultsEntry
--     MAX-ACCESS  not-accessible
--     STATUS      current
--     DESCRIPTION
--         "tnOamLTtraceResultsTable defines the Nokia SROS OAM
--          Trace Route Test Results Table for keeping track of the status
--          of a tnOamTrCtlEntry having tnOamTrCtlTestMode as ldpTreeTrace.
--
--          An entry is added to the tnOamLTtraceResultsTable when an
--          tnOamTrCtlEntry is created with  tnOamTrCtlTestMode having
--          value 'ldpTreeTrace'.
--
--          An entry is removed from the tnOamTrResultsTable when
--          such a corresponding entry, tnOamTrCtlEntry, is deleted."
--    ::= { tnOamTraceRouteObjs 20 }
--
-- tnOamLTtraceResultsEntry OBJECT-TYPE
--     SYNTAX      TnOamLTtraceResultsEntry
--     MAX-ACCESS  not-accessible
--     STATUS      current
--     DESCRIPTION
--         "tnOamLTtraceResultsEntry represents a row in the
--          tnOamLTtraceResultsTable.  The two indices of the
--          tnOamLTtraceResultsTable are the same as that in the
--          tnOamTrCtlTable in order for a tnOamLTtraceResultsEntry to
--          correspond to the tnOamTrCtlEntry that caused it to be
--          created."
--     INDEX {
--            tnOamTrCtlOwnerIndex,
--            tnOamTrCtlTestIndex
--           }
--     ::= { tnOamLTtraceResultsTable 1 }
--
-- TnOamLTtraceResultsEntry ::=
--     SEQUENCE {
--         tnOamLTtraceResultsDisPaths         Unsigned32,
--         tnOamLTtraceResultsFailedHops       Unsigned32,
--         tnOamLTtraceResultsDisState         INTEGER,
--         tnOamLTtraceResultsDisStatus        TmnxOamLTtraceDisStatusBits
--     }
--
-- tnOamLTtraceResultsDisPaths OBJECT-TYPE
--     SYNTAX      Unsigned32
--     MAX-ACCESS  read-only
--     STATUS      current
--     DESCRIPTION
--         "The value of tnOamLTtraceResultsDisPaths indicates the number of
--          discovered ECMP paths in this OAM LDP Tree discovery test."
--     ::= { tnOamLTtraceResultsEntry 2 }
--
-- tnOamLTtraceResultsFailedHops OBJECT-TYPE
--     SYNTAX      Unsigned32
--     MAX-ACCESS  read-only
--     STATUS      current
--     DESCRIPTION
--         "The value of tnOamLTtraceResultsFailedHops indicates the number
--          of hops from which no successful response was received during
--          this OAM LDP Tree discovery test."
--     ::= { tnOamLTtraceResultsEntry 3 }
--
-- tnOamLTtraceResultsDisState       OBJECT-TYPE
--     SYNTAX      INTEGER {
--                     initial (0),
--                     inProgress (1),
--                     done (2)
--                 }
--     MAX-ACCESS  read-only
--     STATUS      current
--     DESCRIPTION
--         "The value of tnOamLTtraceResultsDisState indicates the current
--          state of the discovery process for the LDP IP prefix
--         (tnOamLTtraceCtlLdpPrefix) in this OAM LDP Tree discovery test."
--     ::= { tnOamLTtraceResultsEntry  4 }
--
-- tnOamLTtraceResultsDisStatus OBJECT-TYPE
--     SYNTAX      TmnxOamLTtraceDisStatusBits
--     MAX-ACCESS  read-only
--     STATUS      current
--     DESCRIPTION
--         "The value of tnOamLTtraceResultsDisStatus indicates the current
--          discovery status bits for the LDP IP prefix
--          (tnOamLTtraceCtlLdpPrefix) in this OAM LDP Tree discovery test."
--     ::= { tnOamLTtraceResultsEntry 5 }
--
-- Nokia SROS series LDP ECMP OAM (TREE TRACE) Manual Discovery Test
-- Hops Table
--
-- tnOamLTtraceHopInfoTable OBJECT-TYPE
--     SYNTAX      SEQUENCE OF TnOamLTtraceHopInfoEntry
--     MAX-ACCESS  not-accessible
--     STATUS      current
--     DESCRIPTION
--         "tnOamLTtraceHopInfoTable defines the Nokia SROS OAM LDP
--          Trace Hops table for keeping track of the results of an LDP Tree Trace
--          test on a per hop basis.

--          An entry is added to the tnOamLTtraceHopInfoTable when an
--          hop is discovered after setting the tnOamTrCtlAdminStatus
--          object of the tnOamTrCtlEntry (having tnOamTrCtlTestMode
--          as ldpTreeTrace) to 'enabled(1)'.  An entry is removed from the
--          tnOamLTtraceHopInfoTable when its corresponding tnOamTrCtlEntry
--          is deleted."
--    ::= { tnOamTraceRouteObjs 21 }

-- tnOamLTtraceHopInfoEntry OBJECT-TYPE
--     SYNTAX      TnOamLTtraceHopInfoEntry
--     MAX-ACCESS  not-accessible
--     STATUS      current
--     DESCRIPTION
--         "tnOamLTtraceHopInfoEntry represents a row in the
--          tnOamLTtraceHopInfoTable. The first two indices of the
--          tnOamLTtraceHopInfoTable are the same as the tnOamTrCtlTable in
--          order for a tnOamLTtraceHopInfoEntry to correspond to the
--          tnOamTrCtlEntry that caused it to be created. The third index
--          element, tnOamLTtraceHopIndex, selects a hop in a Nokia
--          SROS Ldp Tree Trace discovered path."
--     INDEX {
--            tnOamTrCtlOwnerIndex,
--            tnOamTrCtlTestIndex,
--            tnOamLTtraceHopIndex
--           }
--     ::= { tnOamLTtraceHopInfoTable 1 }

-- TnOamLTtraceHopInfoEntry ::=
--     SEQUENCE {
--         tnOamLTtraceHopIndex             Unsigned32,
--         tnOamLTtraceUpStreamHopIndex     Unsigned32,
--         tnOamLTtraceHopAddrType          InetAddressType,
--         tnOamLTtraceHopAddr              InetAddress,
--         tnOamLTtraceHopDstAddrType       InetAddressType,
--         tnOamLTtraceHopDstAddr           InetAddress,
--         tnOamLTtraceHopEgrNhAddrType     InetAddressType,
--         tnOamLTtraceHopEgrNhAddr         InetAddress,
--         tnOamLTtraceHopDisTtl            Unsigned32,
--         tnOamLTtraceHopLastRc            TmnxOamPingRtnCode,
--         tnOamLTtraceHopDiscoveryState    INTEGER,
--         tnOamLTtraceHopDiscoveryTime     TimeStamp,
--         tnOamLTtraceHopLabel1            MplsLabel,
--         tnOamLTtraceHopLabel2            MplsLabel,
--         tnOamLTtraceHopLabel3            MplsLabel,
--         tnOamLTtraceHopLabel4            MplsLabel,
--         tnOamLTtraceHopLabel5            MplsLabel,
--         tnOamLTtraceHopLabel6            MplsLabel,
--         tnOamLTtraceHopIfAddrType        InetAddressType,
--         tnOamLTtraceHopIfAddress         InetAddress,
--         tnOamLTtraceHopRouterIdType      InetAddressType,
--         tnOamLTtraceHopRouterId          InetAddress
--     }

-- tnOamLTtraceHopIndex OBJECT-TYPE
--     SYNTAX      Unsigned32
--     MAX-ACCESS  not-accessible
--     STATUS      current
--     DESCRIPTION
--         "The value of tnOamLTtraceHopIndex indicates the hop index
--          for an Nokia SROS OAM Trace hop for an LDP Tree Trace test.
--          The hop index values are assigned starting at 1."
--     ::= { tnOamLTtraceHopInfoEntry 1 }

-- tnOamLTtraceUpStreamHopIndex OBJECT-TYPE
--     SYNTAX      Unsigned32
--     MAX-ACCESS  read-only
--     STATUS      current
--     DESCRIPTION
--         "The value of tnOamLTtraceUpStreamHopIndex indicates the
--          hop index (tnOamLTtraceHopIndex) of its upstream hop
--          discovered during the LDP Tree Trace test.  The value of
--          tnOamLTtraceUpStreamHopIndex is 0 for the hops which are
--          the root of the different discovered paths for the LDP
--          Tree Trace test."
--     ::= { tnOamLTtraceHopInfoEntry 2 }

-- tnOamLTtraceHopAddrType     OBJECT-TYPE
--     SYNTAX      InetAddressType
--     MAX-ACCESS  read-only
--     STATUS      current
--     DESCRIPTION
--         "The value of tnOamLTtraceHopAddrType indicates the type of
--          Internet address stored in tnOamLTtraceHopAddr."
--     ::= { tnOamLTtraceHopInfoEntry 3 }

-- tnOamLTtraceHopAddr     OBJECT-TYPE
--     SYNTAX      InetAddress (SIZE (0|4|16))
--     MAX-ACCESS  read-only
--     STATUS      current
--     DESCRIPTION
--         "The value of tnOamLTtraceHopAddr indicates the IP address
--          of a hop for a given LDP based LSP associated with the
--          OAM LDP Tree trace test."
--     ::= { tnOamLTtraceHopInfoEntry 4 }

-- tnOamLTtraceHopDstAddrType     OBJECT-TYPE
--     SYNTAX      InetAddressType
--     MAX-ACCESS  read-only
--     STATUS      current
--     DESCRIPTION
--         "The value of tnOamLTtraceHopDstAddrType indicates the type of
--          Internet address stored in tnOamLTtraceHopDstAddr."
--     ::= { tnOamLTtraceHopInfoEntry 5 }

-- tnOamLTtraceHopDstAddr     OBJECT-TYPE
--     SYNTAX      InetAddress (SIZE (0|4|16))
--     MAX-ACCESS  read-only
--     STATUS      current
--     DESCRIPTION
--         "The value of tnOamLTtraceHopDstAddr indicates the destination
--          IP address (127 Address) of a path associated with the hop."
--     ::= { tnOamLTtraceHopInfoEntry 6 }

-- tnOamLTtraceHopEgrNhAddrType     OBJECT-TYPE
--     SYNTAX      InetAddressType
--     MAX-ACCESS  read-only
--     STATUS      current
--     DESCRIPTION
--         "The value of tnOamLTtraceHopEgrNhAddrType indicates the type of
--          Internet address stored in tnOamLTtraceHopEgrNhAddr."
--     ::= { tnOamLTtraceHopInfoEntry 7 }

-- tnOamLTtraceHopEgrNhAddr     OBJECT-TYPE
--     SYNTAX      InetAddress (SIZE (0|4|16))
--     MAX-ACCESS  read-only
--     STATUS      current
--     DESCRIPTION
--         "The value of tnOamLTtraceHopEgrNhAddr indicates the
--          next hop  IP address (wrt the ingress router), which is used
--          to reach this Hop (tnOamLTtraceHopAddr)."
--     ::= { tnOamLTtraceHopInfoEntry 8 }

-- tnOamLTtraceHopDisTtl OBJECT-TYPE
--     SYNTAX      Unsigned32
--     MAX-ACCESS  read-only
--     STATUS      current
--     DESCRIPTION
--         "The value of tnOamLTtraceHopDisTtl indicates the label time-to-live
--          value used to discover this hop."
--     ::= { tnOamLTtraceHopInfoEntry 9 }

-- tnOamLTtraceHopLastRc    OBJECT-TYPE
--     SYNTAX      TmnxOamPingRtnCode
--     MAX-ACCESS  read-only
--     STATUS      current
--     DESCRIPTION
--         "The value of tnOamLTtraceHopLastRc indicates the OAM return code
--          received in the OAM trace response."
--     ::= { tnOamLTtraceHopInfoEntry 10 }

-- tnOamLTtraceHopDiscoveryState       OBJECT-TYPE
--     SYNTAX      INTEGER {
--                     inProgress (0),
--                     doneOk (1),
--                     doneTimeout (2),
--                     doneLoopDetected (3),
--                     doneExpiredTtl (4)
--                 }
--     MAX-ACCESS  read-only
--     STATUS      current
--     DESCRIPTION
--         "The value of tnOamLTtraceHopDiscoveryState indicates the current
--          discovery state of this hop."
--     ::= { tnOamLTtraceHopInfoEntry 11 }

-- tnOamLTtraceHopDiscoveryTime   OBJECT-TYPE
--     SYNTAX      TimeStamp
--     MAX-ACCESS  read-only
--     STATUS      current
--     DESCRIPTION
--         "The value of tnOamLTtraceHopDiscoveryTime indicates the sysUpTime
--          when the hop was discovered."
--     ::= { tnOamLTtraceHopInfoEntry 12 }

-- tnOamLTtraceHopLabel1          OBJECT-TYPE
--     SYNTAX      MplsLabel
--     MAX-ACCESS  read-only
--     STATUS      current
--     DESCRIPTION
--         "The value of tnOamLTtraceHopLabel1 indicates the first (top of the
--          label stack) label for this hop."
--     ::= { tnOamLTtraceHopInfoEntry 13 }

-- tnOamLTtraceHopLabel2          OBJECT-TYPE
--     SYNTAX      MplsLabel
--     MAX-ACCESS  read-only
--     STATUS      current
--     DESCRIPTION
--         "The value of tnOamLTtraceHopLabel2 indicates the second label for
--          this hop."
--     ::= { tnOamLTtraceHopInfoEntry 14 }

-- tnOamLTtraceHopLabel3          OBJECT-TYPE
--     SYNTAX      MplsLabel
--     MAX-ACCESS  read-only
--     STATUS      current
--     DESCRIPTION
--         "The value of tnOamLTtraceHopLabel3 indicates the third label for this
--          hop."
--     ::= { tnOamLTtraceHopInfoEntry 15 }

-- tnOamLTtraceHopLabel4          OBJECT-TYPE
--     SYNTAX      MplsLabel
--     MAX-ACCESS  read-only
--     STATUS      current
--     DESCRIPTION
--         "The value of tnOamLTtraceHopLabel4 indicates the fourth label for
--          this hop."
--     ::= { tnOamLTtraceHopInfoEntry 16 }

-- tnOamLTtraceHopLabel5          OBJECT-TYPE
--     SYNTAX      MplsLabel
--     MAX-ACCESS  read-only
--     STATUS      current
--     DESCRIPTION
--         "The value of tnOamLTtraceHopLabel5 indicates the fifth label for this
--          hop."
--     ::= { tnOamLTtraceHopInfoEntry 17 }

-- tnOamLTtraceHopLabel6          OBJECT-TYPE
--     SYNTAX      MplsLabel
--     MAX-ACCESS  read-only
--     STATUS      current
--     DESCRIPTION
--         "The value of tnOamLTtraceHopLabel6 indicates the sixth label for this
--          hop."
--     ::= { tnOamLTtraceHopInfoEntry 18 }

-- tnOamLTtraceHopIfAddrType      OBJECT-TYPE
--     SYNTAX      InetAddressType
--     MAX-ACCESS  read-only
--     STATUS      current
--     DESCRIPTION
--         "The value of tnOamLTtraceHopIfAddrType indicates the IP address type
--          for the interface IP address for this hop."
--     ::= { tnOamLTtraceHopInfoEntry 19 }

-- tnOamLTtraceHopIfAddress       OBJECT-TYPE
--     SYNTAX      InetAddress (SIZE (0|4|16))
--     MAX-ACCESS  read-only
--     STATUS      current
--     DESCRIPTION
--         "The value of tnOamLTtraceHopIfAddress indicates the IP Address for
--          the interface for this hop."
--     ::= { tnOamLTtraceHopInfoEntry 20 }

-- tnOamLTtraceHopRouterIdType    OBJECT-TYPE
--     SYNTAX      InetAddressType
--     MAX-ACCESS  read-only
--     STATUS      current
--     DESCRIPTION
--         "The value of tnOamLTtraceHopRouterIdType indicates the IP address
--          type for the Router ID for this hop."
--     ::= { tnOamLTtraceHopInfoEntry 21 }

-- tnOamLTtraceHopRouterId        OBJECT-TYPE
--     SYNTAX      InetAddress (SIZE (0|4|16))
--     MAX-ACCESS  read-only
--     STATUS      current
--     DESCRIPTION
--         "The value of tnOamLTtraceHopRouterId indicates the IP Address for
--          the Router ID for this hop."
--     ::= { tnOamLTtraceHopInfoEntry 22 }

--
--  Nokia SROS series LDP ECMP OAM (TREE TRACE) Auto Config Table
--

-- tnOamLTtraceAutoConfigTable OBJECT-TYPE
--     SYNTAX     SEQUENCE OF TnOamLTtraceAutoConfigEntry
--     MAX-ACCESS not-accessible
--     STATUS     current
--     DESCRIPTION
--         "tnOamLTtraceAutoConfigTable contains an entry for configuration
--          information about each instance of Automatic (background) LDP Tree
--          Trace."
--     ::= { tnOamTraceRouteObjs 22 }

-- tnOamLTtraceAutoConfigEntry OBJECT-TYPE
--     SYNTAX     TnOamLTtraceAutoConfigEntry
--     MAX-ACCESS not-accessible
--     STATUS     current
--     DESCRIPTION
--         "tnOamLTtraceAutoConfigEntry represents a row in the
--          tnOamLTtraceAutoConfigTable.  Each entry represents the
--          Automatic LDP Tree Trace instance running on a virtual router.

--           A row entry can be created and deleted through the
--           tnOamLTtraceAutoRowStatus object."
--     INDEX      { vRtrID }
--     ::= { tnOamLTtraceAutoConfigTable 1 }

-- TnOamLTtraceAutoConfigEntry ::=
--     SEQUENCE {
--         tnOamLTtraceAutoRowStatus         RowStatus,
--         tnOamLTtraceAutoLastChanged       TimeStamp,
--         tnOamLTtraceAutoStorageType       StorageType,
--         tnOamLTtraceAutoAdminState        TmnxAdminState,
--         tnOamLTtraceAutoFcName            TFCName,
--         tnOamLTtraceAutoProfile           TProfile,
--         tnOamLTtraceAutoDiscIntvl         Unsigned32,
--         tnOamLTtraceAutoMaxPath           Unsigned32,
--         tnOamLTtraceAutoTrMaxTtl          Unsigned32,
--         tnOamLTtraceAutoTrTimeOut         Unsigned32,
--         tnOamLTtraceAutoTrMaxFailures     Unsigned32,
--         tnOamLTtraceAutoPolicy1           TPolicyStatementNameOrEmpty,
--         tnOamLTtraceAutoPolicy2           TPolicyStatementNameOrEmpty,
--         tnOamLTtraceAutoPolicy3           TPolicyStatementNameOrEmpty,
--         tnOamLTtraceAutoPolicy4           TPolicyStatementNameOrEmpty,
--         tnOamLTtraceAutoPolicy5           TPolicyStatementNameOrEmpty,
--         tnOamLTtraceAutoProbeIntvl        Unsigned32,
--         tnOamLTtraceAutoPrTimeOut         Unsigned32,
--         tnOamLTtraceAutoPrMaxFailures     Unsigned32
--    }

-- tnOamLTtraceAutoRowStatus OBJECT-TYPE
--     SYNTAX     RowStatus
--     MAX-ACCESS read-create
--     STATUS     current
--     DESCRIPTION
--         "The value of tnOamLTtraceAutoRowStatus specifies the row status of
--           the Auto LDP Tree Trace instance for the virtual router.

--          A row with default attribute values is created by setting
--          tnOamLTtraceAutoRowStatus to 'createAndGo'. A row entry can be
--          destroyed by setting tnOamLTtraceAutoRowStatus to 'destroy'. An
--          attempt to destroy a row will fail if tnOamLTtraceAutoAdminState
--          is not set to 'outOfService'.

--          Deletion of an entry in this table results in deletion
--          of all the corresponding tables: tnOamLTtraceAutoStatusTable,
--          tnOamLTtraceFecInfoTable, and tnOamLTtracePathInfoTable."
--     ::= { tnOamLTtraceAutoConfigEntry 1 }

-- tnOamLTtraceAutoLastChanged     OBJECT-TYPE
--     SYNTAX      TimeStamp
--     MAX-ACCESS  read-only
--     STATUS      current
--     DESCRIPTION
--         "The value of tnOamLTtraceAutoLastChanged indicates the last time
--         the value of a writable object in this row was modified."
--     ::= { tnOamLTtraceAutoConfigEntry 2 }

-- tnOamLTtraceAutoStorageType OBJECT-TYPE
--     SYNTAX      StorageType
--     MAX-ACCESS  read-create
--     STATUS      current
--     DESCRIPTION
--         "The value of tnOamLTtraceAutoStorageType specifies the storage type
--          for this conceptual row. Conceptual rows having the value 'permanent'
--          need not allow write-access to any columnar objects in the row."
--     DEFVAL { volatile }
--     ::= { tnOamLTtraceAutoConfigEntry 3 }

-- tnOamLTtraceAutoAdminState OBJECT-TYPE
--     SYNTAX     TmnxAdminState
--     MAX-ACCESS read-create
--     STATUS     current
--     DESCRIPTION
--         "The value of tnOamLTtraceAutoAdminState specifies the state based on
--          which the Auto LDP Tree Discovery process starts or stops.

--          When the tnOamLTtraceAutoAdminState becomes 'inService',
--          the Auto LDP Tree Discovery process starts, and periodic
--          path-probing on the previously discovered paths, if any, continues.
--          When the tnOamLTtraceAutoAdminState becomes 'outOfService',
--          the Auto LDP Tree Discovery process and periodic path-probing
--          on the discovered paths stop.

--          At the starting of the Auto discovery process, it selects the
--          address FECs imported from LDP peers (TN-LDP-MIB::
--          vRtrLdpAddrFecTable) provided the FECs pass the configured policies
--          (tnOamLTtraceAutoPolicy1..tnOamLTtraceAutoPolicy5). For all the
--          FECs (tnOamLTtraceAutoTotalFecs), it automatically
--          creates entries from the tnOamLTtraceFecInfoTable. As a part of
--          the auto discovery process, it creates entries from the
--          tnOamLTtracePathInfoTable for each discovered path."
--     DEFVAL { outOfService }
--     ::= { tnOamLTtraceAutoConfigEntry 4 }

-- tnOamLTtraceAutoFcName       OBJECT-TYPE
--     SYNTAX      TFCName
--     MAX-ACCESS  read-create
--     STATUS      current
--     DESCRIPTION
--         "The value of tnOamLTtraceAutoFcName specifies the forwarding class
--          of the MPLS Echo request packets.

--          The forwarding class name must be one of those defined in the
--          tFCNameTable in TN-QOS-MIB.  The agent creates predefined
--          entries in the tFCNameTable for 'premium', 'assured', and 'be'
--          (for best-effort) forwarding classes.  The actual forwarding
--          class encoding is controlled by the network egress LSP-EXP
--          mappings."
--     DEFVAL { "be" }
--     ::= { tnOamLTtraceAutoConfigEntry 5 }

-- tnOamLTtraceAutoProfile      OBJECT-TYPE
--     SYNTAX      TProfile
--     MAX-ACCESS  read-create
--     STATUS      current
--     DESCRIPTION
--         "The value of tnOamLTtraceAutoProfile specifies the profile
--          value to be used with the forwarding class specified in
--          tnOamLTtraceAutoFcName.

--          The profile value must be consistent with the specified forwarding
--          class:
--             'assured' = 'in' or 'out'
--             'premium' = 'in'
--             'be' = 'out'
--         "
--      DEFVAL { out }
--      ::= { tnOamLTtraceAutoConfigEntry 6 }

-- tnOamLTtraceAutoDiscIntvl  OBJECT-TYPE
--     SYNTAX      Unsigned32 (60..1440)
--     UNITS       "minutes"
--     MAX-ACCESS  read-create
--     STATUS      current
--     DESCRIPTION
--         "The value of tnOamLTtraceAutoDiscIntvl specifies number of
--          minutes to wait before repeating LDP Tree Auto Discovery process."
--     DEFVAL { 60 }
--     ::= { tnOamLTtraceAutoConfigEntry 7 }

-- tnOamLTtraceAutoMaxPath OBJECT-TYPE
--     SYNTAX      Unsigned32 (1..128)
--     MAX-ACCESS  read-create
--     STATUS      current
--     DESCRIPTION
--         "The value of tnOamLTtraceAutoMaxPath specifies the maximum
--           number of paths that can be discovered for a selected IP Address
--           FEC (tnOamLTtraceAutoTotalFecs)."
--     DEFVAL { 128 }
--     ::= { tnOamLTtraceAutoConfigEntry 8 }

-- tnOamLTtraceAutoTrMaxTtl OBJECT-TYPE
--     SYNTAX      Unsigned32 (1..255)
--     UNITS       "time-to-live value"
--     MAX-ACCESS  read-create
--     STATUS      current
--     DESCRIPTION
--         "The value of tnOamLTtraceAutoTrMaxTtl specifies the maximum
--          label time-to-live value for an Lsp trace request during the tree
--          discovery."
--     DEFVAL { 30 }
--     ::= { tnOamLTtraceAutoConfigEntry 9 }

-- tnOamLTtraceAutoTrTimeOut OBJECT-TYPE
--     SYNTAX      Unsigned32 (1..60)
--     UNITS       "seconds"
--     MAX-ACCESS  read-create
--     STATUS      current
--     DESCRIPTION
--         "The value of tnOamLTtraceAutoTrTimeOut specifies the time-out
--          value, in seconds, for an lsp trace request during the tree discovery."
--     DEFVAL { 30 }
--     ::= { tnOamLTtraceAutoConfigEntry 10 }

-- tnOamLTtraceAutoTrMaxFailures OBJECT-TYPE
--     SYNTAX      Unsigned32 (1..10)
--     UNITS       "timeouts"
--     MAX-ACCESS  read-create
--     STATUS      current
--     DESCRIPTION
--         "The value of tnOamLTtraceAutoTrMaxFailures specifies the maximum
--          number of consecutive timeouts allowed before terminating an lsp trace
--          request to a hop."
--     DEFVAL { 3 }
--     ::= { tnOamLTtraceAutoConfigEntry 11 }

-- tnOamLTtraceAutoPolicy1 OBJECT-TYPE
--     SYNTAX       TPolicyStatementNameOrEmpty
--     MAX-ACCESS   read-create
--     STATUS       current
--     DESCRIPTION
--         "The value of tnOamLTtraceAutoPolicy1 specifies the first
--          policy used to filter LDP imported Address FECs."
--     DEFVAL { ''H }
--     ::= { tnOamLTtraceAutoConfigEntry 12 }

-- tnOamLTtraceAutoPolicy2 OBJECT-TYPE
--     SYNTAX       TPolicyStatementNameOrEmpty
--     MAX-ACCESS   read-create
--     STATUS       current
--     DESCRIPTION
--         "The value of tnOamLTtraceAutoPolicy2 specifies the second
--          policy used to filter LDP imported Address FECs."
--     DEFVAL { ''H }
--     ::= { tnOamLTtraceAutoConfigEntry 13 }

-- tnOamLTtraceAutoPolicy3 OBJECT-TYPE
--     SYNTAX       TPolicyStatementNameOrEmpty
--     MAX-ACCESS   read-create
--     STATUS       current
--     DESCRIPTION
--         "The value of tnOamLTtraceAutoPolicy3 specifies the third
--          policy used to filter LDP imported Address FECs."
--     DEFVAL { ''H }
--     ::= { tnOamLTtraceAutoConfigEntry 14 }

-- tnOamLTtraceAutoPolicy4 OBJECT-TYPE
--     SYNTAX       TPolicyStatementNameOrEmpty
--     MAX-ACCESS   read-create
--     STATUS       current
--     DESCRIPTION
--         "The value of tnOamLTtraceAutoPolicy4 specifies the fourth
--          policy used to filter LDP imported Address FECs."
--     DEFVAL { ''H }
--     ::= { tnOamLTtraceAutoConfigEntry 15 }

-- tnOamLTtraceAutoPolicy5 OBJECT-TYPE
--     SYNTAX       TPolicyStatementNameOrEmpty
--     MAX-ACCESS   read-create
--     STATUS       current
--     DESCRIPTION
--         "The value of tnOamLTtraceAutoPolicy5 specifies the fifth
--          policy used to filter LDP imported Address FECs."
--     DEFVAL { ''H }
--     ::= { tnOamLTtraceAutoConfigEntry 16 }

-- tnOamLTtraceAutoProbeIntvl  OBJECT-TYPE
--     SYNTAX      Unsigned32 (1..60)
--     UNITS       "minutes"
--     MAX-ACCESS  read-create
--     STATUS      current
--     DESCRIPTION
--         "The value of tnOamLTtraceAutoProbeIntvl specifies the number
--          of minutes to wait before repeating probing (pinging) a discovered
--          path."

--     DEFVAL { 1 }
--     ::= { tnOamLTtraceAutoConfigEntry 17 }

-- tnOamLTtraceAutoPrTimeOut OBJECT-TYPE
--     SYNTAX      Unsigned32 (1..3)
--     UNITS       "minutes"
--     MAX-ACCESS  read-create
--     STATUS      current
--     DESCRIPTION
--         "The value of tnOamLTtraceAutoPrTimeOut specifies the time-out
--          value, in minutes, for a ping request during probing.
--          tnOamLTtraceAutoPrTimeOut cannot be greater than
--          tnOamLTtraceAutoProbeIntvl."
--     DEFVAL { 1 }
--     ::= { tnOamLTtraceAutoConfigEntry 18 }

-- tnOamLTtraceAutoPrMaxFailures OBJECT-TYPE
--     SYNTAX      Unsigned32 (1..10)
--     UNITS       "timeouts"
--     MAX-ACCESS  read-create
--     STATUS      current
--     DESCRIPTION
--         "The value of tnOamLTtraceAutoPrMaxFailures specifies the
--          maximum number of consecutive timeouts allowed before failing a path
--          probe (ping)."
--     DEFVAL { 3 }
--     ::= { tnOamLTtraceAutoConfigEntry 19 }


--
--  Nokia SROS series LDP ECMP OAM (TREE TRACE) Auto Status Table
--
-- tnOamLTtraceAutoStatusTable OBJECT-TYPE
--     SYNTAX     SEQUENCE OF TnOamLTtraceAutoStatusEntry
--     MAX-ACCESS not-accessible
--     STATUS     current
--     DESCRIPTION
--         "tnOamLTtraceAutoStatusTable contains an entry for operational
--          information about each instance of Automatic (background) LDP
--          Tree Trace."
--     ::= { tnOamTraceRouteObjs 23 }

-- tnOamLTtraceAutoStatusEntry OBJECT-TYPE
--     SYNTAX     TnOamLTtraceAutoStatusEntry
--     MAX-ACCESS not-accessible
--     STATUS     current
--     DESCRIPTION
--         "tnOamLTtraceAutoStatusEntry represents a row in the
--          tnOamLTtraceAutoStatusTable.

--          Entries cannot be created or deleted via snmp SET operations.
--          An entry is created whenever a row is created in
--          tnOamLTtraceAutoConfigTable."
--     INDEX      { vRtrID }
--     ::= { tnOamLTtraceAutoStatusTable 1 }

-- TnOamLTtraceAutoStatusEntry ::=
--     SEQUENCE {
--         tnOamLTtraceAutoDiscoveryState    INTEGER,
--         tnOamLTtraceAutoTotalFecs         Unsigned32,
--         tnOamLTtraceAutoDisFecs           Unsigned32,
--         tnOamLTtraceAutoLastDisStart      TimeStamp,
--         tnOamLTtraceAutoLastDisEnd        TimeStamp,
--         tnOamLTtraceAutoLastDisDur        Unsigned32
--    }

-- tnOamLTtraceAutoDiscoveryState       OBJECT-TYPE
--     SYNTAX      INTEGER {
--                     initial (0),
--                     inProgress (1),
--                     done (2),
--                     halt (3)
--                 }
--     MAX-ACCESS  read-only
--     STATUS      current
--     DESCRIPTION
--         "The value of tnOamLTtraceAutoDiscoveryState indicates the current
--          state of the discovery process."
--     ::= { tnOamLTtraceAutoStatusEntry 1 }

-- tnOamLTtraceAutoTotalFecs OBJECT-TYPE
--     SYNTAX      Unsigned32
--     MAX-ACCESS  read-only
--     STATUS      current
--     DESCRIPTION
--         "The value of tnOamLTtraceAutoTotalFecs indicates the number of
--          Address FECs that have been selected for discovery during the
--          current discovery process.

--          An Address FEC imported from an LDP peer
--          (TN-LDP-MIB:: vRtrLdpAddrFecTable)is selected if it passes
--          the associated policies (tnOamLTtraceAutoPolicy1..
--          tnOamLTtraceAutoPolicy5)."
--     ::= { tnOamLTtraceAutoStatusEntry 2 }

-- tnOamLTtraceAutoDisFecs OBJECT-TYPE
--     SYNTAX      Unsigned32
--     MAX-ACCESS  read-only
--     STATUS      current
--     DESCRIPTION
--         "The value of tnOamLTtraceAutoDisFecs indicates the number of
--          selected Address FECs that have been discovered successfully
--          during the current discovery process."
--     ::= { tnOamLTtraceAutoStatusEntry 3 }

-- tnOamLTtraceAutoLastDisStart   OBJECT-TYPE
--     SYNTAX      TimeStamp
--     MAX-ACCESS  read-only
--     STATUS      current
--     DESCRIPTION
--         "The value of tnOamLTtraceAutoLastDisStart indicates the
--          sysUpTime when the last Auto discovery process started.  If
--          no discovery process has started, the value will be 0."
--     ::= { tnOamLTtraceAutoStatusEntry 4 }

-- tnOamLTtraceAutoLastDisEnd   OBJECT-TYPE
--     SYNTAX      TimeStamp
--     MAX-ACCESS  read-only
--     STATUS      current
--     DESCRIPTION
--         "The value of tnOamLTtraceAutoLastDisEnd indicates the
--          sysUpTime when the last Auto discovery process ended. Before
--          the first discovery process ends, it would be 0. At the end of a
--          discovery this value is set. This value is not reset during
--          starting/restarting."
--     ::= { tnOamLTtraceAutoStatusEntry 5 }

-- tnOamLTtraceAutoLastDisDur   OBJECT-TYPE
--     SYNTAX      Unsigned32
--     UNITS       "seconds"
--     MAX-ACCESS  read-only
--     STATUS      current
--     DESCRIPTION
--         "The value of tnOamLTtraceAutoLastDisDur indicates the time
--          (in seconds) it took to finish the last discovery process.If no test
--          has been finished, the value is 0.  This value is updated only when
--          a discovery ends."
--     ::= { tnOamLTtraceAutoStatusEntry 6 }

--
--  Nokia SROS series LDP ECMP OAM (TREE TRACE) Auto  FEC Info Table
--
-- tnOamLTtraceFecInfoTable OBJECT-TYPE
--     SYNTAX     SEQUENCE OF TnOamLTtraceFecInfoEntry
--     MAX-ACCESS not-accessible
--     STATUS     current
--     DESCRIPTION
--         "tnOamLTtraceFecInfoTable contains entries for the operational
--          information about the automatically selected FECs."
--     ::= { tnOamTraceRouteObjs 24 }

-- tnOamLTtraceFecInfoEntry OBJECT-TYPE
--     SYNTAX     TnOamLTtraceFecInfoEntry
--     MAX-ACCESS not-accessible
--     STATUS     current
--     DESCRIPTION
--         "tnOamLTtraceFecInfoEntry represents a row in the
--          tnOamLTtraceFecInfoTable.

--          Entries cannot be created and deleted via SNMP SET operations."

--     INDEX {
--              vRtrID,
--              tnOamLTtraceFecPrefixType,
--              tnOamLTtraceFecPrefix,
--              tnOamLTtraceFecPrefLen
--           }
--     ::= { tnOamLTtraceFecInfoTable 1 }

-- TnOamLTtraceFecInfoEntry ::=
--     SEQUENCE {
--         tnOamLTtraceFecPrefixType         InetAddressType,
--         tnOamLTtraceFecPrefix             InetAddress,
--         tnOamLTtraceFecPrefLen            InetAddressPrefixLength,
--         tnOamLTtraceFecDiscoveryState     INTEGER,
--         tnOamLTtraceFecDisStatusBits      TmnxOamLTtraceDisStatusBits,
--         tnOamLTtraceFecDisPaths           Unsigned32,
--         tnOamLTtraceFecFailedHops         Unsigned32,
--         tnOamLTtraceFecLastDisEnd         TimeStamp,
--         tnOamLTtraceFecFailedProbes       Unsigned32,
--         tnOamLTtraceFecProbeState         INTEGER,
--         tnOamLTtraceFecSendErrProbes      Unsigned32
--    }

-- tnOamLTtraceFecPrefixType     OBJECT-TYPE
--     SYNTAX      InetAddressType
--     MAX-ACCESS  not-accessible
--     STATUS      current
--     DESCRIPTION
--         "The value of tnOamLTtraceFecPrefixType specifies the type of
--          remote IP address stored in tnOamLTtraceFecPrefix.  Currently
--          only ipv4 type is supported."
--     ::= { tnOamLTtraceFecInfoEntry 1 }

-- tnOamLTtraceFecPrefix     OBJECT-TYPE
--     SYNTAX      InetAddress (SIZE (0|4|16))
--     MAX-ACCESS  not-accessible
--     STATUS      current
--     DESCRIPTION
--         "The value of tnOamLTtraceFecPrefix indicates the Internet address
--          prefix for an LDP based LSP associated with the OAM LDP Tree trace
--          test."
--     ::= { tnOamLTtraceFecInfoEntry 2 }

-- tnOamLTtraceFecPrefLen     OBJECT-TYPE
--     SYNTAX      InetAddressPrefixLength
--     MAX-ACCESS  not-accessible
--     STATUS      current
--     DESCRIPTION
--         "The value of tnOamLTtraceFecPrefLen indicates the Internet
--          address prefix length for the LDP based LSP associated with the OAM
--          LDP Tree trace test."
--     ::= { tnOamLTtraceFecInfoEntry 3 }

-- tnOamLTtraceFecDiscoveryState       OBJECT-TYPE
--     SYNTAX      INTEGER {
--                     initial (0),
--                     inProgress (1),
--                     done (2)
--                 }
--     MAX-ACCESS  read-only
--     STATUS      current
--     DESCRIPTION
--         "The value of tnOamLTtraceFecDiscoveryState indicates the current
--          state of the discovery process for the Address FEC."
--     ::= { tnOamLTtraceFecInfoEntry 4 }


-- tnOamLTtraceFecDisStatusBits OBJECT-TYPE
--     SYNTAX      TmnxOamLTtraceDisStatusBits
--     MAX-ACCESS  read-only
--     STATUS      current
--     DESCRIPTION
--         "The value of tnOamLTtraceFecDisStatusBits indicates the current
--          discovery status bits for the Address FEC."
--     ::= { tnOamLTtraceFecInfoEntry 5 }

-- tnOamLTtraceFecDisPaths OBJECT-TYPE
--     SYNTAX      Unsigned32
--     MAX-ACCESS  read-only
--     STATUS      current
--     DESCRIPTION
--         "The value of tnOamLTtraceFecDisPaths indicates the number of
--          discovered ECMP paths for the Address FEC."
--     ::= { tnOamLTtraceFecInfoEntry 6 }

-- tnOamLTtraceFecFailedHops OBJECT-TYPE
--     SYNTAX      Unsigned32
--     MAX-ACCESS  read-only
--     STATUS      current
--     DESCRIPTION
--         "The value of tnOamLTtraceFecFailedHops indicates the number of
--          hops from which no successful response was received."
--     ::= { tnOamLTtraceFecInfoEntry 7 }

-- tnOamLTtraceFecLastDisEnd   OBJECT-TYPE
--     SYNTAX      TimeStamp
--     MAX-ACCESS  read-only
--     STATUS      current
--     DESCRIPTION
--         "The value of tnOamLTtraceFecLastDisEnd indicates the sysUpTime
--          when the FEC was last discovered."
--     ::= { tnOamLTtraceFecInfoEntry 8 }

-- tnOamLTtraceFecFailedProbes OBJECT-TYPE
--     SYNTAX      Unsigned32
--     MAX-ACCESS  read-only
--     STATUS      current
--     DESCRIPTION
--         "The value of tnOamLTtraceFecFailedProbes indicates the number of
--          discovered paths which are in failed probing state."
--     ::= { tnOamLTtraceFecInfoEntry 9 }

-- tnOamLTtraceFecProbeState       OBJECT-TYPE
--     SYNTAX      INTEGER {
--                     oK (0),
--                     partiallyFailed (1),
--                     failed (2)
--                 }
--     MAX-ACCESS  read-only
--     STATUS      current
--     DESCRIPTION
--         "The value of tnOamLTtraceFecProbeState indicates the current
--          overall probing state for the discovered paths of the Address FEC.
--          The tnOamLTtraceFecProbeState is considered as 'oK' when
--          probing on all the associated discovered paths is OK.
--          It is considered as 'failed' when probing on all the associated
--          discovered paths failed. It is considered as partially failed
--          when probing on one or more, but not all, discovered paths failed."
--     ::= { tnOamLTtraceFecInfoEntry 10 }

-- tnOamLTtraceFecSendErrProbes      OBJECT-TYPE
--     SYNTAX      Unsigned32
--     MAX-ACCESS  read-only
--     STATUS      current
--     DESCRIPTION
--         "The value of tnOamLTtraceFecSendErrProbes indicates the number of
--          discovered paths which are experiencing problems in sending probe
--          (ping) requests."
--     ::= { tnOamLTtraceFecInfoEntry 11 }

--
--  Nokia SROS series LDP ECMP OAM (TREE TRACE) Auto Path Info Table
--
-- tnOamLTtracePathInfoTable OBJECT-TYPE
--     SYNTAX     SEQUENCE OF TnOamLTtracePathInfoEntry
--     MAX-ACCESS not-accessible
--     STATUS     current
--     DESCRIPTION
--         "tnOamLTtracePathInfoTable contains entries with operational
--          information about the automatically discovered ECMP paths."
--     ::= { tnOamTraceRouteObjs 25 }

-- tnOamLTtracePathInfoEntry OBJECT-TYPE
--     SYNTAX     TnOamLTtracePathInfoEntry
--     MAX-ACCESS not-accessible
--     STATUS     current
--     DESCRIPTION
--         "tnOamLTtracePathInfoEntry represents a row in the
--          tnOamLTtracePathInfoTable.

--          Entries cannot be created and deleted via SNMP SET operations."
--     INDEX {
--              vRtrID,
--              tnOamLTtraceFecPrefixType,
--              tnOamLTtraceFecPrefix,
--              tnOamLTtraceFecPrefLen,
--              tnOamLTtracePathDstAddrType,
--              tnOamLTtracePathDstAddr
--           }
--     ::= { tnOamLTtracePathInfoTable 1 }

-- TnOamLTtracePathInfoEntry ::=
--     SEQUENCE {
--         tnOamLTtracePathDstAddrType       InetAddressType,
--         tnOamLTtracePathDstAddr           InetAddress,
--         tnOamLTtracePathRemAddrType       InetAddressType,
--         tnOamLTtracePathRemoteAddr        InetAddress,
--         tnOamLTtracePathEgrNhAddrType     InetAddressType,
--         tnOamLTtracePathEgrNhAddr         InetAddress,
--         tnOamLTtracePathDisTtl            Unsigned32,
--         tnOamLTtracePathLastDisTime       TimeStamp,
--         tnOamLTtracePathLastRc            TmnxOamPingRtnCode,
--         tnOamLTtracePathProbeState        INTEGER,
--         tnOamLTtracePathProbeTmOutCnt     Unsigned32,
--         tnOamLTtracePathProbeSendErr      INTEGER
--    }
-- tnOamLTtracePathDstAddrType     OBJECT-TYPE
--     SYNTAX      InetAddressType
--     MAX-ACCESS  not-accessible
--     STATUS      current
--     DESCRIPTION
--         "The value of tnOamLTtracePathDstAddrType indicates the type of
--          Internet address stored in tnOamLTtracePathDstAddr."
--     ::= { tnOamLTtracePathInfoEntry 1 }

-- tnOamLTtracePathDstAddr     OBJECT-TYPE
--     SYNTAX      InetAddress (SIZE (0|4|16))
--     MAX-ACCESS  not-accessible
--     STATUS      current
--     DESCRIPTION
--         "The value of tnOamLTtracePathDstAddr indicates the destination
--          IP address (127 Address) of a path for a given LDP based LSP
--          associated with the OAM LDP Tree trace test."
--     ::= { tnOamLTtracePathInfoEntry 2 }

-- tnOamLTtracePathRemAddrType     OBJECT-TYPE
--     SYNTAX      InetAddressType
--     MAX-ACCESS  read-only
--     STATUS      current
--     DESCRIPTION
--         "The value of tnOamLTtracePathRemAddrType indicates the type of
--          Internet address stored in tnOamLTtracePathRemoteAddr."
--     ::= { tnOamLTtracePathInfoEntry 3 }

-- tnOamLTtracePathRemoteAddr     OBJECT-TYPE
--     SYNTAX      InetAddress (SIZE (0|4|16))
--     MAX-ACCESS  read-only
--     STATUS      current
--     DESCRIPTION
--         "The value of tnOamLTtracePathRemoteAddr indicates the associated
--          interface IP address or the router ID of the egress router."
--     ::= { tnOamLTtracePathInfoEntry 4 }

-- tnOamLTtracePathEgrNhAddrType     OBJECT-TYPE
--     SYNTAX      InetAddressType
--     MAX-ACCESS  read-only
--     STATUS      current
--     DESCRIPTION
--         "The value of tnOamLTtracePathEgrNhAddrType indicates the type of
--          Internet address stored in tnOamLTtracePathEgrNhAddr."
--     ::= { tnOamLTtracePathInfoEntry 5 }

-- tnOamLTtracePathEgrNhAddr     OBJECT-TYPE
--     SYNTAX      InetAddress (SIZE (0|4|16))
--     MAX-ACCESS  read-only
--     STATUS      current
--     DESCRIPTION
--         "The value of tnOamLTtracePathEgrNhAddr indicates the
--          next hop IP address (wrt the ingress router) used to reach the
--          associated ECMP path endpoint."
--     ::= { tnOamLTtracePathInfoEntry 6 }

-- tnOamLTtracePathDisTtl OBJECT-TYPE
--     SYNTAX      Unsigned32
--     MAX-ACCESS  read-only
--     STATUS      current
--     DESCRIPTION
--         "The value of tnOamLTtracePathDisTtl indicates the label
--          time-to-live value used to discover the egress router for
--          the path."
--     ::= { tnOamLTtracePathInfoEntry 7 }

-- tnOamLTtracePathLastDisTime   OBJECT-TYPE
--     SYNTAX      TimeStamp
--     MAX-ACCESS  read-only
--     STATUS      current
--     DESCRIPTION
--         "The value of tnOamLTtracePathLastDisTime indicates the sysUpTime
--          when the path was last discovered."
--     ::= { tnOamLTtracePathInfoEntry 8 }

-- tnOamLTtracePathLastRc    OBJECT-TYPE
--     SYNTAX      TmnxOamPingRtnCode
--     MAX-ACCESS  read-only
--     STATUS      current
--     DESCRIPTION
--         "The value of tnOamLTtracePathLastRc indicates the OAM return code
--          received in the OAM ping response."
--     ::= { tnOamLTtracePathInfoEntry 9 }

-- tnOamLTtracePathProbeState       OBJECT-TYPE
--     SYNTAX      INTEGER {
--                     oK (0),
--                     failed (1)
--                 }
--     MAX-ACCESS  read-only
--     STATUS      current
--     DESCRIPTION
--         "The value of tnOamLTtracePathProbeState indicates the current
--          probing (ping) state for the discovered ECMP path.
--          The tnOamLTtracePathProbeState is considered as 'failed' when
--          number of consecutive timeouts for the ping request reached its
--          maximum allowed limit (tnOamLTtraceAutoPrMaxFailures).
--          The tnOamLTtracePathProbeState is considered as 'oK' after receiving
--          a successful ping response for the associated path."
--     ::= { tnOamLTtracePathInfoEntry 10 }

-- tnOamLTtracePathProbeTmOutCnt OBJECT-TYPE
--     SYNTAX      Unsigned32
--     MAX-ACCESS  read-only
--     STATUS      current
--     DESCRIPTION
--         "The value of tnOamLTtracePathProbeTmOutCnt indicates the number of
--          consecutive timeouts for the associated ping request.
--          This tnOamLTtracePathProbeTmOutCnt is reset to 0
--          after receiving a successful ping response from the path
--          destination."
--     ::= { tnOamLTtracePathInfoEntry 11 }

-- tnOamLTtracePathProbeSendErr  OBJECT-TYPE
--     SYNTAX  INTEGER {
--                 oK (0),
--                 failed (1)
--             }
--     MAX-ACCESS  read-only
--     STATUS      current
--     DESCRIPTION
--         "The value of tnOamLTtracePathProbeSendErr indicates the state of the
--          last path probe (ping) request.

--          The tnOamLTtracePathProbeSendErr is considered as 'failed' if the
--          last probe (ping) request could not be sent due to some local failure
--          else it is 'oK'."
--     ::= { tnOamLTtracePathInfoEntry 12 }

--
-- Nokia SROS series LDP ECMP OAM (TREE TRACE) Notification
-- Definition section
--

-- tnOamLdpTtraceAutoDiscState NOTIFICATION-TYPE
--     OBJECTS {
--         tnOamLTtraceAutoDiscoveryState
--     }
--     STATUS  current
--     DESCRIPTION
--         "The tnOamLdpTtraceAutoDiscState notification is generated when
--          the discovery state of the 'Auto Ldp Tree Trace entity' represented by
--          tnOamLTtraceAutoDiscoveryState has been changed."
--     ::= { tnOamTraceRouteNotifications 4 }

-- tnOamLdpTtraceFecProbeState NOTIFICATION-TYPE
--     OBJECTS {
--         tnOamLTtraceFecProbeState,
--         tnOamLTtraceFecDisPaths,
--         tnOamLTtraceFecFailedProbes,
--         tnOamLTtraceFecSendErrProbes
--     }
--     STATUS  current
--     DESCRIPTION
--         "The tnOamLdpTtraceFecProbeState notification is generated when
--          the probe state of the 'auto discovered FEC' has been changed."
--     ::= { tnOamTraceRouteNotifications 5 }

-- tnOamLdpTtraceFecDisStatus NOTIFICATION-TYPE
--     OBJECTS {
--         tnOamLTtraceFecDisStatusBits,
--         tnOamLTtraceFecDisPaths
--     }
--     STATUS  current
--     DESCRIPTION
--         "The tnOamLdpTtraceFecDisStatus notification is generated when
--          the discovery status BITS or the number of discovered paths of the
--          'auto discovered FEC' has been changed.  Note that the changes are
--          evaluated at the end of a FEC discovery."
--     ::= { tnOamTraceRouteNotifications 6 }

-- tnOamLdpTtraceFecPFailUpdate NOTIFICATION-TYPE
--     OBJECTS {
--         tnOamLTtraceFecProbeState,
--         tnOamLTtraceFecDisPaths,
--         tnOamLTtraceFecFailedProbes,
--         tnOamLTtraceFecSendErrProbes
--     }
--     STATUS  current
--     DESCRIPTION
--         "The tnOamLdpTtraceFecPFailUpdate notification is generated when
--          there is a probe state change in any of the relevant discovered paths
--          while the overall FEC probe state, tnOamLTtraceFecProbeState is in
--          'partially failed' state."
--     ::= { tnOamTraceRouteNotifications 7 }

--
--  Nokia SROS series OAM VCCV Trace Control Table
--
--  Sparse Dependent Extension of the tnOamTrCtlTable.
--
--  The same indexes are used for both the base table, tnOamTrCtlTable,
--  and the sparse dependent table, tnOamVccvTrCtlTable.
--
--  This in effect extends the tnOamTrCtlTable with additional columns.
--  Rows are created in the tnOamVccvTrCtlTable only for those entries
--  in the tnOamTrCtlTable where tnOamTrCtlTestMode has a value of
--  'vccvTraceRoute'.
--
--  Deletion of a row in the tnOamTrCtlTable results in the
--  deletion of the row in the tnOamVccvTrCtlTable.
--
tnOamVccvTrCtlTable     OBJECT-TYPE
    SYNTAX      SEQUENCE OF TnOamVccvTrCtlEntry
    MAX-ACCESS  not-accessible
    STATUS      current
    DESCRIPTION
        "Defines the Nokia SROS OAM VCCV Trace Control Table for
         providing, via SNMP, the capability of performing Nokia
         SROS OAM 'vccvTraceRoute' test operations. The results of these
         tests are stored in the tnOamTrResultsTable, the
         tnOamTrProbeHistoryTable and the tnOamVccvTrNextPwSegmentTable."
::= { tnOamTraceRouteObjs 26 }

tnOamVccvTrCtlEntry OBJECT-TYPE
    SYNTAX      TnOamVccvTrCtlEntry
    MAX-ACCESS  not-accessible
    STATUS      current
    DESCRIPTION
        "Defines an entry in the tnOamVccvTrCtlTable.  The first index
         element, tnOamTrCtlOwnerIndex, is of type SnmpAdminString,
         a textual convention that allows for use of the SNMPv3
         View-Based Access Control Model (RFC 2575 [11], VACM)
         and allows a management application to identify its entries.
         The second index, tnOamTrCtlTestIndex, enables the same
         management application to have multiple outstanding requests."
    INDEX {
             tnSysSwitchId,
             -- tnOamTrCtlOwnerIndex,
             tnOamTrCtlTestIndex
          }
    ::= { tnOamVccvTrCtlTable 1 }

TnOamVccvTrCtlEntry ::=
    SEQUENCE {
        tnOamVccvTrCtlSdpIdVcId        SdpBindId,
        tnOamVccvTrCtlReplyMode        INTEGER,
        tnOamVccvTrCtlSpokeSdpId       TmnxSpokeSdpIdOrZero,
        tnOamVccvTrCtlSaiiGlobalId     TmnxPwGlobalIdOrZero,
        tnOamVccvTrCtlSaiiPrefix       Unsigned32,
        tnOamVccvTrCtlSaiiAcId         Unsigned32,
        tnOamVccvTrCtlTaiiGlobalId     TmnxPwGlobalIdOrZero,
        tnOamVccvTrCtlTaiiPrefix       Unsigned32,
        tnOamVccvTrCtlTaiiAcId         Unsigned32,
        tnOamVccvTrCtlTestSubMode      TmnxOamVccvTestSubMode,
        tnOamVccvTrCtlAssocChannel     TmnxOamVccvAssocChannel
    }

tnOamVccvTrCtlSdpIdVcId    OBJECT-TYPE
    SYNTAX      SdpBindId
    MAX-ACCESS  read-create
    STATUS      current
    DESCRIPTION
        "The value of tnOamVccvTrCtlSdpIdVcId specifies the SDP binding of
         the FEC 128 pseudowire to be used when performing a vccv-trace
         operation.  A non-zero value is mandatory when testing a FEC 128
         pseudowire.

         The all-zeros value indicates an unused SDP binding.

         If tnOamVccvTrCtlSdpIdVcId is set to a non-default value, then
         the following objects must be default: tnOamVccvTrCtlSpokeSdpId,
         tnOamVccvTrCtlSaiiGlobalId, tnOamVccvTrCtlSaiiPrefix,
         tnOamVccvTrCtlSaiiAcId, tnOamVccvTrCtlTaiiGlobalId,
         tnOamVccvTrCtlTaiiPrefix, and tnOamVccvTrCtlTaiiAcId.

         If the value of tnOamVccvTrCtlSdpIdVcId is non-zero and invalid, or
         the pseudowire is administratively down, or unavailable, the OAM Trace
         request message probe is not sent and an appropriate error value is
         written to tnOamTrProbeHistoryStatus for that probe entry.  Once the
         interval timer expires, the next probe attempt will be made if
         required."
    DEFVAL { '0000000000000000'h }
    ::= { tnOamVccvTrCtlEntry 1 }

tnOamVccvTrCtlReplyMode OBJECT-TYPE
    SYNTAX          INTEGER {
                        ip (2),
                        controlChannel (4)
                    }
    MAX-ACCESS      read-create
    STATUS          current
    DESCRIPTION
        "The value of tnOamVccvTrCtlReplyMode specifies the method of reply
         due to the vccv-traceRoute request message.
             ip (2)                 out-of-band reply
             controlChannel (4)     inband reply

         This parameter is optional for vccv-traceRoute."
    REFERENCE   "RFC 4379, Section 7.1"
    DEFVAL { controlChannel }
    ::= { tnOamVccvTrCtlEntry 2 }

tnOamVccvTrCtlSpokeSdpId       OBJECT-TYPE
    SYNTAX         TmnxSpokeSdpIdOrZero
    MAX-ACCESS     read-create
    STATUS         current
    DESCRIPTION
        "The value of tnOamVccvTrCtlSpokeSdpId specifies the spoke SDP
         identifier to be used when performing a vccv-trace test on a FEC 129
         pseudowire.  This object is optional.

         At most one of tnOamVccvTrCtlSdpIdVcId and
         tnOamVccvTrCtlSpokeSdpId can be set to a non-default value on a
         particular row.

         A value of zero indicates that no spoke SDP identifier has been
         configured."
    DEFVAL { 0 }
    ::= { tnOamVccvTrCtlEntry 3 }

tnOamVccvTrCtlSaiiGlobalId     OBJECT-TYPE
    SYNTAX         TmnxPwGlobalIdOrZero
    MAX-ACCESS     read-create
    STATUS         current
    DESCRIPTION
        "The value of tnOamVccvTrCtlSaiiGlobalId specifies the global
         identifier of the Source Attachment Individual Identifier (SAII)
         to be used when testing a FEC 129 AII Type 2 pseudowire.

         tnOamVccvTrCtlSaiiGlobalId, tnOamVccvTrCtlSaiiPrefix,
         tnOamVccvTrCtlSaiiAcId, tnOamVccvTrCtlTaiiGlobalId,
         tnOamVccvTrCtlTaiiPrefix, and tnOamVccvTrCtlTaiiAcId can be
         used (together) to identify a FEC 129 AII Type 2 pseudowire.

         At most one of tnOamVccvTrCtlSdpIdVcId and
         tnOamVccvTrCtlSaiiGlobalId can be set to a non-default value on a
         particular row.

         A value of zero indicates that no global identifier has been
         configured."
    REFERENCE
        "RFC 5003 Section 3.2"
    DEFVAL { 0 }
    ::= { tnOamVccvTrCtlEntry 4 }

tnOamVccvTrCtlSaiiPrefix       OBJECT-TYPE
    SYNTAX         Unsigned32
    MAX-ACCESS     read-create
    STATUS         current
    DESCRIPTION
        "The value of tnOamVccvTrCtlSaiiPrefix specifies the prefix of the
         Source Attachment Individual Identifier (SAII) to be used when testing
         a FEC 129 AII Type 2 pseudowire.

         At most one of tnOamVccvTrCtlSdpIdVcId and
         tnOamVccvTrCtlSaiiPrefix can be set to a non-default value on a
         particular row.

         A value of zero indicates that no prefix has been configured."
    REFERENCE
        "RFC 5003 Section 3.2"
    DEFVAL { 0 }
    ::= { tnOamVccvTrCtlEntry 5 }

tnOamVccvTrCtlSaiiAcId         OBJECT-TYPE
    SYNTAX         Unsigned32
    MAX-ACCESS     read-create
    STATUS         current
    DESCRIPTION
        "The value of tnOamVccvTrCtlSaiiAcId specifies the attachment
         circuit identifier of the Source Attachment Individual Identifier
         (SAII) to be used when testing a FEC 129 AII Type 2 pseudowire.

         At most one of tnOamVccvTrCtlSdpIdVcId and
         tnOamVccvTrCtlSaiiAcId can be set to a non-default value on a
         particular row.

         A value of zero indicates that no attachment circuit identifier has
         been configured."
    REFERENCE
        "RFC 5003 Section 3.2"
    DEFVAL { 0 }
    ::= { tnOamVccvTrCtlEntry 6 }

tnOamVccvTrCtlTaiiGlobalId     OBJECT-TYPE
    SYNTAX         TmnxPwGlobalIdOrZero
    MAX-ACCESS     read-create
    STATUS         current
    DESCRIPTION
        "The value of tnOamVccvTrCtlTaiiGlobalId specifies the global
         identifier of the Target Attachment Individual Identifier (TAII)
         to be used when testing a FEC 129 AII Type 2 pseudowire.

         At most one of tnOamVccvTrCtlSdpIdVcId and
         tnOamVccvTrCtlTaiiGlobalId can be set to a non-default value on a
         particular row.

         A value of zero indicates that no global identifier has been
         configured."
    REFERENCE
        "RFC 5003 Section 3.2"
    DEFVAL { 0 }
    ::= { tnOamVccvTrCtlEntry 7 }

tnOamVccvTrCtlTaiiPrefix       OBJECT-TYPE
    SYNTAX         Unsigned32
    MAX-ACCESS     read-create
    STATUS         current
    DESCRIPTION
        "The value of tnOamVccvTrCtlTaiiPrefix specifies the prefix of the
         Target Attachment Individual Identifier (TAII) to be used when testing
         a FEC 129 AII Type 2 pseudowire.

         At most one of tnOamVccvTrCtlSdpIdVcId and
         tnOamVccvTrCtlTaiiPrefix can be set to a non-default value on a
         particular row.

         A value of zero indicates that no prefix has been configured."
    REFERENCE
        "RFC 5003 Section 3.2"
    DEFVAL { 0 }
    ::= { tnOamVccvTrCtlEntry 8 }

tnOamVccvTrCtlTaiiAcId         OBJECT-TYPE
    SYNTAX         Unsigned32
    MAX-ACCESS     read-create
    STATUS         current
    DESCRIPTION
        "The value of tnOamVccvTrCtlTaiiAcId specifies the attachment
         circuit identifier of the Target Attachment Individual Identifier
         (TAII) to be used when testing a FEC 129 AII Type 2 pseudowire.

         At most one of tnOamVccvTrCtlSdpIdVcId and
         tnOamVccvTrCtlTaiiAcId can be set to a non-default value on a
         particular row.

         A value of zero indicates that no attachment circuit identifier has
         been configured."
    REFERENCE
        "RFC 5003 Section 3.2"
    DEFVAL { 0 }
    ::= { tnOamVccvTrCtlEntry 9 }

tnOamVccvTrCtlTestSubMode      OBJECT-TYPE
    SYNTAX      TmnxOamVccvTestSubMode
    MAX-ACCESS  read-create
    STATUS      current
    DESCRIPTION
        "The value of tnOamVccvTrCtlTestSubMode specifies the type of VCCV
         trace route test to perform.

         When this object is 'unspecified(1)', the type of VCCV trace route test
         to be performed is determined when the test is started, from the set of
         tnOamVccvTrCtlTable objects configured with non-default values.

         If there is a mismatch between tnOamVccvTrCtlTestSubMode and the type
         of the pseudowire to be tested, the test will fail.  For example, if
         tnOamVccvTrCtlTestSubMode is 'static(2)', and
         tnOamVccvTrCtlSdpIdVcId refers to an SDP binding with
         TIMETRA-SDP-MIB::sdpDelivery not equal to 'mplsTp(3)', the test will
         fail.

         The supported object combinations for VCCV trace route tests are listed
         in the tnOamVccvTrCtlTable DESCRIPTION clause."
    DEFVAL { unspecified }
    ::= { tnOamVccvTrCtlEntry 10 }

tnOamVccvTrCtlAssocChannel     OBJECT-TYPE
    SYNTAX      TmnxOamVccvAssocChannel
    MAX-ACCESS  read-create
    STATUS      current
    DESCRIPTION
        "The value of tnOamVccvTrCtlAssocChannel specifies the launched echo
         request's usage of the Associated Channel (ACH) mechanism, when
         performing an MPLS-TP VCCV trace route test.

         When tnOamVccvTrCtlTestSubMode is 'static(2)', the default value
         for tnOamVccvTrCtlAssocChannel is 'nonIp(2)'.

         The supported object combinations for VCCV trace route tests are listed
         in the tnOamVccvTrCtlTable DESCRIPTION clause."
    DEFVAL { notApplicable }
    ::= { tnOamVccvTrCtlEntry 11 }

--
-- Nokia SROS OAM VCCV TraceRoute Route Information Next Hop Table
--
tnOamVccvTrNextPwSegmentTable OBJECT-TYPE
    SYNTAX      SEQUENCE OF TnOamVccvTrNextPwSegmentEntry
    MAX-ACCESS  not-accessible
    STATUS      current
    DESCRIPTION
        "Defines a table for storing the results of an OAM 'vccvTraceRoute'
         probe operation where a Vccv next hop list is returned.

         An entry in this table is created when the result of an OAM
         'vccvTraceRoute' probe is determined. An entry is removed from this
         table when its corresponding tnOamTrCtlEntry is deleted."
   ::= { tnOamTraceRouteObjs 27 }

tnOamVccvTrNextPwSegmentEntry OBJECT-TYPE
    SYNTAX      TnOamVccvTrNextPwSegmentEntry
    MAX-ACCESS  not-accessible
    STATUS      current
    DESCRIPTION
        "Defines an entry in the tnOamVccvTrNextPwSegmentTable. The first two
         index elements identify the tnOamTrCtlEntry that a
         tnOamVccvTrNextPwSegmentEntry belongs to.  The third index element
         identifies an OAM trace route test run.  The fourth, fifth and sixth
         index elements select a single OAM 'vccvTraceRoute' reply."
         INDEX {
              tnSysSwitchId,
--            tnOamTrCtlOwnerIndex,
            tnOamTrCtlTestIndex,
            tnOamTrResultsTestRunIndex,
            tnOamTrProbeHistoryIndex,
            tnOamTrProbeHistoryHopIndex,
            tnOamTrProbeHistoryProbeIndex
           }
    ::= { tnOamVccvTrNextPwSegmentTable 1 }

 TnOamVccvTrNextPwSegmentEntry ::=
    SEQUENCE {
        tnOamVccvTrNextPwID            TmnxVcIdOrNone,
        tnOamVccvTrNextPwType          SdpBindVcType,
        tnOamVccvTrNextSenderAddrType  InetAddressType,
        tnOamVccvTrNextSenderAddr      InetAddress,
        tnOamVccvTrNextRemoteAddrType  InetAddressType,
        tnOamVccvTrNextRemoteAddr      InetAddress,
        tnOamVccvTrNextSaiiGlobalId    TmnxPwGlobalIdOrZero,
        tnOamVccvTrNextSaiiPrefix      Unsigned32,
        tnOamVccvTrNextSaiiAcId        Unsigned32,
        tnOamVccvTrNextTaiiGlobalId    TmnxPwGlobalIdOrZero,
        tnOamVccvTrNextTaiiPrefix      Unsigned32,
        tnOamVccvTrNextTaiiAcId        Unsigned32,
        tnOamVccvTrNextTpAgi           OCTET STRING,
        tnOamVccvTrNextTpSaiiGlobalId  TmnxMplsTpGlobalID,
        tnOamVccvTrNextTpSaiiNodeId    TmnxMplsTpNodeID,
        tnOamVccvTrNextTpSaiiAcId      Unsigned32,
        tnOamVccvTrNextTpTaiiGlobalId  TmnxMplsTpGlobalID,
        tnOamVccvTrNextTpTaiiNodeId    TmnxMplsTpNodeID,
        tnOamVccvTrNextTpTaiiAcId      Unsigned32
    }

tnOamVccvTrNextPwID OBJECT-TYPE
    SYNTAX      TmnxVcIdOrNone
    MAX-ACCESS  read-only
    STATUS      current
    DESCRIPTION
        "The value of tnOamVccvTrNextPwID indicates the next-hop pseudo-wire
         in the trace route operation for a specific 'vccvTraceRoute' probe
         reply. A value of '0' indicates that there are no further next-hops for
         a specific trace route operation."
    ::= { tnOamVccvTrNextPwSegmentEntry 1 }

tnOamVccvTrNextPwType    OBJECT-TYPE
    SYNTAX      SdpBindVcType
    MAX-ACCESS  read-only
    STATUS      current
    DESCRIPTION
        "The value of tnOamVccvTrNextPwType indicates the next-hop pseudo-wire
         type in the trace route operation for a specific 'vccvTraceRoute' probe
         reply."
    ::= { tnOamVccvTrNextPwSegmentEntry 2 }

tnOamVccvTrNextSenderAddrType     OBJECT-TYPE
    SYNTAX      InetAddressType
    MAX-ACCESS  read-only
    STATUS      current
    DESCRIPTION
        "The value of tnOamVccvTrNextSenderAddrType indicates the next-hop
         sender IP address type in the trace route operation for a specific
         'vccvTraceRoute' probe reply."
    ::= { tnOamVccvTrNextPwSegmentEntry 3 }

tnOamVccvTrNextSenderAddr       OBJECT-TYPE
    SYNTAX      InetAddress   (SIZE(0|4|16))
    MAX-ACCESS  read-only
    STATUS      current
    DESCRIPTION
        "The value of tnOamVccvTrNextSenderAddr indicates the next-hop sender
         IP address in the trace route oepration for a specific 'vccvTraceRoute'
         probe reply."
    ::= { tnOamVccvTrNextPwSegmentEntry 4 }

tnOamVccvTrNextRemoteAddrType   OBJECT-TYPE
    SYNTAX      InetAddressType
    MAX-ACCESS  read-only
    STATUS      current
    DESCRIPTION
        "The value of tnOamVccvTrNextRemoteAddrType indicates the next-hop
         remote IP address type in the trace route operation for a specific
         'vccvTraceRoute' probe reply."
    ::= { tnOamVccvTrNextPwSegmentEntry 5 }

tnOamVccvTrNextRemoteAddr       OBJECT-TYPE
    SYNTAX      InetAddress   (SIZE(0|4|16))
    MAX-ACCESS  read-only
    STATUS      current
    DESCRIPTION
        "The value of tnOamVccvTrNextRemoteAddr indicates the next-hop
         remote IP address in the trace route operation for a specific
         'vccvTraceRoute' probe reply."
    ::= { tnOamVccvTrNextPwSegmentEntry 6 }

tnOamVccvTrNextSaiiGlobalId   OBJECT-TYPE
    SYNTAX         TmnxPwGlobalIdOrZero
    MAX-ACCESS     read-only
    STATUS         current
    DESCRIPTION
        "The value of tnOamVccvTrNextSaiiGlobalId indicates the global
         identifier of the Source Attachment Individual Identifier (SAII)
         of a specific 'vccvTraceRoute' probe reply.

         A non-zero value is returned if a FEC 129 AII Type 2 pseudowire was
         probed.  Otherwise, zero is returned."
    REFERENCE
        "RFC 5003 Section 3.2"
    ::= { tnOamVccvTrNextPwSegmentEntry 7 }

tnOamVccvTrNextSaiiPrefix     OBJECT-TYPE
    SYNTAX         Unsigned32
    MAX-ACCESS     read-only
    STATUS         current
    DESCRIPTION
        "The value of tnOamVccvTrNextSaiiPrefix indicates the prefix of the
         Source Attachment Individual Identifier (SAII) of a specific
         'vccvTraceRoute' probe reply.

         A non-zero value is returned if a FEC 129 AII Type 2 pseudowire was
         probed.  Otherwise, zero is returned."
    REFERENCE
        "RFC 5003 Section 3.2"
    ::= { tnOamVccvTrNextPwSegmentEntry 8 }

tnOamVccvTrNextSaiiAcId       OBJECT-TYPE
    SYNTAX         Unsigned32
    MAX-ACCESS     read-only
    STATUS         current
    DESCRIPTION
        "The value of tnOamVccvTrNextSaiiAcId indicates the attachment
         circuit identifier of the Source Attachment Individual Identifier
         (SAII) of a specific 'vccvTraceRoute' probe reply.

         A non-zero value is returned if a FEC 129 AII Type 2 pseudowire was
         probed.  Otherwise, zero is returned."
    REFERENCE
        "RFC 5003 Section 3.2"
    ::= { tnOamVccvTrNextPwSegmentEntry 9 }

tnOamVccvTrNextTaiiGlobalId   OBJECT-TYPE
    SYNTAX         TmnxPwGlobalIdOrZero
    MAX-ACCESS     read-only
    STATUS         current
    DESCRIPTION
        "The value of tnOamVccvTrNextTaiiGlobalId indicates the global
         identifier of the Target Attachment Individual Identifier (TAII)
         of a specific 'vccvTraceRoute' probe reply.

         A non-zero value is returned if a FEC 129 AII Type 2 pseudowire was
         probed.  Otherwise, zero is returned."
    REFERENCE
        "RFC 5003 Section 3.2"
    ::= { tnOamVccvTrNextPwSegmentEntry 10 }

tnOamVccvTrNextTaiiPrefix     OBJECT-TYPE
    SYNTAX         Unsigned32
    MAX-ACCESS     read-only
    STATUS         current
    DESCRIPTION
        "The value of tnOamVccvTrNextTaiiPrefix indicates the prefix of the
         Target Attachment Individual Identifier (TAII) of a specific
         'vccvTraceRoute' probe reply.

         A non-zero value is returned if a FEC 129 AII Type 2 pseudowire was
         probed.  Otherwise, zero is returned."
    REFERENCE
        "RFC 5003 Section 3.2"
    ::= { tnOamVccvTrNextPwSegmentEntry 11 }

tnOamVccvTrNextTaiiAcId       OBJECT-TYPE
    SYNTAX         Unsigned32
    MAX-ACCESS     read-only
    STATUS         current
    DESCRIPTION
        "The value of tnOamVccvTrNextTaiiAcId indicates the attachment
         circuit identifier of the Target Attachment Individual Identifier
         (TAII) of a specific 'vccvTraceRoute' probe reply.

         A non-zero value is returned if a FEC 129 AII Type 2 pseudowire was
         probed.  Otherwise, zero is returned."
    REFERENCE
        "RFC 5003 Section 3.2"
    ::= { tnOamVccvTrNextPwSegmentEntry 12 }

tnOamVccvTrNextTpAgi           OBJECT-TYPE
    SYNTAX         OCTET STRING (SIZE (8))
    MAX-ACCESS     read-only
    STATUS         current
    DESCRIPTION
        "The value of tnOamVccvTrNextTpAgi indicates the Service Identifier
         field of the RFC 6426 Static Pseudowire Sub-TLV of the reply PDU.

         If a pseudowire other than an MPLS-TP pseudowire was probed, the
         all-zeros value is returned."
    REFERENCE
        "RFC 6426, 'MPLS On-Demand Connectivity Verification and Route Tracing',
         section 2.3.2, 'Static Pseudowire Sub-TLV'."
    ::= { tnOamVccvTrNextPwSegmentEntry 13 }

tnOamVccvTrNextTpSaiiGlobalId  OBJECT-TYPE
    SYNTAX         TmnxMplsTpGlobalID
    MAX-ACCESS     read-only
    STATUS         current
    DESCRIPTION
        "The value of tnOamVccvTrNextTpSaiiGlobalId indicates the Source
         Global ID field of the RFC 6426 Static Pseudowire Sub-TLV of the reply
         PDU.

         If a pseudowire other than an MPLS-TP pseudowire was probed, zero is
         returned."
    REFERENCE
        "RFC 6426, 'MPLS On-Demand Connectivity Verification and Route Tracing',
         section 2.3.2, 'Static Pseudowire Sub-TLV'."
    ::= { tnOamVccvTrNextPwSegmentEntry 14 }

tnOamVccvTrNextTpSaiiNodeId    OBJECT-TYPE
    SYNTAX         TmnxMplsTpNodeID
    MAX-ACCESS     read-only
    STATUS         current
    DESCRIPTION
        "The value of tnOamVccvTrNextTpSaiiNodeId indicates the Source
         Node ID field of the RFC 6426 Static Pseudowire Sub-TLV of the reply
         PDU.

         If a pseudowire other than an MPLS-TP pseudowire was probed, zero is
         returned."
    REFERENCE
        "RFC 6426, 'MPLS On-Demand Connectivity Verification and Route Tracing',
         section 2.3.2, 'Static Pseudowire Sub-TLV'."
    ::= { tnOamVccvTrNextPwSegmentEntry 15 }

tnOamVccvTrNextTpSaiiAcId      OBJECT-TYPE
    SYNTAX         Unsigned32
    MAX-ACCESS     read-only
    STATUS         current
    DESCRIPTION
        "The value of tnOamVccvTrNextTpSaiiAcId indicates the Source
         Attachment Circuit ID field of the RFC 6426 Static Pseudowire Sub-TLV
         of the reply PDU.

         If a pseudowire other than an MPLS-TP pseudowire was probed, zero is
         returned."
    REFERENCE
        "RFC 6426, 'MPLS On-Demand Connectivity Verification and Route Tracing',
         section 2.3.2, 'Static Pseudowire Sub-TLV'."
    ::= { tnOamVccvTrNextPwSegmentEntry 16 }

tnOamVccvTrNextTpTaiiGlobalId  OBJECT-TYPE
    SYNTAX         TmnxMplsTpGlobalID
    MAX-ACCESS     read-only
    STATUS         current
    DESCRIPTION
        "The value of tnOamVccvTrNextTpTaiiGlobalId indicates the Destination
         Global ID field of the RFC 6426 Static Pseudowire Sub-TLV of the reply
         PDU.

         If a pseudowire other than an MPLS-TP pseudowire was probed, zero is
         returned."
    REFERENCE
        "RFC 6426, 'MPLS On-Demand Connectivity Verification and Route Tracing',
         section 2.3.2, 'Static Pseudowire Sub-TLV'."
    ::= { tnOamVccvTrNextPwSegmentEntry 17 }

tnOamVccvTrNextTpTaiiNodeId    OBJECT-TYPE
    SYNTAX         TmnxMplsTpNodeID
    MAX-ACCESS     read-only
    STATUS         current
    DESCRIPTION
        "The value of tnOamVccvTrNextTpTaiiNodeId indicates the Destination
         Node ID field of the RFC 6426 Static Pseudowire Sub-TLV of the reply
         PDU.

         If a pseudowire other than an MPLS-TP pseudowire was probed, zero is
         returned."
    REFERENCE
        "RFC 6426, 'MPLS On-Demand Connectivity Verification and Route Tracing',
         section 2.3.2, 'Static Pseudowire Sub-TLV'."
    ::= { tnOamVccvTrNextPwSegmentEntry 18 }

tnOamVccvTrNextTpTaiiAcId      OBJECT-TYPE
    SYNTAX         Unsigned32
    MAX-ACCESS     read-only
    STATUS         current
    DESCRIPTION
        "The value of tnOamVccvTrNextTpTaiiAcId indicates the Destination
         Attachment Circuit ID field of the RFC 6426 Static Pseudowire Sub-TLV
         of the reply PDU.

         If a pseudowire other than an MPLS-TP pseudowire was probed, zero is
         returned."
    REFERENCE
        "RFC 6426, 'MPLS On-Demand Connectivity Verification and Route Tracing',
         section 2.3.2, 'Static Pseudowire Sub-TLV'."
    ::= { tnOamVccvTrNextPwSegmentEntry 19 }
--
--  Nokia SROS series OAM P2MP LSP Trace Route Control Table
--
--
--  Sparsely dependent extension of the tnOamTrCtlTable.
--
--  The same indexes are used for both the base table, tnOamTrCtlTable,
--  and the sparse dependent table, tnOamP2mpLspTrCtlTable.
--
--  This in effect extends the tnOamTrCtlTable with additional columns.
--  Rows are created in the tnOamP2mpLspTrCtlTable only for those entries
--  in the tnOamTrCtlTable where tnOamTrCtlTestMode has a value of
--  'p2mpLspTrace'.
--
--  Deletion of a row in the tnOamTrCtlTable results in the
--  same fate for the row in the tnOamP2mpLspTrCtlTable.
--

-- tnOamP2mpLspTrCtlTable     OBJECT-TYPE
--     SYNTAX      SEQUENCE OF TnOamP2mpLspTrCtlEntry
--     MAX-ACCESS  not-accessible
--     STATUS      current
--     DESCRIPTION
--         "Defines the Nokia SROS OAM P2MP LSP Trace Control Table
--          for providing, via SNMP, the capability of performing Nokia
--          SROS OAM 'p2mpLspTrace' test operations for a single leaf
--          egress node of an P2MP LSP.  The results of these tests are
--          stored in the tnOamTrResultsTable and the
--          tnOamTrProbeHistoryTable."
--    ::= { tnOamTraceRouteObjs 28 }
--
-- tnOamP2mpLspTrCtlEntry OBJECT-TYPE
--     SYNTAX      TnOamP2mpLspTrCtlEntry
--     MAX-ACCESS  not-accessible
--     STATUS      current
--     DESCRIPTION
--         "Defines an entry in the tnOamP2mpLspTrCtlTable.  The first index
--          element, tnOamTrCtlOwnerIndex, is of type SnmpAdminString,
--          a textual convention that allows for use of the SNMPv3
--          View-Based Access Control Model (RFC 2575 [11], VACM)
--          and allows a management application to identify its entries.
--          The second index, tnOamTrCtlTestIndex, enables the same
--          management application to have multiple outstanding requests."
--     INDEX {
--            tnOamTrCtlOwnerIndex,
--            tnOamTrCtlTestIndex
--           }
--     ::= { tnOamP2mpLspTrCtlTable 1 }
--
--  TnOamP2mpLspTrCtlEntry ::=
--     SEQUENCE {
--        tnOamP2mpLspTrCtlLspName           TLNamedItemOrEmpty,
--        tnOamP2mpLspTrCtlInstName          TNamedItemOrEmpty,
--        tnOamP2mpLspTrCtlLeafIpAddr        InetAddress,
--        tnOamP2mpLspTrCtlLeafIpAddrType    InetAddressType
--     }
--
-- tnOamP2mpLspTrCtlLspName        OBJECT-TYPE
--     SYNTAX      TLNamedItemOrEmpty
--     MAX-ACCESS  read-write
--     STATUS      current
--     DESCRIPTION
--         "Administrative name of the target P2MP Labeled Switch Path (LSP)
--          for this OAM P2MP LSP Trace test. This parameter is mandatory."
--     DEFVAL { ''H }  -- -- the empty string
--     ::= { tnOamP2mpLspTrCtlEntry 1 }
--
-- tnOamP2mpLspTrCtlInstName       OBJECT-TYPE
--     SYNTAX      TNamedItemOrEmpty
--     MAX-ACCESS  read-write
--     STATUS      current
--     DESCRIPTION
--         "This parameter identifies an instance of a P2MP LSP, either a primary
--          or secondary instance of a P2MP LSP Tree."
--     DEFVAL { ''H }
--     ::= { tnOamP2mpLspTrCtlEntry 2 }
--
-- tnOamP2mpLspTrCtlLeafIpAddr     OBJECT-TYPE
--     SYNTAX      InetAddress (SIZE (0|4|16))
--     MAX-ACCESS  read-write
--     STATUS      current
--     DESCRIPTION
--         "The value of tnOamP2mpLspTrCtlLeafIpAddr specifies the Internet
--          address of the egress leaf node of a P2MP LSP Tree.
--          This parameter is mandatory."
--     DEFVAL { ''H }
--     ::= { tnOamP2mpLspTrCtlEntry 3 }
--
-- tnOamP2mpLspTrCtlLeafIpAddrType    OBJECT-TYPE
--     SYNTAX      InetAddressType
--     MAX-ACCESS  read-write
--     STATUS      current
--     DESCRIPTION
--         "The value of tnOamP2mpLspTrCtlLeafIpAddrType specifies the type
--          of Internet address stored in tnOamP2mpLspTrCtlLeafIpAddr."
--     DEFVAL { unknown }
--     ::= { tnOamP2mpLspTrCtlEntry 4 }

--
-- Nokia SROS series OAM P2mp Lsp Trace Route Downstream L2 Mapping Table
--

-- tnOamP2mpLspTrMapTable OBJECT-TYPE
--     SYNTAX      SEQUENCE OF TnOamP2mpLspTrMapEntry
--     MAX-ACCESS  not-accessible
--     STATUS      current
--     DESCRIPTION
--         "Defines a table for storing the results of an OAM 'p2mpLspTrace'
--          probe operation when a Downstream Mapping TLV was returned.  Each row
--          represents a single label map within the returned downstream mapping
--          TLV.
--
--          An entry in this table is created when the result of an OAM
--          'p2mpLspTrace' probe is determined.
--
--          An entry is removed from this table when its corresponding
--          tnOamTrCtlEntry is deleted."
--    ::= { tnOamTraceRouteObjs 29 }

-- tnOamP2mpLspTrMapEntry OBJECT-TYPE
--     SYNTAX      TnOamP2mpLspTrMapEntry
--     MAX-ACCESS  not-accessible
--     STATUS      current
--     DESCRIPTION
--         "Defines an entry in the tnOamP2mpLspTrMapTable.  The first two
--          index elements identify the tnOamTrCtlEntry that a
--          tnOamP2mpLspTrMapEntry belongs to.  The third index element
--          identifies an OAM trace route test run.  The fourth index element
--          selects the group of responses associated with a specific
--          probe attempt. The fifth and sixth indexes select the hop and
--          the probe at that hop for a particular Nokia SROS OAM
--          Trace Route operation. The seventh index selects a single downstream
--          L2 map entry within the specific probe reply."
--     INDEX {
--             tnOamTrCtlOwnerIndex,
--             tnOamTrCtlTestIndex,
--             tnOamTrResultsTestRunIndex,
--             tnOamTrProbeHistoryIndex,
--             tnOamTrProbeHistoryHopIndex,
--             tnOamTrProbeHistoryProbeIndex,
--             tnOamP2mpLspTrMapIndex
--            }
--     ::= { tnOamP2mpLspTrMapTable 1 }

--  TnOamP2mpLspTrMapEntry ::=
--     SEQUENCE {
--        tnOamP2mpLspTrMapIndex         Unsigned32,
--        tnOamP2mpLspTrMapDSIPv4Addr    IpAddress,
--        tnOamP2mpLspTrMapAddrType      TmnxOamAddressType,
--        tnOamP2mpLspTrMapDSIfAddr      Unsigned32,
--        tnOamP2mpLspTrMapMTU           Unsigned32,
--        tnOamP2mpLspTrMapP2mpBranch    TruthValue,
--        tnOamP2mpLspTrMapP2mpBud       TruthValue
--     }

-- tnOamP2mpLspTrMapIndex OBJECT-TYPE
--     SYNTAX      Unsigned32 (1..4294967295)
--     MAX-ACCESS  not-accessible
--     STATUS      current
--     DESCRIPTION
--         "An entry in this table is created when the result of a OAM
--          'lspTraceRoute' probe is determined.  The initial 2
--          instance identifier index values identify the tnOamTrCtlEntry
--          that a OAM probe result (tnOamTrProbeHistoryEntry) belongs
--          to.  The tnOamTrProbeHistoryIndex identifies a group of replies
--          received in response to a specific probe transmission. The fourth
--          and fifth indexes select the hop and the probe at that hop for a
--          particular Nokia SROS OAM Trace Route operation.

--          The tnOamP2mpLspTrMapIndex selects a single L2 mapping entry
--          within a specific 'lspTraceRoute' probe reply.

--          The agent starts assigning tnOamP2mpLspTrMapIndex values at 1."
--     ::= { tnOamP2mpLspTrMapEntry 1 }

-- tnOamP2mpLspTrMapDSIPv4Addr    OBJECT-TYPE
--     SYNTAX      IpAddress
--     MAX-ACCESS  read-only
--     STATUS      current
--     DESCRIPTION
--         "The value of tnOamP2mpLspTrMapDSIPv4Addr indicates the IPv4 address
--          of the downstream LSR that this entry in the tnOamP2mpLspTrMapTable
--          describes.  If the interface to the downstream LSR is numbered,
--          then the tnOamP2mpLspTrMapDSIPv4Addr can either be the downstream
--          LSR's Router ID or the interface address of the downstream LSR.

--          If the interface to the downstream LSR is unnumbered, the value
--          of tnOamP2mpLspTrMapDSIPv4Addr indicates the downstream LSR's Router
--          ID."
--     ::= { tnOamP2mpLspTrMapEntry 2 }

-- tnOamP2mpLspTrMapAddrType        OBJECT-TYPE
--     SYNTAX      TmnxOamAddressType
--     MAX-ACCESS  read-only
--     STATUS      current
--     DESCRIPTION
--         "The value of tnOamP2mpLspTrMapAddrType indicates the type of
--          downstream interface address specified by tnOamP2mpLspTrMapDSIfAddr.
--          The only valid values for tnOamP2mpLspTrMapAddrType are
--          'ipv4Address', 'ipv4Unnumbered', 'ipv6Address' and 'ipv6Unnumbered'."
--     ::= { tnOamP2mpLspTrMapEntry 3 }

-- tnOamP2mpLspTrMapDSIfAddr        OBJECT-TYPE
--     SYNTAX      Unsigned32
--     MAX-ACCESS  read-only
--     STATUS      current
--     DESCRIPTION
--         "When tnOamP2mpLspTrMapAddrType has a value of 'ipv4Address'
--          tnOamP2mpLspTrMapDSIfAddr indicates the downstream LSR's
--          interface address.  When tnOamP2mpLspTrMapAddrType has a value
--          of 'unnumbered', tnOamP2mpLspTrMapDSIfAddr indicates the index
--          assigned by the upstream LSR to the interface."
--     ::= { tnOamP2mpLspTrMapEntry 4 }

-- tnOamP2mpLspTrMapMTU     OBJECT-TYPE
--     SYNTAX      Unsigned32 (0..65535)
--     MAX-ACCESS  read-only
--     STATUS      current
--     DESCRIPTION
--         "The value of tnOamP2mpLspTrMapMTU indicates the largest MPLS frame
--          (including the label stack) that fits on the interface to the
--          downstream LSR."
--     ::= { tnOamP2mpLspTrMapEntry 5 }

-- tnOamP2mpLspTrMapP2mpBranch       OBJECT-TYPE
--     SYNTAX      TruthValue
--     MAX-ACCESS  read-only
--     STATUS      current
--     DESCRIPTION
--         "When the value of tnOamP2mpLspTrMapP2mpBranch is 'true', the
--          'p2mpLspTrace' response indicates that the responding router
--          is a branch node of the P2MP LSP tree."
--     ::= { tnOamP2mpLspTrMapEntry 6 }

-- tnOamP2mpLspTrMapP2mpBud       OBJECT-TYPE
--     SYNTAX      TruthValue
--     MAX-ACCESS  read-only
--     STATUS      current
--     DESCRIPTION
--         "When the value of tnOamP2mpLspTrMapP2mpBud is 'true', the
--          'p2mpLspTrace' response indicates that the responding router
--          is a bud node of the P2MP LSP tree."
--     ::= { tnOamP2mpLspTrMapEntry 7 }

--
-- Nokia SROS series OAM P2mp Lsp Trace Route Downstream Label Mapping
-- Table
--
--
-- tnOamP2mpLspTrDSLabelTable OBJECT-TYPE
--     SYNTAX      SEQUENCE OF TnOamP2mpLspTrDSLabelEntry
--     MAX-ACCESS  not-accessible
--     STATUS      current
--     DESCRIPTION
--         "Defines a table for storing the results of an OAM 'p2mpLspTrace'
--          probe operation when a Downstream Mapping TLV was
--          returned.  Each row represents a single downstream label within a
--          returned downstream L2 mapping TLV.
--
--          An entry in this table is created when the result of an OAM
--          'p2mpLspTrace' probe is determined.
--          An entry is removed from this table when its corresponding
--          tnOamTrCtlEntry is deleted."
--    ::= { tnOamTraceRouteObjs 30 }

-- tnOamP2mpLspTrDSLabelEntry OBJECT-TYPE
--     SYNTAX      TnOamP2mpLspTrDSLabelEntry
--     MAX-ACCESS  not-accessible
--     STATUS      current
--     DESCRIPTION
--         "Defines an entry in the tnOamP2mpLspTrDSLabelTable.  The first
--          two index elements identify the tnOamTrCtlEntry that a
--          tnOamLspTrMapEntry belongs to.  The third index element
--          identifies a OAM trace route test run. The fourth index element
--          selects the group of responses associated with a specific
--          probe attempt. The fifth and sixth indexes select the hop and
--          the probe at that hop for a particular Nokia SROS OAM
--          Trace Route operation. The seventh index selects a single downstream
--          L2 map entry within the specific probe reply.  The eigth index
--          selects seccessive downstream L2 label entries contained in a
--          specific probe reply."
--     INDEX {
--             tnOamTrCtlOwnerIndex,
--             tnOamTrCtlTestIndex,
--             tnOamTrResultsTestRunIndex,
--             tnOamTrProbeHistoryIndex,
--             tnOamTrProbeHistoryHopIndex,
--             tnOamTrProbeHistoryProbeIndex,
--             tnOamLspTrMapIndex,
--             tnOamP2mpLspTrDSLabelIndex
--            }
--     ::= { tnOamP2mpLspTrDSLabelTable 1 }

--  TnOamP2mpLspTrDSLabelEntry ::=
--     SEQUENCE {
--        tnOamP2mpLspTrDSLabelIndex        Unsigned32,
--        tnOamP2mpLspTrDSLabelLabel        MplsLabel,
--        tnOamP2mpLspTrDSLabelProtocol     TmnxOamSignalProtocol
--     }

-- tnOamP2mpLspTrDSLabelIndex OBJECT-TYPE
--  NOTE: The UCD snmpget utility program does not parse this correctly
--    SYNTAX      Unsigned32 (1..'ffffffff'h)
--     SYNTAX      Unsigned32 (1..4294967295)
--     MAX-ACCESS  not-accessible
--     STATUS      current
--     DESCRIPTION
--         "The tnOamP2mpLspTrDSLabelIndex selects a single downstream L2 label
--          entry within a specific L2 mapping entry reply.

--          The agent starts assigning tnOamP2mpLspTrDSLabelIndex values at 1."
--     ::= { tnOamP2mpLspTrDSLabelEntry 1 }

-- tnOamP2mpLspTrDSLabelLabel       OBJECT-TYPE
--     SYNTAX      MplsLabel
--     MAX-ACCESS  read-only
--     STATUS      current
--     DESCRIPTION
--         "The value of tnOamP2mpLspTrDSLabelLabel is the label used by the
--          downstream router specified by this downstream L2 label entry."
--     ::= { tnOamP2mpLspTrDSLabelEntry 2 }

-- tnOamP2mpLspTrDSLabelProtocol    OBJECT-TYPE
--     SYNTAX      TmnxOamSignalProtocol
--     MAX-ACCESS  read-only
--     STATUS      current
--     DESCRIPTION
--         "The value of tnOamP2mpLspTrDSLabelProtocol is the signaling protocol
--          used by the router for the label specified by this downstream
--          L2 label entry."
--     ::= { tnOamP2mpLspTrDSLabelEntry 3 }

--
--  Nokia 7x50 SR series OAM GTP Ping Control Table
--
--  Sparse Dependent Extension of the tmnxOamPingCtlTable.
--
--  The same indexes are used for both the base table, tmnxOamPingCtlTable,
--  and the sparse dependent table, tmnxOamMobGtpPingTable.
--
--  This in effect extends the tmnxOamPingCtlTable with additional columns.
--  Rows are created in the tmnxOamMobGtpPingTable only for those entries
--  in the tmnxOamPingCtlTable where tmnxOamPingCtlTestMode has a value of
--  'mobGtpPing'.
--
--  Deletion of a row in the tmnxOamPingCtlTable results in the
--  same fate for the row in the tmnxOamPingCtlTable.
--
-- tmnxOamMobGtpPingCtlTable     OBJECT-TYPE
--     SYNTAX      SEQUENCE OF TmnxOamMobGtpPingCtlEntry
--     MAX-ACCESS  not-accessible
--     STATUS      current
--     DESCRIPTION
--         "Defines the Nokia 7x50 SR OAM VPRN Ping Control Table for providing,
--          via SNMP, the capability of performing Nokia 7x50 SR OAM 'mobGtpPing'
--          test operations.
--
--          The results of these tests are stored in the tmnxOamPingResultsTable
--          and the tmnxOamTrProbeHistoryTable.  There will be no entries for
--          these test in the tmnxOamPingHistoryTable."
--    ::= { tmnxOamMobGatewayObjs 1 }
--
-- tmnxOamMobGtpPingCtlEntry OBJECT-TYPE
--     SYNTAX      TmnxOamMobGtpPingCtlEntry
--     MAX-ACCESS  not-accessible
--     STATUS      current
--     DESCRIPTION
--         "Defines an entry in the tmnxOamMobGtpPingCtlTable.  The first index
--          element, tmnxOamPingCtlOwnerIndex, is of type SnmpAdminString,
--          a textual convention that allows for use of the SNMPv3
--          View-Based Access Control Model (RFC 2575 [11], VACM)
--          and allows a management application to identify its entries.
--          The second index, tmnxOamPingCtlTestIndex, enables the same
--          management application to have multiple outstanding requests."
--     INDEX {
--              tmnxOamPingCtlOwnerIndex,
--              tmnxOamPingCtlTestIndex
--           }
--     ::= { tmnxOamMobGtpPingCtlTable 1 }
--
-- TmnxOamMobGtpPingCtlEntry ::=
--     SEQUENCE {
--         tmnxOamMobGtpPingRefPointType         INTEGER,
--         tmnxOamMobGtpPingVRtrId               TmnxVRtrID,
--         tmnxOamMobGtpPingPort                 InetPortNumber,
--         tmnxOamMobGtpPingGateway              TmnxMobGwId
--     }
--
-- tmnxOamMobGtpPingRefPointType     OBJECT-TYPE
--     SYNTAX       INTEGER {
--                           s11 (1),
--                           s5c (2),
--                           s1u (3),
--                           s5u (4),
--                           gnc (5),
--                           s8c (6),
--                           s8u (7),
--                           gpc (8)
--                          }
--     MAX-ACCESS  read-create
--     STATUS      current
--     DESCRIPTION
--         "The value of tmnxOamMobGtpPingRefPointType specifies the reference
--          point type.
--
--          This object is required."
--     ::= { tmnxOamMobGtpPingCtlEntry 1 }
--
-- tmnxOamMobGtpPingVRtrId      OBJECT-TYPE
--     SYNTAX      TmnxVRtrID
--     MAX-ACCESS  read-create
--     STATUS      current
--     DESCRIPTION
--         "The value of tmnxOamMobGtpPingVRtrId specifies the virtual router.
--
--          This object is required."
--     ::= { tmnxOamMobGtpPingCtlEntry 2 }
--
-- tmnxOamMobGtpPingPort     OBJECT-TYPE
--     SYNTAX      InetPortNumber
--     MAX-ACCESS  read-create
--     STATUS      current
--     DESCRIPTION
--         "The value of tmnxOamMobGtpPingPort specifies the port number of the
--          destination.
--
--          This object is required."
--     ::= { tmnxOamMobGtpPingCtlEntry 3 }
--
-- tmnxOamMobGtpPingGateway     OBJECT-TYPE
--     SYNTAX      TmnxMobGwId
--     MAX-ACCESS  read-create
--     STATUS      current
--     DESCRIPTION
--         "The value of tmnxOamMobGtpPingGateway specifies the mobile gateway id.
--
--          This object is required."
--     ::= { tmnxOamMobGtpPingCtlEntry 4 }
--
--  Nokia SROS series OAM Ethernet Connectivity Fault Management Trace
--  Route Control Table
--

-- tnOamEthCfmTrCtlTable OBJECT-TYPE
--     SYNTAX      SEQUENCE OF TnOamEthCfmTrCtlEntry
--     MAX-ACCESS  not-accessible
--     STATUS      current
--     DESCRIPTION
--         "tnOamEthCfmTrCtlTable contains Ethernet CFM-specific configuration
--          information for 'ethCfmLinkTrace' tests.
--
--          This table extends the tnOamTrCtlTable.  A row is automatically
--          created in this table when a row in tnOamTrCtlTable has
--          tnOamTrCtlTestMode set to 'ethCfmLinkTrace'.  Deleting a row in
--          tnOamTrCtlTable automatically deletes the row (if any) with the same
--          index values in tnOamEthCfmTrCtlTable.
--
--          Test results are stored in tnOamTrResultsTable,
--          tnOamTrProbeHistoryTable, tnOamTrHopsTable, and
--          tnOamEthCfmTrPrHistTable."
--     ::= { tnOamTraceRouteObjs 31 }
--
-- tnOamEthCfmTrCtlEntry OBJECT-TYPE
--     SYNTAX      TnOamEthCfmTrCtlEntry
--     MAX-ACCESS  not-accessible
--     STATUS      current
--     DESCRIPTION
--         "tnOamEthCfmTrCtlEntry defines an entry in the
--          tnOamEthCfmTrCtlTable.  Each index is an object in
--          tnOamTrCtlTable."
--     INDEX {
--              tnOamTrCtlOwnerIndex,
--              tnOamTrCtlTestIndex
--           }
--     ::= { tnOamEthCfmTrCtlTable 1 }
--
-- TnOamEthCfmTrCtlEntry ::= SEQUENCE {
--           tnOamEthCfmTrCtlTgtMacAddr    MacAddress,
--           tnOamEthCfmTrCtlSrcMdIndex    Unsigned32,
--           tnOamEthCfmTrCtlSrcMaIndex    Unsigned32,
--           tnOamEthCfmTrCtlSrcMepId      Dot1agCfmMepIdOrZero
--     }
--
-- tnOamEthCfmTrCtlTgtMacAddr OBJECT-TYPE
--     SYNTAX      MacAddress
--     MAX-ACCESS  read-create
--     STATUS      current
--     DESCRIPTION
--        "The value of tnOamEthCfmTrCtlTgtMacAddr specifies the target MAC
--         address for the test."
--     DEFVAL { '000000000000'H }  -- -- 00:00:00:00:00:00
--     ::= { tnOamEthCfmTrCtlEntry 1 }
--
-- tnOamEthCfmTrCtlSrcMdIndex OBJECT-TYPE
--     SYNTAX      Unsigned32
--     MAX-ACCESS  read-create
--     STATUS      current
--     DESCRIPTION
--         "The value of tnOamEthCfmTrCtlSrcMdIndex specifies the source CFM
--          maintenance domain index for the test.  Zero is the null CFM
--          maintenance domain index."
--     DEFVAL { 0 }
--     ::= { tnOamEthCfmTrCtlEntry 2 }
--
-- tnOamEthCfmTrCtlSrcMaIndex OBJECT-TYPE
--     SYNTAX      Unsigned32
--     MAX-ACCESS  read-create
--     STATUS      current
--     DESCRIPTION
--         "The value of tnOamEthCfmTrCtlSrcMaIndex specifies the source CFM
--          maintenance association index for the test.  Zero is the null CFM
--          maintenance association index."
--     DEFVAL { 0 }
--     ::= { tnOamEthCfmTrCtlEntry 3 }
--
-- tnOamEthCfmTrCtlSrcMepId OBJECT-TYPE
--     SYNTAX      Dot1agCfmMepIdOrZero
--     MAX-ACCESS  read-create
--     STATUS      current
--     DESCRIPTION
--         "The value of tnOamEthCfmTrCtlSrcMepId specifies the source
--          Maintenance association End Point Identifier (MEP ID) for the test.
--          Zero is the null MEP ID."
--     DEFVAL { 0 }
--     ::= { tnOamEthCfmTrCtlEntry 4 }

--
-- Nokia SROS series OAM Ethernet Connectivity Fault Management Trace
-- Route Probe History Table
--
-- tnOamEthCfmTrPrHistTable OBJECT-TYPE
--     SYNTAX      SEQUENCE OF TnOamEthCfmTrPrHistEntry
--     MAX-ACCESS  not-accessible
--     STATUS      current
--     DESCRIPTION
--         "tnOamEthCfmTrPrHistTable contains Ethernet CFM-specific probe
--          history for 'ethCfmLinkTrace' tests.

--          This table extends the tnOamTrProbeHistoryTable.  A row is
--          automatically created in this table when a row is created in
--          tnOamTrProbeHistoryTable for a test with tnOamTrCtlTestMode set to
--          'ethCfmLinkTrace'.  Deleting a row in tnOamTrProbeHistoryTable
--          automatically deletes the row (if any) with the same index values in
--          tnOamEthCfmTrPrHistTable."
--     ::= { tnOamTraceRouteObjs 32 }

-- tnOamEthCfmTrPrHistEntry OBJECT-TYPE
--     SYNTAX      TnOamEthCfmTrPrHistEntry
--     MAX-ACCESS  not-accessible
--     STATUS      current
--     DESCRIPTION
--         "Defines an entry in the tnOamEthCfmTrPrHistTable.  The indices are
--          the same as the tnOamTrProbeHistoryTable indices."
--     INDEX {
--             tnOamTrCtlOwnerIndex,
--             tnOamTrCtlTestIndex,
--             tnOamTrResultsTestRunIndex,
--             tnOamTrProbeHistoryIndex,
--             tnOamTrProbeHistoryHopIndex,
--             tnOamTrProbeHistoryProbeIndex
--           }
--     ::= { tnOamEthCfmTrPrHistTable 1 }

--  TnOamEthCfmTrPrHistEntry ::=
--     SEQUENCE {
--        tnOamEthCfmTrPrHistIngressMac  MacAddress,
--        tnOamEthCfmTrPrHistEgressMac   MacAddress,
--        tnOamEthCfmTrPrHistRelayAction INTEGER,
--        tnOamEthCfmTrPrHistForwarded   TruthValue,
--        tnOamEthCfmTrPrHistTerminalMep TruthValue
--       }

-- tnOamEthCfmTrPrHistIngressMac OBJECT-TYPE
--     SYNTAX      MacAddress
--     MAX-ACCESS  read-only
--     STATUS      current
--     DESCRIPTION
--         "The value of tnOamEthCfmTrPrHistIngressMac indicates the ingress MAC
--          address of the probe."
--     ::= { tnOamEthCfmTrPrHistEntry 1 }

-- tnOamEthCfmTrPrHistEgressMac OBJECT-TYPE
--     SYNTAX      MacAddress
--     MAX-ACCESS  read-only
--     STATUS      current
--     DESCRIPTION
--         "The value of tnOamEthCfmTrPrHistEgressMac indicates the egress MAC
--          address of the probe."
--     ::= { tnOamEthCfmTrPrHistEntry 2 }

-- tnOamEthCfmTrPrHistRelayAction OBJECT-TYPE
--     SYNTAX      INTEGER {
--                     unknown    (0),
--                     rlyHit     (1),
--                     rlyFdb     (2),
--                     rlyMpdb    (3)
--                 }
--     MAX-ACCESS  read-only
--     STATUS      current
--     DESCRIPTION
--         "The value of tnOamEthCfmTrPrHistRelayAction indicates the value of
--          the Relay Action field in the Link Trace Reply.  'unknown(0)' is
--          returned when a Link Trace Reply has not arrived, or the Relay Action
--          field in the Link Trace Reply is outside the expected range."
--     ::= { tnOamEthCfmTrPrHistEntry 3 }

-- tnOamEthCfmTrPrHistForwarded OBJECT-TYPE
--     SYNTAX      TruthValue
--     MAX-ACCESS  read-only
--     STATUS      current
--     DESCRIPTION
--         "The value of tnOamEthCfmTrPrHistForwarded indicates if a Link Trace
--          Message was forwarded by the responding Maintenance Point (MP), as
--          returned in the 'FwdYes' flag of the Flags field of the Link Trace
--          Reply."
--     REFERENCE
--         "Modeled on the dot1agCfmLtrForwarded object in IEEE8021-CFM-MIB."
--     ::= { tnOamEthCfmTrPrHistEntry 4 }

-- tnOamEthCfmTrPrHistTerminalMep OBJECT-TYPE
--     SYNTAX      TruthValue
--     MAX-ACCESS  read-only
--     STATUS      current
--     DESCRIPTION
--         "The value of tnOamEthCfmTrPrHistTerminalMep indicates whether the
--          forwarded Link Trace Message reached a MEP enclosing its MA, as
--          returned in the Terminal MEP flag of the Flags field of the Link Trace
--          Reply."
--     REFERENCE
--         "Modeled on the dot1agCfmLtrTerminalMep object in IEEE8021-CFM-MIB."
--     ::= { tnOamEthCfmTrPrHistEntry 5 }

--
-- Objects applicable to both the ping and trace route test modes.
--
--
-- tnOamMplsPduTimeStampFormat OBJECT-TYPE
--     SYNTAX      INTEGER {
--                     rfc4379(0),
--                     unix(1)
--                 }
--     MAX-ACCESS  read-write
--     STATUS      current
--     DESCRIPTION
--         "The value of tnOamMplsPduTimeStampFormat specifies, on a system-wide
--          basis:
--          a) the format of the time stamp to be written into an RFC 4379 MPLS
--             Echo Request PDU, when initiating a ping or trace route test,
--             and
--          b) the format of the time stamp to be written into an RFC 4379 MPLS
--             Echo Reply PDU, when replying to an incoming MPLS Echo Request PDU,
--             and
--          c) the format to use when decoding the time stamps in an incoming MPLS
--             Echo Request or MPLS Echo Reply PDU.
--
--          'rfc4379(0)' specifies the RFC 4379 time stamp format.  The time
--          stamp's 'seconds' field holds the integral number of seconds since
--          1-Jan-1900 00:00:00 UTC.  The time stamp's 'microseconds' field
--          contains a microseconds value in the range 0..999999.  This setting is
--          used to interoperate with network elements which are fully compliant
--          with RFC 4379 (e.g. an SROS system with the same setting, or any other
--          RFC 4379 compliant router).
--
--          'unix(1)' specifies the Unix time stamp format.  The time stamp's
--          'seconds' field holds a 'Unix time', i.e. the integral number of
--          seconds since 1-Jan-1970 00:00:00 UTC.  The time stamp's 'microseconds'
--          field contains a microseconds value in the range 0..999999.  This
--          setting is used to interoperate with network elements which send and
--          expect a 1970-based timestamp in MPLS Echo Request/Reply PDUs (e.g. an
--          SROS system with the same setting, or an SROS system running software
--          earlier than R8.0 R4).
--
--          Prior to SROS Release 8.0 R4, this object was not supported.  The Unix
--          time stamp format was always used.
--
--          This object is applicable for the ldpTreeTrace, lspPing, lspTraceRoute,
--          p2mpLspPing, p2mpLspTrace, vccvPing, and vccvTraceRoute test modes
--          only."
--     REFERENCE "RFC 4379, Feb-2006, Section 3."
--     DEFVAL { unix }
--     ::= { tnOamGeneralObjs 1 }
--
-- OAM/SAA Global Statistics and Limits

-- tmnxOamSysPerfOprLimitTx         OBJECT-TYPE
--     SYNTAX      Gauge32
--     UNITS       "echo request packets per second"
--     MAX-ACCESS  read-only
--     STATUS      current
--     DESCRIPTION
--         "The value of tmnxOamSysPerfOprLimitTx indicates this node's upper bound
--          on the total echo request packet transmission rate.  Echo reply packets
--          are not affected by this limit.
--
--          The upper bound applies to echo request packets sent by the following
--          test types:
--          1.  SDP keep-alive.
--          2.  Static route CPE check.
--          3.  Filter redirect policy ping test.
--          4.  VRRP policy host unreachable ping test.
--          5.  Any OAM or SAA test configured using TIMETRA-OAM-TEST-MIB."
--     ::= { tmnxOamGeneralStats 1 }
--
-- tmnxOamSysPerfCfgLimitTx         OBJECT-TYPE
--     SYNTAX      Gauge32
--     UNITS       "echo request packets per second"
--     MAX-ACCESS  read-only
--     STATUS      current
--     DESCRIPTION
--         "The value of tmnxOamSysPerfCfgLimitTx indicates this node's upper bound
--          on the total configured echo request packet transmission rate for a set
--          of test types.  The upper bound is enforced to avoid echo request
--          packet transmit overload, i.e. to ensure each enabled test can transmit
--          echo request packets at the test's configured rate.  Echo reply packets
--          are not affected by this limit.
--
--          The upper bound applies to echo request packets sent by the following
--          'always on' test types:
--          1.  SDP keep-alive.
--          2.  Static route CPE check.
--          3.  Filter redirect policy ping test.
--          4.  VRRP policy host unreachable ping test.
--          5.  SAA continuous test (see tmnxOamSaaCtlContinuous).
--
--          For example, suppose:
--          a) tmnxOamSysPerfCfgLimitTx has the value 4000 echo request packets per
--             second, and
--          b) several SDP keep-alive sessions are enabled, totalling 1000 echo
--             request packets per second, and
--          c) several SAA continuous tests are enabled, totalling 3000 echo
--             request packets per second.
--          Then, an attempt to enable an additional SAA continuous test would be
--          rejected with a 'resourceUnavailable(13)' error."
--     ::= { tmnxOamGeneralStats 2 }
--
-- tmnxOamSysPerfCfgTotalTx         OBJECT-TYPE
--     SYNTAX      Gauge32
--     UNITS       "echo request packets per second"
--     MAX-ACCESS  read-only
--     STATUS      current
--     DESCRIPTION
--         "The value of tmnxOamSysPerfCfgTotalTx indicates this node's current
--          total configured echo request packet transmission rate, for the set of
--          tests listed in the tmnxOamSysPerfCfgLimitTx DESCRIPTION clause.
--
--          For example, suppose:
--          a) several SDP keep-alive sessions are enabled, totalling 1000 echo
--             request packets per second, and
--          b) several SAA continuous tests are enabled, totalling 2000 echo
--             request packets per second, and
--          c) no other relevant tests are enabled.
--          Then, tmnxOamSysPerfCfgTotalTx will have the value 3000.
--
--          The value of tmnxOamSysPerfCfgTotalTx will not exceed the value of
--          tmnxOamSysPerfCfgLimitTx."
--     ::= { tmnxOamGeneralStats 3 }
--
-- tmnxOamSysPerfLastClearedTime    OBJECT-TYPE
--     SYNTAX      TimeStamp
--     MAX-ACCESS  read-only
--     STATUS      current
--     DESCRIPTION
--         "The value of tmnxOamSysPerfLastClearedTime indicates the sysUpTime when
--          the following statistics were cleared:  tmnxOamSysPerfLocalTestTx,
--          tmnxOamSysPerfRemoteTestRx, and tmnxOamSysPerfReqTypeTable.  If the
--          statistics have not been cleared since the last CPM restart, zero is
--          returned.
--
--          A packet count which is time stamped by this object can be converted to
--          an average packets per second value using, for example,
--            pps = tmnxOamSysPerfLocalTestTx /
--                  [(sysUpTime - tmnxOamSysPerfLastClearedTime)/100]."
--     ::= { tmnxOamGeneralStats 4 }
--
-- tmnxOamSysPerfLocalTestTx        OBJECT-TYPE
--     SYNTAX      Counter32
--     UNITS       "echo request packets"
--     MAX-ACCESS  read-only
--     STATUS      current
--     DESCRIPTION
--         "The value of tmnxOamSysPerfLocalTestTx indicates this node's total
--          number of echo request packets transmitted by locally initiated tests
--          (since the last clear).  The test types are listed in the
--          tmnxOamSysPerfOprLimitTx DESCRIPTION clause."
--     ::= { tmnxOamGeneralStats 5 }
--
-- tmnxOamSysPerfRemoteTestRx       OBJECT-TYPE
--     SYNTAX      Counter32
--     UNITS       "echo request packets"
--     MAX-ACCESS  read-only
--     STATUS      current
--     DESCRIPTION
--         "The value of tmnxOamSysPerfRemoteTestRx indicates this node's total
--          number of echo request packets received from remotely initiated tests
--          (since the last clear)."
--     ::= { tmnxOamGeneralStats 6 }
--
-- tmnxOamSysPerfReqTypeTable       OBJECT-TYPE
--     SYNTAX      SEQUENCE OF TmnxOamSysPerfReqTypeEntry
--     MAX-ACCESS  not-accessible
--     STATUS      current
--     DESCRIPTION
--         "tmnxOamSysPerfReqTypeTable has a row for each relevant OAM echo request
--          packet type.  Each row contains packet counters."
--     ::= { tmnxOamGeneralStats 7 }
--
-- tmnxOamSysPerfReqTypeEntry       OBJECT-TYPE
--     SYNTAX      TmnxOamSysPerfReqTypeEntry
--     MAX-ACCESS  not-accessible
--     STATUS      current
--     DESCRIPTION
--         "Rows in tmnxOamSysPerfReqTypeTable are system-generated at CPM restart.
--          Rows cannot be created or destroyed using SNMP."
--     INDEX { IMPLIED tmnxOamSysPerfReqTypeName }
--     ::= { tmnxOamSysPerfReqTypeTable 1 }
--
-- TmnxOamSysPerfReqTypeEntry ::=
--     SEQUENCE {
--         tmnxOamSysPerfReqTypeName        TNamedItem,
--         tmnxOamSysPerfReqTypeLocalTestTx Counter32,
--         tmnxOamSysPerfReqTypeRemoteTstRx Counter32
--     }
--
-- tmnxOamSysPerfReqTypeName        OBJECT-TYPE
--     SYNTAX      TNamedItem
--     MAX-ACCESS  not-accessible
--     STATUS      current
--     DESCRIPTION
--         "The value of tmnxOamSysPerfReqTypeName specifies the name of an echo
--          request packet type (e.g. 'ICMP').  The name is the index for the row."
--     ::= { tmnxOamSysPerfReqTypeEntry 1 }
--
-- tmnxOamSysPerfReqTypeLocalTestTx OBJECT-TYPE
--     SYNTAX      Counter32
--     UNITS       "echo request packets"
--     MAX-ACCESS  read-only
--     STATUS      current
--     DESCRIPTION
--         "The value of tmnxOamSysPerfReqTypeLocalTestTx indicates the number of
--          echo request packets transmitted by locally initiated tests (since the
--          last clear) for the echo request packet type specified by
--          tmnxOamSysPerfReqTypeName."
--     ::= { tmnxOamSysPerfReqTypeEntry 2 }
--
-- tmnxOamSysPerfReqTypeRemoteTstRx OBJECT-TYPE
--     SYNTAX      Counter32
--     UNITS       "echo request packets"
--     MAX-ACCESS  read-only
--     STATUS      current
--     DESCRIPTION
--         "The value of tmnxOamSysPerfReqTypeRemoteTstRx indicates the number of
--          echo request packets received from remotely initiated tests (since the
--          last clear) for the echo request packet type specified by
--          tmnxOamSysPerfReqTypeName."
--     ::= { tmnxOamSysPerfReqTypeEntry 3 }
--
-- tmnxOamSysSessionLimit           OBJECT-TYPE
--     SYNTAX      Gauge32
--     UNITS       "sessions"
--     MAX-ACCESS  read-only
--     STATUS      current
--     DESCRIPTION
--         "The value of tmnxOamSysSessionLimit indicates the maximum number of
--          OAM sessions available on this node.  OAM sessions are allocated and
--          freed as described in the tmnxOamSysSessionCount DESCRIPTION clause."
--     ::= { tmnxOamGeneralStats 8 }
--
-- tmnxOamSysSessionCount           OBJECT-TYPE
--     SYNTAX      Gauge32
--     UNITS       "sessions"
--     MAX-ACCESS  read-only
--     STATUS      current
--     DESCRIPTION
--         "The value of tmnxOamSysSessionCount indicates the number of OAM
--          sessions currently allocated on this node.
--
--          One OAM session is allocated when a test is configured (in the case of
--          some test types) or activated (in the remaining cases).  Tests with the
--          following test types allocate OAM sessions:
--          1.  SDP keep-alive.
--          2.  Static route CPE check.
--          3.  Filter redirect policy ping test.
--          4.  VRRP policy host unreachable ping test.
--          5.  Any OAM or SAA test configured using TIMETRA-OAM-TEST-MIB.
--
--          The session is freed when the test is deactivated or deleted.
--
--          tmnxOamSysSessionCount will not exceed tmnxOamSysSessionLimit.
--
--          Configuration or activation of a test will fail when
--          tmnxOamSysSessionCount equals tmnxOamSysSessionLimit."
--     ::= { tmnxOamGeneralStats 9 }
--
-- tmnxOamMplsEchoDownstreamMapTlv  OBJECT-TYPE
--     SYNTAX      TmnxOamMplsEchoDownMapTlv
--     MAX-ACCESS  read-write
--     STATUS      current
--     DESCRIPTION
--         "The value of tmnxOamMplsEchoDownstreamMapTlv specifies the system value
--          for the type of downstream map TLV to be inserted when launching MPLS
--          echo requests.
--
--          The value of tmnxOamMplsEchoDownstreamMapTlv is used on three
--          occasions:
--
--          1.  When a background LDP tree trace test is started (using
--          tmnxOamLTtraceAutoAdminState), the value of
--          tmnxOamMplsEchoDownstreamMapTlv specifies the type of downstream map
--          TLV used during the test.
--
--          2.  When a test of type 'lspTraceRoute' is created, with no value
--          specified for the test's tmnxOamLspTrCtlDownstreamMapTlv object,
--          tmnxOamLspTrCtlDownstreamMapTlv is set to the value of
--          tmnxOamMplsEchoDownstreamMapTlv.
--
--          3.  When a test of type 'ldpTreeTrace' is created, with no value
--          specified for the test's tmnxOamLTtraceCtlDownstreamMpTlv object,
--          tmnxOamLTtraceCtlDownstreamMpTlv is set to the value of
--          tmnxOamMplsEchoDownstreamMapTlv.
--
--          Example usage, for the second and third cases:  suppose every node in
--          this node's network supports the MPLS Echo Request/Reply DDMAP TLV, and
--          the network operator wishes to use the enhanced functionality offered
--          by the DDMAP TLV.  Then, setting tmnxOamMplsEchoDownstreamMapTlv to
--          'ddmap(2)' simplifies configuration.  The simplification:  the
--          tmnxOamLspTrCtlDownstreamMapTlv and tmnxOamLTtraceCtlDownstreamMpTlv
--          objects need not be set when creating tests."
--     DEFVAL { dsmap }
--     ::= { tmnxOamGeneralObjs 3 }
--
-- Conformance Information
--
-- tnOamPingCompliances  OBJECT IDENTIFIER ::= { tnOamPingConformance 1 }
-- tnOamPingGroups       OBJECT IDENTIFIER ::= { tnOamPingConformance 2 }

-- tnOamTrCompliances    OBJECT IDENTIFIER ::= { tnOamTraceRouteConformance 1 }
-- tnOamTrGroups         OBJECT IDENTIFIER ::= { tnOamTraceRouteConformance 2 }

-- tnOamSaaCompliances   OBJECT IDENTIFIER ::= { tnOamSaaConformance 1 }
-- tnOamSaaGroups        OBJECT IDENTIFIER ::= { tnOamSaaConformance 2 }

-- tnOamGeneralCompliances OBJECT IDENTIFIER ::= { tnOamGeneralConformance 1 }
-- tnOamGeneralGroups      OBJECT IDENTIFIER ::= { tnOamGeneralConformance 2 }

-- compliance statements

-- tnOamPingCompliance  MODULE-COMPLIANCE
--    ::= { tnOamPingCompliances 1 }

-- tnOamPingR2r1Compliance  MODULE-COMPLIANCE
--    ::= { tnOamPingCompliances 2 }

-- tnOamPingV3v0Compliance  MODULE-COMPLIANCE
--    ::= { tnOamPingCompliances 3 }

-- tnOamPing7450V4v0Compliance  MODULE-COMPLIANCE
--     STATUS obsolete
--     DESCRIPTION
--         "The compliance statement for management of OAM ping tests on
--          Nokia 7450 ESS series systems release 4.0."
--     MODULE  this module
--         MANDATORY-GROUPS {
--            tnOamPingGeneralV4v0Group,
            --tnOamMacPingL2MapGroup,
--            tnOamMacPingV4v0Group,
--            tnOamLspPingV4v0Group,
            --tnOamVprnPingV4v0Group,
--            tnOamMfibPingV4v0Group,
--            tnOamCpePingV4v0Group,
            --tnOamMRInfoV4v0Group,
            --tnOamAtmPingR2r1Group,
--            tnOamVccvPingGroup,
--            tnOamIcmpPingGroup,
--            tnOamPingNotificationV4v0Group
--         }
--     ::= { tnOamPingCompliances 4 }

-- tnOamPing7750V4v0Compliance  MODULE-COMPLIANCE
--     STATUS  obsolete
--     DESCRIPTION
--         "The compliance statement for management of OAM ping tests on
--          Nokia SROS series systems release 4.0."
--     MODULE  this module
--         MANDATORY-GROUPS {
--            tnOamPingGeneralV4v0Group,
            --tnOamMacPingL2MapGroup,
--            tnOamMacPingV4v0Group,
--            tnOamLspPingV4v0Group,
--            tnOamVprnPingV4v0Group,
--            tnOamMfibPingV4v0Group,
--            tnOamCpePingV4v0Group,
--            tnOamMRInfoV4v0Group,
--            tnOamAtmPingR2r1Group,
--            tnOamVccvPingGroup,
--            tnOamIcmpPingGroup,
--            tnOamPingNotificationV4v0Group
--         }
--     ::= { tnOamPingCompliances 5 }

-- tnOamPing7450V5v0Compliance  MODULE-COMPLIANCE
--     STATUS  obsolete
--     DESCRIPTION
--         "The compliance statement for management of OAM ping tests on
--          Nokia 7450 ESS series systems release 5.0."
--     MODULE  this module
--         MANDATORY-GROUPS {
--            tnOamPingGeneralV4v0Group,
            --tnOamMacPingL2MapGroup,
--            tnOamMacPingV4v0Group,
--            tnOamLspPingV5v0Group,
            --tnOamVprnPingV4v0Group,
--            tnOamMfibPingV4v0Group,
--            tnOamCpePingV4v0Group,
            --tnOamMRInfoV4v0Group,
            --tnOamAtmPingR2r1Group,
--            tnOamVccvPingV5v0Group,
--            tnOamIcmpPingGroup,
--            tnOamAncpTestV5v0Group,
--            tnOamPingNotificationV5v0Group
--         }
--     ::= { tnOamPingCompliances 6 }

-- tnOamPing7750V5v0Compliance  MODULE-COMPLIANCE
--     STATUS  obsolete
--       DESCRIPTION
--           "The compliance statement for management of OAM ping tests on
--            Nokia SROS series systems release 5.0."
--       MODULE  this module
--           MANDATORY-GROUPS {
--              tnOamPingGeneralV4v0Group,
              --tnOamMacPingL2MapGroup,
--              tnOamMacPingV4v0Group,
--              tnOamLspPingV5v0Group,
--              tnOamVprnPingV4v0Group,
--              tnOamMfibPingV4v0Group,
--              tnOamCpePingV4v0Group,
--              tnOamMRInfoV4v0Group,
--              tnOamAtmPingR2r1Group,
--              tnOamVccvPingV5v0Group,
--              tnOamIcmpPingGroup,
--              tnOamAncpTestV5v0Group,
--              tnOamPingNotificationV5v0Group
--           }
--       ::= { tnOamPingCompliances 7 }

-- tnOamPing7450V6v0Compliance  MODULE-COMPLIANCE
--     STATUS obsolete
--     DESCRIPTION
--         "The compliance statement for management of OAM ping tests on
--          Nokia 7450 ESS series systems release 6.0."
--     MODULE  this module
--         MANDATORY-GROUPS {
--            tnOamPingGeneralV6v0Group,
            --tnOamMacPingL2MapGroup,
--            tnOamMacPingV4v0Group,
--            tnOamLspPingV6v0Group,
            --tnOamVprnPingV4v0Group,
--            tnOamMfibPingV6v0Group,
--            tnOamCpePingV4v0Group,
            --tnOamMRInfoV4v0Group,
            --tnOamAtmPingR2r1Group,
--            tnOamVccvPingV5v0Group,
--            tnOamIcmpPingGroup,
--            tnOamAncpTestV5v0Group,
--            tnOamPingNotificationV5v0Group
--         }
--     ::= { tnOamPingCompliances 8 }

-- tnOamPing7750V6v0Compliance  MODULE-COMPLIANCE
--       STATUS  obsolete
--       DESCRIPTION
--           "The compliance statement for management of OAM ping tests on
--            Nokia SROS series systems release 6.0."
--       MODULE  this module
--           MANDATORY-GROUPS {
--              tnOamPingGeneralV6v0Group,
              --tnOamMacPingL2MapGroup,
--              tnOamMacPingV4v0Group,
--              tnOamLspPingV6v0Group,
--              tnOamVprnPingV4v0Group,
--              tnOamMfibPingV6v0Group,
--              tnOamCpePingV4v0Group,
--              tnOamMRInfoV4v0Group,
--              tnOamAtmPingR2r1Group,
--              tnOamVccvPingV5v0Group,
--              tnOamIcmpPingGroup,
--              tnOamAncpTestV5v0Group,
--              tnOamPingNotificationV5v0Group
--           }
--       ::= { tnOamPingCompliances 9 }

-- tnOamPing7450V7v0Compliance  MODULE-COMPLIANCE
--     STATUS obsolete
--     DESCRIPTION
--         "The compliance statement for management of OAM ping tests on
--          Nokia 7450 ESS series systems release 7.0."
--     MODULE  this module
--         MANDATORY-GROUPS {
--            tnOamPingGeneralV7v0Group,
            --tnOamMacPingL2MapGroup,
--            tnOamMacPingV4v0Group,
--            tnOamLspPingV6v0Group,
            --tnOamVprnPingV4v0Group,
--            tnOamMfibPingV6v0Group,
--            tnOamCpePingV4v0Group,
            --tnOamMRInfoV4v0Group,
            --tnOamAtmPingR2r1Group,
--            tnOamVccvPingV5v0Group,
--            tnOamIcmpPingGroup,
--            tnOamAncpTestV5v0Group,
--            tnOamPingNotificationV7v0Group
--         }
--     ::= { tnOamPingCompliances 10 }

-- tnOamPing7750V7v0Compliance  MODULE-COMPLIANCE
--     STATUS  obsolete
--     DESCRIPTION
--         "The compliance statement for management of OAM ping tests on
--          Nokia 7750 and 7710 SR series systems release 7.0."
--     MODULE  this module
--         MANDATORY-GROUPS {
--            tnOamPingGeneralV7v0Group,
            --tnOamMacPingL2MapGroup,
--            tnOamMacPingV4v0Group,
--            tnOamLspPingV6v0Group,
--            tnOamVprnPingV4v0Group,
--            tnOamMfibPingV6v0Group,
--            tnOamCpePingV4v0Group,
--            tnOamMRInfoV4v0Group,
--            tnOamAtmPingR2r1Group,
--            tnOamVccvPingV5v0Group,
--            tnOamIcmpPingGroup,
--            tnOamAncpTestV5v0Group,
--            tnOamPingNotificationV7v0Group,
--            tnOamP2mpLspPingGroup
--         }
--     ::= { tnOamPingCompliances 11 }

-- tnOamPing7450V8v0Compliance  MODULE-COMPLIANCE
--     STATUS current
--     DESCRIPTION
--         "The compliance statement for management of OAM ping tests on
--          Nokia 7450 ESS series systems release 8.0."
--     MODULE  this module
--         MANDATORY-GROUPS {
--            tnOamPingGeneralV8v0Group,
            --tnOamMacPingL2MapGroup,
--            tnOamMacPingV4v0Group,
--            tnOamLspPingV6v0Group,
            --tnOamVprnPingV4v0Group,
--            tnOamMfibPingV6v0Group,
--            tnOamCpePingV4v0Group,
            --tnOamMRInfoV4v0Group,
            --tnOamAtmPingR2r1Group,
--            tnOamVccvPingV5v0Group,
--            tnOamIcmpPingGroup,
--            tnOamAncpTestV5v0Group,
--            tnOamEthCfmPingV8v0Group,
--            tnOamPingNotificationV7v0Group
--         }
--     ::= { tnOamPingCompliances 12 }

-- tnOamPing77x0V8v0Compliance  MODULE-COMPLIANCE
--     STATUS  obsolete
--     DESCRIPTION
--         "The compliance statement for management of OAM ping tests on
--          Nokia 7750 and 7710 SR series systems release 8.0."
--     MODULE  this module
--         MANDATORY-GROUPS {
--            tnOamPingGeneralV8v0Group,
            --tnOamMacPingL2MapGroup,
--            tnOamMacPingV4v0Group,
--            tnOamLspPingV6v0Group,
--            tnOamVprnPingV4v0Group,
--            tnOamMfibPingV6v0Group,
--            tnOamCpePingV4v0Group,
--            tnOamMRInfoV4v0Group,
--            tnOamAtmPingR2r1Group,
--            tnOamVccvPingV5v0Group,
--            tnOamIcmpPingGroup,
--            tnOamAncpTestV5v0Group,
--            tnOamEthCfmPingV8v0Group,
--            tnOamPingNotificationV7v0Group,
--            tnOamP2mpLspPingGroup,
--            tnOamP2mpLspPingV8v0Group
--         }
--     ::= { tnOamPingCompliances 13 }


-- tnOamPing7xx0V9v0Compliance  MODULE-COMPLIANCE
--     STATUS  current
--     DESCRIPTION
--         "The compliance statement for management of OAM ping tests on
--          Nokia SROS series systems, release 9.0."
--     MODULE  this module
--         MANDATORY-GROUPS {
--            tnOamPingGeneralV8v0Group,
            --tnOamMacPingL2MapGroup,
--            tnOamMacPingV4v0Group,
--            tnOamLspPingV6v0Group,
--            tnOamVprnPingV4v0Group,
--            tnOamMfibPingV6v0Group,
--            tnOamCpePingV4v0Group,
--            tnOamMRInfoV4v0Group,
--            tnOamAtmPingR2r1Group,
--            tnOamVccvPingV5v0Group,
--            tnOamIcmpPingGroup,
--            tnOamAncpTestV5v0Group,
--            tnOamEthCfmPingV8v0Group,
--            tnOamPingNotificationV7v0Group,
--            tnOamP2mpLspPingGroup,
--            tnOamP2mpLspPingV8v0Group,
--            tnOamVccvPingV9v0Group
--         }
--     ::= { tnOamPingCompliances 14 }

-- tnOamTrCompliance  MODULE-COMPLIANCE
--    ::= { tnOamTrCompliances 1 }

-- tnOamTrV3v0Compliance  MODULE-COMPLIANCE
--    ::= { tnOamTrCompliances 2 }

-- tnOamTr7450V4v0Compliance  MODULE-COMPLIANCE
--     STATUS  obsolete
--     DESCRIPTION
--         "The compliance statement for management of OAM Trace Route
--          tests on Nokia 7450 ESS series systems."
--     MODULE  this module
--         MANDATORY-GROUPS {
--            tnOamTrGeneralV4v0Group,
--            tnOamTrHopsV4v0Group,
--            tnOamMacTrV3v0Group,
--            tnOamLspTrV4v0Group,
            --tnOamVprnTrV4v0Group,
--            tnOamMcastTrV4v0Group,
--            tnOamTrNotificationV4v0Group
--         }
--     ::= { tnOamTrCompliances 3 }

-- tnOamTr7750V4v0Compliance  MODULE-COMPLIANCE
--     STATUS  obsolete
--     DESCRIPTION
--         "The compliance statement for management of OAM Trace Route
--          tests on Nokia SROS series systems."
--     MODULE  this module
--         MANDATORY-GROUPS {
--            tnOamTrGeneralV4v0Group,
--            tnOamTrHopsV4v0Group,
--            tnOamMacTrV3v0Group,
--            tnOamLspTrV4v0Group,
--            tnOamVprnTrV4v0Group,
--            tnOamMcastTrV4v0Group,
--            tnOamTrNotificationV4v0Group
--          }
--     ::= { tnOamTrCompliances 4 }

-- tnOamTr7450V5v0Compliance  MODULE-COMPLIANCE
--     STATUS  obsolete
--     DESCRIPTION
--         "The compliance statement for management of OAM Trace Route
--          tests on Nokia 7450 ESS series systems."
--     MODULE  this module
--         MANDATORY-GROUPS {
--            tnOamTrGeneralV5v0Group,
--            tnOamTrHopsV4v0Group,
--            tnOamMacTrV3v0Group,
--            tnOamLspTrV5v0Group,
            --tnOamVprnTrV4v0Group,
--            tnOamMcastTrV4v0Group,
--            tnOamTrNotificationV5v0Group
--         }
--     ::= { tnOamTrCompliances 5 }

-- tnOamTr7750V5v0Compliance  MODULE-COMPLIANCE
--     STATUS  obsolete
--     DESCRIPTION
--         "The compliance statement for management of OAM Trace Route
--          tests on Nokia SROS series systems."
--     MODULE  this module
--         MANDATORY-GROUPS {
--            tnOamTrGeneralV5v0Group,
--            tnOamTrHopsV4v0Group,
--            tnOamMacTrV3v0Group,
--            tnOamLspTrV5v0Group,
--            tnOamVprnTrV4v0Group,
--            tnOamMcastTrV4v0Group,
--            tnOamTrNotificationV5v0Group
--          }
--     ::= { tnOamTrCompliances 6 }

-- tnOamTr7450V6v0Compliance  MODULE-COMPLIANCE
--     STATUS  obsolete
--     DESCRIPTION
--         "The compliance statement for management of OAM Trace Route
--          tests on Nokia 7450 ESS series systems."
--     MODULE  this module
--         MANDATORY-GROUPS {
--            tnOamTrGeneralV6v0Group,
--            tnOamTrHopsV4v0Group,
--            tnOamMacTrV3v0Group,
--            tnOamLspTrV6v0Group,
            --tnOamVprnTrV4v0Group,
--            tnOamMcastTrV4v0Group,
--            tnOamVccvTrV6v0Group,
--            tnOamTrNotificationV5v0Group
--         }
--     ::= { tnOamTrCompliances 7 }

-- tnOamTr77x0V6v0Compliance  MODULE-COMPLIANCE
--     STATUS  obsolete
--     DESCRIPTION
--         "The compliance statement for management of OAM Trace Route
--          tests on Nokia 7710/7750 SR series systems."
--     MODULE  this module
--         MANDATORY-GROUPS {
--            tnOamTrGeneralV6v0Group,
--            tnOamTrHopsV4v0Group,
--            tnOamMacTrV3v0Group,
--            tnOamLspTrV6v0Group,
--            tnOamVprnTrV6v0Group,
--            tnOamMcastTrV4v0Group,
--            tnOamVccvTrV6v0Group,
--            tnOamTrNotificationV5v0Group
--          }
--     ::= { tnOamTrCompliances 8 }

-- tnOamTr7450V7v0Compliance  MODULE-COMPLIANCE
--     STATUS  obsolete
--     DESCRIPTION
--         "The compliance statement for management of OAM Trace Route
--          tests on Nokia 7450 ESS series systems."
--     MODULE  this module
--         MANDATORY-GROUPS {
--            tnOamTrGeneralV7v0Group,
--            tnOamTrHopsV4v0Group,
--            tnOamMacTrV3v0Group,
--            tnOamLspTrV6v0Group,
            --tnOamVprnTrV4v0Group,
--            tnOamMcastTrV4v0Group,
--            tnOamVccvTrV6v0Group,
--            tnOamTrNotificationV5v0Group
--         }
--     ::= { tnOamTrCompliances 9 }

-- tnOamTr77x0V7v0Compliance  MODULE-COMPLIANCE
--     STATUS  obsolete
--     DESCRIPTION
--         "The compliance statement for management of OAM Trace Route
--          tests on Nokia 7710/7750 SR series systems."
--     MODULE  this module
--         MANDATORY-GROUPS {
--            tnOamTrGeneralV7v0Group,
--            tnOamTrHopsV4v0Group,
--            tnOamMacTrV3v0Group,
--            tnOamLspTrV6v0Group,
--            tnOamVprnTrV6v0Group,
--            tnOamMcastTrV4v0Group,
--            tnOamVccvTrV6v0Group,
--            tnOamTrNotificationV5v0Group,
--            tnOamP2mpLspTraceGroup
--          }
--     ::= { tnOamTrCompliances 10 }


-- tnOamTr7xx0V8v0Compliance  MODULE-COMPLIANCE
--     STATUS  obsolete
--     DESCRIPTION
--         "The compliance statement for management of OAM Trace Route
--          tests on Nokia 7450/7710/7750 series systems."
--     MODULE  this module
--         MANDATORY-GROUPS {
--            tnOamTrGeneralV7v0Group,
--            tnOamTrHopsV4v0Group,
--            tnOamMacTrV3v0Group,
--            tnOamLspTrV6v0Group,
--            tnOamVprnTrV6v0Group,
--            tnOamMcastTrV4v0Group,
--            tnOamVccvTrV6v0Group,
--            tnOamTrNotificationV5v0Group,
--            tnOamP2mpLspTraceGroup,
--            tnOamEthCfmTrV8v0Group,
--            tnOamTrGeneralV8v0Group,
--            tnOamTrNotificationV8v0Group
--         }
--     ::= { tnOamTrCompliances 11 }

-- tnOamTr7xx0V9v0Compliance  MODULE-COMPLIANCE
--     STATUS  current
--     DESCRIPTION
--         "The compliance statement for management of OAM Trace Route
--          tests on Nokia SROS series systems, release 9.0."
--     MODULE  this module
--         MANDATORY-GROUPS {
--            tnOamEthCfmTrV8v0Group,
--            tnOamLTtraceV9v0Group,
--            tnOamLspTrV6v0Group,
--            tnOamMacTrV3v0Group,
--            tnOamMcastTrV4v0Group,
--            tnOamP2mpLspTraceGroup,
--            tnOamTrGeneralV7v0Group,
--            tnOamTrGeneralV8v0Group,
--            tnOamTrHopsV4v0Group,
--            tnOamTrNotificationV5v0Group,
--            tnOamTrNotificationV8v0Group,
--            tnOamVccvTrV6v0Group,
--            tnOamVccvTrV9v0Group,
--            tnOamVprnTrV6v0Group
--         }
--     ::= { tnOamTrCompliances 12 }


-- tnOamSaaV3v0Compliance  MODULE-COMPLIANCE
--     STATUS  obsolete
--     DESCRIPTION
--         "The compliance statement for management of OAM SAA
--          tests on Nokia SROS series systems."
--     MODULE  this module
--         MANDATORY-GROUPS {
--            tnOamSaaGeneralV3v0Group,
--            tnOamSaaThresholdV3v0Group,
--            tnOamSaaNotificationV3v0Group
--         }
--     ::= { tnOamSaaCompliances 1 }

-- tnOamSaaV7v0Compliance  MODULE-COMPLIANCE
--     STATUS  obsolete
--     DESCRIPTION
--         "The compliance statement for management of OAM SAA
--          tests on Nokia SROS series systems."
--     MODULE  this module
--         MANDATORY-GROUPS {
--            tnOamSaaGeneralV7v0Group,
--            tnOamSaaThresholdV3v0Group,
--            tnOamSaaNotificationV3v0Group
--         }
--     ::= { tnOamSaaCompliances 2 }

-- tnOamSaaV8v0Compliance  MODULE-COMPLIANCE
--     STATUS  current
--     DESCRIPTION
--         "The compliance statement for management of OAM SAA
--          tests on Nokia SROS series systems."
--     MODULE  this module
--         MANDATORY-GROUPS {
--            tnOamSaaGeneralV7v0Group,
--            tnOamSaaGeneralV8v0Group,
--            tnOamSaaThresholdV3v0Group,
--            tnOamSaaNotificationV3v0Group
--         }
--     ::= { tnOamSaaCompliances 3 }

-- tnOamGeneralV8v0Compliance  MODULE-COMPLIANCE
--     STATUS  current
--     DESCRIPTION
--         "The compliance statement for management of OAM general capabilities on
--          Nokia SROS series systems for Release 8.0."
--     MODULE  this module
--         MANDATORY-GROUPS {
--             tnOamGeneralV8v0Group
--         }
--     ::= { tnOamGeneralCompliances 1 }

-- units of conformance

--
--  OAM Ping Groups
--

-- tnOamPingGeneralGroup   OBJECT-GROUP
--    ::= { tnOamPingGroups 1 }

-- tnOamMacPingGroup     OBJECT-GROUP
--    ::= { tnOamPingGroups 2 }

-- tnOamMacPingL2MapGroup     OBJECT-GROUP
--     OBJECTS {  tnOamMacPingL2MapRouterID,
--                tnOamMacPingL2MapLabel,
--                tnOamMacPingL2MapProtocol,
--                tnOamMacPingL2MapVCType,
--                tnOamMacPingL2MapVCID,
--                tnOamMacPingL2MapDirection
--             }
--     STATUS     obsolete
--     DESCRIPTION
--         "The group of optional objects to report OAM Mac Ping layer-2
--          mapping information returned in response to OAM Mac Ping
--          tests on Nokia SROS series systems."
--     ::= { tnOamPingGroups 3 }

-- tnOamLspPingGroup     OBJECT-GROUP
--    ::= { tnOamPingGroups 4 }

-- tnOamVprnPingGroup     OBJECT-GROUP
--    ::= { tnOamPingGroups 5 }

-- tnOamPingNotifyObjsGroup   OBJECT-GROUP
--    ::= { tnOamPingGroups 6 }

-- tnOamPingNotificationGroup NOTIFICATION-GROUP
--    ::= { tnOamPingGroups 7 }

-- tnOamAtmPingR2r1Group OBJECT-GROUP
--     OBJECTS {  tnOamAtmPingCtlPortId,
--                tnOamAtmPingCtlVpi,
--                tnOamAtmPingCtlVci,
--                tnOamAtmPingCtlLpbkLocation,
--                tnOamAtmPingCtlSegment
--             }
--     STATUS      current
--     DESCRIPTION
--         "The group of objects supporting management of OAM ATM Ping tests
--          on Nokia SROS series systems."
--     ::= { tnOamPingGroups 8}

-- tnOamMRInfoR2r1Group OBJECT-GROUP
--    ::= { tnOamPingGroups 9}

-- tnOamMfibPingV3v0Group    OBJECT-GROUP
--    ::= { tnOamPingGroups 10 }

-- tnOamCpePingV3v0Group     OBJECT-GROUP
--    ::= { tnOamPingGroups 11 }

-- tnOamPingGeneralV3v0Group   OBJECT-GROUP
--    ::= { tnOamPingGroups 12 }

-- tnOamMacPingV3v0Group     OBJECT-GROUP
--    ::= { tnOamPingGroups 13 }

-- tnOamMacPingV4v0Group     OBJECT-GROUP
--     OBJECTS {  tnOamMacPingCtlTargetMacAddr,
--                tnOamMacPingCtlSourceMacAddr,
--                tnOamMacPingCtlSendControl,
--                tnOamMacPingCtlReplyControl,
--                tnOamMacPingCtlTtl,
--                tnOamMacPingCtlRegister,
--                tnOamMacPingCtlFlood,
--                tnOamMacPingCtlForce,
--                tnOamMacPingCtlAge,
--                tnOamMacPingCtlSapPortId,
--                tnOamMacPingCtlSapEncapValue,
--                tnOamMacPingCtlFibEntryName,
--                tnOamMacPingHistoryResponse,
--                tnOamMacPingHistoryOneWayTime,
--                tnOamMacPingHistoryStatus,
--                tnOamMacPingHistoryTime,
--                tnOamMacPingHistoryReturnCode,
--                tnOamMacPingHistoryAddressType,
--                tnOamMacPingHistorySapId,
--                tnOamMacPingHistorySdpId,
--                tnOamMacPingHistoryAdminStatus,
--                tnOamMacPingHistoryOperStatus,
--                tnOamMacPingHistoryResponsePlane,
--                tnOamMacPingHistorySize,
--                tnOamMacPingHistoryInOneWayTime,
--                tnOamMacPingHistorySrcAddrType,
--                tnOamMacPingHistorySrcAddress
--             }
--     STATUS      current
--     DESCRIPTION
--         "The group of objects supporting management of OAM Mac Ping tests
--          on Nokia SROS series systems release 4.0."
--     ::= { tnOamPingGroups 14 }

-- tnOamVccvPingGroup OBJECT-GROUP
--     OBJECTS {
--                tnOamVccvPingCtlSdpIdVcId,
--                tnOamVccvPingCtlReplyMode
--             }
--     STATUS     obsolete
--     DESCRIPTION
--         "The group of objects supporting management of OAM VCCV Ping tests
--          on Nokia SROS series systems."
--     ::= { tnOamPingGroups 15 }

-- tnOamPingGeneralV4v0Group   OBJECT-GROUP
--     OBJECTS {  tnOamPingMaxConcurrentTests,
--                tnOamPingCtlRowStatus,
--                tnOamPingCtlStorageType,
--                tnOamPingCtlDescr,
--                tnOamPingCtlTestMode,
--                tnOamPingCtlAdminStatus,
--                tnOamPingCtlOrigSdpId,
--                tnOamPingCtlRespSdpId,
--                tnOamPingCtlFcName,
--                tnOamPingCtlProfile,
--                tnOamPingCtlMtuStartSize,
--                tnOamPingCtlMtuEndSize,
--                tnOamPingCtlMtuStepSize,
--                tnOamPingCtlServiceId,
--                tnOamPingCtlLocalSdp,
--                tnOamPingCtlRemoteSdp,
--                tnOamPingCtlSize,
--                tnOamPingCtlTimeOut,
--                tnOamPingCtlProbeCount,
--                tnOamPingCtlInterval,
--                tnOamPingCtlMaxRows,
--                tnOamPingCtlTrapGeneration,
--                tnOamPingCtlTrapProbeFailureFilter,
--                tnOamPingCtlTrapTestFailureFilter,
--                tnOamPingCtlSAA,
--                tnOamPingCtlRuns,
--                tnOamPingCtlFailures,
--                tnOamPingCtlLastRunResult,
--                tnOamPingCtlLastChanged,
--                tnOamPingCtlVRtrID,
--                tnOamPingCtlTgtAddrType,
--                tnOamPingCtlTgtAddress,
--                tnOamPingCtlSrcAddrType,
--                tnOamPingCtlSrcAddress,
--                tnOamPingCtlDnsName,
--                tnOamPingResultsOperStatus,
--                tnOamPingResultsMinRtt,
--                tnOamPingResultsMaxRtt,
--                tnOamPingResultsAverageRtt,
--                tnOamPingResultsRttSumOfSquares,
--                tnOamPingResultsMtuResponseSize,
--                tnOamPingResultsSvcPing,
--                tnOamPingResultsProbeResponses,
--                tnOamPingResultsSentProbes,
--                tnOamPingResultsLastGoodProbe,
--                tnOamPingResultsLastRespHeader,
--                tnOamPingResultsMinTt,
--                tnOamPingResultsMaxTt,
--                tnOamPingResultsAverageTt,
--                tnOamPingResultsTtSumOfSquares,
--                tnOamPingResultsMinInTt,
--                tnOamPingResultsMaxInTt,
--                tnOamPingResultsAverageInTt,
--                tnOamPingResultsInTtSumOfSqrs,
--                tnOamPingResultsOutJitter,
--                tnOamPingResultsInJitter,
--                tnOamPingResultsRtJitter,
--                tnOamPingResultsProbeTimeouts,
--                tnOamPingResultsProbeFailures,
--                tnOamPingHistoryResponse,
--                tnOamPingHistoryOneWayTime,
--                tnOamPingHistorySize,
--                tnOamPingHistoryStatus,
--                tnOamPingHistoryTime,
--                tnOamPingHistoryReturnCode,
--                tnOamPingHistAddressType,
--                tnOamPingHistoryVersion,
--                tnOamPingHistSapId,
--                tnOamPingHistoryCpeMacAddr,
--                tnOamPingHistoryRespSvcId,
--                tnOamPingHistorySequence,
--                tnOamPingHistoryIfIndex,
--                tnOamPingHistoryDataLen,
--                tnOamPingHistoryRespPlane,
--                tnOamPingHistoryReqHdr,
--                tnOamPingHistoryRespHdr,
--                tnOamPingHistoryDnsAddrType,
--                tnOamPingHistoryDnsAddress,
--                tnOamPingHistorySrcAddrType,
--                tnOamPingHistorySrcAddress,
--                tnOamPingHistoryInOneWayTime
--            }
--     STATUS        obsolete
--     DESCRIPTION
--         "The group of objects supporting management of OAM ping tests general
--          capabilities on Nokia SROS series systems 4.0 release"
--     ::= { tnOamPingGroups 16 }

-- tnOamLspPingV4v0Group     OBJECT-GROUP
--     OBJECTS {  tnOamLspPingCtlVRtrID,
--                tnOamLspPingCtlLspName,
--                tnOamLspPingCtlReturnLsp,
--                tnOamLspPingCtlTtl,
--                tnOamLspPingCtlPathName,
--                tnOamLspPingCtlLdpPrefixType,
--                tnOamLspPingCtlLdpPrefix,
--                tnOamLspPingCtlLdpPrefixLen
--             }
--     STATUS      obsolete
--     DESCRIPTION
--         "The group of objects supporting management of OAM LSP Ping tests
--          on Nokia SROS series systems 4.0 release."
--     ::= { tnOamPingGroups 17 }

-- tnOamVprnPingV4v0Group     OBJECT-GROUP
--     OBJECTS {  tnOamVprnPingCtlReplyControl,
--                tnOamVprnPingCtlTtl,
--                tnOamVprnPingCtlSrcAddrType,
--                tnOamVprnPingCtlSrcAddress
--             }
--     STATUS      current
--     DESCRIPTION
--         "The group of objects supporting management of OAM VPRN Ping tests
--          on Nokia SROS series systems 4.0 release."
--     ::= { tnOamPingGroups 19 }

-- tnOamMfibPingV4v0Group    OBJECT-GROUP
--     OBJECTS {  tnOamMfibPingCtlReplyControl,
--                tnOamMfibPingCtlTtl,
--                tnOamMfibPingCtlSrcAddrType,
--                tnOamMfibPingCtlSrcAddress,
--                tnOamMfibPingCtlDestAddrType,
--                tnOamMfibPingCtlDestAddress,
--                tnOamPingHistoryRespSvcId
--             }
--     STATUS      obsolete
--     DESCRIPTION
--         "The group of objects supporting management of OAM MFIB Ping tests
--          on Nokia SROS series systems release 4.0."
--     ::= { tnOamPingGroups 20 }

-- tnOamCpePingV4v0Group     OBJECT-GROUP
--     OBJECTS { tnOamCpePingCtlSendControl,
--               tnOamCpePingCtlReplyControl,
--               tnOamCpePingCtlTtl,
--               tnOamCpePingCtlSrceMacAddr,
--               tnOamCpePingCtlSrcAddrType,
--               tnOamCpePingCtlSrcAddress,
--               tnOamPingHistoryCpeMacAddr
--             }
--     STATUS      current
--     DESCRIPTION
--         "The group of objects supporting management of OAM CPE Ping tests
--          on Nokia SROS series systems release 4.0."
--     ::= { tnOamPingGroups 21 }

-- tnOamMRInfoV4v0Group OBJECT-GROUP
--     OBJECTS {
--                tnOamMRInfoRespCapabilities,
--                tnOamMRInfoRespMinorVersion,
--                tnOamMRInfoRespMajorVersion,
--                tnOamMRInfoRespNumInterfaces,
--                tnOamMRInfoRespIfMetric,
--                tnOamMRInfoRespIfThreshold,
--                tnOamMRInfoRespIfFlags,
--                tnOamMRInfoRespIfNbrCount,
--                tnOamMRInfoRespIfAddrType,
--                tnOamMRInfoRespIfAddr,
--                tnOamMRInfoRespIfNbrAddrType,
--                tnOamMRInfoRespIfNbrAddr
--             }
--     STATUS      current
--     DESCRIPTION
--         "The group of objects supporting management of OAM Multicast Router
--          Information(mrinfo) tests on Nokia SROS series systems
--          release 4.0."
--     ::= { tnOamPingGroups 22 }

-- tnOamIcmpPingGroup OBJECT-GROUP
--     OBJECTS {
--                 tnOamIcmpPingCtlRapid,
--                 tnOamIcmpPingCtlTtl,
--                 tnOamIcmpPingCtlDSField,
--                 tnOamIcmpPingCtlPattern,
--                 tnOamIcmpPingCtlNhAddrType,
--                 tnOamIcmpPingCtlNhAddress,
--                 tnOamIcmpPingCtlEgrIfIndex,
--                 tnOamIcmpPingCtlEgrIfName,
--                 tnOamIcmpPingCtlBypassRouting,
--                 tnOamIcmpPingCtlDoNotFragment
--             }
--     STATUS      current
--     DESCRIPTION
--         "The group of objects supporting management of OAM ICMP Ping
--          tests on Nokia SROS series systems."
--     ::= { tnOamPingGroups 23 }

-- tnOamPingObsoleteV4v0Group OBJECT-GROUP
--     OBJECTS {
--                 tnOamPingCtlTargetIpAddress,
--                 tnOamPingHistorySrcIpAddress,
--                 tnOamMacPingHistorySrcIpAddress,
--                 tnOamLspPingCtlLdpIpPrefix,
--                 tnOamLspPingCtlLdpIpPrefixLen,
--                 tnOamVprnPingCtlSourceIpAddr,
--                 tnOamMfibPingCtlSourceIpAddr,
--                 tnOamMfibPingCtlDestIpAddr,
--                 tnOamCpePingCtlSourceIpAddr,
--                 tnOamMRInfoRespIfAddress,
--                 tnOamMRInfoRespIfNbrAddress
--             }
--     STATUS      current
--     DESCRIPTION
--         "The group of objects supporting management of OAM ICMP Ping
--          tests on Nokia SROS series systems that were made
--          obsolete in release 4.0."
--     ::= { tnOamPingGroups 24 }

-- tnOamPingNotificationV4v0Group NOTIFICATION-GROUP
--     NOTIFICATIONS   {  tnOamPingProbeFailedV2,
--                        tnOamPingTestFailedV2,
--                        tnOamPingTestCompletedV2
--                     }
--     STATUS      obsolete
--     DESCRIPTION
--         "The group of notifications supporting the OAM ping feature
--          on Nokia SROS series systems release 4.0."
--     ::= { tnOamPingGroups 25 }

-- tnOamPingNotificationObsoleteV4v0Group NOTIFICATION-GROUP
--     NOTIFICATIONS   {  tnOamPingProbeFailed,
--                        tnOamPingTestFailed,
--                        tnOamPingTestCompleted
--                     }
--     STATUS      current
--     DESCRIPTION
--          "The group of notifications supporting the OAM ping feature
--           on Nokia SROS series systems release 4.0."
--     ::= { tnOamPingGroups 26 }

-- tnOamLspPingV5v0Group     OBJECT-GROUP
--     OBJECTS {  tnOamLspPingCtlVRtrID,
--                tnOamLspPingCtlLspName,
--                tnOamLspPingCtlReturnLsp,
--                tnOamLspPingCtlTtl,
--                tnOamLspPingCtlPathName,
--                tnOamLspPingCtlLdpPrefixType,
--                tnOamLspPingCtlLdpPrefix,
--                tnOamLspPingCtlLdpPrefixLen,
--                tnOamLspPingCtlPathDestType,
--                tnOamLspPingCtlPathDest,
--                tnOamLspPingCtlNhIntfName,
--                tnOamLspPingCtlNhAddressType,
--                tnOamLspPingCtlNhAddress
--             }
--     STATUS      obsolete
--     DESCRIPTION
--         "The group of objects supporting management of OAM LSP Ping tests
--          on Nokia SROS series systems 5.0 release."
--     ::= { tnOamPingGroups 27 }

-- tnOamVccvPingV5v0Group OBJECT-GROUP
--     OBJECTS {
--                tnOamVccvPingCtlSdpIdVcId,
--                tnOamVccvPingCtlReplyMode,
--                tnOamVccvPingCtlPwId,
--                tnOamVccvPingCtlTtl
--             }
--     STATUS      current
--     DESCRIPTION
--         "The group of objects supporting management of OAM VCCV Ping tests
--          on Nokia SROS series systems 5.0 release."
--     ::= { tnOamPingGroups 28 }

-- tnOamAncpTestV5v0Group OBJECT-GROUP
--     OBJECTS {
--                tnOamAncpTestTarget,
--                tnOamAncpTestTargetId,
--                tnOamAncpTestcount,
--                tnOamAncpTestTimeout,
--                tnOamAncpHistoryAncpString,
--                tnOamAncpHistoryAccNodeResult,
--                tnOamAncpHistoryAccNodeCode,
--                tnOamAncpHistoryAccNodeRspStr,
--                tnOamVccvPingCtlTtl
--             }
--     STATUS      current
--     DESCRIPTION
--         "The group of objects supporting management of OAM ANCP tests
--          on Nokia SROS series systems 5.0 release."
--     ::= { tnOamPingGroups 29 }

-- tnOamPingNotificationV5v0Group NOTIFICATION-GROUP
--     NOTIFICATIONS   {  tnOamPingProbeFailedV2,
--                        tnOamPingTestFailedV2,
--                        tnOamPingTestCompletedV2,
--                        tnAncpLoopbackTestCompleted
--                     }
--     STATUS      obsolete
--     DESCRIPTION
--         "The group of notifications supporting the OAM ping feature
--          on Nokia SROS series systems release 5.0."
--     ::= { tnOamPingGroups 30 }

-- tnOamMfibPingV6v0Group    OBJECT-GROUP
--     OBJECTS {  tnOamMfibPingCtlReplyControl,
--                tnOamMfibPingCtlTtl,
--                tnOamMfibPingCtlSrcAddrType,
--                tnOamMfibPingCtlSrcAddress,
--                tnOamMfibPingCtlDestAddrType,
--                tnOamMfibPingCtlDestAddress,
--                tnOamPingHistoryRespSvcId,
--                tnOamMfibPingCtlDestMacAddr
--             }
--     STATUS      current
--     DESCRIPTION
--         "The group of objects supporting management of OAM MFIB Ping tests
--          on Nokia SROS series systems release 6.0."
--     ::= { tnOamPingGroups 31 }

-- tnOamPingGeneralV6v0Group   OBJECT-GROUP
--     OBJECTS {  tnOamPingMaxConcurrentTests,
--                tnOamPingCtlRowStatus,
--                tnOamPingCtlStorageType,
--                tnOamPingCtlDescr,
--                tnOamPingCtlTestMode,
--                tnOamPingCtlAdminStatus,
--                tnOamPingCtlOrigSdpId,
--                tnOamPingCtlRespSdpId,
--                tnOamPingCtlFcName,
--                tnOamPingCtlProfile,
--                tnOamPingCtlMtuStartSize,
--                tnOamPingCtlMtuEndSize,
--                tnOamPingCtlMtuStepSize,
--                tnOamPingCtlServiceId,
--                tnOamPingCtlLocalSdp,
--                tnOamPingCtlRemoteSdp,
--                tnOamPingCtlSize,
--                tnOamPingCtlTimeOut,
--                tnOamPingCtlProbeCount,
--                tnOamPingCtlInterval,
--                tnOamPingCtlTrapGeneration,
--                tnOamPingCtlTrapProbeFailureFilter,
--                tnOamPingCtlTrapTestFailureFilter,
--                tnOamPingCtlSAA,
--                tnOamPingCtlRuns,
--                tnOamPingCtlFailures,
--                tnOamPingCtlLastRunResult,
--                tnOamPingCtlLastChanged,
--                tnOamPingCtlVRtrID,
--                tnOamPingCtlTgtAddrType,
--                tnOamPingCtlTgtAddress,
--                tnOamPingCtlSrcAddrType,
--                tnOamPingCtlSrcAddress,
--                tnOamPingCtlDnsName,
--                tnOamPingResultsOperStatus,
--                tnOamPingResultsMinRtt,
--                tnOamPingResultsMaxRtt,
--                tnOamPingResultsAverageRtt,
--                tnOamPingResultsRttSumOfSquares,
--                tnOamPingResultsMtuResponseSize,
--                tnOamPingResultsSvcPing,
--                tnOamPingResultsProbeResponses,
--                tnOamPingResultsSentProbes,
--                tnOamPingResultsLastGoodProbe,
--                tnOamPingResultsLastRespHeader,
--                tnOamPingResultsMinTt,
--                tnOamPingResultsMaxTt,
--                tnOamPingResultsAverageTt,
--                tnOamPingResultsTtSumOfSquares,
--                tnOamPingResultsMinInTt,
--                tnOamPingResultsMaxInTt,
--                tnOamPingResultsAverageInTt,
--                tnOamPingResultsInTtSumOfSqrs,
--                tnOamPingResultsOutJitter,
--                tnOamPingResultsInJitter,
--                tnOamPingResultsRtJitter,
--                tnOamPingResultsProbeTimeouts,
--                tnOamPingResultsProbeFailures,
--                tnOamPingHistoryResponse,
--                tnOamPingHistoryOneWayTime,
--                tnOamPingHistorySize,
--                tnOamPingHistoryStatus,
--                tnOamPingHistoryTime,
--                tnOamPingHistoryReturnCode,
--                tnOamPingHistAddressType,
--                tnOamPingHistoryVersion,
--                tnOamPingHistSapId,
--                tnOamPingHistoryCpeMacAddr,
--                tnOamPingHistoryRespSvcId,
--                tnOamPingHistorySequence,
--                tnOamPingHistoryIfIndex,
--                tnOamPingHistoryDataLen,
--                tnOamPingHistoryRespPlane,
--                tnOamPingHistoryReqHdr,
--                tnOamPingHistoryRespHdr,
--                tnOamPingHistoryDnsAddrType,
--                tnOamPingHistoryDnsAddress,
--                tnOamPingHistorySrcAddrType,
--                tnOamPingHistorySrcAddress,
--                tnOamPingHistoryInOneWayTime,
--                tnOamPingCtlDNSRecord,
--                tnOamPingCtlIntervalUnits
--             }
--     STATUS        obsolete
--     DESCRIPTION
--         "The group of objects supporting management of OAM ping tests general
--          capabilities on Nokia SROS series systems 6.0 release"
--     ::= { tnOamPingGroups 32 }

-- tnOamP2mpLspPingGroup          OBJECT-GROUP
--     OBJECTS {
--               tnOamP2mpLspPingCtlLspName,
--               tnOamP2mpLspPingCtlInstName,
--               tnOamP2mpLspPingCtlTtl,
--               tnOamP2mpLspPingCtlIpRowStatus,
--               tnOamP2mpLspPingCtlIpAddrType,
--               tnOamP2mpLspPingCtlIpAddr
--             }
--     STATUS       current
--     DESCRIPTION
--         "The group of objects supporting management of P2MP LSP Ping and
--          Traceroute tests on Nokia SROS series systems 7.0 release."
--     ::= { tnOamPingGroups 33 }

-- tnOamLspPingV6v0Group     OBJECT-GROUP
--     OBJECTS {  tnOamLspPingCtlLspName,
--                tnOamLspPingCtlTtl,
--                tnOamLspPingCtlPathName,
--                tnOamLspPingCtlLdpPrefixType,
--                tnOamLspPingCtlLdpPrefix,
--                tnOamLspPingCtlLdpPrefixLen,
--                tnOamLspPingCtlPathDestType,
--                tnOamLspPingCtlPathDest,
--                tnOamLspPingCtlNhIntfName,
--                tnOamLspPingCtlNhAddressType,
--                tnOamLspPingCtlNhAddress
--             }
--     STATUS      current
--     DESCRIPTION
--         "The group of objects supporting management of OAM LSP Ping tests
--          on Nokia SROS series systems 6.0 release."
--     ::= { tnOamPingGroups 34 }

-- tnOamPingGeneralV7v0Group   OBJECT-GROUP
--     OBJECTS {  tnOamPingMaxConcurrentTests,
--                tnOamPingCtlRowStatus,
--                tnOamPingCtlStorageType,
--                tnOamPingCtlDescr,
--                tnOamPingCtlTestMode,
--                tnOamPingCtlAdminStatus,
--                tnOamPingCtlOrigSdpId,
--                tnOamPingCtlRespSdpId,
--                tnOamPingCtlFcName,
--                tnOamPingCtlProfile,
--                tnOamPingCtlMtuStartSize,
--                tnOamPingCtlMtuEndSize,
--                tnOamPingCtlMtuStepSize,
--                tnOamPingCtlServiceId,
--                tnOamPingCtlLocalSdp,
--                tnOamPingCtlRemoteSdp,
--                tnOamPingCtlSize,
--                tnOamPingCtlTimeOut,
--                tnOamPingCtlProbeCount,
--                tnOamPingCtlInterval,
--                tnOamPingCtlTrapGeneration,
--                tnOamPingCtlTrapProbeFailureFilter,
--                tnOamPingCtlTrapTestFailureFilter,
--                tnOamPingCtlSAA,
--                tnOamPingCtlRuns,
--                tnOamPingCtlFailures,
--                tnOamPingCtlLastRunResult,
--                tnOamPingCtlLastChanged,
--                tnOamPingCtlVRtrID,
--                tnOamPingCtlTgtAddrType,
--                tnOamPingCtlTgtAddress,
--                tnOamPingCtlSrcAddrType,
--                tnOamPingCtlSrcAddress,
--                tnOamPingCtlDnsName,
--                tnOamPingResultsOperStatus,
--                tnOamPingResultsMinRtt,
--                tnOamPingResultsMaxRtt,
--                tnOamPingResultsAverageRtt,
--                tnOamPingResultsRttSumOfSquares,
--                tnOamPingResultsMtuResponseSize,
--                tnOamPingResultsSvcPing,
--                tnOamPingResultsProbeResponses,
--                tnOamPingResultsSentProbes,
--                tnOamPingResultsLastGoodProbe,
--                tnOamPingResultsLastRespHeader,
--                tnOamPingResultsMinTt,
--                tnOamPingResultsMaxTt,
--                tnOamPingResultsAverageTt,
--                tnOamPingResultsTtSumOfSquares,
--                tnOamPingResultsMinInTt,
--                tnOamPingResultsMaxInTt,
--                tnOamPingResultsAverageInTt,
--                tnOamPingResultsInTtSumOfSqrs,
--                tnOamPingResultsOutJitter,
--                tnOamPingResultsInJitter,
--                tnOamPingResultsRtJitter,
--                tnOamPingResultsProbeTimeouts,
--                tnOamPingResultsProbeFailures,
--                tnOamPingHistoryResponse,
--                tnOamPingHistoryOneWayTime,
--                tnOamPingHistorySize,
--                tnOamPingHistoryStatus,
--                tnOamPingHistoryTime,
--                tnOamPingHistoryReturnCode,
--                tnOamPingHistAddressType,
--                tnOamPingHistoryVersion,
--                tnOamPingHistSapId,
--                tnOamPingHistoryCpeMacAddr,
--                tnOamPingHistoryRespSvcId,
--                tnOamPingHistorySequence,
--                tnOamPingHistoryIfIndex,
--                tnOamPingHistoryDataLen,
--                tnOamPingHistoryRespPlane,
--                tnOamPingHistoryReqHdr,
--                tnOamPingHistoryRespHdr,
--                tnOamPingHistoryDnsAddrType,
--                tnOamPingHistoryDnsAddress,
--                tnOamPingHistorySrcAddrType,
--                tnOamPingHistorySrcAddress,
--                tnOamPingHistoryInOneWayTime,
--                tnOamPingCtlDNSRecord,
--                tnOamPingResultsRttOFSumSquares,
--                tnOamPingResultsRttHCSumSquares,
--                tnOamPingResultsTtOFSumSquares,
--                tnOamPingResultsTtHCSumSquares,
--                tnOamPingResultsInTtOFSumSqrs,
--                tnOamPingResultsInTtHCSumSqrs,
--                tnOamPingResultsTestRunResult
--             }
--     STATUS       obsolete
--     DESCRIPTION
--         "The group of objects supporting management of OAM ping tests general
--          capabilities on Nokia SROS series systems 7.0 release"
--     ::= { tnOamPingGroups 35 }

-- tnOamPingNotificationV7v0Group NOTIFICATION-GROUP
--     NOTIFICATIONS   {  tnOamPingProbeFailedV3,
--                        tnOamPingTestFailedV3,
--                        tnOamPingTestCompletedV3,
--                        tnAncpLoopbackTestCompleted
--                     }
--     STATUS      current
--     DESCRIPTION
--         "The group of notifications supporting the OAM ping feature
--          on Nokia SROS series systems release 7.0."
--     ::= { tnOamPingGroups 36 }

-- tnOamPingObsoleteV6v0Group OBJECT-GROUP
--     OBJECTS {
--         tnOamLspPingCtlReturnLsp,
--         tnOamLspPingCtlVRtrID,
--         tnOamPingCtlMaxRows
--             }
--     STATUS      current
--     DESCRIPTION
--         "The group of objects supporting management of OAM ping
--          operations on Nokia SR series systems that were made
--          obsolete in release 6.0."
--     ::= { tnOamPingGroups 37 }

-- tnOamPingObsoleteV6v1Group OBJECT-GROUP
--     OBJECTS {
--         tnOamMacPingL2MapRouterID,
--         tnOamMacPingL2MapLabel,
--         tnOamMacPingL2MapProtocol,
--         tnOamMacPingL2MapVCType,
--         tnOamMacPingL2MapVCID,
--         tnOamMacPingL2MapDirection
--             }
--     STATUS      current
--     DESCRIPTION
--         "The group of objects supporting management of OAM ping
--          operations on Nokia SR series systems that were made
--          obsolete in release 6.1."
--     ::= { tnOamPingGroups 38 }


-- tnOamEthCfmPingV8v0Group     OBJECT-GROUP
--     OBJECTS {  tnOamEthCfmPingCtlTgtMacAddr,
--                tnOamEthCfmPingCtlSrcMdIndex,
--                tnOamEthCfmPingCtlSrcMaIndex,
--                tnOamEthCfmPingCtlSrcMepId
--             }
--     STATUS      current
--     DESCRIPTION
--         "The group of objects supporting management of OAM Ethernet CFM Ping
--          tests on Nokia SROS series systems 8.0 release."
--     ::= { tnOamPingGroups 39 }

-- tnOamP2mpLspPingV8v0Group     OBJECT-GROUP
--     OBJECTS {   tnOamP2mpLspPingCtlP2MPId
--             }
--     STATUS      current
--     DESCRIPTION
--         "The group of objects supporting management of OAM Lsp Ping
--          tests on Nokia SROS series systems 8.0 release."
--     ::= { tnOamPingGroups 40 }

-- tnOamPingGeneralV8v0Group   OBJECT-GROUP
--     OBJECTS {  tnOamPingMaxConcurrentTests,
--                tnOamPingCtlRowStatus,
--                tnOamPingCtlStorageType,
--                tnOamPingCtlDescr,
--                tnOamPingCtlTestMode,
--                tnOamPingCtlAdminStatus,
--                tnOamPingCtlOrigSdpId,
--                tnOamPingCtlRespSdpId,
--                tnOamPingCtlFcName,
--                tnOamPingCtlProfile,
--                tnOamPingCtlMtuStartSize,
--                tnOamPingCtlMtuEndSize,
--                tnOamPingCtlMtuStepSize,
--                tnOamPingCtlServiceId,
--                tnOamPingCtlLocalSdp,
--                tnOamPingCtlRemoteSdp,
--                tnOamPingCtlSize,
--                tnOamPingCtlTimeOut,
--                tnOamPingCtlProbeCount,
--                tnOamPingCtlInterval,
--                tnOamPingCtlTrapGeneration,
--                tnOamPingCtlTrapProbeFailureFilter,
--                tnOamPingCtlTrapTestFailureFilter,
--                tnOamPingCtlSAA,
--                tnOamPingCtlRuns,
--                tnOamPingCtlFailures,
--                tnOamPingCtlLastRunResult,
--                tnOamPingCtlLastChanged,
--                tnOamPingCtlVRtrID,
--                tnOamPingCtlTgtAddrType,
--                tnOamPingCtlTgtAddress,
--                tnOamPingCtlSrcAddrType,
--                tnOamPingCtlSrcAddress,
--                tnOamPingCtlDnsName,
--                tnOamPingResultsOperStatus,
--                tnOamPingResultsMinRtt,
--                tnOamPingResultsMaxRtt,
--                tnOamPingResultsAverageRtt,
--                tnOamPingResultsRttSumOfSquares,
--                tnOamPingResultsMtuResponseSize,
--                tnOamPingResultsSvcPing,
--                tnOamPingResultsProbeResponses,
--                tnOamPingResultsSentProbes,
--                tnOamPingResultsLastGoodProbe,
--                tnOamPingResultsMinTt,
--                tnOamPingResultsMaxTt,
--                tnOamPingResultsAverageTt,
--                tnOamPingResultsTtSumOfSquares,
--                tnOamPingResultsMinInTt,
--                tnOamPingResultsMaxInTt,
--                tnOamPingResultsAverageInTt,
--                tnOamPingResultsInTtSumOfSqrs,
--                tnOamPingResultsOutJitter,
--                tnOamPingResultsInJitter,
--                tnOamPingResultsRtJitter,
--                tnOamPingResultsProbeTimeouts,
--                tnOamPingResultsProbeFailures,
--                tnOamPingHistoryResponse,
--                tnOamPingHistoryOneWayTime,
--                tnOamPingHistorySize,
--                tnOamPingHistoryStatus,
--                tnOamPingHistoryTime,
--                tnOamPingHistoryReturnCode,
--                tnOamPingHistAddressType,
--                tnOamPingHistoryVersion,
--                tnOamPingHistSapId,
--                tnOamPingHistoryCpeMacAddr,
--                tnOamPingHistoryRespSvcId,
--                tnOamPingHistorySequence,
--                tnOamPingHistoryIfIndex,
--                tnOamPingHistoryDataLen,
--                tnOamPingHistoryRespPlane,
--                tnOamPingHistoryReqHdr,
--                tnOamPingHistoryRespHdr,
--                tnOamPingHistoryDnsAddrType,
--                tnOamPingHistoryDnsAddress,
--                tnOamPingHistorySrcAddrType,
--                tnOamPingHistorySrcAddress,
--                tnOamPingHistoryInOneWayTime,
--                tnOamPingHistoryLspName,
--                tnOamPingHistNextHopAddrType,
--                tnOamPingHistNextHopAddress,
--                tnOamPingCtlDNSRecord,
--                tnOamPingResultsRttOFSumSquares,
--                tnOamPingResultsRttHCSumSquares,
--                tnOamPingResultsTtOFSumSquares,
--                tnOamPingResultsTtHCSumSquares,
--                tnOamPingResultsInTtOFSumSqrs,
--                tnOamPingResultsInTtHCSumSqrs,
--                tnOamPingResultsTestRunResult
--             }
--     STATUS       current
--     DESCRIPTION
--         "The group of objects supporting management of OAM ping tests general
--          capabilities on Nokia SROS series systems 8.0 release"
--     ::= { tnOamPingGroups 41 }

-- tnOamPingObsoleteV8v0Group OBJECT-GROUP
--     OBJECTS {
--         tnOamPingResultsLastRespHeader
--             }
--     STATUS      current
--     DESCRIPTION
--         "The group of objects supporting management of OAM ping
--          operations on Nokia SR series systems that were made
--          obsolete in release 8.0."
--     ::= { tnOamPingGroups 42 }

-- tnOamVccvPingV9v0Group OBJECT-GROUP
--     OBJECTS {
--                tnOamVccvPingCtlSpokeSdpId,
--                tnOamVccvPingCtlSaiiGlobalId,
--                tnOamVccvPingCtlSaiiPrefix,
--                tnOamVccvPingCtlSaiiAcId,
--                tnOamVccvPingCtlTaiiGlobalId,
--                tnOamVccvPingCtlTaiiPrefix,
--                tnOamVccvPingCtlTaiiAcId
--             }
--     STATUS      current
--     DESCRIPTION
--         "The group of additional objects supporting management of OAM VCCV Ping
--          tests on Nokia SROS series systems 9.0 release."
--     ::= { tnOamPingGroups 43 }

--
--      OAM Trace Route Groups
--

-- tnOamTrGeneralGroup   OBJECT-GROUP
--    ::= { tnOamTrGroups 1 }

-- tnOamTrHopsGroup     OBJECT-GROUP
--    ::= { tnOamTrGroups 2 }

-- tnOamMacTrGroup     OBJECT-GROUP
--    ::= { tnOamTrGroups 3 }

-- tnOamLspTrGroup     OBJECT-GROUP
--    ::= { tnOamTrGroups 4 }

-- tnOamVprnTrGroup     OBJECT-GROUP
--    ::= { tnOamTrGroups 5 }

--tnOamTrNotifyObjsGroup   OBJECT-GROUP
--    ::= { tnOamTrGroups 5 }

-- tnOamTrNotificationGroup NOTIFICATION-GROUP
--    ::= { tnOamTrGroups 6 }

-- tnOamMcastTrGroup     OBJECT-GROUP
--    ::= { tnOamTrGroups 7 }

-- tnOamTrGeneralV3v0Group   OBJECT-GROUP
--    ::= { tnOamTrGroups 8 }

-- tnOamTrHopsV3v0Group     OBJECT-GROUP
--    ::= { tnOamTrGroups 9 }

-- tnOamMacTrV3v0Group     OBJECT-GROUP
--     OBJECTS {  tnOamMacTrCtlTargetMacAddr,
--                tnOamMacTrCtlSourceMacAddr,
--                tnOamMacTrCtlSendControl,
--                tnOamMacTrCtlReplyControl,
--                tnOamMacTrL2MapRouterID,
--                tnOamMacTrL2MapLabel,
--                tnOamMacTrL2MapProtocol,
--                tnOamMacTrL2MapVCType,
--                tnOamMacTrL2MapVCID,
--                tnOamMacTrL2MapDirection,
--                tnOamMacTrL2MapSdpId,
--                tnOamMacTrL2MapSapName
--             }
--     STATUS        current
--     DESCRIPTION
--         "The group of objects supporting management of OAM MAC Trace Route
--          tests on Nokia SROS series systems."
--     ::= { tnOamTrGroups 10 }

-- tnOamTrObsoleteV3v0Group  OBJECT-GROUP
--     OBJECTS {  tnOamTrResultsTestAttempts,
--                tnOamTrResultsTestSuccesses
--             }
--     STATUS      current
--     DESCRIPTION
--         "The group of objects supporting management of OAM Trace Route
--          tests that became obsolete in the 3.0 release."
--     ::= { tnOamTrGroups 11 }

-- tnOamTrGeneralV4v0Group   OBJECT-GROUP
--     OBJECTS {  tnOamTrMaxConcurrentRequests,
--                tnOamTrCtlRowStatus,
--                tnOamTrCtlStorageType,
--                tnOamTrCtlDescr,
--                tnOamTrCtlTestMode,
--                tnOamTrCtlAdminStatus,
--                tnOamTrCtlFcName,
--                tnOamTrCtlProfile,
--                tnOamTrCtlServiceId,
--                tnOamTrCtlDataSize,
--                tnOamTrCtlTimeOut,
--                tnOamTrCtlProbesPerHop,
--                tnOamTrCtlMaxTtl,
--                tnOamTrCtlInitialTtl,
--                tnOamTrCtlDSField,
--                tnOamTrCtlMaxFailures,
--                tnOamTrCtlInterval,
--                tnOamTrCtlMaxRows,
--                tnOamTrCtlTrapGeneration,
--                tnOamTrCtlCreateHopsEntries,
--                tnOamTrCtlSAA,
--                tnOamTrCtlRuns,
--                tnOamTrCtlFailures,
--                tnOamTrCtlLastRunResult,
--                tnOamTrCtlLastChanged,
--                tnOamTrCtlVRtrID,
--                tnOamTrCtlTgtAddrType,
--                tnOamTrCtlTgtAddress,
--                tnOamTrCtlSrcAddrType,
--                tnOamTrCtlSrcAddress,
--                tnOamTrCtlWaitMilliSec,
--                tnOamTrResultsOperStatus,
--                tnOamTrResultsCurHopCount,
--                tnOamTrResultsCurProbeCount,
--                tnOamTrResultsLastGoodPath,
--                tnOamTrResultsTgtAddrType,
--                tnOamTrResultsTgtAddress,
--                tnOamTrProbeHistoryResponse,
--                tnOamTrProbeHistoryOneWayTime,
--                tnOamTrProbeHistoryStatus,
--                tnOamTrProbeHistoryLastRC,
--                tnOamTrProbeHistoryTime,
--                tnOamTrProbeHistoryResponsePlane,
--                tnOamTrProbeHistoryAddressType,
--                tnOamTrProbeHistorySapId,
--                tnOamTrProbeHistoryVersion,
--                tnOamTrProbeHistoryRouterID,
--                tnOamTrProbeHistoryIfIndex,
--                tnOamTrProbeHistoryDataLen,
--                tnOamTrProbeHistorySize,
--                tnOamTrProbeHistoryInOneWayTime,
--                tnOamTrProbeHistoryAddrType,
--                tnOamTrProbeHistoryAddress
--             }
--     STATUS      obsolete
--     DESCRIPTION
--         "The group of objects supporting management of OAM Trace Route test
--          general capabilities on Nokia SROS series systems 4.0R1 release."
--     ::= { tnOamTrGroups 12 }

-- tnOamTrHopsV4v0Group     OBJECT-GROUP
--     OBJECTS {  tnOamTrHopsMinRtt,
--                tnOamTrHopsMaxRtt,
--                tnOamTrHopsAverageRtt,
--                tnOamTrHopsRttSumOfSquares,
--                tnOamTrHopsMinTt,
--                tnOamTrHopsMaxTt,
--                tnOamTrHopsAverageTt,
--                tnOamTrHopsTtSumOfSquares,
--                tnOamTrHopsSentProbes,
--                tnOamTrHopsProbeResponses,
--                tnOamTrHopsLastGoodProbe,
--                tnOamTrHopsMinInTt,
--                tnOamTrHopsMaxInTt,
--                tnOamTrHopsAverageInTt,
--                tnOamTrHopsInTtSumOfSqrs,
--                tnOamTrHopsOutJitter,
--                tnOamTrHopsInJitter,
--                tnOamTrHopsRtJitter,
--                tnOamTrHopsProbeTimeouts,
--                tnOamTrHopsProbeFailures,
--                tnOamTrHopsTgtAddrType,
--                tnOamTrHopsTgtAddress
--             }
--     STATUS      current
--     DESCRIPTION
--         "The group of optional objects to report OAM Trace Route Hops
--          returned in response to OAM Trace Route tests on Nokia
--          7x50 SR series systems 4.0R1."
--     ::= { tnOamTrGroups 13 }

-- tnOamLspTrV4v0Group     OBJECT-GROUP
--     OBJECTS {  tnOamLspTrCtlVRtrID,
--                tnOamLspTrCtlLspName,
--                tnOamLspTrCtlPathName,
--                tnOamLspTrCtlLdpPrefixType,
--                tnOamLspTrCtlLdpPrefix,
--                tnOamLspTrCtlLdpPrefixLen,
--                tnOamLspTrMapAddrType,
--                tnOamLspTrMapDSIPv4Addr,
--                tnOamLspTrMapDSIfAddr,
--                tnOamLspTrMapMTU,
--                tnOamLspTrMapDSIndex,
--                tnOamLspTrDSLabelLabel,
--                tnOamLspTrDSLabelProtocol
--             }
--     STATUS       obsolete
--     DESCRIPTION
--         "The group of objects supporting management of OAM LSP Trace Route
--          tests on Nokia SROS series systems 4.0 release."
--     ::= { tnOamTrGroups 14 }

-- tnOamVprnTrV4v0Group     OBJECT-GROUP
--     OBJECTS {  tnOamVprnTrCtlReplyControl,
--                tnOamVprnTrCtlSrcAddrType,
--                tnOamVprnTrCtlSrcAddress,
--                tnOamVprnTrL3MapRouterID,
--                tnOamVprnTrL3MapRteVprnLabel,
--                tnOamVprnTrL3MapRteMetrics,
--                tnOamVprnTrL3MapRteLastUp,
--                tnOamVprnTrL3MapRteOwner,
--                tnOamVprnTrL3MapRtePref,
--                tnOamVprnTrL3MapRteDist,
--                tnOamVprnTrL3MapNumNextHops,
--                tnOamVprnTrL3MapNumRteTargets,
--                tnOamVprnTrL3MapDestAddrType,
--                tnOamVprnTrL3MapDestAddress,
--                tnOamVprnTrL3MapDestMaskLen,
--                tnOamVprnTrNextHopRtrID,
--                tnOamVprnTrNextHopType,
--                tnOamVprnTrNextHopTunnelID,
--                tnOamVprnTrNextHopTunnelType,
--                tnOamVprnTrNextHopIfIndex,
--                tnOamVprnTrRouteTarget
--             }
--     STATUS        obsolete
--     DESCRIPTION
--         "The group of objects supporting management of OAM VPRN Trace Route
--          tests on Nokia SROS series systems release 4.0."
--     ::= { tnOamTrGroups 15 }

-- tnOamMcastTrV4v0Group     OBJECT-GROUP
--     OBJECTS {  tnOamMcastTrCtlVRtrID,
--                tnOamMcastTrCtlHops,
--                tnOamMcastTrQueryId,
--                tnOamMcastTrCtlSrcAddrType,
--                tnOamMcastTrCtlSrcAddress,
--                tnOamMcastTrCtlDestAddrType,
--                tnOamMcastTrCtlDestAddress,
--                tnOamMcastTrCtlRespAddrType,
--                tnOamMcastTrCtlRespAddress,
--                tnOamMcastTrCtlGrpAddrType,
--                tnOamMcastTrCtlGrpAddress,
--                tnOamMcastTrRespQueryArrivalTime,
--                tnOamMcastTrRespInPktCount,
--                tnOamMcastTrRespOutPktCount,
--                tnOamMcastTrRespSGPktCount,
--                tnOamMcastTrRespRtgProtocol,
--                tnOamMcastTrRespFwdTtl,
--                tnOamMcastTrRespMBZBit,
--                tnOamMcastTrRespSrcBit,
--                tnOamMcastTrRespSrcMask,
--                tnOamMcastTrRespFwdCode,
--                tnOamMcastTrRespInIfAddrType,
--                tnOamMcastTrRespInIfAddress,
--                tnOamMcastTrRespOutIfAddrType,
--                tnOamMcastTrRespOutIfAddress,
--                tnOamMcastTrRespPhRtrAddrType,
--                tnOamMcastTrRespPhRtrAddress
--             }
--     STATUS        current
--     DESCRIPTION
--         "The group of objects supporting management of OAM Multicast Trace Route
--          tests on Nokia SROS series systems release 4.0."
--     ::= { tnOamTrGroups 16 }

-- tnOamTrObsoleteV4v0Group OBJECT-GROUP
--     OBJECTS {
--                 tnOamTrCtlTargetIpAddress,
--                 tnOamTrResultsIpTgtAddr,
--                 tnOamTrProbeHistoryIpAddr,
--                 tnOamTrHopsIpTgtAddress,
--                 tnOamLspTrCtlLdpIpPrefix,
--                 tnOamLspTrCtlLdpIpPrefixLen,
--                 tnOamVprnTrCtlSourceIpAddr,
--                 tnOamVprnTrL3MapRteDestAddr,
--                 tnOamVprnTrL3MapRteDestMask,
--                 tnOamMcastTrCtlSrcIpAddr,
--                 tnOamMcastTrCtlDestIpAddr,
--                 tnOamMcastTrCtlRespIpAddr,
--                 tnOamMcastTrCtlGrpIpAddr,
--                 tnOamMcastTrRespPrevHopRtrAddr,
--                 tnOamMcastTrRespInIfAddr,
--                 tnOamMcastTrRespOutIfAddr
--             }
--     STATUS      current
--     DESCRIPTION
--         "The group of objects supporting management of OAM ICMP Ping
--          tests on Nokia SROS series systems that were made
--          obsolete in release 4.0."
--     ::= { tnOamTrGroups 17 }

-- tnOamTrNotificationV4v0Group NOTIFICATION-GROUP
--     NOTIFICATIONS   {  tnOamTrPathChange,
--                        tnOamTrTestFailed,
--                        tnOamTrTestCompleted
--                     }
--     STATUS        obsolete
--     DESCRIPTION
--         "The group of notifications supporting the OAM Trace Route test
--          feature on Nokia SROS series systems release 4.0."
--     ::= { tnOamTrGroups 18 }

-- tnOamLspTrV5v0Group     OBJECT-GROUP
--     OBJECTS {  tnOamLspTrCtlVRtrID,
--                tnOamLspTrCtlLspName,
--                tnOamLspTrCtlPathName,
--                tnOamLspTrCtlLdpPrefixType,
--                tnOamLspTrCtlLdpPrefix,
--                tnOamLspTrCtlLdpPrefixLen,
--                tnOamLspTrCtlPathDestType,
--                tnOamLspTrCtlPathDest,
--                tnOamLspTrCtlNhIntfName,
--                tnOamLspTrCtlNhAddressType,
--                tnOamLspTrCtlNhAddress,
--                tnOamLspTrMapAddrType,
--                tnOamLspTrMapDSIPv4Addr,
--                tnOamLspTrMapDSIfAddr,
--                tnOamLspTrMapMTU,
--                tnOamLspTrDSLabelLabel,
--                tnOamLspTrDSLabelProtocol
--             }
--     STATUS       obsolete
--     DESCRIPTION
--         "The group of objects supporting management of OAM LSP Trace Route
--          tests on Nokia SROS series systems 5.0 release."
--     ::= { tnOamTrGroups 19 }

-- tnOamTrObsoleteV5v0Group OBJECT-GROUP
--     OBJECTS {
--               tnOamLspTrMapDSIndex
--             }
--     STATUS      current
--     DESCRIPTION
--         "The group of objects supporting management of OAM Trace
--          tests on Nokia SROS series systems that were made
--          obsolete in release 5.0."
--     ::={ tnOamTrGroups 20 }

-- tnOamTrGeneralV5v0Group   OBJECT-GROUP
--     OBJECTS {  tnOamTrMaxConcurrentRequests,
--                tnOamTrCtlRowStatus,
--                tnOamTrCtlStorageType,
--                tnOamTrCtlDescr,
--                tnOamTrCtlTestMode,
--                tnOamTrCtlAdminStatus,
--                tnOamTrCtlFcName,
--                tnOamTrCtlProfile,
--                tnOamTrCtlServiceId,
--                tnOamTrCtlDataSize,
--                tnOamTrCtlTimeOut,
--                tnOamTrCtlProbesPerHop,
--                tnOamTrCtlMaxTtl,
--                tnOamTrCtlInitialTtl,
--                tnOamTrCtlDSField,
--                tnOamTrCtlMaxFailures,
--                tnOamTrCtlInterval,
--                tnOamTrCtlMaxRows,
--                tnOamTrCtlTrapGeneration,
--                tnOamTrCtlCreateHopsEntries,
--                tnOamTrCtlSAA,
--                tnOamTrCtlRuns,
--                tnOamTrCtlFailures,
--                tnOamTrCtlLastRunResult,
--                tnOamTrCtlLastChanged,
--                tnOamTrCtlVRtrID,
--                tnOamTrCtlTgtAddrType,
--                tnOamTrCtlTgtAddress,
--                tnOamTrCtlSrcAddrType,
--                tnOamTrCtlSrcAddress,
--                tnOamTrCtlWaitMilliSec,
--                tnOamTrResultsOperStatus,
--                tnOamTrResultsCurHopCount,
--                tnOamTrResultsCurProbeCount,
--                tnOamTrResultsLastGoodPath,
--                tnOamTrResultsTgtAddrType,
--                tnOamTrResultsTgtAddress,
--                tnOamTrProbeHistoryResponse,
--                tnOamTrProbeHistoryOneWayTime,
--                tnOamTrProbeHistoryStatus,
--                tnOamTrProbeHistoryLastRC,
--                tnOamTrProbeHistoryTime,
--                tnOamTrProbeHistoryResponsePlane,
--                tnOamTrProbeHistoryAddressType,
--                tnOamTrProbeHistorySapId,
--                tnOamTrProbeHistoryVersion,
--                tnOamTrProbeHistoryRouterID,
--                tnOamTrProbeHistoryIfIndex,
--                tnOamTrProbeHistoryDataLen,
--                tnOamTrProbeHistorySize,
--                tnOamTrProbeHistoryInOneWayTime,
--                tnOamTrProbeHistoryAddrType,
--                tnOamTrProbeHistoryAddress,
--                tnOamLTtraceFecDiscoveryState,
--                tnOamLTtraceFecDisStatusBits,
--                tnOamLTtraceFecDisPaths,
--                tnOamLTtraceFecFailedHops,
--                tnOamLTtraceFecLastDisEnd,
--                tnOamLTtraceFecFailedProbes,
--                tnOamLTtraceFecProbeState,
--                tnOamLTtracePathRemAddrType,
--                tnOamLTtracePathRemoteAddr,
--                tnOamLTtracePathEgrNhAddrType,
--                tnOamLTtracePathEgrNhAddr,
--                tnOamLTtracePathDisTtl,
--                tnOamLTtracePathLastDisTime,
--                tnOamLTtracePathLastRc,
--                tnOamLTtracePathProbeState,
--                tnOamLTtraceCtlLdpPrefixType,
--                tnOamLTtraceCtlLdpPrefix,
--                tnOamLTtraceCtlLdpPrefixLen,
--                tnOamLTtraceCtlMaxPath,
--                tnOamLTtraceResultsDisPaths,
--                tnOamLTtraceResultsFailedHops,
--                tnOamLTtraceResultsDisState,
--                tnOamLTtraceResultsDisStatus,
--                tnOamLTtraceUpStreamHopIndex,
--                tnOamLTtraceHopAddrType,
--                tnOamLTtraceHopAddr,
--                tnOamLTtraceHopDstAddrType,
--                tnOamLTtraceHopDstAddr,
--                tnOamLTtraceHopEgrNhAddrType,
--                tnOamLTtraceHopEgrNhAddr,
--                tnOamLTtraceHopDisTtl,
--                tnOamLTtraceHopLastRc,
--                tnOamLTtraceHopDiscoveryState,
--                tnOamLTtraceHopDiscoveryTime,
--                tnOamLTtraceAutoRowStatus,
--                tnOamLTtraceAutoLastChanged,
--                tnOamLTtraceAutoStorageType,
--                tnOamLTtraceAutoAdminState,
--                tnOamLTtraceAutoFcName,
--                tnOamLTtraceAutoProfile,
--                tnOamLTtraceAutoDiscIntvl,
--                tnOamLTtraceAutoMaxPath,
--                tnOamLTtraceAutoTrMaxTtl,
--                tnOamLTtraceAutoTrTimeOut,
--                tnOamLTtraceAutoTrMaxFailures,
--                tnOamLTtraceAutoPolicy1,
--                tnOamLTtraceAutoPolicy2,
--                tnOamLTtraceAutoPolicy3,
--                tnOamLTtraceAutoPolicy4,
--                tnOamLTtraceAutoPolicy5,
--                tnOamLTtraceAutoProbeIntvl,
--                tnOamLTtraceAutoPrTimeOut,
--                tnOamLTtraceAutoPrMaxFailures,
--                tnOamLTtraceAutoDiscoveryState,
--                tnOamLTtraceAutoTotalFecs,
--                tnOamLTtraceAutoDisFecs,
--                tnOamLTtraceAutoLastDisStart,
--                tnOamLTtraceAutoLastDisEnd,
--                tnOamLTtraceAutoLastDisDur,
--                tnOamLTtracePathProbeState,
--                tnOamLTtracePathProbeTmOutCnt,
--                tnOamLTtraceMaxConRequests
--             }
--     STATUS      obsolete
--     DESCRIPTION
--         "The group of objects supporting management of OAM Trace Route test
--          general capabilities on Nokia SROS series systems 5.0 release."
--     ::= { tnOamTrGroups 21 }

-- tnOamTrNotificationV5v0Group NOTIFICATION-GROUP
--     NOTIFICATIONS   {  tnOamTrPathChange,
--                        tnOamTrTestFailed,
--                        tnOamTrTestCompleted,
--                        tnOamLdpTtraceAutoDiscState,
--                        tnOamLdpTtraceFecProbeState,
--                        tnOamLdpTtraceFecDisStatus
--                     }
--     STATUS        current
--     DESCRIPTION
--         "The group of notifications supporting the OAM Trace Route test
--          feature on Nokia SROS series systems release 5.0."
--     ::= { tnOamTrGroups 22 }

-- tnOamVccvTrV6v0Group    OBJECT-GROUP
--     OBJECTS {   tnOamVccvTrCtlSdpIdVcId,
--                tnOamVccvTrCtlReplyMode,
--                tnOamVccvTrNextPwID,
--                tnOamVccvTrNextPwType,
--                tnOamVccvTrNextSenderAddrType,
--                tnOamVccvTrNextSenderAddr,
--                tnOamVccvTrNextRemoteAddrType,
--                tnOamVccvTrNextRemoteAddr
--             }
--     STATUS      current
--     DESCRIPTION
--         "The group of objects supporting management of OAM VCCV Trace Route
--          test general capabilities on Nokia SROS series systems 6.0
--         release."
--     ::= { tnOamTrGroups 23 }

-- tnOamVprnTrObsoleteV6v0Group OBJECT-GROUP
--     OBJECTS {
--               tnOamVprnTrNextHopRtrID
--             }
--     STATUS      current
--     DESCRIPTION
--         "The group of objects supporting management of OAM VPRN Trace Route
--          tests on Nokia SROS series systems that were made
--          obsolete in release 6.0."
--     ::={ tnOamTrGroups 24 }

-- tnOamVprnTrV6v0Group     OBJECT-GROUP
--     OBJECTS {  tnOamVprnTrCtlReplyControl,
--                tnOamVprnTrCtlSrcAddrType,
--                tnOamVprnTrCtlSrcAddress,
--                tnOamVprnTrL3MapRouterID,
--                tnOamVprnTrL3MapRteVprnLabel,
--                tnOamVprnTrL3MapRteMetrics,
--                tnOamVprnTrL3MapRteLastUp,
--                tnOamVprnTrL3MapRteOwner,
--                tnOamVprnTrL3MapRtePref,
--                tnOamVprnTrL3MapRteDist,
--                tnOamVprnTrL3MapNumNextHops,
--                tnOamVprnTrL3MapNumRteTargets,
--                tnOamVprnTrL3MapDestAddrType,
--                tnOamVprnTrL3MapDestAddress,
--                tnOamVprnTrL3MapDestMaskLen,
--                tnOamVprnTrNextHopType,
--                tnOamVprnTrNextHopTunnelID,
--                tnOamVprnTrNextHopTunnelType,
--                tnOamVprnTrNextHopIfIndex,
--                tnOamVprnTrNextHopAddrType,
--                tnOamVprnTrNextHopAddress,
--                tnOamVprnTrRouteTarget
--             }
--     STATUS        current
--     DESCRIPTION
--         "The group of objects supporting management of OAM VPRN Trace Route
--          tests on Nokia SROS series systems release 6.0."
--     ::= { tnOamTrGroups 25 }

-- tnOamP2mpLspTraceGroup         OBJECT-GROUP
--     OBJECTS {
--               tnOamP2mpLspTrCtlInstName,
--               tnOamP2mpLspTrCtlLeafIpAddr,
--               tnOamP2mpLspTrCtlLeafIpAddrType,
--               tnOamP2mpLspTrCtlLspName,
--               tnOamP2mpLspTrMapAddrType,
--               tnOamP2mpLspTrMapDSIPv4Addr,
--               tnOamP2mpLspTrMapDSIfAddr,
--               tnOamP2mpLspTrMapMTU,
--               tnOamP2mpLspTrMapP2mpBranch,
--               tnOamP2mpLspTrMapP2mpBud,
--               tnOamP2mpLspTrDSLabelLabel,
--               tnOamP2mpLspTrDSLabelProtocol
--             }
--     STATUS       current
--     DESCRIPTION
--         "The group of objects supporting management of OAM P2MP LSP Trace Route
--          tests on Nokia SROS series systems release 7.0."
--     ::= { tnOamTrGroups 26 }

-- tnOamTrGeneralV6v0Group   OBJECT-GROUP
--     OBJECTS {  tnOamTrMaxConcurrentRequests,
--                tnOamTrCtlRowStatus,
--                tnOamTrCtlStorageType,
--                tnOamTrCtlDescr,
--                tnOamTrCtlTestMode,
--                tnOamTrCtlAdminStatus,
--                tnOamTrCtlFcName,
--                tnOamTrCtlProfile,
--                tnOamTrCtlServiceId,
--                tnOamTrCtlDataSize,
--                tnOamTrCtlTimeOut,
--                tnOamTrCtlProbesPerHop,
--                tnOamTrCtlMaxTtl,
--                tnOamTrCtlInitialTtl,
--                tnOamTrCtlDSField,
--                tnOamTrCtlMaxFailures,
--                tnOamTrCtlInterval,
--                tnOamTrCtlTrapGeneration,
--                tnOamTrCtlSAA,
--                tnOamTrCtlRuns,
--                tnOamTrCtlFailures,
--                tnOamTrCtlLastRunResult,
--                tnOamTrCtlLastChanged,
--                tnOamTrCtlVRtrID,
--                tnOamTrCtlTgtAddrType,
--                tnOamTrCtlTgtAddress,
--                tnOamTrCtlSrcAddrType,
--                tnOamTrCtlSrcAddress,
--                tnOamTrCtlWaitMilliSec,
--                tnOamTrResultsOperStatus,
--                tnOamTrResultsCurHopCount,
--                tnOamTrResultsCurProbeCount,
--                tnOamTrResultsLastGoodPath,
--                tnOamTrResultsTgtAddrType,
--                tnOamTrResultsTgtAddress,
--                tnOamTrProbeHistoryResponse,
--                tnOamTrProbeHistoryOneWayTime,
--                tnOamTrProbeHistoryStatus,
--                tnOamTrProbeHistoryLastRC,
--                tnOamTrProbeHistoryTime,
--                tnOamTrProbeHistoryResponsePlane,
--                tnOamTrProbeHistoryAddressType,
--                tnOamTrProbeHistorySapId,
--                tnOamTrProbeHistoryVersion,
--                tnOamTrProbeHistoryRouterID,
--                tnOamTrProbeHistoryIfIndex,
--                tnOamTrProbeHistoryDataLen,
--                tnOamTrProbeHistorySize,
--                tnOamTrProbeHistoryInOneWayTime,
--                tnOamTrProbeHistoryAddrType,
--                tnOamTrProbeHistoryAddress,
--                tnOamLTtraceFecDiscoveryState,
--                tnOamLTtraceFecDisStatusBits,
--                tnOamLTtraceFecDisPaths,
--                tnOamLTtraceFecFailedHops,
--                tnOamLTtraceFecLastDisEnd,
--                tnOamLTtraceFecFailedProbes,
--                tnOamLTtraceFecProbeState,
--                tnOamLTtracePathRemAddrType,
--                tnOamLTtracePathRemoteAddr,
--                tnOamLTtracePathEgrNhAddrType,
--                tnOamLTtracePathEgrNhAddr,
--                tnOamLTtracePathDisTtl,
--                tnOamLTtracePathLastDisTime,
--                tnOamLTtracePathLastRc,
--                tnOamLTtracePathProbeState,
--                tnOamLTtraceCtlLdpPrefixType,
--                tnOamLTtraceCtlLdpPrefix,
--                tnOamLTtraceCtlLdpPrefixLen,
--                tnOamLTtraceCtlMaxPath,
--                tnOamLTtraceResultsDisPaths,
--                tnOamLTtraceResultsFailedHops,
--                tnOamLTtraceResultsDisState,
--                tnOamLTtraceResultsDisStatus,
--                tnOamLTtraceUpStreamHopIndex,
--                tnOamLTtraceHopAddrType,
--                tnOamLTtraceHopAddr,
--                tnOamLTtraceHopDstAddrType,
--                tnOamLTtraceHopDstAddr,
--                tnOamLTtraceHopEgrNhAddrType,
--                tnOamLTtraceHopEgrNhAddr,
--                tnOamLTtraceHopDisTtl,
--                tnOamLTtraceHopLastRc,
--                tnOamLTtraceHopDiscoveryState,
--                tnOamLTtraceHopDiscoveryTime,
--                tnOamLTtraceAutoRowStatus,
--                tnOamLTtraceAutoLastChanged,
--                tnOamLTtraceAutoStorageType,
--                tnOamLTtraceAutoAdminState,
--                tnOamLTtraceAutoFcName,
--                tnOamLTtraceAutoProfile,
--                tnOamLTtraceAutoDiscIntvl,
--                tnOamLTtraceAutoMaxPath,
--                tnOamLTtraceAutoTrMaxTtl,
--                tnOamLTtraceAutoTrTimeOut,
--                tnOamLTtraceAutoTrMaxFailures,
--                tnOamLTtraceAutoPolicy1,
--                tnOamLTtraceAutoPolicy2,
--                tnOamLTtraceAutoPolicy3,
--                tnOamLTtraceAutoPolicy4,
--                tnOamLTtraceAutoPolicy5,
--                tnOamLTtraceAutoProbeIntvl,
--                tnOamLTtraceAutoPrTimeOut,
--                tnOamLTtraceAutoPrMaxFailures,
--                tnOamLTtraceAutoDiscoveryState,
--                tnOamLTtraceAutoTotalFecs,
--                tnOamLTtraceAutoDisFecs,
--                tnOamLTtraceAutoLastDisStart,
--                tnOamLTtraceAutoLastDisEnd,
--                tnOamLTtraceAutoLastDisDur,
--                tnOamLTtracePathProbeState,
--                tnOamLTtracePathProbeTmOutCnt,
--                tnOamLTtraceMaxConRequests
--             }
--     STATUS      obsolete
--     DESCRIPTION
--         "The group of objects supporting management of OAM Trace Route test
--          general capabilities on Nokia SROS series systems 6.0
--          release."
--     ::= { tnOamTrGroups 27 }

-- tnOamTrObsoleteV6v0Group OBJECT-GROUP
--     OBJECTS {  tnOamTrCtlCreateHopsEntries,
--                tnOamLspTrCtlVRtrID,
--                tnOamTrCtlMaxRows
--             }
--     STATUS      current
--     DESCRIPTION
--         "The group of objects supporting management of OAM trace route
--          operations on Nokia SR series systems that were made
--          obsolete in release 6.0.
--          Please see tnOamVprnTrObsoleteV6v0Group for additional
--          obsoleted objects."
--     ::= { tnOamTrGroups 28 }

-- tnOamTrGeneralV7v0Group   OBJECT-GROUP
--     OBJECTS {  tnOamTrMaxConcurrentRequests,
--                tnOamTrCtlRowStatus,
--                tnOamTrCtlStorageType,
--                tnOamTrCtlDescr,
--                tnOamTrCtlTestMode,
--                tnOamTrCtlAdminStatus,
--                tnOamTrCtlFcName,
--                tnOamTrCtlProfile,
--                tnOamTrCtlServiceId,
--                tnOamTrCtlDataSize,
--                tnOamTrCtlTimeOut,
--                tnOamTrCtlProbesPerHop,
--                tnOamTrCtlMaxTtl,
--                tnOamTrCtlInitialTtl,
--                tnOamTrCtlDSField,
--                tnOamTrCtlMaxFailures,
--                tnOamTrCtlInterval,
--                tnOamTrCtlTrapGeneration,
--                tnOamTrCtlSAA,
--                tnOamTrCtlRuns,
--                tnOamTrCtlFailures,
--                tnOamTrCtlLastRunResult,
--                tnOamTrCtlLastChanged,
--                tnOamTrCtlVRtrID,
--                tnOamTrCtlTgtAddrType,
--                tnOamTrCtlTgtAddress,
--                tnOamTrCtlSrcAddrType,
--                tnOamTrCtlSrcAddress,
--                tnOamTrCtlWaitMilliSec,
--                tnOamTrResultsOperStatus,
--                tnOamTrResultsCurHopCount,
--                tnOamTrResultsCurProbeCount,
--                tnOamTrResultsLastGoodPath,
--                tnOamTrResultsTgtAddrType,
--                tnOamTrResultsTgtAddress,
--                tnOamTrProbeHistoryResponse,
--                tnOamTrProbeHistoryOneWayTime,
--                tnOamTrProbeHistoryStatus,
--                tnOamTrProbeHistoryLastRC,
--                tnOamTrProbeHistoryTime,
--                tnOamTrProbeHistoryResponsePlane,
--                tnOamTrProbeHistoryAddressType,
--                tnOamTrProbeHistorySapId,
--                tnOamTrProbeHistoryVersion,
--                tnOamTrProbeHistoryRouterID,
--                tnOamTrProbeHistoryIfIndex,
--                tnOamTrProbeHistoryDataLen,
--                tnOamTrProbeHistorySize,
--                tnOamTrProbeHistoryInOneWayTime,
--                tnOamTrProbeHistoryAddrType,
--                tnOamTrProbeHistoryAddress,
--                tnOamLTtraceFecDiscoveryState,
--                tnOamLTtraceFecDisStatusBits,
--                tnOamLTtraceFecDisPaths,
--                tnOamLTtraceFecFailedHops,
--                tnOamLTtraceFecLastDisEnd,
--                tnOamLTtraceFecFailedProbes,
--                tnOamLTtraceFecProbeState,
--                tnOamLTtracePathRemAddrType,
--                tnOamLTtracePathRemoteAddr,
--                tnOamLTtracePathEgrNhAddrType,
--                tnOamLTtracePathEgrNhAddr,
--                tnOamLTtracePathDisTtl,
--                tnOamLTtracePathLastDisTime,
--                tnOamLTtracePathLastRc,
--                tnOamLTtracePathProbeState,
--                tnOamLTtraceCtlLdpPrefixType,
--                tnOamLTtraceCtlLdpPrefix,
--                tnOamLTtraceCtlLdpPrefixLen,
--                tnOamLTtraceCtlMaxPath,
--                tnOamLTtraceResultsDisPaths,
--                tnOamLTtraceResultsFailedHops,
--                tnOamLTtraceResultsDisState,
--                tnOamLTtraceResultsDisStatus,
--                tnOamLTtraceUpStreamHopIndex,
--                tnOamLTtraceHopAddrType,
--                tnOamLTtraceHopAddr,
--                tnOamLTtraceHopDstAddrType,
--                tnOamLTtraceHopDstAddr,
--                tnOamLTtraceHopEgrNhAddrType,
--                tnOamLTtraceHopEgrNhAddr,
--                tnOamLTtraceHopDisTtl,
--                tnOamLTtraceHopLastRc,
--                tnOamLTtraceHopDiscoveryState,
--                tnOamLTtraceHopDiscoveryTime,
--                tnOamLTtraceAutoRowStatus,
--                tnOamLTtraceAutoLastChanged,
--                tnOamLTtraceAutoStorageType,
--                tnOamLTtraceAutoAdminState,
--                tnOamLTtraceAutoFcName,
--                tnOamLTtraceAutoProfile,
--                tnOamLTtraceAutoDiscIntvl,
--                tnOamLTtraceAutoMaxPath,
--                tnOamLTtraceAutoTrMaxTtl,
--                tnOamLTtraceAutoTrTimeOut,
--                tnOamLTtraceAutoTrMaxFailures,
--                tnOamLTtraceAutoPolicy1,
--                tnOamLTtraceAutoPolicy2,
--                tnOamLTtraceAutoPolicy3,
--                tnOamLTtraceAutoPolicy4,
--                tnOamLTtraceAutoPolicy5,
--                tnOamLTtraceAutoProbeIntvl,
--                tnOamLTtraceAutoPrTimeOut,
--                tnOamLTtraceAutoPrMaxFailures,
--                tnOamLTtraceAutoDiscoveryState,
--                tnOamLTtraceAutoTotalFecs,
--                tnOamLTtraceAutoDisFecs,
--                tnOamLTtraceAutoLastDisStart,
--                tnOamLTtraceAutoLastDisEnd,
--                tnOamLTtraceAutoLastDisDur,
--                tnOamLTtracePathProbeState,
--                tnOamLTtracePathProbeTmOutCnt,
--                tnOamLTtraceMaxConRequests,
--                tnOamTrHopsRttOFSumSquares,
--                tnOamTrHopsRttHCSumSquares,
--                tnOamTrHopsTtOFSumSquares,
--                tnOamTrHopsTtHCSumSquares,
--                tnOamTrHopsInTtOFSumSqrs,
--                tnOamTrHopsInTtHCSumSqrs,
--                tnOamTrResultsTestRunResult
--             }
--     STATUS      current
--     DESCRIPTION
--         "The group of objects supporting management of OAM Trace Route test
--          general capabilities on Nokia SROS series systems 7.0
--          release."
--     ::= { tnOamTrGroups 29 }

-- tnOamEthCfmTrV8v0Group     OBJECT-GROUP
--     OBJECTS {  tnOamEthCfmTrCtlTgtMacAddr,
--                tnOamEthCfmTrCtlSrcMdIndex,
--                tnOamEthCfmTrCtlSrcMaIndex,
--                tnOamEthCfmTrCtlSrcMepId,
--                tnOamEthCfmTrPrHistIngressMac,
--                tnOamEthCfmTrPrHistEgressMac,
--                tnOamEthCfmTrPrHistRelayAction,
--                tnOamEthCfmTrPrHistForwarded,
--                tnOamEthCfmTrPrHistTerminalMep
--             }
--     STATUS      current
--     DESCRIPTION
--         "The group of objects supporting management of OAM Ethernet CFM trace
--          route tests on Nokia SROS series systems 8.0 release."
--     ::= { tnOamTrGroups 30 }

-- tnOamLspTrV6v0Group     OBJECT-GROUP
--     OBJECTS {  tnOamLspTrCtlLspName,
--                tnOamLspTrCtlPathName,
--                tnOamLspTrCtlLdpPrefixType,
--                tnOamLspTrCtlLdpPrefix,
--                tnOamLspTrCtlLdpPrefixLen,
--                tnOamLspTrCtlPathDestType,
--                tnOamLspTrCtlPathDest,
--                tnOamLspTrCtlNhIntfName,
--                tnOamLspTrCtlNhAddressType,
--                tnOamLspTrCtlNhAddress,
--                tnOamLspTrMapAddrType,
--                tnOamLspTrMapDSIPv4Addr,
--                tnOamLspTrMapDSIfAddr,
--                tnOamLspTrMapMTU,
--                tnOamLspTrDSLabelLabel,
--                tnOamLspTrDSLabelProtocol
--             }
--     STATUS       current
--     DESCRIPTION
--         "The group of objects supporting management of OAM LSP Trace Route
--          tests on Nokia SROS series systems 6.0 release."
--     ::= { tnOamTrGroups 31 }

-- tnOamTrGeneralV8v0Group   OBJECT-GROUP
--     OBJECTS {  tnOamLTtracePathProbeSendErr,
--                tnOamLTtraceFecSendErrProbes
--             }
--     STATUS      current
--     DESCRIPTION
--         "The group of objects supporting management of OAM Trace Route test
--          general capabilities on Nokia SROS series systems 8.0
--          release."
--     ::= { tnOamTrGroups 32 }

-- tnOamTrNotificationV8v0Group NOTIFICATION-GROUP
--     NOTIFICATIONS   {  tnOamLdpTtraceFecPFailUpdate
--                     }
--     STATUS        current
--     DESCRIPTION
--         "The group of notifications supporting the OAM Trace Route test
--          feature on Nokia SROS series systems release 8.0."
--     ::= { tnOamTrGroups 33 }

-- tnOamVccvTrV9v0Group    OBJECT-GROUP
--     OBJECTS {
--                tnOamVccvTrCtlSpokeSdpId,
--                tnOamVccvTrCtlSaiiGlobalId,
--                tnOamVccvTrCtlSaiiPrefix,
--                tnOamVccvTrCtlSaiiAcId,
--                tnOamVccvTrCtlTaiiGlobalId,
--                tnOamVccvTrCtlTaiiPrefix,
--                tnOamVccvTrCtlTaiiAcId,
--                tnOamVccvTrNextSaiiGlobalId,
--                tnOamVccvTrNextSaiiPrefix,
--                tnOamVccvTrNextSaiiAcId,
--                tnOamVccvTrNextTaiiGlobalId,
--                tnOamVccvTrNextTaiiPrefix,
--                tnOamVccvTrNextTaiiAcId
--             }
--     STATUS      current
--     DESCRIPTION
--         "The group of addtional objects supporting management of OAM VCCV Trace
--          Route test general capabilities on Nokia SROS series 9.0
--          release."
--     ::= { tnOamTrGroups 34 }

-- tnOamLTtraceV9v0Group          OBJECT-GROUP
--     OBJECTS {
--                tnOamLTtraceHopLabel1,
--                tnOamLTtraceHopLabel2,
--                tnOamLTtraceHopLabel3,
--                tnOamLTtraceHopLabel4,
--                tnOamLTtraceHopLabel5,
--                tnOamLTtraceHopLabel6,
--                tnOamLTtraceHopIfAddrType,
--                tnOamLTtraceHopIfAddress,
--                tnOamLTtraceHopRouterIdType,
--                tnOamLTtraceHopRouterId
--             }
--     STATUS      current
--     DESCRIPTION
--         "The group of additional objects supporting management of OAM LDP
--          Tree Discovery capabilities on Nokia SROS series 9.0 release."
--     ::= { tnOamTrGroups 35 }
--
--      OAM SAA Test Groups
--
-- tnOamSaaGeneralV3v0Group   OBJECT-GROUP
--     OBJECTS {   tnOamSaaCtlRowStatus,
--                tnOamSaaCtlStorageType,
--                tnOamSaaCtlLastChanged,
--                tnOamSaaCtlAdminStatus,
--                tnOamSaaCtlTestMode,
--                tnOamSaaCtlDescr,
--                tnOamSaaCtlRuns,
--                tnOamSaaCtlFailures,
--                tnOamSaaCtlLastRunResult
--             }
--     STATUS      obsolete
--     DESCRIPTION
--         "The group of objects supporting management of OAM SAA test
--          general capabilities on Nokia SROS series systems."
--     ::= { tnOamSaaGroups 1 }

-- tnOamSaaThresholdV3v0Group     OBJECT-GROUP
--     OBJECTS {   tnOamSaaTRowStatus,
--                 tnOamSaaTLastChanged,
--                 tnOamSaaTThreshold,
--                 tnOamSaaTValue,
--                 tnOamSaaTLastSent,
--                 tnOamSaaTTestMode,
--                 tnOamSaaTTestRunIndex
--             }
--     STATUS        current
--     DESCRIPTION
--         "The group of objects supporting management of OAM Trace Route
--          SAA tests thresholds on Nokia SROS series systems 3.0R1."
--     ::= { tnOamSaaGroups 2 }

-- tnOamSaaNotificationV3v0Group NOTIFICATION-GROUP
--     NOTIFICATIONS   {  tnOamSaaThreshold
--                     }
--     STATUS        current
--     DESCRIPTION
--         "The group of notifications supporting the OAM Trace Route test
--          feature on Nokia SROS series systems."
--     ::= { tnOamSaaGroups 3 }

-- tnOamSaaGeneralV7v0Group   OBJECT-GROUP
--     OBJECTS {   tnOamSaaCtlRowStatus,
--                 tnOamSaaCtlStorageType,
--                 tnOamSaaCtlLastChanged,
--                 tnOamSaaCtlAdminStatus,
--                 tnOamSaaCtlTestMode,
--                 tnOamSaaCtlDescr,
--                 tnOamSaaCtlRuns,
--                 tnOamSaaCtlFailures,
--                 tnOamSaaCtlLastRunResult,
--                 tnOamSaaCtlAcctPolicyId,
--                 tnOamSaaCtlSuppressAccounting
--             }
--     STATUS      current
--     DESCRIPTION
--         "The group of objects supporting management of OAM SAA test
--          general capabilities on Nokia SROS series systems 7.0 release."
--     ::= { tnOamSaaGroups 4 }

-- tnOamSaaGeneralV8v0Group   OBJECT-GROUP
--     OBJECTS {   tnOamSaaCtlContinuous
--             }
--     STATUS      current
--     DESCRIPTION
--         "The group of additional objects supporting management of OAM SAA test
--          general capabilities on Nokia SROS series systems 8.0
--          release."
--     ::= { tnOamSaaGroups 5 }

--
--      OAM General Groups
--

-- tnOamGeneralV8v0Group   OBJECT-GROUP
--     OBJECTS {
--         tnOamMplsPduTimeStampFormat
--     }
--     STATUS      current
--     DESCRIPTION
--         "The group of objects supporting management of OAM test general
--          capabilities on Nokia SROS systems, release 8.0 R4."
--     ::= { tnOamGeneralGroups 1 }

 --
 -- Dummy Scalars
 --

 tnOamTestScalar1 OBJECT-TYPE
     SYNTAX      Unsigned32
     MAX-ACCESS  read-only
     STATUS      current
     DESCRIPTION
         "A dummy scalar that satisfies a SNMP get request quickly.Otherwise,
     it has to traverse the remaining MIB to get to the next applicable
          item."
     ::= { tnOamTestObjs 101 }

 tnOamTestScalar2 OBJECT-TYPE
     SYNTAX      Unsigned32
     MAX-ACCESS  read-only
     STATUS      current
     DESCRIPTION
         "."
     ::= { tnOamTestObjs 102 }
END

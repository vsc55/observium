TN-FILTER-MIB DEFINITIONS ::= BEGIN

-- (c) Copyright 2021 Nokia Networks.  All rights reserved.
-- This software is the confidential and proprietary property of
-- Nokia and may only be used in accordance with the terms of the
-- license agreement provided with this software.

IMPORTS
    MODULE-IDENTITY, OBJECT-TYPE,
--  NOTIFICATION-TYPE,
    Unsigned32, Integer32, Counter64
--  IpAddress, Counter32,
--  Gauge32, TimeTicks, Opaque
        FROM SNMPv2-SMI

--  MODULE-COMPLIANCE, OBJECT-GROUP, NOTIFICATION-GROUP
--      FROM SNMPv2-CONF

    TEXTUAL-CONVENTION, RowStatus, MacAddress,
    TruthValue, DisplayString
--  TimeStamp, RowPointer

        FROM SNMPv2-TC

    tnSRMIBModules, tnSRObjs, tnSRNotifyPrefix
        FROM TROPIC-GLOBAL-REG

--  TmnxAdminState, TmnxOperState, TNamedItem,
    TNamedItemOrEmpty, Dot1PPriority,
--  IpAddressPrefixLength,
    ServiceAccessPoint, TItemDescription, TDSCPNameOrEmpty,
--  TDSCPFilterActionValue, TIpProtocol, TIpOption,
--  TTcpUdpPort, TTcpUdpPortOperator,
    TFrameType, TmnxServId, TmnxPortID, TmnxEncapVal,
    SdpBindId, TEntryId,
--  TItemMatch, TEntryIndicator,
    TMacFilterType, TItemScope, TLNamedItemOrEmpty, TMACFilterID
        FROM TN-TC-MIB

    tnSysSwitchId
       FROM TROPIC-SYSTEM-MIB

--  InetAddressIPv6,InetAddressPrefixLength
--      FROM INET-ADDRESS-MIB

    tnSvcId
        FROM TN-SERV-MIB

    tnSapPortId, tnSapEncapValue
        FROM TN-SAP-MIB
    ;

tnFilterMIBModule   MODULE-IDENTITY
        LAST-UPDATED    "201611280000Z"
        ORGANIZATION    "Nokia"
        CONTACT-INFO
            "Nokia 7x50 Support
             Web: http://www.nokia.com/comps/pages/carrier_support.jhtml"
        DESCRIPTION
        "This document is the SNMP MIB module to manage and provision
         Filter features on Nokia 7x50 systems.

         This SNMP MIB module (Specification) embodies Nokia's
         proprietary intellectual property.  Nokia retains
         all title and ownership in the Specification, including any
         revisions.

         Nokia grants all interested parties a non-exclusive
         license to use and distribute an unmodified copy of this
         Specification in connection with management of Nokia
         products, and without fee, provided this copyright notice and
         license appear on all copies.

         This Specification is supplied 'as is', and Nokia
         makes no warranty, either express or implied, as to the use,
         operation, condition, or performance of the Specification."

--
--  Revision History
--
        REVISION        "201611280000Z"
        DESCRIPTION     "Moved the following textual conventions to TN-TC-MIB:
                         TFilterID
                         TIPFilterID
                         TMACFilterID."

        REVISION        "201410170000Z"
        DESCRIPTION     "1) Added the following to tnMacFilterTable:
                            tnMacFilterApplied
                            tnMacFilterNumEntries.
                         2) Added the following table:
                            tnMacFilterAssociationTable."

        REVISION        "201308220000Z"
        DESCRIPTION     "Added the following to tnMacFilterTable:
                         tnMacFilterType
                         tnMacFilterName."

        REVISION        "201212050000Z"
        DESCRIPTION     "Commented out unsupported MIB tables and
                         attributes for 1830."

        REVISION        "200807010000Z"
        DESCRIPTION     "Rev 6.1                01 Jul 2008 00:00
                         6.1 release of the TIMETRA-FILTER-MIB."

        REVISION        "200801010000Z"
        DESCRIPTION     "Rev 6.0                01 Jan 2008 00:00
                         6.0 release of the TIMETRA-FILTER-MIB."

        REVISION        "200701010000Z"
        DESCRIPTION     "Rev 5.0                01 Jan 2007 00:00
                         5.0 release of the TIMETRA-FILTER-MIB."

        REVISION        "200602280000Z"
        DESCRIPTION     "Rev 4.0                28 Feb 2006 00:00
                         4.0 release of the TIMETRA-FILTER-MIB."

        REVISION        "200508310000Z"
        DESCRIPTION     "Rev 3.0                31 Aug 2005 00:00
                         3.0 release of the TIMETRA-FILTER-MIB."

        REVISION        "200501240000Z"
        DESCRIPTION     "Rev 2.1                24 Jan 2005 00:00
                         2.1 release of the TIMETRA-FILTER-MIB."

        REVISION        "200401150000Z"
        DESCRIPTION     "Rev 2.0                15 Jan 2004 00:00
                         2.0 release of the TIMETRA-FILTER-MIB."

        REVISION        "200308150000Z"
        DESCRIPTION     "Rev 1.2                15 Aug 2003 00:00
                         1.2 release of the TIMETRA-FILTER-MIB."

        REVISION        "200301290000Z"
        DESCRIPTION     "Rev 0.1                29 Jan 2003 00:00
                         Initial version of the TIMETRA-FILTER-MIB."

        ::= { tnSRMIBModules 21 }

tnFilterObjects             OBJECT IDENTIFIER ::= { tnSRObjs 21 }
-- tnFilterNotificationsPrefix       OBJECT IDENTIFIER ::= { tnSRNotifyPrefix 21 }
-- tnFilterNotifications                OBJECT IDENTIFIER ::= { tnFilterNotificationsPrefix 0 }
-- tnFilterMIBConformance      OBJECT IDENTIFIER ::= { tnSRConfs 21 }

-- tnFilterNotificationObjects OBJECT IDENTIFIER ::= { tnFilterObjects 8 }
-- tnFilterTimeStampObjects    OBJECT IDENTIFIER ::= { tnFilterObjects 9 }

--
-- TEXTUAL-CONVENTIONs for Nokia 7x50 SR series Filter Elements
--

-- TItemScope ::= TEXTUAL-CONVENTION
--     STATUS       current
--     DESCRIPTION
--         "This textual-convention determines some aspects of an item's
--          behavior regarding creation and use, unused entry garbage collection,
--          and automated promulgation by Element Management System to
--          other systems in the service domain.
--
--          TItemScope applies to SAP-ingress, SAP-egress, and Network policies,
--          and to IP filters and MAC filters.
--
--          exclusive:
--
--             When the scope of an item is defined as exclusive, the item can
--             only be applied once, for example to a single SAP.  Attempting
--             to assign the policy to a second SAP is not allowed and will
--             result in an error.  If the item is removed from the exclusive
--             SAP, it will become available for assignment to another
--             exclusive SAP.
--
--             A non-applied exclusive scope policy is a candidate to be removed
--             from the system by a TBD garbage collection command.
--
--             The system default policies cannot be put into the exclusive scope.
--             An error will be generated if scope exclusive is executed in
--             any policies with a policy-id equal to 1.
--
--          template:
--
--             When the scope of an item is defined as template, the item can be
--             applied any number of times.  Policies with template scope
--             will not be considered for deletion by a TBD garbage collection
--             command; all items of scope 'template' must be deleted explicitly.
--
--             The system default policies will always be scope template.
--             An error will occur if a policy-id 1 is attempted to be
--             set to scope exclusive."
--     SYNTAX INTEGER { exclusive(1), template(2) }

-- TItemMatch  ::= TEXTUAL-CONVENTION
--     STATUS       current
--     DESCRIPTION
--         "when set to off, the item is not matched.
--          when set to false, packets without the item match the filter.
--          when set to true, packets with the item match the filter."
--     SYNTAX INTEGER { off(1), false(2), true(3) }

-- TEntryIndicator ::= TEXTUAL-CONVENTION
--     STATUS       current
--     DESCRIPTION
--         "Uniquely identifies an entry in a policy or filter table. The
--          value 0 is not a valid entry-id. When used as insertion point
--          the value 0 indicates that entries must be inserted at the very
--          beginning, i.e.before the first entry defined."
--     SYNTAX Unsigned32 (0..65535)

-- TEntryId ::= TEXTUAL-CONVENTION
--     STATUS       current
--     DESCRIPTION
--         "uniquely identifies an entry in a policy or filter table.
--         to facilitate insertion of entries in the tables, we recommend
--         assigning entry IDs by 10s:  10, 20, 30, etc.
--         "
--     SYNTAX TEntryIndicator (1..65535)

-- TEntryIdOrZero ::= TEXTUAL-CONVENTION
--     STATUS       current
--     DESCRIPTION
--         "uniquely identifies an entry in a policy or filter table.
--         to facilitate insertion of entries in the tables, we recommend
--         assigning entry IDs by 10s:  10, 20, 30, etc.
--         The value 0, means that the object does not refer to a filter
--         entry at this time.
--         "
--     SYNTAX TEntryIndicator (0..65535)

TFilterAction ::= TEXTUAL-CONVENTION
    STATUS       current
    DESCRIPTION
        "action to take on the traffic when no filter entry matches.

        when set to drop(1), packets matching the filter entry are dropped.

        when set to forward(2), packets matching the filter entry are forwarded.
        "
    SYNTAX INTEGER { drop(1), forward(2), httpRedirect(4) }

TFilterActionOrDefault ::= TEXTUAL-CONVENTION
    STATUS       current
    DESCRIPTION
        "action to take on the traffic when the filter entry matches.

        when set to drop(1), packets matching the filter entry are dropped.

        when set to forward(2), packets matching the filter entry are forwarded.

        when set to default(3), packets matching the filter entry are dropped.
        "
    SYNTAX INTEGER { drop(1), forward(2), default(3), httpRedirect(4) }

TFilterLogId ::= TEXTUAL-CONVENTION
    STATUS       current
    DESCRIPTION
        "uniquely identifies an entry in the filter log table. 0 indicates an
         invalid log-id."
    SYNTAX Unsigned32 (0 | 101..199)

-- TFilterLogDestination ::= TEXTUAL-CONVENTION
--     STATUS       current
--     DESCRIPTION
--         "determines the location where filtered packets are logged."
--     SYNTAX INTEGER { memory(1), syslog(2), file(3) }

TTimeRangeState ::= TEXTUAL-CONVENTION
    STATUS       current
    DESCRIPTION
        "The textual convention TTimeRangeState is used to indicate the state
         of an object that is controlled by a time range.
         - timeRangeNotApplic:
           no time range is applicable for this entry.
         - timeRangeNotActive:
           A time range is defined but is not active at this moment.
         - timeRangeActive.
           A time range is defined, and is activated successfully.
         - timeRangeActiveDownloadFailed:
           A time range is defined and is activated, but the corresponding
           object could not be installed due to resource problems."
    SYNTAX INTEGER { timeRangeNotApplic(0),
                     timeRangeNotActive(1),
                     timeRangeActive(2),
                     timeRangeActiveDownloadFailed(3) }

-- TFilterLogSummaryCriterium ::= TEXTUAL-CONVENTION
--     STATUS       current
--     DESCRIPTION
--         "Indicates the field on which log summarisation will be done.
--          - when set to srcAddr, received log packets are summarized
--            based on the src ip/mac-addr
--          - when set to dstAddr, received log packets are summarized
--            based on the dst ip/mac-addr"
--
--     SYNTAX INTEGER { srcAddr  (0),
--                      dstAddr  (1) }

-- TFilterType ::= TEXTUAL-CONVENTION
--     STATUS       current
--     DESCRIPTION
--         "Type of filter."
--     SYNTAX INTEGER { fltrtypeselNone   (0),
--                      fltrtypeselIp     (1),
--                      fltrtypeselMac    (2),
--                      fltrtypeselCpm    (3),
--                      fltrtypeselIpv6   (4),
--                      fltrtypeselCpm6   (5),
--                      fltrtypeselCpmMac (6)
--                    }

--
-- mib objects
--

--
-- IP Filter Table
--

-- tnIPFilterTable OBJECT-TYPE
--     SYNTAX       SEQUENCE OF TIPFilterEntry
--     MAX-ACCESS   not-accessible
--     STATUS       current
--     DESCRIPTION
--         "Contains a List of all ip filters configured on this system."
--     ::= { tnFilterObjects 1 }
--
-- tnIPFilterEntry OBJECT-TYPE
--     SYNTAX       TIPFilterEntry
--     MAX-ACCESS   not-accessible
--     STATUS       current
--     DESCRIPTION
--         "Information about a particular IP Filter entry. Entries are
--          created/deleted  by user. Entries have a presumed StorageType of
--          nonVolatile."
--     INDEX { tnSysSwitchId, tnIPFilterId }
--     ::= { tnIPFilterTable 1 }
--
-- TIPFilterEntry ::= SEQUENCE
--     {
--         tnIPFilterId               TIPFilterID,
--         tnIPFilterRowStatus        RowStatus,
--         tnIPFilterScope            TItemScope,
--         tnIPFilterDescription      TItemDescription,
--         tnIPFilterDefaultAction    TFilterAction
--     }
--
-- tnIPFilterId  OBJECT-TYPE
--     SYNTAX       TIPFilterID (1..65535)
--     MAX-ACCESS   not-accessible
--     STATUS       current
--     DESCRIPTION
--         "Uniquely identifies an ip filter as configures on this system."
--     ::= { tnIPFilterEntry 1 }
--
-- tnIPFilterRowStatus  OBJECT-TYPE
--     SYNTAX       RowStatus
--     MAX-ACCESS   read-create
--     STATUS       current
--     DESCRIPTION
--         "This object allows entries to be created and deleted in the
--          tnIPFilterTable."
--     ::= { tnIPFilterEntry 2 }
--
-- tnIPFilterScope  OBJECT-TYPE
--     SYNTAX       TItemScope
--     MAX-ACCESS   read-create
--     STATUS       current
--     DESCRIPTION
--         "This object specifies the scope of this filter definition. If defined
--          as exclusive(1), this filter can be instantiated only once as compared
--          to the multiple instances that the filter can have if defined as
--          template(2)."
--     DEFVAL { template }
--     ::= { tnIPFilterEntry 3 }
--
-- tnIPFilterDescription  OBJECT-TYPE
--     SYNTAX       TItemDescription
--     MAX-ACCESS   read-create
--     STATUS       current
--     DESCRIPTION
--         "User-provided description for this filter."
--     DEFVAL { ''H }
--     ::= { tnIPFilterEntry 4 }
--
-- tnIPFilterDefaultAction  OBJECT-TYPE
--     SYNTAX       TFilterAction
--     MAX-ACCESS   read-create
--     STATUS       current
--     DESCRIPTION
--         "The action to take for packets that do not match any filter entries."
--     DEFVAL { drop }
--     ::= { tnIPFilterEntry 5 }

--
-- IP Filter Entry parameters
--

-- tnIPFilterParamsTable OBJECT-TYPE
--     SYNTAX       SEQUENCE OF TIPFilterParamsEntry
--     MAX-ACCESS   not-accessible
--     STATUS       current
--     DESCRIPTION  "A table of all IP filter match entries for all IP filters."
--     ::= { tnFilterObjects 2 }
--
-- tnIPFilterParamsEntry OBJECT-TYPE
--     SYNTAX       TIPFilterParamsEntry
--     MAX-ACCESS   not-accessible
--     STATUS       current
--     DESCRIPTION
--         "Information about a particular IP Filter entry.
--         Every IP Filter can have zero or more IP Filter match entries.
--
--         a filter entry with no match criteria set will match every
--         packet, and the entry action will be taken.
--
--         Entries are created/deleted by user.
--
--         There is no StorageType object, entries have a presumed
--         StorageType of nonVolatile.
--         "
--     INDEX { tnSysSwitchId, tnIPFilterId, tnIPFilterParamsIndex }
--     ::= { tnIPFilterParamsTable 1 }
--
-- TIPFilterParamsEntry ::= SEQUENCE
--     {
--         tnIPFilterParamsIndex               TEntryId,
--         tnIPFilterParamsRowStatus           RowStatus,
--         tnIPFilterParamsLogId               TFilterLogId,
--         tnIPFilterParamsDescription         TItemDescription,
--         tnIPFilterParamsAction              TFilterActionOrDefault,
--         tnIPFilterParamsForwardNH           IpAddress,
--         tnIPFilterParamsForwardNHIndirect   TruthValue,
--         tnIPFilterParamsRemarkDSCP          TDSCPFilterActionValue,
--         tnIPFilterParamsRemarkDSCPMask      TDSCPFilterActionValue,
--         tnIPFilterParamsRemarkDot1p         Dot1PPriority,
--         tnIPFilterParamsSourceIpAddr        IpAddress,
--         tnIPFilterParamsSourceIpMask        IpAddressPrefixLength,
--         tnIPFilterParamsDestinationIpAddr   IpAddress,
--         tnIPFilterParamsDestinationIpMask   IpAddressPrefixLength,
--         tnIPFilterParamsProtocol            TIpProtocol,
--         tnIPFilterParamsSourcePortValue1    TTcpUdpPort,
--         tnIPFilterParamsSourcePortValue2    TTcpUdpPort,
--         tnIPFilterParamsSourcePortOperator  TTcpUdpPortOperator,
--         tnIPFilterParamsDestPortValue1      TTcpUdpPort,
--         tnIPFilterParamsDestPortValue2      TTcpUdpPort,
--         tnIPFilterParamsDestPortOperator    TTcpUdpPortOperator,
--         tnIPFilterParamsDSCP                TDSCPNameOrEmpty,
--         tnIPFilterParamsFragment            TItemMatch,
--         tnIPFilterParamsOptionPresent       TItemMatch,
--         tnIPFilterParamsIpOptionValue       TIpOption,
--         tnIPFilterParamsIpOptionMask        TIpOption,
--         tnIPFilterParamsMultipleOption      TItemMatch,
--         tnIPFilterParamsTcpSyn              TItemMatch,
--         tnIPFilterParamsTcpAck              TItemMatch,
--         tnIPFilterParamsIcmpCode            INTEGER,
--         tnIPFilterParamsIcmpType            INTEGER,
--         tnIPFilterParamsCflowdSample        TruthValue,
--         tnIPFilterParamsCflowdIfSample      TruthValue,
--         tnIPFilterParamsForwardNHInterface  DisplayString,
--         tnIPFilterParamsIngressHitCount     Counter64,
--         tnIPFilterParamsEgressHitCount      Counter64,
--         tnIPFilterParamsLogInstantiated     TruthValue,
--         tnIPFilterParamsForwardRedPlcy      TNamedItemOrEmpty,
--         tnIPFilterParamsActiveDest          IpAddress,
--         tnIPFilterParamsFwdSvcId            TmnxServId,
--         tnIPFilterParamsFwdSapPortId        TmnxPortID,
--         tnIPFilterParamsFwdSapEncapVal      TmnxEncapVal,
--         tnIPFilterParamsFwdSdpBind          SdpBindId,
--         tnIPFilterParamsTimeRangeName       TNamedItemOrEmpty,
--         tnIPFilterParamsTimeRangeState      TTimeRangeState,
--         tnIPFilterParamsRedirectURL         DisplayString,
--         tnIPFilterParamsSrcIpFullMask       IpAddress,
--         tnIPFilterParamsDestIpFullMask      IpAddress,
--         tnIPFilterParamsIngrHitByteCount    Counter64,
--         tnIPFilterParamsEgrHitByteCount     Counter64
--     }
--
-- tnIPFilterParamsIndex  OBJECT-TYPE
--     SYNTAX       TEntryId
--     MAX-ACCESS   not-accessible
--     STATUS       current
--     DESCRIPTION
--         "This is the secondary index for the entry. Every ip filter can have
--          multiple entries, therefore every ip filter entry is identified by
--          the tnIPFilterId and tnIPFilterParamsIndex."
--     ::= { tnIPFilterParamsEntry 1 }
--
-- tnIPFilterParamsRowStatus  OBJECT-TYPE
--     SYNTAX       RowStatus
--     MAX-ACCESS   read-create
--     STATUS       current
--     DESCRIPTION
--         "This object allows entries to be created and deleted in the
--          tnIPFilterParamsTable."
--     ::= { tnIPFilterParamsEntry 2 }
--
-- tnIPFilterParamsLogId  OBJECT-TYPE
--     SYNTAX       TFilterLogId
--     MAX-ACCESS   read-create
--     STATUS       current
--     DESCRIPTION
--         "This object specifies the log to use for packets that match
--          this entry. The value zero indicates that logging is disabled."
--     DEFVAL { 0 }
--     ::= { tnIPFilterParamsEntry 3 }
--
-- tnIPFilterParamsDescription  OBJECT-TYPE
--     SYNTAX       TItemDescription
--     MAX-ACCESS   read-create
--     STATUS       current
--     DESCRIPTION
--         "User-provided description for this filter entry."
--     DEFVAL { ''H }
--     ::= { tnIPFilterParamsEntry 4 }
--
-- tnIPFilterParamsAction  OBJECT-TYPE
--     SYNTAX       TFilterActionOrDefault
--     MAX-ACCESS   read-create
--     STATUS       current
--     DESCRIPTION
--         "The action to take for packets that match this filter entry. The value
--          default(3) specifies this entry to inherit the behavior defined as the
--          default for the filter."
--     DEFVAL { drop }
--     ::= { tnIPFilterParamsEntry 5 }
--
-- tnIPFilterParamsForwardNH  OBJECT-TYPE
--     SYNTAX       IpAddress
--     MAX-ACCESS   read-create
--     STATUS       current
--     DESCRIPTION
--         "The ip-address of the nexthop to which the packet should be forwarded
--          if it hits this filter entry. The action of this entry should be
--          'forward' in such a case."
--     DEFVAL { '00000000'H }
--     ::= { tnIPFilterParamsEntry 6 }
--
-- tnIPFilterParamsForwardNHIndirect  OBJECT-TYPE
--     SYNTAX       TruthValue
--     MAX-ACCESS   read-create
--     STATUS       current
--     DESCRIPTION
--         "tnIPFilterParamsForwardNHIndirect specifies if the nexthop is directly/
--          indirectly reachable."
--     DEFVAL { false }
--     ::= { tnIPFilterParamsEntry 7 }
--
-- tnIPFilterParamsRemarkDSCP  OBJECT-TYPE
--     SYNTAX       TDSCPFilterActionValue
--     MAX-ACCESS   read-create
--     STATUS       current
--     DESCRIPTION
--         "The DSCP value that should be remarked in case a packet hits this
--          filter entry."
--     DEFVAL { -1 }
--     ::= { tnIPFilterParamsEntry 8 }
--
-- tnIPFilterParamsRemarkDSCPMask  OBJECT-TYPE
--     SYNTAX       TDSCPFilterActionValue
--     MAX-ACCESS   read-create
--     STATUS       current
--     DESCRIPTION
--         "tnIPFilterParamsRemarkDSCPMask specifies the care bits while remarking
--          with the DSCP value."
--     DEFVAL { 255 }
--     ::= { tnIPFilterParamsEntry 9 }
--
-- tnIPFilterParamsRemarkDot1p  OBJECT-TYPE
--     SYNTAX       Dot1PPriority
--     MAX-ACCESS   read-create
--     STATUS       current
--     DESCRIPTION
--         "tnIPFilterParamsRemarkDot1p specifies the Dot1p value that needs to be
--          remarked on the packet if it hits this filter entry."
--     DEFVAL { -1 }
--     ::= { tnIPFilterParamsEntry 10 }
--
-- tnIPFilterParamsSourceIpAddr  OBJECT-TYPE
--     SYNTAX       IpAddress
--     MAX-ACCESS   read-create
--     STATUS       current
--     DESCRIPTION
--         "IP address to match the source-ip of the packet."
--     DEFVAL { '00000000'H }
--     ::= { tnIPFilterParamsEntry 11 }
--
-- tnIPFilterParamsSourceIpMask  OBJECT-TYPE
--     SYNTAX       IpAddressPrefixLength
--     MAX-ACCESS   read-create
--     STATUS       current
--     DESCRIPTION
--         "If different from 0, the object tnIPFilterParamsSourceIpMask
--          specifies the IP Mask value for this policy IP Filter entry.
--          The mask is ANDed with the received source IP address to match
--          the tnIPFilterParamsSourceIpAddr.
--
--          If the value of tnIPFilterParamsSourceIpMask is 0, and the
--          value of tnIPFilterParamsSrcIpFullMask is non zero then the
--          value of tnIPFilterParamsSrcIpFullMask is used as mask.
--
--          If the value of tnIPFilterParamsSourceIpMask is non zero,
--          it will be equal to the mask expressed the object
--          tnIPFilterParamsSrcIpFullMask.
--
--          If both tnIPFilterParamsSourceIpMask and
--          tnIPFilterParamsSrcIpFullMask are set to 0, not matching is done
--          on the source Ip address.
--
--          If a value is specified for this object, then the value of the
--          object tnIPFilterParamsSrcIpFullMask will be set to reflect
--          this same mask."
--     DEFVAL { 0 }
--     ::= { tnIPFilterParamsEntry 12 }
--
-- tnIPFilterParamsDestinationIpAddr  OBJECT-TYPE
--     SYNTAX       IpAddress
--     MAX-ACCESS   read-create
--     STATUS       current
--     DESCRIPTION
--         "IP address to match the destination-ip of the packet."
--     DEFVAL { '00000000'H }
--     ::= { tnIPFilterParamsEntry 13 }
--
-- tnIPFilterParamsDestinationIpMask  OBJECT-TYPE
--     SYNTAX       IpAddressPrefixLength
--     MAX-ACCESS   read-create
--     STATUS       current
--     DESCRIPTION
--         "If different from 0, the object tnIPFilterParamsDestinationIpMask
--          specifies the IP Mask value for this policy IP Filter entry.
--          The mask is ANDed with the received Destination IP address to match
--          the tnIPFilterParamsDestinationIpAddr.
--
--          If the value of tnIPFilterParamsDestinationIpMask is 0, and the
--          value of tnIPFilterParamsDestIpFullMask is non zero then the
--          value of tnIPFilterParamsDestIpFullMask is used as mask.
--
--          If the value of tnIPFilterParamsDestinationIpMask is non zero,
--          it will be equal to the mask expressed the object
--          tnIPFilterParamsDestIpFullMask.
--
--          If both tnIPFilterParamsDestinationIpMask and
--          tnIPFilterParamsDestIpFullMask are set to 0, not matching is done
--          on the Destination Ip address.
--
--          If a value is specified for this object, then the value of the
--          object tnIPFilterParamsDestIpFullMask will be set to reflect
--          this same mask."
--     DEFVAL { 0 }
--     ::= { tnIPFilterParamsEntry 14 }
--
-- tnIPFilterParamsProtocol  OBJECT-TYPE
--     SYNTAX       TIpProtocol
--     MAX-ACCESS   read-create
--     STATUS       current
--     DESCRIPTION
--         "IP protocol to match.  set to -1 to disable matching IP protocol. If
--          the protocol is changed the protocol specific parameters are reset.
--          For instance if protocol is changed from TCP to UDP, then the objects
--          tnIPFilterParamsTcpSyn and tnIPFilterParamsTcpAck will be turned off."
--     DEFVAL { -1 }
--     ::= { tnIPFilterParamsEntry 15 }
--
-- tnIPFilterParamsSourcePortValue1 OBJECT-TYPE
--     SYNTAX       TTcpUdpPort
--     MAX-ACCESS   read-create
--     STATUS       current
--     DESCRIPTION
--         "TCP/UDP port value1. The value of this object is used as per the
--          description for tnIPFilterParamsSourcePortOperator."
--     DEFVAL { 0 }
--     ::= { tnIPFilterParamsEntry 16 }
--
-- tnIPFilterParamsSourcePortValue2  OBJECT-TYPE
--     SYNTAX       TTcpUdpPort
--     MAX-ACCESS   read-create
--     STATUS       current
--     DESCRIPTION
--         "TCP/UDP port value2. The value of this object is used as per the
--          description for tnIPFilterParamsSourcePortOperator."
--     DEFVAL { 0 }
--     ::= { tnIPFilterParamsEntry 17 }
--
-- tnIPFilterParamsSourcePortOperator OBJECT-TYPE
--     SYNTAX       TTcpUdpPortOperator
--     MAX-ACCESS   read-create
--     STATUS       current
--     DESCRIPTION
--         "The operator specifies the manner in which
--          tnIPFilterParamsSourcePortValue1 and tnIPFilterParamsSourcePortValue2
--          are to be used. The value of these latter 2 objects and
--          tnIPFilterParamsSourcePortOperator is used as described in
--          TTcpUdpPortOperator."
--     DEFVAL { none }
--     ::= { tnIPFilterParamsEntry 18 }
--
-- tnIPFilterParamsDestPortValue1  OBJECT-TYPE
--     SYNTAX       TTcpUdpPort
--     MAX-ACCESS   read-create
--     STATUS       current
--     DESCRIPTION
--         "TCP/UDP port value1. The value of this object is used as per the
--          description for tnIPFilterParamsDestPortOperator."
--     DEFVAL { 0 }
--     ::= { tnIPFilterParamsEntry 19 }
--
-- tnIPFilterParamsDestPortValue2  OBJECT-TYPE
--     SYNTAX       TTcpUdpPort
--     MAX-ACCESS   read-create
--     STATUS       current
--     DESCRIPTION
--         "TCP/UDP port value2. The value of this object is used as per the
--          description for tnIPFilterParamsDestPortOperator."
--     DEFVAL { 0 }
--     ::= { tnIPFilterParamsEntry 20 }
--
-- tnIPFilterParamsDestPortOperator OBJECT-TYPE
--     SYNTAX       TTcpUdpPortOperator
--     MAX-ACCESS   read-create
--     STATUS       current
--     DESCRIPTION
--         "The operator specifies the manner in which
--          tnIPFilterParamsDestPortValue1 and tnIPFilterParamsDestPortValue2
--          are to be used. The value of these latter 2 objects and
--          tnIPFilterParamsDestPortOperator is used as described in
--          TTcpUdpPortOperator."
--     DEFVAL { none }
--     ::= { tnIPFilterParamsEntry 21 }
--
-- tnIPFilterParamsDSCP OBJECT-TYPE
--     SYNTAX       TDSCPNameOrEmpty
--     MAX-ACCESS   read-create
--     STATUS       current
--     DESCRIPTION
--         "DSCP to be matched on the packet."
--     DEFVAL { ''H }
--     ::= { tnIPFilterParamsEntry 22 }
--
-- tnIPFilterParamsFragment OBJECT-TYPE
--     SYNTAX       TItemMatch
--     MAX-ACCESS   read-create
--     STATUS       current
--     DESCRIPTION
--         "If enabled, this object matches fragmented/unfragmented packets as per
--          the value of the object."
--     DEFVAL { off }
--     ::= { tnIPFilterParamsEntry 24 }
--
-- tnIPFilterParamsOptionPresent  OBJECT-TYPE
--     SYNTAX       TItemMatch
--     MAX-ACCESS   read-create
--     STATUS       current
--     DESCRIPTION
--         "If enabled, this object matches packets if they have options present
--          or not as per the value of the object."
--     DEFVAL { off }
--     ::= { tnIPFilterParamsEntry 25 }
--
-- tnIPFilterParamsIpOptionValue OBJECT-TYPE
--     SYNTAX       TIpOption
--     MAX-ACCESS   read-create
--     STATUS       current
--     DESCRIPTION
--         "The value of the specific ip-option to match."
--     DEFVAL { 0 }
--     ::= { tnIPFilterParamsEntry 26 }
--
-- tnIPFilterParamsIpOptionMask  OBJECT-TYPE
--     SYNTAX       TIpOption
--     MAX-ACCESS   read-create
--     STATUS       current
--     DESCRIPTION
--         "Mask is ANDed with the ip-option before being compared to
--         tnIPFilterParamsIpOptionValue."
--     DEFVAL { 0 }
--     ::= { tnIPFilterParamsEntry 27 }
--
-- tnIPFilterParamsMultipleOption  OBJECT-TYPE
--     SYNTAX       TItemMatch
--     MAX-ACCESS   read-create
--     STATUS       current
--     DESCRIPTION
--         "If enabled, matches multiple options as per the value of the object."
--     DEFVAL { off }
--     ::= { tnIPFilterParamsEntry 28 }
--
-- tnIPFilterParamsTcpSyn  OBJECT-TYPE
--     SYNTAX       TItemMatch
--     MAX-ACCESS   read-create
--     STATUS       current
--     DESCRIPTION
--         "If Enabled, matches a TCP Syn as per value of the object."
--     DEFVAL { off }
--     ::= { tnIPFilterParamsEntry 29 }
--
-- tnIPFilterParamsTcpAck  OBJECT-TYPE
--     SYNTAX       TItemMatch
--     MAX-ACCESS   read-create
--     STATUS       current
--     DESCRIPTION
--         "If Enabled, matches a TCP Ack as per value of the object."
--     DEFVAL { off }
--     ::= { tnIPFilterParamsEntry 30 }
--
-- tnIPFilterParamsIcmpCode  OBJECT-TYPE
--     SYNTAX       INTEGER (-1|0..255)
--     MAX-ACCESS   read-create
--     STATUS       current
--     DESCRIPTION
--         "Icmp code to be matched. tnIPFilterParamsIcmpCode complements the
--         object tnIPFilterParamsIcmpType. Both of them need to be set to actually
--         enable ICMP matching. The value -1 means Icmp code matching is not
--         enabled."
--     DEFVAL { -1 }
--     ::= { tnIPFilterParamsEntry 31 }
--
-- tnIPFilterParamsIcmpType  OBJECT-TYPE
--     SYNTAX       INTEGER (-1|0..255)
--     MAX-ACCESS   read-create
--     STATUS       current
--     DESCRIPTION
--         "Icmp type to be matched. tnIPFilterParamsIcmpType complements the
--         object tnIPFilterParamsIcmpCode. Both of them need to be set to actually
--         enable ICMP matching. The value -1 means Icmp type matching is not
--         enabled."
--     DEFVAL { -1 }
--     ::= { tnIPFilterParamsEntry 32 }
--
-- tnIPFilterParamsCflowdSample  OBJECT-TYPE
--     SYNTAX       TruthValue
--     MAX-ACCESS   read-create
--     STATUS       current
--     DESCRIPTION
--         "When tnIPFilterParamsCflowdSample has a value of 'true',  Cflowd
--          sampling and analysis is performed on those packet streams where this
--          filter has been applied.  Only packets matching this IP filter entry
--          are subjected to Cflowd sampling and analysis.  A Cflowd profile
--          controls the sampling and analysis of data flows through the router."
--     DEFVAL { false }
--     ::= { tnIPFilterParamsEntry 33 }
--
-- tnIPFilterParamsCflowdIfSample  OBJECT-TYPE
--     SYNTAX       TruthValue
--     MAX-ACCESS   read-create
--     STATUS       current
--     DESCRIPTION
--         "When tnIPFilterParamsCflowdIfSample has a value of 'true', Cflowd
--          sampling and analysis is performed on those packet streams where this
--          filter has been applied.  Only packets matching this IP filter entry
--          are subjected to Cflowd sampling and analysis.  A Cflowd profile
--          controls the sampling and analysis of data flows through the router."
--     DEFVAL { true }
--     ::= { tnIPFilterParamsEntry 34 }
--
-- tnIPFilterParamsForwardNHInterface  OBJECT-TYPE
--     SYNTAX       DisplayString (SIZE(0..32))
--     MAX-ACCESS   read-create
--     STATUS       current
--     DESCRIPTION
--         "The interface name for the nexthop to which the packet should be
--          forwarded if it hits this filter entry. The action of this entry
--          should be 'forward' in such a case."
--     DEFVAL { ''H }
--     ::= { tnIPFilterParamsEntry 35 }
--
-- tnIPFilterParamsIngressHitCount OBJECT-TYPE
--     SYNTAX       Counter64
--     MAX-ACCESS   read-only
--     STATUS       current
--     DESCRIPTION
--         "This object indicates the number of times an ingress packet
--          matched this entry."
--     ::= { tnIPFilterParamsEntry 36 }
--
-- tnIPFilterParamsEgressHitCount OBJECT-TYPE
--     SYNTAX       Counter64
--     MAX-ACCESS   read-only
--     STATUS       current
--     DESCRIPTION
--         "This object indicates the number of times an egress packet
--          matched this entry."
--     ::= { tnIPFilterParamsEntry 37 }
--
-- tnIPFilterParamsLogInstantiated OBJECT-TYPE
--     SYNTAX       TruthValue
--     MAX-ACCESS   read-only
--     STATUS       current
--     DESCRIPTION
--         "tnIPFilterParamsLogInstantiated indicates if the filter log for
--          this filter entry has been instantiated or not."
--     ::= { tnIPFilterParamsEntry 38 }
--
-- tnIPFilterParamsForwardRedPlcy  OBJECT-TYPE
--     SYNTAX       TNamedItemOrEmpty
--     MAX-ACCESS   read-create
--     STATUS       current
--     DESCRIPTION
--         "tnIPFilterParamsForwardRedPlcy specifies the redirect policy to be
--          used to determine the nexthop."
--     DEFVAL { ''H }
--     ::= { tnIPFilterParamsEntry 39 }
--
-- tnIPFilterParamsActiveDest  OBJECT-TYPE
--     SYNTAX       IpAddress
--     MAX-ACCESS   read-only
--     STATUS       current
--     DESCRIPTION
--         "tnIPFilterParamsActiveDest indicates the IP address of the active
--          destination for this IP filter. A value of 0 indicates that there
--          is currently no active destination."
--     ::= { tnIPFilterParamsEntry 40 }
--
-- tnIPFilterParamsFwdSvcId  OBJECT-TYPE
--     SYNTAX       TmnxServId
--     MAX-ACCESS   read-only
--     STATUS       current
--     DESCRIPTION
--         "tnIPFilterParamsFwdSvcId indicates the service id of the
--          destination for this IP filter entry. A value of 0 indicates that
--          there is currently no active SAP or SDP destination."
--     ::= { tnIPFilterParamsEntry 41 }
--
-- tnIPFilterParamsFwdSapPortId  OBJECT-TYPE
--     SYNTAX       TmnxPortID
--     MAX-ACCESS   read-create
--     STATUS       current
--     DESCRIPTION
--         "tnIPFilterParamsFwdSapPortId specifies the sap port identity of the
--          destination for this IP filter entry.
--
--          A value of 0 indicates that there is currently no SAP destination
--          defined. A value different from 0 can only be specified if the value
--          of the tnIPFilterParamsAction object of this entry is 'forward'.
--          In addition a non-zero value can only be given if the object
--          tnIPFilterParamsFwdSdpBind has a zero value."
--     DEFVAL { 0 }
--     ::= { tnIPFilterParamsEntry 42 }
--
-- tnIPFilterParamsFwdSapEncapVal  OBJECT-TYPE
--     SYNTAX       TmnxEncapVal
--     MAX-ACCESS   read-create
--     STATUS       current
--     DESCRIPTION
--         "tnIPFilterParamsFwdSapEncapVal specifies the sap port encap value
--          of the destination SAP for this IP filter entry.
--
--          A value different from 0 can only be specified if the value of the
--          tnIPFilterParamsAction object of this entry is 'forward'.  In addition
--          a non-zero value can only be given if the object
--          tnIPFilterParamsFwdSdpBind has a zero value. A value of 0 indicates
--          that either
--          1) the sap encapsulation value is not specified when
--             tnIPFilterParamsFwdSapPortId and tnIPFilterParamsFwdSvcId
--             have valid values; or
--          2) that there is no SAP destination."
--     DEFVAL { 0 }
--     ::= { tnIPFilterParamsEntry 43 }
--
-- tnIPFilterParamsFwdSdpBind  OBJECT-TYPE
--     SYNTAX       SdpBindId
--     MAX-ACCESS   read-create
--     STATUS       current
--     DESCRIPTION
--         "tnIPFilterParamsFwdSdpBind specifies the sdp bibd identity of the
--          destination for this IP filter entry.
--
--          A value of 0 indicates that there is currently no SDP binding defined.
--          A value different from 0 can only be specified if the value of the
--          tnIPFilterParamsAction object of this entry is 'forward'. In addition
--          a non-zero value can only be given if the objects
--          tnIPFilterParamsFwdSapPortId and tnIPFilterParamsFwdSapEncapVal have a
--          zero value."
--     DEFVAL { '0'H }
--     ::= { tnIPFilterParamsEntry 44 }
--
-- tnIPFilterParamsTimeRangeName  OBJECT-TYPE
--     SYNTAX       TNamedItemOrEmpty
--     MAX-ACCESS   read-create
--     STATUS       current
--     DESCRIPTION
--         "tnIPFilterParamsTimeRangeName specifies the tmnxTimeRangeEntry to be
--          associated with this filter entry.
--
--          A value for this object can only be specified during row creation, and
--          cannot be altered lateron.
--          Also, a value is accepted only if the tmnxTimeRangeEntry is defined
--          in the TIMETRA-SCHEDULER-MIB::tmnxTimeRangeTable.tTimeRangeName."
--     DEFVAL { ''H }
--     ::= { tnIPFilterParamsEntry 45 }
--
-- tnIPFilterParamsTimeRangeState  OBJECT-TYPE
--     SYNTAX       TTimeRangeState
--     MAX-ACCESS   read-only
--     STATUS       current
--     DESCRIPTION
--         "tnIPFilterParamsTimeRangeState indicates whether or not the entry
--          is currently in effect.
--          - timeRangeNotApplic:
--            no time range is applicable for this entry.
--          - timeRangeNotActive:
--            A time range is defined in tnIPFilterParamsTimeRangeName, but is not
--            active at this moment. Consequently the filter entry is not
--            installed.
--          - timeRangeActive.
--            A time range is defined in tnIPFilterParamsTimeRangeName, and is
--            activated successfully.
--          - timeRangeActiveDownloadFailed:
--            A time range is defined in tnIPFilterParamsTimeRangeName, and is
--            activated, but the corresponding filter entry could not be
--            installed due to resource problems."
--     ::= { tnIPFilterParamsEntry 46 }
--
-- tnIPFilterParamsRedirectURL      OBJECT-TYPE
--     SYNTAX      DisplayString
--     MAX-ACCESS  read-create
--     STATUS      current
--     DESCRIPTION
--         "The value of tnIPFilterParamsRedirectURL specifies the URL
--          to redirect to, when the value of tnIPFilterParamsAction is
--          'httpRedirect'."
--     ::= { tnIPFilterParamsEntry 47 }
--
-- tnIPFilterParamsSrcIpFullMask OBJECT-TYPE
--     SYNTAX       IpAddress
--     MAX-ACCESS   read-create
--     STATUS       current
--     DESCRIPTION
--         "If different from 0, the object tnIPFilterParamsSrcIpFullMask
--          specifies the IP Mask value for this policy IP Filter entry.
--          The mask is ANDed with the received Source IP address to match
--          the tnIPFilterParamsSourceIpAddr.
--
--          If the value of tnIPFilterParamsSourceIpMask is non zero,
--          it will be equal to the mask expressed the object
--          tnIPFilterParamsSrcIpFullMask.
--
--          If both tnIPFilterParamsSourceIpMask and
--          tnIPFilterParamsSrcIpFullMask are set to 0, no matching is done
--          on the Source Ip address.
--
--          This object should contain consecutive ones and zeros. Both
--          a regular and an inverse mask is allowed (i.e. the sequence of
--          consecutive ones can appear at the front or at the end of the
--          mask).
--
--          If a regular mask is specified for tnIPFilterParamsSrcIpFullMask
--          then the value of tnIPFilterParamsSourceIpMask will be changed
--          to reflect this value. If an inverse is specified, the value of
--          tnIPFilterParamsSourceIpMask will be set to 0."
--     DEFVAL { 0 }
--     ::= { tnIPFilterParamsEntry 48 }
--
-- tnIPFilterParamsDestIpFullMask OBJECT-TYPE
--     SYNTAX       IpAddress
--     MAX-ACCESS   read-create
--     STATUS       current
--     DESCRIPTION
--         "If different from 0, the object tnIPFilterParamsDestIpFullMask
--          specifies the IP Mask value for this policy IP Filter entry.
--          The mask is ANDed with the received Destination IP address to match
--          the tnIPFilterParamsDestinationIpAddr.
--
--          If the value of tnIPFilterParamsDestinationIpMask is non zero,
--          it will be equal to the mask expressed the object
--          tnIPFilterParamsDestIpFullMask.
--
--          If both tnIPFilterParamsDestinationIpMask and
--          tnIPFilterParamsDestIpFullMask are set to 0, no matching is done
--          on the Destination Ip address.
--
--          This object should contain consecutive ones and zeros. Both
--          a regular and an inverse mask is allowed (i.e. the sequence of
--          consecutive ones can appear at the front or at the end of the
--          mask).
--
--          If a regular mask is specified for tnIPFilterParamsDestIpFullMask
--          then the value of tnIPFilterParamsDestinationIpMask will be changed
--          to reflect this value. If an inverse is specified, the value of
--          tnIPFilterParamsDestinationIpMask will be set to 0."
--     DEFVAL { 0 }
--     ::= { tnIPFilterParamsEntry 49 }
--
-- tnIPFilterParamsIngrHitByteCount OBJECT-TYPE
--     SYNTAX       Counter64
--     MAX-ACCESS   read-only
--     STATUS       current
--     DESCRIPTION
--         "The value of tnIPFilterParamsIngrHitByteCount indicates the number
--          of bytes of all ingress packets that matched this entry."
--     ::= { tnIPFilterParamsEntry 50 }
--
-- tnIPFilterParamsEgrHitByteCount OBJECT-TYPE
--     SYNTAX       Counter64
--     MAX-ACCESS   read-only
--     STATUS       current
--     DESCRIPTION
--         "The value of tnIPFilterParamsEgrHitByteCount indicates the number
--          of bytes of all egress packets that matched this entry."
--     ::= { tnIPFilterParamsEntry 51 }

--
-- MAC filter table
--

tnMacFilterTable OBJECT-TYPE
    SYNTAX       SEQUENCE OF TnMacFilterEntry
    MAX-ACCESS   not-accessible
    STATUS       current
    DESCRIPTION
        "Contains a List of all mac filters configured on this system."
    ::= { tnFilterObjects 3 }

tnMacFilterEntry OBJECT-TYPE
    SYNTAX       TnMacFilterEntry
    MAX-ACCESS   not-accessible
    STATUS       current
    DESCRIPTION
        "Information about a particular MAC Filter. Entries are created/deleted
         by user. Entries have a presumed StorageType of nonVolatile."
    INDEX { tnSysSwitchId, tnMacFilterId }
    ::= { tnMacFilterTable 1 }

TnMacFilterEntry ::= SEQUENCE
    {
        tnMacFilterId            TMACFilterID,
        tnMacFilterRowStatus     RowStatus,
        tnMacFilterScope         TItemScope,
        tnMacFilterDescription   TItemDescription,
        tnMacFilterDefaultAction TFilterAction,
        tnMacFilterType          TMacFilterType,
        tnMacFilterName          TLNamedItemOrEmpty,
        tnMacFilterApplied       TruthValue,
        tnMacFilterNumEntries    Unsigned32
    }

tnMacFilterId  OBJECT-TYPE
    SYNTAX       TMACFilterID (1..65535)
    MAX-ACCESS   not-accessible
    STATUS       current
    DESCRIPTION
        "Uniquely identifies a mac filter as configures on this system."
    ::= { tnMacFilterEntry 1 }

tnMacFilterRowStatus  OBJECT-TYPE
    SYNTAX       RowStatus
    MAX-ACCESS   read-create
    STATUS       current
    DESCRIPTION
        "This object allows entries to be created and deleted in the
         tnMacFilterTable."
    ::= { tnMacFilterEntry 2 }

tnMacFilterScope  OBJECT-TYPE
    SYNTAX       TItemScope
    MAX-ACCESS   read-create
    STATUS       current
    DESCRIPTION
        "This object specifies the scope of this filter definition. If defined
         as exclusive(1), this filter can be instantiated only once as compared
         to the multiple instances that the filter can have if defined as
         template(2)."
    DEFVAL { template }
    ::= { tnMacFilterEntry 3 }

tnMacFilterDescription  OBJECT-TYPE
    SYNTAX       TItemDescription
    MAX-ACCESS   read-create
    STATUS       current
    DESCRIPTION
        "User-provided description for this filter."
    DEFVAL { ''H }
    ::= { tnMacFilterEntry 4 }

tnMacFilterDefaultAction  OBJECT-TYPE
    SYNTAX       TFilterAction
    MAX-ACCESS   read-create
    STATUS       current
    DESCRIPTION
        "The action to take for packets that do not match any filter entries."
    DEFVAL { drop }
    ::= { tnMacFilterEntry 5 }

tnMacFilterType  OBJECT-TYPE
    SYNTAX      TMacFilterType
    MAX-ACCESS   read-create
    STATUS       current
    DESCRIPTION
        "tnMacFilterType specifies which type of entries this mac filter
         can contain.

         If tnMacFilterType is set to 'normal(1)', all match criteria
         are accepted except the criteria mentioned below that belong to type
         isid(2) and vid(3).

         if tnMacFilterType is set to 'isid(2)' the only accepted match
         criteria for the filter entries are:
         - tMacFilterParamsLowISID
         - tMacFilterParamsHighISID

         If tnMacFilterType is set to vid(3) the only accepted match
         criteria for the filter entries are:
         - tMacFilterParamsInnerTagValue
         - tMacFilterParamsInnerTagMask
         - tMacFilterParamsOuterTagValue
         - tMacFilterParamsOuterTagMask

         tnMacFilterType can only be changed if the filter is not applied
         and has no entries.
         "
    DEFVAL { normal }
    ::= { tnMacFilterEntry 6 }

tnMacFilterName OBJECT-TYPE
    SYNTAX       TLNamedItemOrEmpty
    MAX-ACCESS   read-create
    STATUS       current
    DESCRIPTION
        "The value of tnMacFilterName specifies the name to associate
        with this filter."
    DEFVAL { ''H }
    ::= { tnMacFilterEntry 7 }

tnMacFilterApplied  OBJECT-TYPE
    SYNTAX       TruthValue
    MAX-ACCESS   read-only
    STATUS       current
    DESCRIPTION
        "Indicates if the filter has been applied or not."
    DEFVAL { false }
    ::= { tnMacFilterEntry 8 }

tnMacFilterNumEntries  OBJECT-TYPE
    SYNTAX       Unsigned32
    MAX-ACCESS   read-only
    STATUS       current
    DESCRIPTION
        "The number of MAC filter match entries configure
         against the MAC filter."
    DEFVAL { 0 }
    ::= { tnMacFilterEntry 9 }

--
-- MAC Filter Entry parameters
--

tnMacFilterParamsTable OBJECT-TYPE
    SYNTAX       SEQUENCE OF TnMacFilterParamsEntry
    MAX-ACCESS   not-accessible
    STATUS       current
    DESCRIPTION  "A table of all MAC filter match entries for all MAC filters."
    ::= { tnFilterObjects 4 }

tnMacFilterParamsEntry OBJECT-TYPE
    SYNTAX       TnMacFilterParamsEntry
    MAX-ACCESS   not-accessible
    STATUS       current
    DESCRIPTION
        "Information about a particular MAC Filter entry.
        Every MAC Filter can have zero or more MAC Filter match entries.

        a filter entry with no match criteria set will match every
        packet, and the entry action will be taken.

        Entries are created/deleted by user.

        There is no StorageType object, entries have a presumed
        StorageType of nonVolatile.
        "
    INDEX { tnSysSwitchId, tnMacFilterId, tnMacFilterParamsIndex }
    ::= { tnMacFilterParamsTable 1 }

TnMacFilterParamsEntry ::= SEQUENCE
    {
        tnMacFilterParamsIndex            TEntryId,
        tnMacFilterParamsRowStatus        RowStatus,
        tnMacFilterParamsLogId            TFilterLogId,
        tnMacFilterParamsDescription      TItemDescription,
        tnMacFilterParamsAction           TFilterActionOrDefault,
        tnMacFilterParamsFrameType        TFrameType,
        tnMacFilterParamsSrcMAC           MacAddress,
        tnMacFilterParamsSrcMACMask       MacAddress,
        tnMacFilterParamsDstMAC           MacAddress,
        tnMacFilterParamsDstMACMask       MacAddress,
        tnMacFilterParamsDot1pValue       Dot1PPriority,
        tnMacFilterParamsDot1pMask        Dot1PPriority,
        tnMacFilterParamsEtherType        Integer32,
        tnMacFilterParamsDsap             ServiceAccessPoint,
        tnMacFilterParamsDsapMask         ServiceAccessPoint,
        tnMacFilterParamsSsap             ServiceAccessPoint,
        tnMacFilterParamsSsapMask         ServiceAccessPoint,
        tnMacFilterParamsSnapPid          Integer32,
        tnMacFilterParamsSnapOui          INTEGER,
        tnMacFilterParamsIngressHitCount  Counter64,
        tnMacFilterParamsEgressHitCount   Counter64,
        tnMacFilterParamsLogInstantiated  TruthValue,
        tnMacFilterParamsFwdSvcId         TmnxServId,
        tnMacFilterParamsFwdSapPortId     TmnxPortID,
        tnMacFilterParamsFwdSapEncapVal   TmnxEncapVal,
        tnMacFilterParamsFwdSdpBind       SdpBindId,
        tnMacFilterParamsTimeRangeName    TNamedItemOrEmpty,
        tnMacFilterParamsTimeRangeState   TTimeRangeState,
        tnMacFilterParamsRedirectURL      DisplayString,
        tnMacFilterParamsIngrHitByteCount Counter64,
        tnMacFilterParamsEgrHitByteCount  Counter64

    }
tnMacFilterParamsIndex  OBJECT-TYPE
    SYNTAX       TEntryId
    MAX-ACCESS   not-accessible
    STATUS       current
    DESCRIPTION
        "This is the secondary index for the entry. Every mac filter can have
         multiple entries, therefore every mac filter entry is identified by
         the tnMacFilterId and tnMacFilterParamsIndex."
    ::= { tnMacFilterParamsEntry 1 }

tnMacFilterParamsRowStatus  OBJECT-TYPE
    SYNTAX       RowStatus
    MAX-ACCESS   read-create
    STATUS       current
    DESCRIPTION
        "This object allows entries to be created and deleted in the
         tnMacFilterParamsTable."
    ::= { tnMacFilterParamsEntry 2 }

tnMacFilterParamsLogId  OBJECT-TYPE
    SYNTAX       TFilterLogId
    MAX-ACCESS   read-create
    STATUS       current
    DESCRIPTION
        "This object specifies the log to use for packets that match
         this entry. The value zero indicates that logging is disabled."
    DEFVAL { 0 }
    ::= { tnMacFilterParamsEntry 3 }

tnMacFilterParamsDescription  OBJECT-TYPE
    SYNTAX       TItemDescription
    MAX-ACCESS   read-create
    STATUS       current
    DESCRIPTION
        "User-provided description for this filter entry."
    DEFVAL { ''H }
    ::= { tnMacFilterParamsEntry 4 }

tnMacFilterParamsAction  OBJECT-TYPE
    SYNTAX       TFilterActionOrDefault
    MAX-ACCESS   read-create
    STATUS       current
    DESCRIPTION
        "The action to take for packets that match this filter entry. The value
         default(3) specifies this entry to inherit the behavior defined as the
         default for the filter."
    DEFVAL { drop }
    ::= { tnMacFilterParamsEntry 5 }

tnMacFilterParamsFrameType  OBJECT-TYPE
    SYNTAX       TFrameType
    MAX-ACCESS   read-create
    STATUS       current
    DESCRIPTION
        "The type of mac frame for which we are defining this match criteria."
    DEFVAL { e802dot3 }
    ::= { tnMacFilterParamsEntry 6 }

tnMacFilterParamsSrcMAC OBJECT-TYPE
    SYNTAX          MacAddress
    MAX-ACCESS      read-create
    STATUS          current
    DESCRIPTION
        "Source MAC to match for this policy MAC filter entry."
    DEFVAL { '000000000000'H }
    ::= { tnMacFilterParamsEntry 8 }

tnMacFilterParamsSrcMACMask OBJECT-TYPE
    SYNTAX          MacAddress
    MAX-ACCESS      read-create
    STATUS          current
    DESCRIPTION
        "Source MAC mask value for this policy MAC filter entry.
         The mask is ANDed with the MAC to match tnMacFilterParamsSrcMAC.
         A zero bit means ignore this bit, do not match.  a one bit means
         match this bit with tnMacFilterParamsSrcMAC.
         Use the value 00-00-00-00-00-00 to disable this filter criteria."
    DEFVAL { '000000000000'H }
    ::= { tnMacFilterParamsEntry 9 }

tnMacFilterParamsDstMAC OBJECT-TYPE
    SYNTAX          MacAddress
    MAX-ACCESS      read-create
    STATUS          current
    DESCRIPTION
        "Destination MAC mask value for this policy MAC filter entry."
    DEFVAL { '000000000000'H }
    ::= { tnMacFilterParamsEntry 10 }

tnMacFilterParamsDstMACMask OBJECT-TYPE
    SYNTAX          MacAddress
    MAX-ACCESS      read-create
    STATUS          current
    DESCRIPTION
        "Destination MAC mask value for this policy MAC filter entry.
         The mask is ANDed with the MAC to match tnMacFilterParamsDstMAC.
         A zero bit means ignore this bit, do not match.  a one bit means
         match this bit with tnMacFilterParamsDstMAC.
         Use the value 00-00-00-00-00-00 to disable this filter criteria."
    DEFVAL { '000000000000'H }
    ::= { tnMacFilterParamsEntry 11 }

tnMacFilterParamsDot1pValue OBJECT-TYPE
    SYNTAX          Dot1PPriority
    MAX-ACCESS      read-create
    STATUS          current
    DESCRIPTION
         "IEEE 802.1p priority value for this policy MAC filter entry.
      Use -1 to disable matching this filter criteria."
    DEFVAL { -1 }
    ::= { tnMacFilterParamsEntry 12 }

tnMacFilterParamsDot1pMask OBJECT-TYPE
    SYNTAX          Dot1PPriority (0..7)
    MAX-ACCESS      read-create
    STATUS          current
    DESCRIPTION
         "IEEE 802.1p priority mask value for this policy MAC filter entry.
          Use zero to disable matching, use 7 to match everything."
    DEFVAL { 0 }
    ::= { tnMacFilterParamsEntry 13 }

tnMacFilterParamsEtherType OBJECT-TYPE
    SYNTAX          Integer32 (-1 | 0..65535)
    MAX-ACCESS      read-create
    STATUS          current
    DESCRIPTION
        "Ethertype for this policy MAC filter entry. Use -1 to disable matching
         by this criteria. This object has no significance if the object
         tnMacFilterParamsFrameType is not set to Ethernet_II."
    DEFVAL { -1 }
    ::= { tnMacFilterParamsEntry 14 }

tnMacFilterParamsDsap OBJECT-TYPE
    SYNTAX          ServiceAccessPoint
    MAX-ACCESS      read-create
    STATUS          current
    DESCRIPTION
        "MAC DSAP to match for this policy MAC filter entry. This object has no
         significance if the object tnMacFilterParamsFrameType is not set to
         802dot2LLC."
    DEFVAL { -1 }
    ::= { tnMacFilterParamsEntry 15 }

tnMacFilterParamsDsapMask OBJECT-TYPE
    SYNTAX          ServiceAccessPoint
    MAX-ACCESS      read-create
    STATUS          current
    DESCRIPTION
        "MAC DSAP mask for this policy MAC filter entry. use 0 to disable
         matching by this criteria. This object has no significance if the
         object tnMacFilterParamsFrameType is not set to 802dot2LLC."
    DEFVAL { -1 }
    ::= { tnMacFilterParamsEntry 16 }

tnMacFilterParamsSsap OBJECT-TYPE
    SYNTAX          ServiceAccessPoint
    MAX-ACCESS      read-create
    STATUS          current
    DESCRIPTION
        "MAC SSAP to match for this policy MAC filter entry. This object has no
         significance if the object tnMacFilterParamsFrameType is not set to
         802dot2LLC."
    DEFVAL { -1 }
    ::= { tnMacFilterParamsEntry 17 }

tnMacFilterParamsSsapMask OBJECT-TYPE
    SYNTAX          ServiceAccessPoint
    MAX-ACCESS      read-create
    STATUS          current
    DESCRIPTION
        "MAC SSAP mask for this policy MAC filter entry. use 0 to disable
         matching by this criteria. This object has no significance if the
         object tnMacFilterParamsFrameType is not set to 802dot2LLC."
    DEFVAL { -1 }
    ::= { tnMacFilterParamsEntry 18 }

tnMacFilterParamsSnapPid OBJECT-TYPE
    SYNTAX          Integer32 (-1 | 0..65535)
    MAX-ACCESS      read-create
    STATUS          current
    DESCRIPTION
         "MAC SNAP PID to match for this policy MAC filter entry.  use -1 to
          disable matching by this criteria. This object has no significance if
          object tnMacFilterParamsFrameType is not set to 802dot2SNAP."
    DEFVAL { -1 }
    ::= { tnMacFilterParamsEntry 19 }

tnMacFilterParamsSnapOui OBJECT-TYPE
    SYNTAX          INTEGER {
                      off(1),
                      zero(2),
                      nonZero(3)
                    }
    MAX-ACCESS      read-create
    STATUS          current
    DESCRIPTION
        "MAC SNAP OUI to match. The values zero(2) and nonZero(3) specify what
         to match. Matching can be disabled by the use of the value off(1).
         This object has no significance if the object
         tnMacFilterParamsFrameType is not set to 802dot2SNAP."
    DEFVAL { off }
    ::= { tnMacFilterParamsEntry 20 }

tnMacFilterParamsIngressHitCount OBJECT-TYPE
    SYNTAX       Counter64
    MAX-ACCESS   read-only
    STATUS       current
    DESCRIPTION
        "This object indicates the number of times an ingress packet
         matched this entry."
    ::= { tnMacFilterParamsEntry 21 }

tnMacFilterParamsEgressHitCount OBJECT-TYPE
    SYNTAX       Counter64
    MAX-ACCESS   read-only
    STATUS       current
    DESCRIPTION
        "This object indicates the number of times an egress packet
         matched this entry."
    ::= { tnMacFilterParamsEntry 22 }

tnMacFilterParamsLogInstantiated OBJECT-TYPE
    SYNTAX       TruthValue
    MAX-ACCESS   read-only
    STATUS       current
    DESCRIPTION
        "tnMacFilterParamsLogInstantiated indicates if the filter log for
         this filter entry has been instantiated or not."
    ::= { tnMacFilterParamsEntry 23 }

tnMacFilterParamsFwdSvcId  OBJECT-TYPE
    SYNTAX       TmnxServId
    MAX-ACCESS   read-only
    STATUS       current
    DESCRIPTION
        "tnMacFilterParamsFwdSvcId indicates the service id of the
         destination for this Mac filter entry. A value of 0 indicates that
         there is currently no active SAP or SDP destination."
    ::= { tnMacFilterParamsEntry 24 }

tnMacFilterParamsFwdSapPortId  OBJECT-TYPE
    SYNTAX       TmnxPortID
    MAX-ACCESS   read-create
    STATUS       current
    DESCRIPTION
        "tnMacFilterParamsFwdSapPortId specifies the sap port identity of the
         destination for this Mac filter entry. A value of 0 indicates that
         there is currently no SAP destination defined.
         A value different from 0 can only be specified if the
         tnMacFilterParamsFwdSvcId object also has a non-zero value,
         and if the the value of the tnMacFilterParamsAction object of this
         entry is 'forward'. In addition a non-zero value can only be given if
         the object tnMacFilterParamsFwdSdpBind has a zero value."
    DEFVAL { 0 }
    ::= { tnMacFilterParamsEntry 25 }

tnMacFilterParamsFwdSapEncapVal  OBJECT-TYPE
    SYNTAX       TmnxEncapVal
    MAX-ACCESS   read-create
    STATUS       current
    DESCRIPTION
        "tnMacFilterParamsFwdSapEncapVal specifies the sap port encap value
         of the destination SAP for this Mac filter entry.
         A value different from 0 can only be specified if the
         tnMacFilterParamsFwdSvcId object also has a non-zero value,
         the tnMacFilterParamsFwdSapPortId object has a non zero value,
         and if the the value of the tnMacFilterParamsAction object of this entry
         is 'forward'.
         In addition a non-zero value can only be given if the object
         tnMacFilterParamsFwdSdpBind has a zero value.
         A value of 0 indicates that either
         1) the sap encapsulation value is not specified when
            tnMacFilterParamsFwdSapPortId and tnMacFilterParamsFwdSvcId
            have valid values; or
         2) that there is no SAP destination."
    DEFVAL { 0 }
    ::= { tnMacFilterParamsEntry 26 }

tnMacFilterParamsFwdSdpBind  OBJECT-TYPE
    SYNTAX       SdpBindId
    MAX-ACCESS   read-create
    STATUS       current
    DESCRIPTION
        "tnMacFilterParamsFwdSdpBind specifies the sdp bibd identity of the
         destination for this Mac filter entry. A value of 0 indicates that
         there is currently no SDP binding defined.
         A value different from 0 can only be specified if the
         tnMacFilterParamsFwdSvcId object also has a non-zero value,
         and if the the value of the tnMacFilterParamsAction object of this
         entry is 'forward'. In addition a non-zero value can only be given if
         the objects tnMacFilterParamsFwdSapPortId and
         tnMacFilterParamsFwdSapEncapVal have a zero value."
    DEFVAL { '0'H }
    ::= { tnMacFilterParamsEntry 27 }

tnMacFilterParamsTimeRangeName  OBJECT-TYPE
    SYNTAX       TNamedItemOrEmpty
    MAX-ACCESS   read-create
    STATUS       current
    DESCRIPTION
        "tnMacFilterParamsTimeRangeName specifies the tmnxTimeRangeEntry to be
         associated with this filter entry.

         A value for this object can only be specified during row creation, and
         cannot be altered lateron.
         Also, a value is accepted only if the tmnxTimeRangeEntry is defined in
         the TIMETRA-SCHEDULER-MIB::tmnxTimeRangeTable.tTimeRangeName."
    DEFVAL { ''H }
    ::= { tnMacFilterParamsEntry 28 }

tnMacFilterParamsTimeRangeState  OBJECT-TYPE
    SYNTAX       TTimeRangeState
    MAX-ACCESS   read-only
    STATUS       current
    DESCRIPTION
        "tnMacFilterParamsTimeRangeState indicates whether or not the entry
         is currently in effect.
         - timeRangeNotApplic:
           no time range is applicable for this entry.
         - timeRangeNotActive:
           A time range is defined in tnMacFilterParamsTimeRangeName, but is not
           active at this moment. Consequently the filter entry is not
           installed.
         - timeRangeActive.
           A time range is defined in tnMacFilterParamsTimeRangeName, and is
           activated successfully.
         - timeRangeActiveDownloadFailed:
           A time range is defined in tnMacFilterParamsTimeRangeName, and is
           activated, but the corresponding filter entry could not be
           installed due to resource problems."
    ::= { tnMacFilterParamsEntry 29 }

tnMacFilterParamsRedirectURL     OBJECT-TYPE
    SYNTAX      DisplayString
    MAX-ACCESS  read-create
    STATUS      current
    DESCRIPTION
        "The value of tnMacFilterParamsRedirectURL specifies the URL
         to redirect to, when the value of tnMacFilterParamsAction is
         'httpRedirect'."
    ::= { tnMacFilterParamsEntry 30 }

tnMacFilterParamsIngrHitByteCount OBJECT-TYPE
    SYNTAX       Counter64
    MAX-ACCESS   read-only
    STATUS       current
    DESCRIPTION
        "The value of tnMacFilterParamsIngrHitByteCount indicates the number
         of bytes of all ingress packets that matched this entry."
    ::= { tnMacFilterParamsEntry 31 }

tnMacFilterParamsEgrHitByteCount OBJECT-TYPE
    SYNTAX       Counter64
    MAX-ACCESS   read-only
    STATUS       current
    DESCRIPTION
        "The value of tnMacFilterParamsEgrHitByteCount indicates the number
         of bytes of all egress packets that matched this entry."
    ::= { tnMacFilterParamsEntry 32 }

--
-- MAC filter association scalar
--

tnMacFilterAssociationScalar OBJECT-TYPE
    SYNTAX Integer32
    MAX-ACCESS read-only
    STATUS current
    DESCRIPTION "Dummy scalar for tnMacFilterAssociationTable."
    ::= { tnFilterObjects 7 }

--
-- MAC filter association table
--

tnMacFilterAssociationTable OBJECT-TYPE
    SYNTAX       SEQUENCE OF TnMacFilterAssociationEntry
    MAX-ACCESS   not-accessible
    STATUS       current
    DESCRIPTION
        "Contains a List of all mac filters associations present
         on this system."
    ::= { tnFilterObjects 8 }

tnMacFilterAssociationEntry OBJECT-TYPE
    SYNTAX       TnMacFilterAssociationEntry
    MAX-ACCESS   not-accessible
    STATUS       current
    DESCRIPTION
        "Information about a particular MAC Filter association.
         Entries are automatically created when a filter is
         applied to a SAP."
    INDEX { tnSysSwitchId, tnMacFilterId, tnSvcId, tnSapPortId, tnSapEncapValue }
    ::= { tnMacFilterAssociationTable 1 }

TnMacFilterAssociationEntry ::= SEQUENCE
    {
        tnMacFilterAssociationDirection INTEGER
    }

tnMacFilterAssociationDirection  OBJECT-TYPE
    SYNTAX       INTEGER { ingress(1), egress(2) }
    MAX-ACCESS   read-only
    STATUS       current
    DESCRIPTION
        "The value of tnMacFilterAssociationDirection specifies the
         direction (ingress/egress) that the filter is applied."
    ::= { tnMacFilterAssociationEntry 1 }

--
-- Filter Log table
--

-- tnFilterLogTable OBJECT-TYPE
--     SYNTAX       SEQUENCE OF TFilterLogEntry
--     MAX-ACCESS   not-accessible
--     STATUS       current
--     DESCRIPTION  "A table of all filter logs."
--     ::= { tnFilterObjects 5 }
--
-- tnFilterLogEntry OBJECT-TYPE
--     SYNTAX       TFilterLogEntry
--     MAX-ACCESS   not-accessible
--     STATUS       current
--     DESCRIPTION
--         "Information about a particular Filter Log entry."
--     INDEX { tnSysSwitchId, tnFilterLogId }
--     ::= { tnFilterLogTable 1 }
--
-- TFilterLogEntry ::= SEQUENCE
--     {
--         tnFilterLogId              TFilterLogId,
--         tnFilterLogRowStatus       RowStatus,
--         tnFilterLogDestination     TFilterLogDestination,
--         tnFilterLogDescription     TItemDescription,
--         tnFilterLogMaxNumEntries   Unsigned32,
--         tnFilterLogSysLogId        Unsigned32,
--         tnFilterLogFileId          Unsigned32,
--         tnFilterLogStopOnFull      TruthValue,
--         tnFilterLogEnabled         TruthValue,
--         tnFilterLogSummaryEnabled  TruthValue,
--         tnFilterLogSummaryCrit1    TFilterLogSummaryCriterium
--     }
--
-- tnFilterLogId  OBJECT-TYPE
--     SYNTAX       TFilterLogId
--     MAX-ACCESS   not-accessible
--     STATUS       current
--     DESCRIPTION
--         "This is the index for the entry. An entry cannot be created with an
--         id of 0."
--     ::= { tnFilterLogEntry 1 }
--
-- tnFilterLogRowStatus  OBJECT-TYPE
--     SYNTAX       RowStatus
--     MAX-ACCESS   read-create
--     STATUS       current
--     DESCRIPTION
--         "This object allows entries to be created and deleted in the
--          tnFilterLogTable."
--     ::= { tnFilterLogEntry 2 }
--
-- tnFilterLogDestination  OBJECT-TYPE
--     SYNTAX       TFilterLogDestination
--     MAX-ACCESS   read-create
--     STATUS       current
--     DESCRIPTION
--         "This object specifies the destination of the log."
--     DEFVAL { memory }
--     ::= { tnFilterLogEntry 3 }
--
-- tnFilterLogDescription  OBJECT-TYPE
--     SYNTAX       TItemDescription
--     MAX-ACCESS   read-create
--     STATUS       current
--     DESCRIPTION
--         "User-provided description for this filter log entry."
--     DEFVAL { ''H }
--     ::= { tnFilterLogEntry 4 }
--
-- tnFilterLogMaxNumEntries  OBJECT-TYPE
--     SYNTAX       Unsigned32 (0..50000)
--     MAX-ACCESS   read-create
--     STATUS       current
--     DESCRIPTION
--        "The object tFilterLogMaxNumEntries specifies the maximum number
--         of entries that the log can store.
--
--         If tFilterLogDestination is not 'memory(1)' then
--         the object tFilterLogMaxNumEntries maintains a value of '0',
--         and Any change attempts will be silently discarded."
--     DEFVAL { 1000 }
--     ::= { tnFilterLogEntry 5 }
--
-- tnFilterLogSysLogId  OBJECT-TYPE
--     SYNTAX       Unsigned32
--     MAX-ACCESS   read-create
--     STATUS       current
--     DESCRIPTION
--        "The object tFilterLogSysLogId specifies the syslog Id to be used
--         as destination.
--
--         If tFilterLogDestination is not 'sysLog(2)' then the object
--         tFilterLogSysLogId maintains a value of '0',
--         and any change attempts will be silently discarded."
--     DEFVAL { 0 }
--     ::= { tnFilterLogEntry 6 }
--
-- tnFilterLogFileId  OBJECT-TYPE
--     SYNTAX       Unsigned32
--     MAX-ACCESS   read-create
--     STATUS       current
--     DESCRIPTION
--        "The object tFilterLogFileId specifies the File Id to be used
--         as destination.
--
--         If tFilterLogDestination is not 'file(3)' then the object
--         tFilterLogFileId Imaintains a value of '0',
--         and any change attempts will be silently discarded."
--     DEFVAL { 0 }
--     ::= { tnFilterLogEntry 7 }
--
-- tnFilterLogStopOnFull  OBJECT-TYPE
--     SYNTAX       TruthValue
--     MAX-ACCESS   read-create
--     STATUS       current
--     DESCRIPTION
--         "."
--     DEFVAL { false }
--     ::= { tnFilterLogEntry 8 }
--
-- tnFilterLogEnabled  OBJECT-TYPE
--     SYNTAX       TruthValue
--     MAX-ACCESS   read-create
--     STATUS       current
--     DESCRIPTION
--         "."
--     DEFVAL { true }
--     ::= { tnFilterLogEntry 9 }
--
-- tnFilterLogSummaryEnabled  OBJECT-TYPE
--     SYNTAX       TruthValue
--     MAX-ACCESS   read-create
--     STATUS       current
--     DESCRIPTION
--          "The value of tnFilterLogSummaryEnabled specifies whether
--           or not summarization of filter log entries is performed.
--           Summarization is only allowed in case tnFilterLogDestination is set
--           to syslog."
--     DEFVAL { false }
--     ::= { tnFilterLogEntry 10 }
--
-- tnFilterLogSummaryCrit1  OBJECT-TYPE
--     SYNTAX       TFilterLogSummaryCriterium
--     MAX-ACCESS   read-create
--     STATUS       current
--     DESCRIPTION
--         "The value of tnFilterLogSummaryCrit1 specifies how
--          filter log entries will be summarized.
--
--          This field is only meaningful if the object
--          tnFilterLogSummaryEnabled is set to true."
--     DEFVAL { srcAddr }
--     ::= { tnFilterLogEntry 11 }

--
-- Filter Log Scalars
--
-- tnFilterLogScalars  OBJECT IDENTIFIER ::= { tnFilterObjects 6 }

-- tnFilterLogMaxInstances  OBJECT-TYPE
--     SYNTAX       Gauge32
--     MAX-ACCESS   read-only
--     STATUS       current
--     DESCRIPTION
--         "tnFilterLogMaxInstances maintains the maximum allowed instances
--          of filter logs allowed on the system"
--     ::= { tnFilterLogScalars 1 }

-- tnFilterLogInstances  OBJECT-TYPE
--     SYNTAX       Gauge32
--     MAX-ACCESS   read-only
--     STATUS       current
--     DESCRIPTION
--         "tnFilterLogInstances maintains the instances of filter logs
--          presently existing on the system"
--     ::= { tnFilterLogScalars 2 }

-- tnFilterLogBindings  OBJECT-TYPE
--     SYNTAX       Gauge32
--     MAX-ACCESS   read-only
--     STATUS       current
--     DESCRIPTION
--         "tnFilterLogBindings maintains the count of the configured
--          filter log bindings presently existing on the system. The
--          bindings get instantiated when the filter is instantiated"
--     ::= { tnFilterLogScalars 3 }

--
-- Filter Redirect Policies
--

-- tnFilterRedirectPolicyTable OBJECT-TYPE
--     SYNTAX       SEQUENCE OF TFilterRedirectPolicyEntry
--     MAX-ACCESS   not-accessible
--     STATUS       current
--     DESCRIPTION
--         "Contains a List of all redirect policies configured on this system."
--     ::= { tnFilterObjects 10 }
--
-- tnFilterRedirectPolicyEntry OBJECT-TYPE
--     SYNTAX       TFilterRedirectPolicyEntry
--     MAX-ACCESS   not-accessible
--     STATUS       current
--     DESCRIPTION
--         "Information about a particular redirect policy. Entries are
--         created/deleted by user."
--     INDEX { tnSysSwitchId, tnFilterRedirectPolicy }
--     ::= { tnFilterRedirectPolicyTable 1 }
--
-- TFilterRedirectPolicyEntry ::= SEQUENCE
--     {
--         tnFilterRedirectPolicy     TNamedItem,
--         tnFilterRPRowStatus        RowStatus,
--         tnFilterRPDescription      TItemDescription,
--         tnFilterRPAdminState       TmnxAdminState,
--         tnFilterRPActiveDest       IpAddress
--     }
--
-- tnFilterRedirectPolicy  OBJECT-TYPE
--     SYNTAX       TNamedItem
--     MAX-ACCESS   not-accessible
--     STATUS       current
--     DESCRIPTION
--         "tnFilterRedirectPolicy uniquely identifies each redirect policy
--         configured on this system."
--     ::= { tnFilterRedirectPolicyEntry 1 }
--
-- tnFilterRPRowStatus  OBJECT-TYPE
--     SYNTAX       RowStatus
--     MAX-ACCESS   read-create
--     STATUS       current
--     DESCRIPTION
--         "tnFilterRPRowStatus allows entries to be created and deleted in the
--         tnFilterRedirectPolicyTable."
--     ::= { tnFilterRedirectPolicyEntry 2 }
--
-- tnFilterRPDescription  OBJECT-TYPE
--     SYNTAX       TItemDescription
--     MAX-ACCESS   read-create
--     STATUS       current
--     DESCRIPTION
--         "User-provided description for this redirect policy is maintained in
--         the object tnFilterRPDescription."
--     DEFVAL { ''H }
--     ::= { tnFilterRedirectPolicyEntry 3 }
--
-- tnFilterRPAdminState  OBJECT-TYPE
--     SYNTAX       TmnxAdminState
--     MAX-ACCESS   read-create
--     STATUS       current
--     DESCRIPTION
--         "tnFilterRPAdminState holds the admin state of the policy. If the
--         admin state is 'outOfService', the tests will not be conducted."
--     DEFVAL { inService }
--     ::= { tnFilterRedirectPolicyEntry 4 }
--
-- tnFilterRPActiveDest  OBJECT-TYPE
--     SYNTAX       IpAddress
--     MAX-ACCESS   read-only
--     STATUS       current
--     DESCRIPTION
--         "tnFilterRPActiveDest indicates the IP address of the active
--         destination. A value of 0 indicates that there is currently
--         no active destination."
--     ::= { tnFilterRedirectPolicyEntry 5 }

--
-- Filter Redirect Destinations
--

-- tnFilterRedirectDestTable OBJECT-TYPE
--     SYNTAX       SEQUENCE OF TFilterRedirectDestEntry
--     MAX-ACCESS   not-accessible
--     STATUS       current
--     DESCRIPTION
--         "Contains a List of all redirect destinations configured on this
--         system."
--     ::= { tnFilterObjects 11 }
--
-- tnFilterRedirectDestEntry OBJECT-TYPE
--     SYNTAX       TFilterRedirectDestEntry
--     MAX-ACCESS   not-accessible
--     STATUS       current
--     DESCRIPTION
--         "Information about a particular Redirect destination. Entries are
--          created/deleted by user."
--     INDEX { tnSysSwitchId, tnFilterRedirectPolicy, tnFilterRedirectDest }
--     ::= { tnFilterRedirectDestTable 1 }
--
-- TFilterRedirectDestEntry ::= SEQUENCE
--     {
--         tnFilterRedirectDest       IpAddress,
--         tnFilterRDRowStatus        RowStatus,
--         tnFilterRDDescription      TItemDescription,
--         tnFilterRDAdminPriority    Unsigned32,
--         tnFilterRDOperPriority     Unsigned32,
--         tnFilterRDAdminState       TmnxAdminState,
--         tnFilterRDOperState        TmnxOperState
--     }
--
-- tnFilterRedirectDest  OBJECT-TYPE
--     SYNTAX       IpAddress
--     MAX-ACCESS   not-accessible
--     STATUS       current
--     DESCRIPTION
--         "tnFilterRedirectDest holds the IP address of the destination
--         entry."
--     ::= { tnFilterRedirectDestEntry 1 }
--
-- tnFilterRDRowStatus  OBJECT-TYPE
--     SYNTAX       RowStatus
--     MAX-ACCESS   read-create
--     STATUS       current
--     DESCRIPTION
--         "tnFilterRDRowStatus allows entries to be created and deleted
--         in the tnFilterRedirectDestTable."
--     ::= { tnFilterRedirectDestEntry 2 }
--
-- tnFilterRDDescription  OBJECT-TYPE
--     SYNTAX       TItemDescription
--     MAX-ACCESS   read-create
--     STATUS       current
--     DESCRIPTION
--         "User-provided description for this destination is maintained in
--         the object tnFilterRDDescription."
--     DEFVAL { ''H }
--     ::= { tnFilterRedirectDestEntry 3 }
--
-- tnFilterRDAdminPriority  OBJECT-TYPE
--     SYNTAX       Unsigned32 (1..255)
--     MAX-ACCESS   read-create
--     STATUS       current
--     DESCRIPTION
--         "tnFilterRDAdminPriority holds the configured base priority for
--         the destination."
--     DEFVAL { 100 }
--     ::= { tnFilterRedirectDestEntry 4 }
--
-- tnFilterRDOperPriority  OBJECT-TYPE
--     SYNTAX       Unsigned32 (0..255)
--     MAX-ACCESS   read-only
--     STATUS       current
--     DESCRIPTION
--         "tnFilterRDAdminPriority maintains the operational value of the
--         priority for this destination. The highest operational priority
--         across multiple destinations is used as the preferred destination.
--
--         A value of '0' is maintained if the destination if tnFilterRDOperState
--         is 'outOfService'."
--     ::= { tnFilterRedirectDestEntry 5 }
--
-- tnFilterRDAdminState  OBJECT-TYPE
--     SYNTAX       TmnxAdminState
--     MAX-ACCESS   read-create
--     STATUS       current
--     DESCRIPTION
--         "tnFilterRDAdminState maintains the configured state of the destination.
--         If the admin state is 'outOfService', the tests for this destination
--         will not be conducted."
--     DEFVAL { inService }
--     ::= { tnFilterRedirectDestEntry 6 }
--
-- tnFilterRDOperState  OBJECT-TYPE
--     SYNTAX       TmnxOperState
--     MAX-ACCESS   read-only
--     STATUS       current
--     DESCRIPTION
--         "The value of tnFilterRDOperState indicates the operational state of
--          the destination."
--     ::= { tnFilterRedirectDestEntry 7 }

--
-- Filter Redirect SNMP Test Table
--

-- tnFilterRedirectSNMPTestTable OBJECT-TYPE
--     SYNTAX       SEQUENCE OF TFilterRedirectSNMPTestEntry
--     MAX-ACCESS   not-accessible
--     STATUS       current
--     DESCRIPTION
--         "Contains a List of all redirect SNMP tests configured on this
--         system."
--     ::= { tnFilterObjects 12 }
--
-- tnFilterRedirectSNMPTestEntry OBJECT-TYPE
--     SYNTAX       TFilterRedirectSNMPTestEntry
--     MAX-ACCESS   not-accessible
--     STATUS       current
--     DESCRIPTION
--         "Information about a specific SNMP test configured for a destination.
--         Entries are created/deleted  by user."
--     INDEX { tnSysSwitchId,
--               tnFilterRedirectPolicy,
--               tnFilterRedirectDest,
--               tnFilterRedirectSNMPTest
--           }
--     ::= { tnFilterRedirectSNMPTestTable 1 }
--
-- TFilterRedirectSNMPTestEntry ::= SEQUENCE
--     {
--         tnFilterRedirectSNMPTest       TNamedItem,
--         tnFilterRSTRowStatus           RowStatus,
--         tnFilterRSTOID                 OBJECT IDENTIFIER,
--         tnFilterRSTCommunity           DisplayString,
--         tnFilterRSTSNMPVersion         INTEGER,
--         tnFilterRSTInterval            Unsigned32,
--         tnFilterRSTTimeout             Unsigned32,
--         tnFilterRSTDropCount           Unsigned32,
--         tnFilterRSTHoldDown            Unsigned32,
--         tnFilterRSTHoldDownRemain      Unsigned32,
--         tnFilterRSTLastActionTime      TimeStamp,
--         tnFilterRSTLastOID             OBJECT IDENTIFIER,
--         tnFilterRSTLastType            INTEGER,
--         tnFilterRSTLastCounter32Val    Counter32,
--         tnFilterRSTLastUnsigned32Val   Unsigned32,
--         tnFilterRSTLastTimeTicksVal    TimeTicks,
--         tnFilterRSTLastInt32Val        Integer32,
--         tnFilterRSTLastOctetStringVal  OCTET STRING,
--         tnFilterRSTLastIpAddressVal    IpAddress,
--         tnFilterRSTLastOidVal          OBJECT IDENTIFIER,
--         tnFilterRSTLastCounter64Val    Counter64,
-- ##         tnFilterRSTLastOpaqueVal       Opaque,
--         tnFilterRSTLastAction          INTEGER,
--         tnFilterRSTLastPrioChange      Integer32,
--         tnFilterRSTNextRespIndex       Integer32
--     }
--
-- tnFilterRedirectSNMPTest  OBJECT-TYPE
--     SYNTAX       TNamedItem
--     MAX-ACCESS   not-accessible
--     STATUS       current
--     DESCRIPTION
--         "tnFilterRedirectSNMPTest specifies the name of the SNMP test."
--     ::= { tnFilterRedirectSNMPTestEntry 1 }
--
-- tnFilterRSTRowStatus  OBJECT-TYPE
--     SYNTAX       RowStatus
--     MAX-ACCESS   read-create
--     STATUS       current
--     DESCRIPTION
--         "tnFilterRSTRowStatus allows tests to be created and deleted in the
--          tnFilterRedirectSNMPTestTable."
--     ::= { tnFilterRedirectSNMPTestEntry 2 }
--
-- tnFilterRSTOID  OBJECT-TYPE
--     SYNTAX       OBJECT IDENTIFIER
--     MAX-ACCESS   read-create
--     STATUS       current
--     DESCRIPTION
--         "tnFilterRSTOID stores the OID of the object to be fetched from the
--        destination.
--        The value of this object can only be changed if the object
--        tFilterRSTCommunity is changed at the same time."
--     ::= { tnFilterRedirectSNMPTestEntry 3 }
--
-- tnFilterRSTCommunity  OBJECT-TYPE
--     SYNTAX       DisplayString (SIZE(0..32))
--     MAX-ACCESS   read-create
--     STATUS       current
--     DESCRIPTION
--         "The value of tnFilterRSTCommunity is the SNMPv1 or SNMPv2c Community
--          String or the SNMPv3 Context Name used to conduct this SNMP test as
--          described in RFC2571 and RFC2737.
--
--          When the value of tnFilterRSTSNMPVersion is 'snmpv1' or 'snmpv2c'
--          this object represents a community string.  When the value of
--          tnFilterRSTSNMPVersion is 'snmpv3' this object represents a SNMPv3
--          context name.
--          The value of this object can only be changed if the object
--          tFilterRSTOID is changed at the same time."
--     DEFVAL { ''H }
--     ::= { tnFilterRedirectSNMPTestEntry 4 }
--
-- tnFilterRSTSNMPVersion OBJECT-TYPE
--     SYNTAX       INTEGER {
--                      snmpv1 (1),
--                      snmpv2c (2),
--                      snmpv3 (3)
--                  }
--     MAX-ACCESS   read-create
--     STATUS       current
--     DESCRIPTION
--         "tnFilterRSTSNMPVersion specifies the SNMP PDU format to be used
--         while conducting the test."
--     DEFVAL { snmpv2c }
--     ::= { tnFilterRedirectSNMPTestEntry 5 }
--
-- tnFilterRSTInterval  OBJECT-TYPE
--     SYNTAX       Unsigned32 (1..60)
--     UNITS        "seconds"
--     MAX-ACCESS   read-create
--     STATUS       current
--     DESCRIPTION
--         "The value of tnFilterRSTInterval specifies the amount of time
--         in seconds between consecutive requests sent to the far end
--         host."
--     DEFVAL { 1 }
--     ::= { tnFilterRedirectSNMPTestEntry 6 }
--
-- tnFilterRSTTimeout  OBJECT-TYPE
--     SYNTAX       Unsigned32 (1..60)
--     UNITS        "seconds"
--     MAX-ACCESS   read-create
--     STATUS       current
--     DESCRIPTION
--         "The value of tnFilterRSTTimeout specifies the amount of time
--         in seconds that is allowed for receiving a response from the
--         far end host. If a reply is not received within this time the
--         far end host is considered unresponsive."
--     DEFVAL { 1 }
--     ::= { tnFilterRedirectSNMPTestEntry 7 }
--
-- tnFilterRSTDropCount  OBJECT-TYPE
--     SYNTAX       Unsigned32 (1..60)
--     MAX-ACCESS   read-create
--     STATUS       current
--     DESCRIPTION
--         "The value of tnFilterRSTDropCount specifies the number of
--         consecutive requests that must fail for the destination to
--         declared unreachable."
--     DEFVAL { 3 }
--     ::= { tnFilterRedirectSNMPTestEntry 8 }
--
-- tnFilterRSTHoldDown  OBJECT-TYPE
--     SYNTAX       Unsigned32 (0..86400)
--     UNITS        "seconds"
--     MAX-ACCESS   read-create
--     STATUS       current
--     DESCRIPTION
--         "The value of tnFilterRSTHoldDown specifies the amount of time
--         in seconds that the system should be held down if any of the test
--         has marked it unreachable."
--     DEFVAL { 0 }
--     ::= { tnFilterRedirectSNMPTestEntry 9 }
--
-- tnFilterRSTHoldDownRemain  OBJECT-TYPE
--     SYNTAX       Unsigned32 (0..86400)
--     UNITS        "seconds"
--     MAX-ACCESS   read-only
--     STATUS       current
--     DESCRIPTION
--         "The value of tnFilterRSTHoldDownRemain indicates the amount of time
--         in seconds that the system will remain in held down state before
--         being used again."
--     ::= { tnFilterRedirectSNMPTestEntry 10 }
--
-- tnFilterRSTLastActionTime  OBJECT-TYPE
--     SYNTAX       TimeStamp
--     MAX-ACCESS   read-only
--     STATUS       current
--     DESCRIPTION
--         "tnFilterRSTLastActionTime maintains the time stamp when this test
--         received a response for a probe sent out."
--     ::= { tnFilterRedirectSNMPTestEntry 11 }
--
-- tnFilterRSTLastOID OBJECT-TYPE
--     SYNTAX     OBJECT IDENTIFIER
--     MAX-ACCESS read-only
--     STATUS     current
--     DESCRIPTION
--      "The object tnFilterRSTLastOID holds the OID received in the
--      response."
--     ::= { tnFilterRedirectSNMPTestEntry 12 }
--
-- tnFilterRSTLastType OBJECT-TYPE
--     SYNTAX      INTEGER {
--                     none(0),
--                     counter32(1),
--                     unsigned32(2),
--                     timeTicks(3),
--                     integer32(4),
--                     ipAddress(5),
--                     octetString(6),
--                     objectId(7),
--                     counter64(8),
--                     opaque(9)
--                 }
--     MAX-ACCESS  read-only
--     STATUS      current
--     DESCRIPTION
--      "tnFilterRSTLastType maintains the type of the value received.
--       A value of none(0) indicated that no value has been received"
--     ::= { tnFilterRedirectSNMPTestEntry  13 }
--
-- tnFilterRSTLastCounter32Val OBJECT-TYPE
--     SYNTAX      Counter32
--     MAX-ACCESS  read-only
--     STATUS      current
--     DESCRIPTION
--      "The value tnFilterRSTLastType is 'counter32'."
--     ::= { tnFilterRedirectSNMPTestEntry  14 }
--
-- tnFilterRSTLastUnsigned32Val OBJECT-TYPE
--     SYNTAX      Unsigned32
--     MAX-ACCESS  read-only
--     STATUS      current
--     DESCRIPTION
--      "The value tnFilterRSTLastType is 'unsigned32'."
--     ::= { tnFilterRedirectSNMPTestEntry  15 }
--
-- tnFilterRSTLastTimeTicksVal OBJECT-TYPE
--     SYNTAX      TimeTicks
--     MAX-ACCESS  read-only
--     STATUS      current
--     DESCRIPTION
--      "The value tnFilterRSTLastType is 'timeTicks'."
--     ::= { tnFilterRedirectSNMPTestEntry  16 }
--
-- tnFilterRSTLastInt32Val OBJECT-TYPE
--     SYNTAX      Integer32
--     MAX-ACCESS  read-only
--     STATUS      current
--     DESCRIPTION
--      "The value tnFilterRSTLastType is 'integer32'."
--     ::= { tnFilterRedirectSNMPTestEntry  17 }
--
-- tnFilterRSTLastOctetStringVal OBJECT-TYPE
--     SYNTAX      OCTET STRING
--     MAX-ACCESS  read-only
--     STATUS      current
--     DESCRIPTION
--      "The value tnFilterRSTLastType is 'octetString'."
--     ::= { tnFilterRedirectSNMPTestEntry  18 }
--
-- tnFilterRSTLastIpAddressVal OBJECT-TYPE
--     SYNTAX      IpAddress
--     MAX-ACCESS  read-only
--     STATUS      current
--     DESCRIPTION
--      "The value tnFilterRSTLastType is 'ipAddress'. Although
--      this seems to be unfriendly for IPv6, we have to
--      recognize that there are a number of older MIBs that do
--      contain an IPv4 format address, known as IpAddress.
--
--      IPv6 addresses are represented using TAddress or InetAddress,
--      and so the underlying datatype is OCTET STRING, and their
--      value would be stored in the tnFilterRSTLastOctetStringVal
--      column."
--     ::= { tnFilterRedirectSNMPTestEntry  19 }
--
-- tnFilterRSTLastOidVal OBJECT-TYPE
--     SYNTAX      OBJECT IDENTIFIER
--     MAX-ACCESS  read-only
--     STATUS      current
--     DESCRIPTION
--      "The value tnFilterRSTLastType is 'objectId'."
--     ::= { tnFilterRedirectSNMPTestEntry  20 }
--
-- tnFilterRSTLastCounter64Val OBJECT-TYPE
--     SYNTAX      Counter64
--     MAX-ACCESS  read-only
--     STATUS      current
--     DESCRIPTION
--      "The value tnFilterRSTLastType is 'counter64'."
--     ::= { tnFilterRedirectSNMPTestEntry  21 }
--
-- ## tnFilterRSTLastOpaqueVal OBJECT-TYPE
-- ##     SYNTAX      Opaque
-- ##     MAX-ACCESS  read-only
-- ##     STATUS      current
-- ##     DESCRIPTION
-- ##      "The value tnFilterRSTLastType is 'opaque'."
-- ##     ::= { tnFilterRedirectSNMPTestEntry  22 }
--
-- tnFilterRSTLastAction  OBJECT-TYPE
--     SYNTAX       INTEGER {
--                      enable (1),
--                      disable (2),
--                      none (3)
--                  }
--     MAX-ACCESS   read-only
--     STATUS       current
--     DESCRIPTION
--         "tnFilterRSTLastAction maintains impact that the last test probe
--         made on the operational status of the destination as maintained
--         in tnFilterRDOperState.
--
--         If the last action was 'disable', the destination may not be
--         used for tnFilterRSTHoldDown seconds."
--     ::= { tnFilterRedirectSNMPTestEntry 23 }
--
-- tnFilterRSTLastPrioChange  OBJECT-TYPE
--     SYNTAX       Integer32 (-255..255)
--     MAX-ACCESS   read-only
--     STATUS       current
--     DESCRIPTION
--         "If the last action on the operational state of the destination
--         i.e. tnFilterRSTLastAction is 'enable', tnFilterRSTLastPrioChange
--         maintains the impact that the last test probe made on the
--         operational priority of the destination.
--
--         In other cases, this object has no significance and hence should
--         be holding the value '0'."
--     ::= { tnFilterRedirectSNMPTestEntry 24 }
--
-- tnFilterRSTNextRespIndex  OBJECT-TYPE
--     SYNTAX       Integer32 (-1|1..2147483647)
--     MAX-ACCESS   read-only
--     STATUS       current
--     DESCRIPTION
--         "The value of tnFilterRSTNextRespIndex indicates the next response index
--         to be used while creating a row in the tnFilterRedirectSNMPRespTable.
--
--         The value of '-1' means that the maximum number of return values
--         for this OID are already configured."
--     ::= { tnFilterRedirectSNMPTestEntry 25 }

--
-- Filter Redirect SNMP Response Table
--

-- tnFilterRedirectSNMPRespTable OBJECT-TYPE
--     SYNTAX       SEQUENCE OF TFilterRedirectSNMPRespEntry
--     MAX-ACCESS   not-accessible
--     STATUS       current
--     DESCRIPTION
--         "Each row in this table holds the effect of the test on the
--         destination for a specific return value."
--     ::= { tnFilterObjects 13 }
--
-- tnFilterRedirectSNMPRespEntry OBJECT-TYPE
--     SYNTAX       TFilterRedirectSNMPRespEntry
--     MAX-ACCESS   not-accessible
--     STATUS       current
--     DESCRIPTION
--         "Information about action to be taken for a specific destination
--         when a specific response is received."
--     INDEX { tnSysSwitchId,
--               tnFilterRedirectPolicy,
--               tnFilterRedirectDest,
--               tnFilterRedirectSNMPTest,
--               tnFilterRSTRespId
--           }
--     ::= { tnFilterRedirectSNMPRespTable 1 }
--
-- TFilterRedirectSNMPRespEntry ::= SEQUENCE
--     {
--         tnFilterRSTRespId          Integer32,
--         tnFilterRSTRespRowStatus   RowStatus,
--         tnFilterRSTRespAction      INTEGER,
--         tnFilterRSTRespPrioChange  Unsigned32,
--         tnFilterRSTRespOID         OBJECT IDENTIFIER,
--         tnFilterRSTRespType        INTEGER,
--         tnFilterRSTCounter32Val    Counter32,
--         tnFilterRSTUnsigned32Val   Unsigned32,
--         tnFilterRSTTimeTicksVal    TimeTicks,
--         tnFilterRSTInt32Val        Integer32,
--         tnFilterRSTOctetStringVal  OCTET STRING,
--         tnFilterRSTIpAddressVal    IpAddress,
--         tnFilterRSTOidVal          OBJECT IDENTIFIER,
--         tnFilterRSTCounter64Val    Counter64  ## ,
-- ##         tnFilterRSTOpaqueVal       Opaque
--     }
--
-- tnFilterRSTRespId  OBJECT-TYPE
--     SYNTAX       Integer32 (1..2147483647)
--     MAX-ACCESS   not-accessible
--     STATUS       current
--     DESCRIPTION
--         "tnFilterRSTRespId holds the response value received from
--         the destination."
--     ::= { tnFilterRedirectSNMPRespEntry 1 }
--
-- tnFilterRSTRespRowStatus  OBJECT-TYPE
--     SYNTAX       RowStatus
--     MAX-ACCESS   read-create
--     STATUS       current
--     DESCRIPTION
--         "This object allows response strings to be specified for a specific
--         test and the change it will cause to the priority of the destination."
--     ::= { tnFilterRedirectSNMPRespEntry 2 }
--
-- tnFilterRSTRespAction OBJECT-TYPE
--     SYNTAX       INTEGER {
--                      increase (1),
--                      decrease (2),
--                      disable (3)
--                      }
--     MAX-ACCESS   read-create
--     STATUS       current
--     DESCRIPTION
--         "tnFilterRSTRespAction specifies the type of change that should
--         be made to the destination priority tnFilterRDOperPriority, if
--         the return value is same as tnFilterRSTRespId."
--     DEFVAL { disable }
--     ::= { tnFilterRedirectSNMPRespEntry 3 }
--
-- tnFilterRSTRespPrioChange OBJECT-TYPE
--     SYNTAX       Unsigned32 (0..255)
--     MAX-ACCESS   read-create
--     STATUS       current
--     DESCRIPTION
--         "tnFilterRSTRespPrioChange specifies the amount of change to
--         be made to the priority of the destination if the
--         tnFilterRSTRespAction is either 'increase' or 'decrease'."
--     DEFVAL { 0 }
--     ::= { tnFilterRedirectSNMPRespEntry 4 }
--
-- tnFilterRSTRespOID OBJECT-TYPE
--     SYNTAX     OBJECT IDENTIFIER
--     MAX-ACCESS read-create
--     STATUS     current
--     DESCRIPTION
--      "The object tnFilterRSTRespOID holds the OID to be received in the
--      response."
--     ::= { tnFilterRedirectSNMPRespEntry 5 }
--
-- tnFilterRSTRespType OBJECT-TYPE
--     SYNTAX      INTEGER {
--                     counter32(1),
--                     unsigned32(2),
--                     timeTicks(3),
--                     integer32(4),
--                     ipAddress(5),
--                     octetString(6),
--                     objectId(7),
--                     counter64(8),
--                     opaque(9)
--                 }
--     MAX-ACCESS  read-create
--     STATUS      current
--     DESCRIPTION
--      "tnFilterRSTRespType maintains the type of the value to be received."
--     ::= { tnFilterRedirectSNMPRespEntry  6 }
--
-- tnFilterRSTCounter32Val OBJECT-TYPE
--     SYNTAX      Counter32
-- ##     MAX-ACCESS  read-create
--     MAX-ACCESS  read-only
--     STATUS      current
--     DESCRIPTION
--      "The value tnFilterRSTRespType is 'counter32'."
--     ::= { tnFilterRedirectSNMPRespEntry  7 }
--
-- tnFilterRSTUnsigned32Val OBJECT-TYPE
--     SYNTAX      Unsigned32
--     MAX-ACCESS  read-create
--     STATUS      current
--     DESCRIPTION
--      "The value tnFilterRSTRespType is 'unsigned32'."
--     ::= { tnFilterRedirectSNMPRespEntry  8 }
--
-- tnFilterRSTTimeTicksVal OBJECT-TYPE
--     SYNTAX      TimeTicks
--     MAX-ACCESS  read-create
--     STATUS      current
--     DESCRIPTION
--      "The value tnFilterRSTRespType is 'timeTicks'."
--     ::= { tnFilterRedirectSNMPRespEntry  9 }
--
-- tnFilterRSTInt32Val OBJECT-TYPE
--     SYNTAX      Integer32
--     MAX-ACCESS  read-create
--     STATUS      current
--     DESCRIPTION
--      "The value tnFilterRSTRespType is 'integer32'."
--     ::= { tnFilterRedirectSNMPRespEntry  10 }
--
-- tnFilterRSTOctetStringVal OBJECT-TYPE
--     SYNTAX      OCTET STRING
--     MAX-ACCESS  read-create
--     STATUS      current
--     DESCRIPTION
--      "The value tnFilterRSTRespType is 'octetString'."
--     ::= { tnFilterRedirectSNMPRespEntry  11 }
--
-- tnFilterRSTIpAddressVal OBJECT-TYPE
--     SYNTAX      IpAddress
--     MAX-ACCESS  read-create
--     STATUS      current
--     DESCRIPTION
--      "The value tnFilterRSTRespType is 'ipAddress'. Although
--      this seems to be unfriendly for IPv6, we have to
--      recognize that there are a number of older MIBs that do
--      contain an IPv4 format address, known as IpAddress.
--
--      IPv6 addresses are represented using TAddress or InetAddress,
--      and so the underlying datatype is OCTET STRING, and their
--      value would be stored in the tnFilterRSTOctetStringVal
--      column."
--     ::= { tnFilterRedirectSNMPRespEntry  12 }
--
-- tnFilterRSTOidVal OBJECT-TYPE
--     SYNTAX      OBJECT IDENTIFIER
--     MAX-ACCESS  read-create
--     STATUS      current
--     DESCRIPTION
--      "The value tnFilterRSTRespType is 'objectId'."
--     ::= { tnFilterRedirectSNMPRespEntry  13 }
--
-- tnFilterRSTCounter64Val OBJECT-TYPE
--     SYNTAX      Counter64
-- ##     MAX-ACCESS  read-create
--     MAX-ACCESS  read-only
--     STATUS      current
--     DESCRIPTION
--      "The value tnFilterRSTRespType is 'counter64'."
--     ::= { tnFilterRedirectSNMPRespEntry  14 }
--
-- ## tnFilterRSTOpaqueVal OBJECT-TYPE
-- ##    SYNTAX      Opaque
-- ##    MAX-ACCESS  read-create
-- ##    STATUS      current
-- ##    DESCRIPTION
-- ##     "The value tnFilterRSTRespType is 'opaque'."
-- ##    ::= { tnFilterRedirectSNMPRespEntry  15 }

--
-- Filter Redirect URL Test Table
--

-- tnFilterRedirectURLTestTable OBJECT-TYPE
--     SYNTAX       SEQUENCE OF TFilterRedirectURLTestEntry
--     MAX-ACCESS   not-accessible
--     STATUS       current
--     DESCRIPTION
--         "Contains a List of all redirect snmp tests configured on this
--         system."
--     ::= { tnFilterObjects 14 }
--
-- tnFilterRedirectURLTestEntry OBJECT-TYPE
--     SYNTAX       TFilterRedirectURLTestEntry
--     MAX-ACCESS   not-accessible
--     STATUS       current
--     DESCRIPTION
--         "Information about a specific URL test configured for a destination.
--         Entries are created/deleted  by user. Entries have a presumed
--         StorageType of nonVolatile."
--     INDEX { tnSysSwitchId,
--               tnFilterRedirectPolicy,
--               tnFilterRedirectDest,
--               tnFilterRedirectURLTest
--           }
--     ::= { tnFilterRedirectURLTestTable 1 }
--
-- TFilterRedirectURLTestEntry ::= SEQUENCE
--     {
--         tnFilterRedirectURLTest    TNamedItem,
--         tnFilterRUTRowStatus       RowStatus,
--         tnFilterRUTURL             DisplayString,
--         tnFilterRUTHTTPVersion     DisplayString,
--         tnFilterRUTInterval        Unsigned32,
--         tnFilterRUTTimeout         Unsigned32,
--         tnFilterRUTDropCount       Unsigned32,
--         tnFilterRUTHoldDown        Unsigned32,
--         tnFilterRUTHoldDownRemain  Unsigned32,
--         tnFilterRUTLastActionTime  TimeStamp,
--         tnFilterRUTLastRetCode     Unsigned32,
--         tnFilterRUTLastAction      INTEGER,
--         tnFilterRUTLastPrioChange  Integer32
--     }
--
-- tnFilterRedirectURLTest  OBJECT-TYPE
--     SYNTAX       TNamedItem
--     MAX-ACCESS   not-accessible
--     STATUS       current
--     DESCRIPTION
--         "tnFilterRedirectURLTest holds the name of the URL test."
--     ::= { tnFilterRedirectURLTestEntry 1 }
--
-- tnFilterRUTRowStatus  OBJECT-TYPE
--     SYNTAX       RowStatus
--     MAX-ACCESS   read-create
--     STATUS       current
--     DESCRIPTION
--         "tnFilterRUTRowStatus allows tests to be created and deleted in the
--         tnFilterRedirectURLTestTable."
--     ::= { tnFilterRedirectURLTestEntry 2 }
--
-- tnFilterRUTURL  OBJECT-TYPE
--     SYNTAX       DisplayString
--     MAX-ACCESS   read-create
--     STATUS       current
--     DESCRIPTION
--         "This object holds the URL to be probed."
--     DEFVAL { ''H }
--     ::= { tnFilterRedirectURLTestEntry 3 }
--
-- tnFilterRUTHTTPVersion OBJECT-TYPE
--     SYNTAX       DisplayString
--     MAX-ACCESS   read-create
--     STATUS       current
--     DESCRIPTION
--         "The HTTP Version to be used while performing the URL test.
--         The system by default uses HTTP Version 1.1 until explicitly
--         specified."
--     DEFVAL { ''H }
--     ::= { tnFilterRedirectURLTestEntry 4 }
--
-- tnFilterRUTInterval  OBJECT-TYPE
--     SYNTAX       Unsigned32 (1..60)
--     UNITS        "seconds"
--     MAX-ACCESS   read-create
--     STATUS       current
--     DESCRIPTION
--         "The value of tnFilterRUTInterval specifies the amount of time
--         in seconds between consecutive requests sent to the far end
--         host."
--     DEFVAL { 1 }
--     ::= { tnFilterRedirectURLTestEntry 5 }
--
-- tnFilterRUTTimeout  OBJECT-TYPE
--     SYNTAX       Unsigned32 (1..60)
--     UNITS        "seconds"
--     MAX-ACCESS   read-create
--     STATUS       current
--     DESCRIPTION
--         "The value of tnFilterRUTTimeout specifies the amount of time
--         in seconds that is allowed for receiving a response from the
--         far end host. If a reply is not received within this time the
--         far end host is considered unresponsive."
--     DEFVAL { 1 }
--     ::= { tnFilterRedirectURLTestEntry 6 }
--
-- tnFilterRUTDropCount  OBJECT-TYPE
--     SYNTAX       Unsigned32 (1..60)
--     MAX-ACCESS   read-create
--     STATUS       current
--     DESCRIPTION
--         "The value of tnFilterRUTDropCount specifies the number of
--         consecutive requests that must fail for the destination to
--         declared unreachable."
--     DEFVAL { 3 }
--     ::= { tnFilterRedirectURLTestEntry 7 }
--
-- tnFilterRUTHoldDown  OBJECT-TYPE
--     SYNTAX       Unsigned32 (0..86400)
--     UNITS        "seconds"
--     MAX-ACCESS   read-create
--     STATUS       current
--     DESCRIPTION
--         "The value of tnFilterRUTHoldDown specifies the amount of time
--         in seconds that the system should be held down if any of the test
--         has marked it unreachable."
--     DEFVAL { 0 }
--     ::= { tnFilterRedirectURLTestEntry 8 }
--
-- tnFilterRUTHoldDownRemain  OBJECT-TYPE
--     SYNTAX       Unsigned32 (0..86400)
--     UNITS        "seconds"
--     MAX-ACCESS   read-only
--     STATUS       current
--     DESCRIPTION
--         "The value of tnFilterRUTHoldDownRemain indicates the amount of time
--         in seconds that the system will remain in held down state before
--         being used again."
--     ::= { tnFilterRedirectURLTestEntry 9 }
--
-- tnFilterRUTLastActionTime  OBJECT-TYPE
--     SYNTAX       TimeStamp
--     MAX-ACCESS   read-only
--     STATUS       current
--     DESCRIPTION
--         "tnFilterRUTLastActionTime maintains the time stamp when this test
--         received a response for a probe sent out."
--     ::= { tnFilterRedirectURLTestEntry 10 }
--
-- tnFilterRUTLastRetCode  OBJECT-TYPE
--     SYNTAX       Unsigned32
--     MAX-ACCESS   read-only
--     STATUS       current
--     DESCRIPTION
--         "tnFilterRUTLastRetCode holds the return code received in the last
--         response."
--     ::= { tnFilterRedirectURLTestEntry 11 }
--
-- tnFilterRUTLastAction  OBJECT-TYPE
--     SYNTAX       INTEGER {
--                      enable (1),
--                      disable (2),
--                      none (3)
--                  }
--     MAX-ACCESS   read-only
--     STATUS       current
--     DESCRIPTION
--         "tnFilterRUTLastAction maintains impact that the last test probe
--         made on the operational status of the destination as maintained
--         in tnFilterRDOperState.
--
--         If the last action was 'disable', the destination may not be
--         used for tnFilterRUTHoldDown seconds."
--     ::= { tnFilterRedirectURLTestEntry 12 }
--
-- tnFilterRUTLastPrioChange  OBJECT-TYPE
--     SYNTAX       Integer32 (-255..255)
--     MAX-ACCESS   read-only
--     STATUS       current
--     DESCRIPTION
--         "If the last action on the operational state of the destination
--         i.e. tnFilterRUTLastAction is 'enable', tnFilterRUTLastPrioChange
--         maintains the impact that the last test probe made on the
--         operational priority of the destination.
--
--         In other cases, this object has no significance and hence should
--         be holding the value '0'."
--     ::= { tnFilterRedirectURLTestEntry 13 }

--
-- Filter Redirect URL Response Table
--

-- tnFilterRedirectURLRespTable OBJECT-TYPE
--     SYNTAX       SEQUENCE OF TFilterRedirectURLRespEntry
--     MAX-ACCESS   not-accessible
--     STATUS       current
--     DESCRIPTION
--         "Each row in this table holds the effect of the test on
--         the destination for a range of return values."
--     ::= { tnFilterObjects 15 }
--
-- tnFilterRedirectURLRespEntry OBJECT-TYPE
--     SYNTAX       TFilterRedirectURLRespEntry
--     MAX-ACCESS   not-accessible
--     STATUS       current
--     DESCRIPTION
--         "Information about action to be taken for a specific destination
--         when a return value within the range specified between
--         tnFilterRedirectURLLowRespCode and tnFilterRedirectURLHighRespCode
--         is received."
--     INDEX { tnSysSwitchId,
--               tnFilterRedirectPolicy,
--               tnFilterRedirectDest,
--               tnFilterRedirectURLTest,
--               tnFilterRedirectURLLowRespCode,
--               tnFilterRedirectURLHighRespCode
--           }
--     ::= { tnFilterRedirectURLRespTable 1 }
--
-- TFilterRedirectURLRespEntry ::= SEQUENCE
--     {
--         tnFilterRedirectURLLowRespCode  Unsigned32,
--         tnFilterRedirectURLHighRespCode Unsigned32,
--         tnFilterRUTRespRowStatus        RowStatus,
--         tnFilterRUTRespAction           INTEGER,
--         tnFilterRUTRespPrioChange       Unsigned32
--     }
--
-- tnFilterRedirectURLLowRespCode  OBJECT-TYPE
--     SYNTAX       Unsigned32
--     MAX-ACCESS   not-accessible
--     STATUS       current
--     DESCRIPTION
--         "tnFilterRedirectURLLowRespCode specifies the lower return
--         code of the range specified by this entry."
--     ::= { tnFilterRedirectURLRespEntry 1 }
--
-- tnFilterRedirectURLHighRespCode  OBJECT-TYPE
--     SYNTAX       Unsigned32
--     MAX-ACCESS   not-accessible
--     STATUS       current
--     DESCRIPTION
--         "tnFilterRedirectURLHighRespCode specifies the higher return
--         code of the range specified by this entry."
--     ::= { tnFilterRedirectURLRespEntry 2 }
--
-- tnFilterRUTRespRowStatus  OBJECT-TYPE
--     SYNTAX       RowStatus
--     MAX-ACCESS   read-create
--     STATUS       current
--     DESCRIPTION
--         "tnFilterRUTRespRowStatus allows the mapping of a range of
--         return codes returned from a specific test to the change it
--         will cause to the priority of the destination."
--     ::= { tnFilterRedirectURLRespEntry 3 }
--
-- tnFilterRUTRespAction  OBJECT-TYPE
--     SYNTAX       INTEGER {
--                      increase (1),
--                      decrease (2),
--                      disable  (3)
--                      }
--     MAX-ACCESS   read-create
--     STATUS       current
--     DESCRIPTION
--        "If the tFilterRUTRespAction is either 'increase(1)' or 'decrease(2)'
--        tFilterRUTRespPrioChange specifies the offset to be applied to the
--        destination base priority (tFilterRDAdminPriority) in order to
--        compute the tFilterRDOperPriority as a result of this test.
--
--        If the tFilterRUTRespAction is set to 'disable(3)', on the reception
--        of the specified response, the destination will be deemed
--        unusable and the tFilterRDOperPriority will be set to '0'.
--        The value of tFilterRUTRespAction will be forced by the system to
--        the value 'disable(3)' if the tFilterRUTRespPrioChange has the value '0'."
--     DEFVAL { disable }
--     ::= { tnFilterRedirectURLRespEntry 4 }
--
-- tnFilterRUTRespPrioChange OBJECT-TYPE
--     SYNTAX       Unsigned32 (0..255)
--     MAX-ACCESS   read-create
--     STATUS       current
--     DESCRIPTION
--         "tnFilterRUTRespPrioChange specifies the amount of change
--         to be made to the priority of the destination if the
--         tFilterRUTRespAction is either 'increase' or 'decrease'.
--
--         Setting the object tFilterRUTRespPrioChange will cause the value of
--         tFilterRUTRespAction to be set to disable"
--     DEFVAL { 0 }
--     ::= { tnFilterRedirectURLRespEntry 5 }

--
-- Filter Redirect Ping Test Table
--

-- tnFilterRedirectPingTestTable OBJECT-TYPE
--     SYNTAX       SEQUENCE OF TFilterRedirectPingTestEntry
--     MAX-ACCESS   not-accessible
--     STATUS       current
--     DESCRIPTION
--         "Contains a List of all redirect Ping tests configured on this
--         system."
--     ::= { tnFilterObjects 16 }
--
-- tnFilterRedirectPingTestEntry OBJECT-TYPE
--     SYNTAX       TFilterRedirectPingTestEntry
--     MAX-ACCESS   not-accessible
--     STATUS       current
--     DESCRIPTION
--         "Information about a specific Ping test configured for a destination.
--         Entries are created/deleted  by user. Entries have a presumed
--         StorageType of nonVolatile."
--     INDEX { tnSysSwitchId,
--               tnFilterRedirectPolicy,
--               tnFilterRedirectDest
--           }
--     ::= { tnFilterRedirectPingTestTable 1 }
--
-- TFilterRedirectPingTestEntry ::= SEQUENCE
--     {
--         tnFilterRPTRowStatus       RowStatus,
--         tnFilterRPTInterval        Unsigned32,
--         tnFilterRPTTimeout         Unsigned32,
--         tnFilterRPTDropCount       Unsigned32,
--         tnFilterRPTHoldDown        Unsigned32,
--         tnFilterRPTHoldDownRemain  Unsigned32,
--         tnFilterRPTLastActionTime  TimeStamp,
--         tnFilterRPTLastAction      INTEGER
--     }
--
-- tnFilterRPTRowStatus  OBJECT-TYPE
--     SYNTAX       RowStatus
--     MAX-ACCESS   read-create
--     STATUS       current
--     DESCRIPTION
--         "This object allows tests to be created and deleted in the
--          tnFilterRedirectPingTestTable."
--     ::= { tnFilterRedirectPingTestEntry 1 }
--
-- tnFilterRPTInterval  OBJECT-TYPE
--     SYNTAX       Unsigned32 (1..60)
--     UNITS        "seconds"
--     MAX-ACCESS   read-create
--     STATUS       current
--     DESCRIPTION
--         "The value of tnFilterRPTInterval specifies the amount of time
--         in seconds between consecutive requests sent to the far end
--         host."
--     DEFVAL { 1 }
--     ::= { tnFilterRedirectPingTestEntry 2 }
--
-- tnFilterRPTTimeout  OBJECT-TYPE
--     SYNTAX       Unsigned32 (1..60)
--     UNITS        "seconds"
--     MAX-ACCESS   read-create
--     STATUS       current
--     DESCRIPTION
--         "The value of tnFilterRPTTimeout specifies the amount of time
--         in seconds that is allowed for receiving a response from the
--         far end host. If a reply is not received within this time the
--         far end host is considered unresponsive."
--     DEFVAL { 1 }
--     ::= { tnFilterRedirectPingTestEntry 3 }
--
-- tnFilterRPTDropCount  OBJECT-TYPE
--     SYNTAX       Unsigned32 (1..60)
--     MAX-ACCESS   read-create
--     STATUS       current
--     DESCRIPTION
--         "The value of tnFilterRPTDropCount specifies the number of
--         consecutive requests that must fail for the destination to
--         declared unreachable."
--     DEFVAL { 3 }
--     ::= { tnFilterRedirectPingTestEntry 4 }
--
-- tnFilterRPTHoldDown  OBJECT-TYPE
--     SYNTAX       Unsigned32 (0..86400)
--     UNITS        "seconds"
--     MAX-ACCESS   read-create
--     STATUS       current
--     DESCRIPTION
--         "The value of tnFilterRPTHoldDown specifies the amount of time
--         in seconds that the system should be held down if any of the test
--         has marked it unreachable."
--     DEFVAL { 0 }
--     ::= { tnFilterRedirectPingTestEntry 5 }
--
-- tnFilterRPTHoldDownRemain  OBJECT-TYPE
--     SYNTAX       Unsigned32 (0..86400)
--     UNITS        "seconds"
--     MAX-ACCESS   read-only
--     STATUS       current
--     DESCRIPTION
--         "The value of tnFilterRPTHoldDownRemain indicates the amount of time
--         in seconds that the system will remain in held down state before
--         being used again."
--     ::= { tnFilterRedirectPingTestEntry 6 }
--
-- tnFilterRPTLastActionTime  OBJECT-TYPE
--     SYNTAX       TimeStamp
--     MAX-ACCESS   read-only
--     STATUS       current
--     DESCRIPTION
--         "tnFilterRPTLastActionTime maintains the time stamp when this test
--         received a response for a probe sent out."
--     ::= { tnFilterRedirectPingTestEntry 7 }
--
-- tnFilterRPTLastAction  OBJECT-TYPE
--     SYNTAX       INTEGER {
--                      enable (1),
--                      disable (2),
--                      none (3)
--                  }
--     MAX-ACCESS   read-only
--     STATUS       current
--     DESCRIPTION
--         "tnFilterRPTLastAction maintains impact that the last test probe
--         made on the operational status of the destination as maintained
--         in tnFilterRDOperState.
--
--         If the last action was 'disable', the destination may not be
--         used for tnFilterRPTHoldDown seconds."
--     ::= { tnFilterRedirectPingTestEntry 8 }

--
-- Auto IP Filter Entries
--
--
-- tnAutoIPFilterEntryTable OBJECT-TYPE
--     SYNTAX       SEQUENCE OF TAutoIPFilterEntry
--     MAX-ACCESS   not-accessible
--     STATUS       obsolete
--     DESCRIPTION
--         "Defines the Nokia 7x50 SR series automatic IP filters
--          for providing, via SNMP, the capability of gathering
--          information regarding the same.
--
--          tnAutoIPFilterEntryTable holds a list of all automatic
--          filter entries being used for filtering.
--
--          This table is obsoleted in release 3.0."
--     ::= { tnFilterObjects 17 }
--
-- tnAutoIPFilterEntry OBJECT-TYPE
--     SYNTAX       TAutoIPFilterEntry
--     MAX-ACCESS   not-accessible
--     STATUS       obsolete
--     DESCRIPTION
--         "Defines an entry in the tnAutoIPFilterEntryTable.
--
--          Entries are created and deleted in this table by the
--          system.
--
--          Each entry provides information about a single active
--          automatic filter entry.
--
--          This entry is obsoleted in release 3.0."
--     INDEX { tnSysSwitchId, tnAutoIPFilterId, tnAutoIPFilterEntrySourceIpAddr }
--     ::= { tnAutoIPFilterEntryTable 1 }
--
-- TAutoIPFilterEntry ::= SEQUENCE
--     {
--         tnAutoIPFilterId                   TFilterID,
--         tnAutoIPFilterEntrySourceIpAddr    IpAddress,
--         tnAutoIPFilterEntrySourceIpMask    IpAddressPrefixLength
--     }
--
-- tnAutoIPFilterId  OBJECT-TYPE
--     SYNTAX       TFilterID (1..65535)
--     MAX-ACCESS   not-accessible
--     STATUS       obsolete
--     DESCRIPTION
--         "tnAutoIPFilterId serves as a primary index and uniquely
--          identifies an application point such as a routed
--          interface or a SAP.
--
--          This object is obsoleted in release 3.0."
--     ::= { tnAutoIPFilterEntry 1 }
--
-- tnAutoIPFilterEntrySourceIpAddr  OBJECT-TYPE
--     SYNTAX       IpAddress
--     MAX-ACCESS   not-accessible
--     STATUS       obsolete
--     DESCRIPTION
--         "tnAutoIPFilterEntrySourceIpAddr specifies the source
--          ip-address and also serves as the secondary index to
--          this table.
--
--          This object is obsoleted in release 3.0."
--     ::= { tnAutoIPFilterEntry 2 }
--
-- tnAutoIPFilterEntrySourceIpMask  OBJECT-TYPE
--     SYNTAX       IpAddressPrefixLength
--     MAX-ACCESS   read-only
--     STATUS       obsolete
--     DESCRIPTION
--         "The value of tnAutoIPFilterEntrySourceIpMask indicates the number
--          of bits to be matched in the source ip-address.
--
--          This object is obsoleted in release 3.0."
--     ::= { tnAutoIPFilterEntry 3 }

--
-- Filter Domain Time Stamp
--

-- tnFilterDomainLastChanged OBJECT-TYPE
--     SYNTAX       TimeStamp
--     MAX-ACCESS   read-only
--     STATUS       current
--     DESCRIPTION
--         "timestamp of last change to tnFilterObjects."
--     ::= { tnFilterTimeStampObjects 1 }

--
-- IPv6 Filter Table
--

-- tnIPv6FilterTable OBJECT-TYPE
--     SYNTAX       SEQUENCE OF TIPv6FilterEntry
--     MAX-ACCESS   not-accessible
--     STATUS       current
--     DESCRIPTION
--         "Contains a List of all IPv6 filters configured on this system."
--     ::= { tnFilterObjects 18 }
--
-- tnIPv6FilterEntry OBJECT-TYPE
--     SYNTAX       TIPv6FilterEntry
--     MAX-ACCESS   not-accessible
--     STATUS       current
--     DESCRIPTION
--         "Information about a particular IPv6 Filter entry. Entries are
--          created/deleted  by user. Entries have a presumed StorageType of
--          nonVolatile."
--     INDEX { tnSysSwitchId, tnIPv6FilterId }
--     ::= { tnIPv6FilterTable 1 }
--
-- TIPv6FilterEntry ::= SEQUENCE
--     {
--         tnIPv6FilterId               TIPFilterID,
--         tnIPv6FilterRowStatus        RowStatus,
--         tnIPv6FilterScope            TItemScope,
--         tnIPv6FilterDescription      TItemDescription,
--         tnIPv6FilterDefaultAction    TFilterAction
--     }
--
-- tnIPv6FilterId  OBJECT-TYPE
--     SYNTAX       TIPFilterID (1..65535)
--     MAX-ACCESS   not-accessible
--     STATUS       current
--     DESCRIPTION
--         "The value of the object tnIPv6FilterId uniquely identifies a
--          IPv6 filter on this system."
--     ::= { tnIPv6FilterEntry 1 }
--
-- tnIPv6FilterRowStatus  OBJECT-TYPE
--     SYNTAX       RowStatus
--     MAX-ACCESS   read-create
--     STATUS       current
--     DESCRIPTION
--         "The value of the object tnIPv6FilterRowStatus specifies
--          the status of the IPv6 filter. The object allows
--          entries to be created and deleted in the tnIPv6FilterTable."
--     ::= { tnIPv6FilterEntry 2 }
--
-- tnIPv6FilterScope  OBJECT-TYPE
--     SYNTAX       TItemScope
--     MAX-ACCESS   read-create
--     STATUS       current
--     DESCRIPTION
--         "The value of the object  tnIPv6FilterScope specifies the
--          scope of this filter definition. If defined as exclusive(1),
--          this filter can be instantiated only once as compared
--          to the multiple instances that the filter can have if defined as
--          template(2)."
--     DEFVAL { template }
--     ::= { tnIPv6FilterEntry 3 }
--
-- tnIPv6FilterDescription  OBJECT-TYPE
--     SYNTAX       TItemDescription
--     MAX-ACCESS   read-create
--     STATUS       current
--     DESCRIPTION
--         "The value of the object tnIPv6FilterDescription specifies
--          a user-provided description for this filter."
--     DEFVAL { ''H }
--     ::= { tnIPv6FilterEntry 4 }
--
-- tnIPv6FilterDefaultAction  OBJECT-TYPE
--     SYNTAX       TFilterAction
--     MAX-ACCESS   read-create
--     STATUS       current
--     DESCRIPTION
--         "The value of the object tnIPv6FilterDefaultAction specifies
--          the action to be taken for packets that do not match any
--          of the filter entries."
--     DEFVAL { drop }
--     ::= { tnIPv6FilterEntry 5 }

--
-- IPv6 Filter Entry parameters
--

-- tnIPv6FilterParamsTable OBJECT-TYPE
--     SYNTAX       SEQUENCE OF TIPv6FilterParamsEntry
--     MAX-ACCESS   not-accessible
--     STATUS       current
--     DESCRIPTION  "A table of all IPv6 filter match entries for all IPv6 filters."
--     ::= { tnFilterObjects 19 }
--
-- tnIPv6FilterParamsEntry OBJECT-TYPE
--     SYNTAX       TIPv6FilterParamsEntry
--     MAX-ACCESS   not-accessible
--     STATUS       current
--     DESCRIPTION
--         "Information about a particular IPv6 Filter entry.
--          Every IPv6 Filter can have zero or more IPv6 Filter match entries.
--
--          a filter entry with no match criteria set will match every
--          packet, and the entry action will be taken.
--
--          Entries are created/deleted by user.
--
--          There is no StorageType object, entries have a presumed
--          StorageType of nonVolatile."
--     INDEX { tnSysSwitchId, tnIPv6FilterId, tnIPv6FilterParamsIndex }
--     ::= { tnIPv6FilterParamsTable 1 }
--
-- TIPv6FilterParamsEntry ::= SEQUENCE
--     {
--         tnIPv6FilterParamsIndex               TEntryId,
--         tnIPv6FilterParamsRowStatus           RowStatus,
--         tnIPv6FilterParamsLogId               TFilterLogId,
--         tnIPv6FilterParamsDescription         TItemDescription,
--         tnIPv6FilterParamsAction              TFilterActionOrDefault,
--         tnIPv6FilterParamsForwardNH           InetAddressIPv6,
--         tnIPv6FilterParamsForwardNHIndirect   TruthValue,
--         tnIPv6FilterParamsRemarkDSCP          TDSCPFilterActionValue,
--         tnIPv6FilterParamsRemarkDSCPMask      TDSCPFilterActionValue,
--         tnIPv6FilterParamsRemarkDot1p         Dot1PPriority,
--         tnIPv6FilterParamsSourceIpAddr        InetAddressIPv6,
--         tnIPv6FilterParamsSourceIpMask        InetAddressPrefixLength,
--         tnIPv6FilterParamsDestinationIpAddr   InetAddressIPv6,
--         tnIPv6FilterParamsDestinationIpMask   InetAddressPrefixLength,
--         tnIPv6FilterParamsNextHeader          TIpProtocol,
--         tnIPv6FilterParamsSourcePortValue1    TTcpUdpPort,
--         tnIPv6FilterParamsSourcePortValue2    TTcpUdpPort,
--         tnIPv6FilterParamsSourcePortOperator  TTcpUdpPortOperator,
--         tnIPv6FilterParamsDestPortValue1      TTcpUdpPort,
--         tnIPv6FilterParamsDestPortValue2      TTcpUdpPort,
--         tnIPv6FilterParamsDestPortOperator    TTcpUdpPortOperator,
--         tnIPv6FilterParamsDSCP                TDSCPNameOrEmpty,
--         tnIPv6FilterParamsTcpSyn              TItemMatch,
--         tnIPv6FilterParamsTcpAck              TItemMatch,
--         tnIPv6FilterParamsIcmpCode            INTEGER,
--         tnIPv6FilterParamsIcmpType            INTEGER,
--         tnIPv6FilterParamsCflowdSample        TruthValue,
--         tnIPv6FilterParamsCflowdIfSample      TruthValue,
--         tnIPv6FilterParamsForwardNHInterface  DisplayString,
--         tnIPv6FilterParamsIngressHitCount     Counter64,
--         tnIPv6FilterParamsEgressHitCount      Counter64,
--         tnIPv6FilterParamsLogInstantiated     TruthValue,
--         tnIPv6FilterParamsForwardRedPlcy      TNamedItemOrEmpty,
--         tnIPv6FilterParamsActiveDest          InetAddressIPv6,
--         tnIPv6FilterParamsTimeRangeName       TNamedItemOrEmpty,
--         tnIPv6FilterParamsTimeRangeState      TTimeRangeState,
--         tnIPv6FilterParamsIngrHitByteCount    Counter64,
--         tnIPv6FilterParamsEgrHitByteCount     Counter64
--     }
--
-- tnIPv6FilterParamsIndex  OBJECT-TYPE
--     SYNTAX       TEntryId
--     MAX-ACCESS   not-accessible
--     STATUS       current
--     DESCRIPTION
--         "This is the secondary index for the entry. Every IPv6 filter can have
--          multiple entries, therefore every IPv6 filter entry is identified by
--          the tnIPv6FilterId and tnIPv6FilterParamsIndex."
--     ::= { tnIPv6FilterParamsEntry 1 }
--
-- tnIPv6FilterParamsRowStatus  OBJECT-TYPE
--     SYNTAX       RowStatus
--     MAX-ACCESS   read-create
--     STATUS       current
--     DESCRIPTION
--         "This object allows entries to be created and deleted in the
--          tnIPv6FilterParamsTable."
--     ::= { tnIPv6FilterParamsEntry 2 }
--
-- tnIPv6FilterParamsLogId  OBJECT-TYPE
--     SYNTAX       TFilterLogId
--     MAX-ACCESS   read-create
--     STATUS       current
--     DESCRIPTION
--         "This object specifies the log to use for packets that match
--          this entry. The value zero indicates that logging is disabled."
--     DEFVAL { 0 }
--     ::= { tnIPv6FilterParamsEntry 3 }
--
-- tnIPv6FilterParamsDescription  OBJECT-TYPE
--     SYNTAX       TItemDescription
--     MAX-ACCESS   read-create
--     STATUS       current
--     DESCRIPTION
--         "User-provided description for this filter entry."
--     DEFVAL { ''H }
--     ::= { tnIPv6FilterParamsEntry 4 }
--
-- tnIPv6FilterParamsAction  OBJECT-TYPE
--     SYNTAX       TFilterActionOrDefault
--     MAX-ACCESS   read-create
--     STATUS       current
--     DESCRIPTION
--         "The action to take for packets that match this filter entry. The value
--          default(3) specifies this entry to inherit the behavior defined as the
--          default for the filter."
--     DEFVAL { drop }
--     ::= { tnIPv6FilterParamsEntry 5 }
--
-- tnIPv6FilterParamsForwardNH  OBJECT-TYPE
--     SYNTAX       InetAddressIPv6
--     MAX-ACCESS   read-create
--     STATUS       current
--     DESCRIPTION
--         "The ipv6-address of the nexthop to which the packet should be forwarded
--          if it hits this filter entry. The action of this entry should be
--          'forward' in such a case."
--     DEFVAL { '00000000000000000000000000000000'H }
--     ::= { tnIPv6FilterParamsEntry 6 }
--
-- tnIPv6FilterParamsForwardNHIndirect  OBJECT-TYPE
--     SYNTAX       TruthValue
--     MAX-ACCESS   read-create
--     STATUS       current
--     DESCRIPTION
--         "tnIPv6FilterParamsForwardNHIndirect specifies if the nexthop is directly or
--          indirectly reachable."
--     DEFVAL { false }
--     ::= { tnIPv6FilterParamsEntry 7 }
--
-- tnIPv6FilterParamsRemarkDSCP  OBJECT-TYPE
--     SYNTAX       TDSCPFilterActionValue
--     MAX-ACCESS   read-create
--     STATUS       current
--     DESCRIPTION
--         "The DSCP value that should be remarked in case a packet hits this
--          filter entry."
--     DEFVAL { -1 }
--     ::= { tnIPv6FilterParamsEntry 8 }
--
-- tnIPv6FilterParamsRemarkDSCPMask  OBJECT-TYPE
--     SYNTAX       TDSCPFilterActionValue
--     MAX-ACCESS   read-create
--     STATUS       current
--     DESCRIPTION
--         "tnIPv6FilterParamsRemarkDSCPMask specifies the care bits while remarking
--          with the DSCP value."
--     DEFVAL { 255 }
--     ::= { tnIPv6FilterParamsEntry 9 }
--
-- tnIPv6FilterParamsRemarkDot1p  OBJECT-TYPE
--     SYNTAX       Dot1PPriority
--     MAX-ACCESS   read-create
--     STATUS       current
--     DESCRIPTION
--         "tnIPv6FilterParamsRemarkDot1p specifies the Dot1p value that needs to be
--          remarked on the packet if it hits this filter entry."
--     DEFVAL { -1 }
--     ::= { tnIPv6FilterParamsEntry 10 }
--
-- tnIPv6FilterParamsSourceIpAddr  OBJECT-TYPE
--     SYNTAX       InetAddressIPv6
--     MAX-ACCESS   read-create
--     STATUS       current
--     DESCRIPTION
--         "IPv6 address to match the source-ip of the packet."
--     DEFVAL { '00000000000000000000000000000000'H }
--     ::= { tnIPv6FilterParamsEntry 11 }
--
-- tnIPv6FilterParamsSourceIpMask  OBJECT-TYPE
--     SYNTAX        InetAddressPrefixLength (0..128)
--     MAX-ACCESS   read-create
--     STATUS       current
--     DESCRIPTION
--         "The IPv6 Mask value for this policy IPv6 Filter entry. The mask is
--          ANDed with the IPv6 to match the tnIPv6FilterParamsSourceIpAddr."
--     DEFVAL { 0 }
--     ::= { tnIPv6FilterParamsEntry 12 }
--
-- tnIPv6FilterParamsDestinationIpAddr  OBJECT-TYPE
--     SYNTAX       InetAddressIPv6
--     MAX-ACCESS   read-create
--     STATUS       current
--     DESCRIPTION
--         "IPv6 address to match the destination-ip of the packet."
--     DEFVAL { '00000000000000000000000000000000'H }
--     ::= { tnIPv6FilterParamsEntry 13 }
--
-- tnIPv6FilterParamsDestinationIpMask  OBJECT-TYPE
--     SYNTAX        InetAddressPrefixLength (0..128)
--     MAX-ACCESS   read-create
--     STATUS       current
--     DESCRIPTION
--         "The IPv6 Mask value for this policy IPv6 Filter entry. The mask is
--          ANDed with the IPv6 to match the tnIPv6FilterParamsDestinationIpAddr."
--     DEFVAL { 0 }
--     ::= { tnIPv6FilterParamsEntry 14 }
--
-- tnIPv6FilterParamsNextHeader  OBJECT-TYPE
--     SYNTAX       TIpProtocol
--     MAX-ACCESS   read-create
--     STATUS       current
--     DESCRIPTION
--         "IPv6 next header to match.  set to -1 to disable matching IPv6 next
--          header. If the next header is changed the next header specific parameters
--          are reset. For instance if next header is changed from TCP to UDP, then the
--          objects tnIPv6FilterParamsTcpSyn and tnIPv6FilterParamsTcpAck will be turned off.
--          Because the match criteria only pertains to the last next-header, the
--          following values are not accepted: 0, 43, 44, 50, 51, and 60."
--     DEFVAL { -1 }
--     ::= { tnIPv6FilterParamsEntry 15 }
--
-- tnIPv6FilterParamsSourcePortValue1  OBJECT-TYPE
--     SYNTAX       TTcpUdpPort
--     MAX-ACCESS   read-create
--     STATUS       current
--     DESCRIPTION
--         "TCP/UDP port value1. The value of this object is used as per the
--          description for tnIPv6FilterParamsSourcePortOperator."
--     DEFVAL { 0 }
--     ::= { tnIPv6FilterParamsEntry 16 }
--
-- tnIPv6FilterParamsSourcePortValue2  OBJECT-TYPE
--     SYNTAX       TTcpUdpPort
--     MAX-ACCESS   read-create
--     STATUS       current
--     DESCRIPTION
--         "TCP/UDP port value2. The value of this object is used as per the
--          description for tnIPv6FilterParamsSourcePortOperator."
--     DEFVAL { 0 }
--     ::= { tnIPv6FilterParamsEntry 17 }
--
-- tnIPv6FilterParamsSourcePortOperator OBJECT-TYPE
--     SYNTAX       TTcpUdpPortOperator
--     MAX-ACCESS   read-create
--     STATUS       current
--     DESCRIPTION
--         "The operator specifies the manner in which
--          tnIPFilterParamsSourcePortValue1 and tnIPFilterParamsSourcePortValue2
--          are to be used."
--     DEFVAL { none }
--     ::= { tnIPv6FilterParamsEntry 18 }
--
-- tnIPv6FilterParamsDestPortValue1  OBJECT-TYPE
--     SYNTAX       TTcpUdpPort
--     MAX-ACCESS   read-create
--     STATUS       current
--     DESCRIPTION
--         "TCP/UDP port value1. The value of this object is used as per the
--          description for tnIPv6FilterParamsDestPortOperator."
--     DEFVAL { 0 }
--     ::= { tnIPv6FilterParamsEntry 19 }
--
-- tnIPv6FilterParamsDestPortValue2  OBJECT-TYPE
--     SYNTAX       TTcpUdpPort
--     MAX-ACCESS   read-create
--     STATUS       current
--     DESCRIPTION
--         "TCP/UDP port value2. The value of this object is used as per the
--          description for tnIPv6FilterParamsDestPortOperator."
--     DEFVAL { 0 }
--     ::= { tnIPv6FilterParamsEntry 20 }
--
-- tnIPv6FilterParamsDestPortOperator  OBJECT-TYPE
--     SYNTAX       TTcpUdpPortOperator
--     MAX-ACCESS   read-create
--     STATUS       current
--     DESCRIPTION
--         "The operator specifies the manner in which tnIPFilterParamsDestPortValue1
--          and tnIPFilterParamsDestPortValue2 are to be used."
--     DEFVAL { none }
--     ::= { tnIPv6FilterParamsEntry 21 }
--
-- tnIPv6FilterParamsDSCP  OBJECT-TYPE
--     SYNTAX       TDSCPNameOrEmpty
--     MAX-ACCESS   read-create
--     STATUS       current
--     DESCRIPTION
--         "DSCP to be matched on the packet."
--     DEFVAL { ''H }
--     ::= { tnIPv6FilterParamsEntry 22 }
--
-- tnIPv6FilterParamsTcpSyn  OBJECT-TYPE
--     SYNTAX       TItemMatch
--     MAX-ACCESS   read-create
--     STATUS       current
--     DESCRIPTION
--         "If Enabled, matches a TCP Syn as per value of the object."
--     DEFVAL { off }
--     ::= { tnIPv6FilterParamsEntry 23 }
--
-- tnIPv6FilterParamsTcpAck  OBJECT-TYPE
--     SYNTAX       TItemMatch
--     MAX-ACCESS   read-create
--     STATUS       current
--     DESCRIPTION
--         "If Enabled, matches a TCP Ack as per value of the object."
--     DEFVAL { off }
--     ::= { tnIPv6FilterParamsEntry 24 }
--
-- tnIPv6FilterParamsIcmpCode  OBJECT-TYPE
--     SYNTAX       INTEGER (-1|0..255)
--     MAX-ACCESS   read-create
--     STATUS       current
--     DESCRIPTION
--         "Icmp code to be matched. tnIPv6FilterParamsIcmpCode complements the
--          object tnIPv6FilterParamsIcmpType. Both of them need to be set to actually
--          enable ICMP matching. The value -1 means Icmp code matching is not
--          enabled."
--     DEFVAL { -1 }
--     ::= { tnIPv6FilterParamsEntry 25 }
--
-- tnIPv6FilterParamsIcmpType  OBJECT-TYPE
--     SYNTAX       INTEGER (-1|0..255)
--     MAX-ACCESS   read-create
--     STATUS       current
--     DESCRIPTION
--         "Icmp type to be matched. tnIPv6FilterParamsIcmpType complements the
--          object tnIPv6FilterParamsIcmpCode. Both of them need to be set to actually
--          enable ICMP matching. The value -1 means Icmp type matching is not
--          enabled."
--     DEFVAL { -1 }
--     ::= { tnIPv6FilterParamsEntry 26 }
--
-- tnIPv6FilterParamsCflowdSample  OBJECT-TYPE
--     SYNTAX       TruthValue
--     MAX-ACCESS   read-create
--     STATUS       current
--     DESCRIPTION
--         "When tnIPFilterParamsCflowdSample has a value of 'true',  Cflowd sampling
--          and analysis is performed on those packet streams where this filter
--          has been applied.  Only packets matching this IPv6 filter entry are
--          subjected to Cflowd sampling and analysis.  A Cflowd profile controls
--          the sampling and analysis of data flows through the router."
--     DEFVAL { false }
--     ::= { tnIPv6FilterParamsEntry 27 }
--
-- tnIPv6FilterParamsCflowdIfSample  OBJECT-TYPE
--     SYNTAX       TruthValue
--     MAX-ACCESS   read-create
--     STATUS       current
--     DESCRIPTION
--         "When tnIPv6FilterParamsCflowdIfSample has a value of 'true', Cflowd
--          sampling and analysis is performed on those packet streams where this
--          filter has been applied.  Only packets matching this IPv6 filter entry
--          are subjected to Cflowd sampling and analysis.  A Cflowd profile
--          controls the sampling and analysis of data flows through the router."
--     DEFVAL { true }
--     ::= { tnIPv6FilterParamsEntry 28 }
--
-- tnIPv6FilterParamsForwardNHInterface  OBJECT-TYPE
--     SYNTAX       DisplayString (SIZE(0..32))
--     MAX-ACCESS   read-create
--     STATUS       current
--     DESCRIPTION
--         "The interface name for the nexthop to which the packet should be
--          forwarded if it hits this filter entry. The action of this entry
--          should be 'forward' in such a case."
--     DEFVAL { ''H }
--     ::= { tnIPv6FilterParamsEntry 29 }
--
-- tnIPv6FilterParamsIngressHitCount OBJECT-TYPE
--     SYNTAX       Counter64
--     MAX-ACCESS   read-only
--     STATUS       current
--     DESCRIPTION
--         "This object indicates the number of times an ingress packet
--          matched this entry."
--     ::= { tnIPv6FilterParamsEntry 30 }
--
-- tnIPv6FilterParamsEgressHitCount OBJECT-TYPE
--     SYNTAX       Counter64
--     MAX-ACCESS   read-only
--     STATUS       current
--     DESCRIPTION
--         "This object indicates the number of times an egress packet
--          matched this entry."
--     ::= { tnIPv6FilterParamsEntry 31 }
--
-- tnIPv6FilterParamsLogInstantiated OBJECT-TYPE
--     SYNTAX       TruthValue
--     MAX-ACCESS   read-only
--     STATUS       current
--     DESCRIPTION
--         "tnIPv6FilterParamsLogInstantiated indicates if the filter log for
--          this filter entry has been instantiated or not."
--     ::= { tnIPv6FilterParamsEntry 32 }
--
-- tnIPv6FilterParamsForwardRedPlcy  OBJECT-TYPE
--     SYNTAX       TNamedItemOrEmpty
--     MAX-ACCESS   read-create
--     STATUS       current
--     DESCRIPTION
--         "tnIPv6FilterParamsForwardRedPlcy specifies the redirect policy to be
--          used to determine the nexthop."
--     DEFVAL { ''H }
--     ::= { tnIPv6FilterParamsEntry 33 }
--
-- tnIPv6FilterParamsActiveDest  OBJECT-TYPE
--     SYNTAX       InetAddressIPv6
--     MAX-ACCESS   read-only
--     STATUS       current
--     DESCRIPTION
--         "tnIPv6FilterParamsActiveDest indicates the IPv6 address of the active
--          destination for this IPv6 filter. A value of 0 indicates that there
--          is currently no active destination."
--     ::= { tnIPv6FilterParamsEntry 34 }
--
-- tnIPv6FilterParamsTimeRangeName  OBJECT-TYPE
--     SYNTAX       TNamedItemOrEmpty
--     MAX-ACCESS   read-create
--     STATUS       current
--     DESCRIPTION
--         "tnIPv6FilterParamsTimeRangeName specifies the tmnxTimeRangeEntry to be
--          associated with this filter entry.
--
--          A value for this object can only be specified during row creation, and
--          cannot be altered lateron.
--          Also, a value is accepted only if the tmnxTimeRangeEntry is defined in
--          the TIMETRA-SCHEDULER-MIB::tmnxTimeRangeTable.tTimeRangeName."
--     DEFVAL { ''H }
--     ::= { tnIPv6FilterParamsEntry 35 }
--
-- tnIPv6FilterParamsTimeRangeState  OBJECT-TYPE
--     SYNTAX       TTimeRangeState
--     MAX-ACCESS   read-only
--     STATUS       current
--     DESCRIPTION
--         "tnIPv6FilterParamsTimeRangeState indicates whether or not the entry
--          is currently in effect.
--          - timeRangeNotApplic:
--            no time range is applicable for this entry.
--          - timeRangeNotActive:
--            A time range is defined in tnIPv6FilterParamsTimeRangeName, but is not
--            active at this moment. Consequently the filter entry is not
--            installed.
--          - timeRangeActive.
--            A time range is defined in tnIPv6FilterParamsTimeRangeName, and is
--            activated successfully.
--          - timeRangeActiveDownloadFailed:
--            A time range is defined in tnIPv6FilterParamsTimeRangeName, and is
--            activated, but the corresponding filter entry could not be
--            installed due to resource problems."
--     ::= { tnIPv6FilterParamsEntry 36 }
--
-- tnIPv6FilterParamsIngrHitByteCount OBJECT-TYPE
--     SYNTAX       Counter64
--     MAX-ACCESS   read-only
--     STATUS       current
--     DESCRIPTION
--         "The value of tnIPv6FilterParamsIngrHitByteCount indicates the number
--          of bytes of all ingress packets that matched this entry."
--     ::= { tnIPv6FilterParamsEntry 37 }
--
-- tnIPv6FilterParamsEgrHitByteCount OBJECT-TYPE
--     SYNTAX       Counter64
--     MAX-ACCESS   read-only
--     STATUS       current
--     DESCRIPTION
--         "This tnIPv6FilterParamsEgrHitByteCount indicates the number
--          of bytes of all egress packets that matched this entry."
--     ::= { tnIPv6FilterParamsEntry 38 }

--
-- Dummy Scalars
--
tnFilterScalar1 OBJECT-TYPE
    SYNTAX      Unsigned32
    MAX-ACCESS  read-only
    STATUS      current
    DESCRIPTION
        "A dummy scalar that satisfies a SNMP get request quickly when
         there is no 11QPE24 card provisioned.  Otherwise, it has to
         traverse the remaining 11QPE24 MIB to get to the next applicable
         item."
    ::= { tnFilterObjects 101 }

tnFilterScalar2 OBJECT-TYPE
    SYNTAX      Unsigned32
    MAX-ACCESS  read-only
    STATUS      current
    DESCRIPTION
        "."
    ::= { tnFilterObjects 102 }

--
-- Notification Information
--

--
-- Filter Notification Objects
--
-- tnFilterPBRDropReason OBJECT-TYPE
--     SYNTAX  INTEGER {
--                 invalidInterface (0),
--                 interfaceDown (1)
--             }
--     MAX-ACCESS   accessible-for-notify
--     STATUS       current
--     DESCRIPTION
--         "Used by tnIPFilterPBRPacketsDrop to report the failure reason code."
--     ::= { tnFilterNotificationObjects 1 }
--
-- tnFilterParmRow OBJECT-TYPE
--     SYNTAX  RowPointer
--     MAX-ACCESS  accessible-for-notify
--     STATUS      current
--     DESCRIPTION
--         "The value of the object tnFilterParmRow indicates the OID of the row
--          status of the applicable filter parameter table. This can be a row from
--          either one of the following tables:
--          - tnIPFilterParamsTable;
--          - tnMacFilterParamsTable; or
--          - tnIPv6FilterParamsTable"
--     ::= { tnFilterNotificationObjects 2 }
--
-- tnFilterAlarmDescription OBJECT-TYPE
--     SYNTAX  DisplayString
--     MAX-ACCESS  accessible-for-notify
--     STATUS      current
--     DESCRIPTION
--         "The value of the object tnFilterAlarmDescription is a printable
--          character string which contains information about the cause of the
--          problem."
--     ::= { tnFilterNotificationObjects 3 }

-- tnIPFilterPBRPacketsDrop NOTIFICATION-TYPE
--     OBJECTS {
--       tnIPFilterParamsForwardNHInterface,
--       tnFilterPBRDropReason
--     }
--     STATUS  current
--     DESCRIPTION
--         "The tnIPFilterPBRPacketsDrop event is generated either
--          when the configuration of a forwarding action refers to an
--          invalid/unconfigured next-hop or if the active interface goes down
--          operationally in the process of active filtering."
--     ::= { tnFilterNotifications 1 }
--
-- tnFilterEntryActivationFailed NOTIFICATION-TYPE
--     OBJECTS {
--         tnFilterParmRow,
--         tnFilterAlarmDescription
--     }
--     STATUS  current
--     DESCRIPTION
--         "The tnFilterEntryActivationFailed event can only be
--          generated for entries that are controlled by a tmnxTimeRangeEntry.
--          If the tmnxTimeRangeEntry becomes active the indicated entry must be
--          installed.
--          The event is generated when this installation failed because
--          of resource problems."
--     ::= { tnFilterNotifications 2 }
--
-- tnFilterEntryActivationRestored NOTIFICATION-TYPE
--     OBJECTS {
--         tnFilterParmRow,
--         tnFilterAlarmDescription
--     }
--     STATUS  current
--     DESCRIPTION
--         "The tnFilterEntryActivationRestored event can only be
--          generated for entries that are controlled by a tmnxTimeRangeEntry.
--          If the tmnxTimeRangeEntry becomes active the indicated entry must be
--          installed.
--          The event tnFilterEntryActivationFailed is generated when
--          this installation originally failed because of resources
--          problems,
--          The notification tnFilterEntryActivationRestored is sent
--          when either the time range associated with the filter is no
--          longer active, or when the filter entry
--          was installed due to the availability of new resources."
--     ::= { tnFilterNotifications 3 }

--
-- Conformance Information
--

-- tnFilterMIBCompliances OBJECT IDENTIFIER ::= { tnFilterMIBConformance 1 }
-- tnFilterMIBGroups      OBJECT IDENTIFIER ::= { tnFilterMIBConformance 2 }

--
-- Compliance Statements
--

-- tnFilterMIBCompliance MODULE-COMPLIANCE
--    ::= { tnFilterMIBCompliances 1 }

-- tnFilterR2r1MIBCompliance MODULE-COMPLIANCE
--    ::= { tnFilterMIBCompliances 2 }

-- tnFilterV3v0MIBCompliance MODULE-COMPLIANCE
--    ::= { tnFilterMIBCompliances 3 }

-- tnFilter7450V4v0Compliance MODULE-COMPLIANCE
--    STATUS  obsolete
--    DESCRIPTION
--        "The compliance statement for management of Filter features
--         on Nokia 7450 ESS series systems release R4.0."
--    MODULE  this module
--        MANDATORY-GROUPS {
--            tnFilterScalarGroup,
--            tnIPFilterV4v0Group,
--            tnMacFilterV4v0Group,
--            tnFilterLogGroup,
--            tnFilterRedirectPolicyGroup,
--            tnFilterNotificationsGroup
--            tnIPv6FilterV4v0Group
--            tTodPoliciesV4v0Group
--        }
--    ::= { tnFilterMIBCompliances 4 }

-- tnFilter7750V4v0Compliance MODULE-COMPLIANCE
--    STATUS  obsolete
--    DESCRIPTION
--        "The compliance statement for management of Filter features
--         on Nokia 7750 SR series systems release R4.0."
--    MODULE  this module
--        MANDATORY-GROUPS {
--            tnFilterScalarGroup,
--            tnIPFilterV4v0Group,
--            tnMacFilterV4v0Group,
--            tnFilterLogGroup,
--            tnFilterRedirectPolicyGroup,
--            tnFilterNotificationsGroup,
--            tnIPv6FilterV4v0Group
--            tTodPoliciesV4v0Group
--        }
--    ::= { tnFilterMIBCompliances 5 }

-- tnFilter7450V5v0Compliance MODULE-COMPLIANCE
--    STATUS  obsolete
--    DESCRIPTION
--        "The compliance statement for management of Filter features
--         on Nokia 7450 ESS series systems release R5.0."
--    MODULE  this module
--        MANDATORY-GROUPS {
--            tnFilterScalarGroup,
--            tnIPFilterV5v0Group,
--            tnMacFilterV4v0Group,
--            tnFilterLogGroup,
--            tnFilterRedirectPolicyGroup,
--            tnFilterNotificationsGroup,
--            tnIPv6FilterV4v0Group
--            tTodPolicies77450V5v0Group,
--            tToDPoliciesV5v0NotifyGroup,
--            tnFilterLogV5v0Group
--        }
--    ::= { tnFilterMIBCompliances 6 }

-- tnFilter77x0V5v0Compliance MODULE-COMPLIANCE
--    STATUS  obsolete
--    DESCRIPTION
--        "The compliance statement for management of Filter features
--         on Nokia 77x0 SPR/SR series systems release R5.0."
--    MODULE  this module
--        MANDATORY-GROUPS {
--            tnFilterScalarGroup,
--            tnIPFilterV5v0Group,
--            tnMacFilterV4v0Group,
--            tnFilterLogGroup,
--            tnFilterRedirectPolicyGroup,
--            tnFilterNotificationsGroup,
--            tnIPv6FilterV4v0Group,
--            tTodPolicies77x0V5v0Group,
--            tToDPoliciesV5v0NotifyGroup,
--            tnFilterLogV5v0Group
--        }
--    ::= { tnFilterMIBCompliances 7 }

-- tnFilter7450V6v0Compliance MODULE-COMPLIANCE
--    STATUS  current
--    DESCRIPTION
--        "The compliance statement for management of Filter features
--         on Nokia 7450 ESS series systems release R5.0."
--    MODULE  this module
--        MANDATORY-GROUPS {
--            tnFilterScalarGroup,
--            tnIPFilterV6v0Group,
--            tnMacFilterV6v0Group,
--            tnFilterLogGroup,
--            tnFilterRedirectPolicyGroup,
--            tnFilterNotificationsGroup,
--            tnIPv6FilterV6v0Group
--            tTodPolicies77450V5v0Group,
--            tToDPoliciesV5v0NotifyGroup,
--            tnFilterLogV5v0Group
--        }
--    ::= { tnFilterMIBCompliances 8 }

-- tnFilter77x0V6v0Compliance MODULE-COMPLIANCE
--    STATUS  current
--    DESCRIPTION
--        "The compliance statement for management of Filter features
--         on Nokia 77x0 SPR/SR series systems release R5.0."
--    MODULE  this module
--        MANDATORY-GROUPS {
--            tnFilterScalarGroup,
--            tnIPFilterV6v0Group,
--            tnMacFilterV6v0Group,
--            tnFilterLogGroup,
--            tnFilterRedirectPolicyGroup,
--            tnFilterNotificationsGroup,
--            tnIPv6FilterV6v0Group,
--            tTodPolicies77x0V5v0Group,
--            tToDPoliciesV5v0NotifyGroup,
--            tnFilterLogV5v0Group
--        }
--    ::= { tnFilterMIBCompliances 9 }
--
-- Units of conformance
--

-- tnIPFilterGroup OBJECT-GROUP
--    ::= { tnFilterMIBGroups 1 }

-- tnMacFilterGroup OBJECT-GROUP
--    ::= { tnFilterMIBGroups 2 }

-- tnFilterLogGroup OBJECT-GROUP
--    OBJECTS {
--                tnFilterLogRowStatus,
--                tnFilterLogDestination,
--                tnFilterLogDescription,
--                tnFilterLogMaxNumEntries,
--                tnFilterLogSysLogId,
--                tnFilterLogFileId,
--                tnFilterLogStopOnFull,
--                tnFilterLogEnabled,
--                tnFilterLogMaxInstances,
--                tnFilterLogInstances,
--                tnFilterLogBindings
--            }
--    STATUS    current
--    DESCRIPTION
--        "The group of objects supporting management of filter log objects
--        on Nokia 7x50 SR series systems."
--    ::= { tnFilterMIBGroups 3 }

-- tnFilterRedirectPolicyGroup OBJECT-GROUP
--    OBJECTS {
--                tnFilterRPRowStatus,
--                tnFilterRPDescription,
--                tnFilterRPAdminState,
--                tnFilterRPActiveDest,

--                tnFilterRDRowStatus,
--                tnFilterRDDescription,
--                tnFilterRDAdminPriority,
--                tnFilterRDOperPriority,
--                tnFilterRDAdminState,
--                tnFilterRDOperState,

--                tnFilterRSTRowStatus,
--                tnFilterRSTOID,
--                tnFilterRSTCommunity,
--                tnFilterRSTSNMPVersion,
--                tnFilterRSTInterval,
--                tnFilterRSTTimeout,
--                tnFilterRSTDropCount,
--                tnFilterRSTHoldDown,
--                tnFilterRSTHoldDownRemain,
--                tnFilterRSTLastActionTime,
--                tnFilterRSTLastOID,
--                tnFilterRSTLastType,
--                tnFilterRSTLastCounter32Val,
--                tnFilterRSTLastUnsigned32Val,
--                tnFilterRSTLastTimeTicksVal,
--                tnFilterRSTLastInt32Val,
--                tnFilterRSTLastOctetStringVal,
--                tnFilterRSTLastIpAddressVal,
--                tnFilterRSTLastOidVal,
--                tnFilterRSTLastCounter64Val,
--                tnFilterRSTLastOpaqueVal,
--                tnFilterRSTLastAction,
--                tnFilterRSTLastPrioChange,
--                tnFilterRSTNextRespIndex,

--                tnFilterRSTRespRowStatus,
--                tnFilterRSTRespAction,
--                tnFilterRSTRespPrioChange,
--                tnFilterRSTRespOID,
--                tnFilterRSTRespType,
--                tnFilterRSTCounter32Val,
--                tnFilterRSTUnsigned32Val,
--                tnFilterRSTTimeTicksVal,
--                tnFilterRSTInt32Val,
--                tnFilterRSTOctetStringVal,
--                tnFilterRSTIpAddressVal,
--                tnFilterRSTOidVal,
--                tnFilterRSTCounter64Val,
--                tnFilterRSTOpaqueVal,

--                tnFilterRUTRowStatus,
--                tnFilterRUTURL,
--                tnFilterRUTHTTPVersion,
--                tnFilterRUTInterval,
--                tnFilterRUTTimeout,
--                tnFilterRUTDropCount,
--                tnFilterRUTHoldDown,
--                tnFilterRUTHoldDownRemain,
--                tnFilterRUTLastActionTime,
--                tnFilterRUTLastRetCode,
--                tnFilterRUTLastAction,
--                tnFilterRUTLastPrioChange,

--                tnFilterRUTRespRowStatus,
--                tnFilterRUTRespAction,
--                tnFilterRUTRespPrioChange,

--                tnFilterRPTRowStatus,
--                tnFilterRPTInterval,
--                tnFilterRPTTimeout,
--                tnFilterRPTDropCount,
--                tnFilterRPTHoldDown,
--                tnFilterRPTHoldDownRemain,
--                tnFilterRPTLastActionTime,
--                tnFilterRPTLastAction
--            }
--    STATUS    current
--    DESCRIPTION
--        "The group of objects supporting management of filter redirect policy
--        objects on Nokia 7x50 SR series systems."
--    ::= { tnFilterMIBGroups 4 }

-- tnFilterScalarGroup OBJECT-GROUP
--    OBJECTS {
--                tnFilterDomainLastChanged
--            }
--    STATUS    current
--    DESCRIPTION
--        "The group of objects supporting management of filter scalar
--        objects on Nokia 7x50 SR series systems."
--    ::= { tnFilterMIBGroups 7 }

-- tnFilterNotificationObjGroup OBJECT-GROUP
--    OBJECTS {
--                tnFilterPBRDropReason
--            }
--    STATUS    obsolete
--    DESCRIPTION
--         "The group of objects supporting management of filter
--         notification objects on Nokia 7x50 SR series systems."
--    ::= { tnFilterMIBGroups 8 }

-- tnFilterNotificationsGroup NOTIFICATION-GROUP
--     NOTIFICATIONS {
--                 tnIPFilterPBRPacketsDrop
--            }
--     STATUS current
--     DESCRIPTION
--         "The group of notifications supporting management of
--          filter notifications on Nokia 7x50 SR series systems."
--     ::= { tnFilterMIBGroups 9 }

-- tnAutoIPFilterR2r1Group OBJECT-GROUP
--    ::= { tnFilterMIBGroups 10 }

-- tnIPv6FilterV4v0Group OBJECT-GROUP
--    OBJECTS {
--                tnIPv6FilterRowStatus,
--                tnIPv6FilterScope,
--                tnIPv6FilterDescription,
--                tnIPv6FilterDefaultAction,
--                tnIPv6FilterParamsRowStatus,
--                tnIPv6FilterParamsLogId,
--                tnIPv6FilterParamsDescription,
--                tnIPv6FilterParamsAction,
--                tnIPv6FilterParamsForwardNH,
--                tnIPv6FilterParamsForwardNHIndirect,
--                tnIPv6FilterParamsRemarkDSCP,
--                tnIPv6FilterParamsRemarkDSCPMask,
--                tnIPv6FilterParamsRemarkDot1p,
--                tnIPv6FilterParamsSourceIpAddr,
--                tnIPv6FilterParamsSourceIpMask,
--                tnIPv6FilterParamsDestinationIpAddr,
--                tnIPv6FilterParamsDestinationIpMask,
--                tnIPv6FilterParamsNextHeader,
--                tnIPv6FilterParamsSourcePortValue1,
--                tnIPv6FilterParamsSourcePortValue2,
--                tnIPv6FilterParamsSourcePortOperator,
--                tnIPv6FilterParamsDestPortValue1,
--                tnIPv6FilterParamsDestPortValue2,
--                tnIPv6FilterParamsDestPortOperator,
--                tnIPv6FilterParamsDSCP,
--                tnIPv6FilterParamsTcpSyn,
--                tnIPv6FilterParamsTcpAck,
--                tnIPv6FilterParamsIcmpCode,
--                tnIPv6FilterParamsIcmpType,
--                tnIPv6FilterParamsCflowdSample,
--                tnIPv6FilterParamsCflowdIfSample,
--                tnIPv6FilterParamsForwardNHInterface,
--                tnIPv6FilterParamsIngressHitCount,
--                tnIPv6FilterParamsEgressHitCount,
--                tnIPv6FilterParamsLogInstantiated,
--                tnIPv6FilterParamsForwardRedPlcy,
--                tnIPv6FilterParamsActiveDest
--            }
--    STATUS    obsolete
--    DESCRIPTION
--        "The group of objects supporting management of IPv6 filter objects
--        on Nokia 7x50 SR series systems."
--    ::= { tnFilterMIBGroups 11 }

-- tnIPFilterV4v0Group OBJECT-GROUP
--    OBJECTS {
--                tnIPFilterRowStatus,
--                tnIPFilterScope,
--                tnIPFilterDescription,
--                tnIPFilterDefaultAction,
--                tnIPFilterParamsRowStatus,
--                tnIPFilterParamsLogId,
--                tnIPFilterParamsDescription,
--                tnIPFilterParamsAction,
--                tnIPFilterParamsForwardNH,
--                tnIPFilterParamsForwardNHIndirect,
--                tnIPFilterParamsRemarkDSCP,
--                tnIPFilterParamsRemarkDSCPMask,
--                tnIPFilterParamsRemarkDot1p,
--                tnIPFilterParamsSourceIpAddr,
--                tnIPFilterParamsSourceIpMask,
--                tnIPFilterParamsDestinationIpAddr,
--                tnIPFilterParamsDestinationIpMask,
--                tnIPFilterParamsProtocol,
--                tnIPFilterParamsSourcePortValue1,
--                tnIPFilterParamsSourcePortValue2,
--                tnIPFilterParamsSourcePortOperator,
--                tnIPFilterParamsDestPortValue1,
--                tnIPFilterParamsDestPortValue2,
--                tnIPFilterParamsDestPortOperator,
--                tnIPFilterParamsDSCP,
--                tnIPFilterParamsFragment,
--                tnIPFilterParamsOptionPresent,
--                tnIPFilterParamsIpOptionValue,
--                tnIPFilterParamsIpOptionMask,
--                tnIPFilterParamsMultipleOption,
--                tnIPFilterParamsTcpSyn,
--                tnIPFilterParamsTcpAck,
--                tnIPFilterParamsIcmpCode,
--                tnIPFilterParamsIcmpType,
--                tnIPFilterParamsCflowdSample,
--                tnIPFilterParamsCflowdIfSample,
--                tnIPFilterParamsForwardNHInterface,
--                tnIPFilterParamsIngressHitCount,
--                tnIPFilterParamsEgressHitCount,
--                tnIPFilterParamsLogInstantiated,
--                tnIPFilterParamsForwardRedPlcy,
--                tnIPFilterParamsActiveDest,
--                tnIPFilterParamsFwdSvcId,
--                tnIPFilterParamsFwdSapPortId,
--                tnIPFilterParamsFwdSapEncapVal,
--                tnIPFilterParamsFwdSdpBind,
--                tnIPFilterParamsRedirectURL
--            }
--    STATUS    obsolete
--    DESCRIPTION
--        "The group of objects supporting IP Filters
--         on Nokia 7x50 ESS/SR series systems 4.0 release."
--    ::= { tnFilterMIBGroups 12 }

-- tnMacFilterV4v0Group OBJECT-GROUP
--    OBJECTS {
--                tnMacFilterRowStatus,
--                tnMacFilterScope,
--                tnMacFilterDescription,
--                tnMacFilterDefaultAction,
--                tMaccFilterType,
--                tnMacFilterName,
--                tnMacFilterParamsRowStatus,
--                tnMacFilterParamsLogId,
--                tnMacFilterParamsDescription,
--                tnMacFilterParamsAction,
--                tnMacFilterParamsFrameType,
--                tnMacFilterParamsSrcMAC,
--                tnMacFilterParamsSrcMACMask,
--                tnMacFilterParamsDstMAC,
--                tnMacFilterParamsDstMACMask,
--                tnMacFilterParamsDot1pValue,
--                tnMacFilterParamsDot1pMask,
--                tnMacFilterParamsEtherType,
--                tnMacFilterParamsDsap,
--                tnMacFilterParamsDsapMask,
--                tnMacFilterParamsSsap,
--                tnMacFilterParamsSsapMask,
--                tnMacFilterParamsSnapPid,
--                tnMacFilterParamsSnapOui,
--                tnMacFilterParamsIngressHitCount,
--                tnMacFilterParamsEgressHitCount,
--                tnMacFilterParamsLogInstantiated,
--                tnMacFilterParamsFwdSvcId,
--                tnMacFilterParamsFwdSapPortId,
--                tnMacFilterParamsFwdSapEncapVal,
--                tnMacFilterParamsFwdSdpBind,
--                tnMacFilterParamsRedirectURL
--            }
--    STATUS    obsolete
--    DESCRIPTION
--        "The group of objects supporting management of mac filter objects
--        on Nokia 7x50 SR series systems 4.0 release."
--    ::= { tnFilterMIBGroups 13 }

-- tTodPoliciesV4v0Group OBJECT-GROUP
--    OBJECTS {
--                tnIPFilterParamsTimeRangeName,
--                tnIPFilterParamsTimeRangeState,
--                tnMacFilterParamsTimeRangeName,
--                tnMacFilterParamsTimeRangeState,
--                tnIPv6FilterParamsTimeRangeName,
--                tnIPv6FilterParamsTimeRangeState
--            }
--    STATUS    obsolete
--    DESCRIPTION
--        "The group of objects supporting management of time of day policy
--        related objects on Nokia 7x50 SR series systems 4.0 release."
--    ::= { tnFilterMIBGroups 14 }

-- tmnxFilterObsoleteGroup OBJECT-GROUP
--    OBJECTS {
--                tnAutoIPFilterEntrySourceIpMask
--            }
--    STATUS    current
--    DESCRIPTION
--        "The group of objects in TIMETRA-FILTER-MIB which are obsoleted."
--    ::= { tnFilterMIBGroups 15 }

-- tToDPoliciesV5v0NotifyGroup NOTIFICATION-GROUP
--     NOTIFICATIONS {
--                 tnFilterEntryActivationFailed,
--                 tnFilterEntryActivationRestored
--            }
--     STATUS current
--     DESCRIPTION
--        "The group of notifications generated by the time of time of day
--        policy feature on Nokia 7x50 SR series systems 5.0 release."
--     ::= { tnFilterMIBGroups 16 }

-- tnIPFilterV5v0Group OBJECT-GROUP
--    OBJECTS {
--                tnIPFilterRowStatus,
--                tnIPFilterScope,
--                tnIPFilterDescription,
--                tnIPFilterDefaultAction,
--                tnIPFilterParamsRowStatus,
--                tnIPFilterParamsLogId,
--                tnIPFilterParamsDescription,
--                tnIPFilterParamsAction,
--                tnIPFilterParamsForwardNH,
--                tnIPFilterParamsForwardNHIndirect,
--                tnIPFilterParamsRemarkDSCP,
--                tnIPFilterParamsRemarkDSCPMask,
--                tnIPFilterParamsRemarkDot1p,
--                tnIPFilterParamsSourceIpAddr,
--                tnIPFilterParamsSourceIpMask,
--                tnIPFilterParamsDestinationIpAddr,
--                tnIPFilterParamsDestinationIpMask,
--                tnIPFilterParamsProtocol,
--                tnIPFilterParamsSourcePortValue1,
--                tnIPFilterParamsSourcePortValue2,
--                tnIPFilterParamsSourcePortOperator,
--                tnIPFilterParamsDestPortValue1,
--                tnIPFilterParamsDestPortValue2,
--                tnIPFilterParamsDestPortOperator,
--                tnIPFilterParamsDSCP,
--                tnIPFilterParamsFragment,
--                tnIPFilterParamsOptionPresent,
--                tnIPFilterParamsIpOptionValue,
--                tnIPFilterParamsIpOptionMask,
--                tnIPFilterParamsMultipleOption,
--                tnIPFilterParamsTcpSyn,
--                tnIPFilterParamsTcpAck,
--                tnIPFilterParamsIcmpCode,
--                tnIPFilterParamsIcmpType,
--                tnIPFilterParamsCflowdSample,
--                tnIPFilterParamsCflowdIfSample,
--                tnIPFilterParamsForwardNHInterface,
--                tnIPFilterParamsIngressHitCount,
--                tnIPFilterParamsEgressHitCount,
--                tnIPFilterParamsLogInstantiated,
--                tnIPFilterParamsForwardRedPlcy,
--                tnIPFilterParamsActiveDest,
--                tnIPFilterParamsFwdSvcId,
--                tnIPFilterParamsFwdSapPortId,
--                tnIPFilterParamsFwdSapEncapVal,
--                tnIPFilterParamsFwdSdpBind,
--                tnIPFilterParamsRedirectURL,
--                tnIPFilterParamsSrcIpFullMask,
--                tnIPFilterParamsDestIpFullMask
--            }
--    STATUS    obsolete
--    DESCRIPTION
--        "The group of objects supporting IP Filters
--         on Nokia 7x50 ESS/SR series systems 5.0 release."
--    ::= { tnFilterMIBGroups 17 }

-- tnFilterLogV5v0Group OBJECT-GROUP
--    OBJECTS {
--                tnFilterLogSummaryEnabled,
--                tnFilterLogSummaryCrit1
--            }
--    STATUS    current
--    DESCRIPTION
--        "The group of objects supporting Filter Log Summarization
--         on Nokia 7x50 ESS/SR series systems 5.0 release."
--    ::= { tnFilterMIBGroups 18 }

-- tTodPolicies77450V5v0Group OBJECT-GROUP
--    OBJECTS {
--                tnIPFilterParamsTimeRangeName,
--                tnIPFilterParamsTimeRangeState,
--                tnMacFilterParamsTimeRangeName,
--                tnMacFilterParamsTimeRangeState
--            }
--    STATUS    current
--    DESCRIPTION
--        "The group of objects supporting management of time of day policy
--        related objects on Nokia 7450 ESS series systems 5.0 release."
--    ::= { tnFilterMIBGroups 19 }

-- tTodPolicies77x0V5v0Group OBJECT-GROUP
--    OBJECTS {
--                tnIPFilterParamsTimeRangeName,
--                tnIPFilterParamsTimeRangeState,
--                tnMacFilterParamsTimeRangeName,
--                tnMacFilterParamsTimeRangeState,
--                tnIPv6FilterParamsTimeRangeName,
--                tnIPv6FilterParamsTimeRangeState
--            }
--    STATUS    current
--    DESCRIPTION
--        "The group of objects supporting management of time of day policy
--        related objects on Nokia 77x0 series systems 5.0 release."
--    ::= { tnFilterMIBGroups 20 }

-- tnFilterNotificationObjV5v0Group OBJECT-GROUP
--    OBJECTS {
--                tnFilterPBRDropReason,
--                tnFilterParmRow,
--                tnFilterAlarmDescription
--            }
--    STATUS    current
--    DESCRIPTION
--         "The group of objects supporting management of filter
--         notification objects on Nokia 7x50 SR series systems."
--    ::= { tnFilterMIBGroups 21 }

-- tnIPFilterV6v0Group OBJECT-GROUP
--    OBJECTS {
--                tnIPFilterRowStatus,
--                tnIPFilterScope,
--                tnIPFilterDescription,
--                tnIPFilterDefaultAction,
--                tnIPFilterParamsRowStatus,
--                tnIPFilterParamsLogId,
--                tnIPFilterParamsDescription,
--                tnIPFilterParamsAction,
--                tnIPFilterParamsForwardNH,
--                tnIPFilterParamsForwardNHIndirect,
--                tnIPFilterParamsRemarkDSCP,
--                tnIPFilterParamsRemarkDSCPMask,
--                tnIPFilterParamsRemarkDot1p,
--                tnIPFilterParamsSourceIpAddr,
--                tnIPFilterParamsSourceIpMask,
--                tnIPFilterParamsDestinationIpAddr,
--                tnIPFilterParamsDestinationIpMask,
--                tnIPFilterParamsProtocol,
--                tnIPFilterParamsSourcePortValue1,
--                tnIPFilterParamsSourcePortValue2,
--                tnIPFilterParamsSourcePortOperator,
--                tnIPFilterParamsDestPortValue1,
--                tnIPFilterParamsDestPortValue2,
--                tnIPFilterParamsDestPortOperator,
--                tnIPFilterParamsDSCP,
--                tnIPFilterParamsFragment,
--                tnIPFilterParamsOptionPresent,
--                tnIPFilterParamsIpOptionValue,
--                tnIPFilterParamsIpOptionMask,
--                tnIPFilterParamsMultipleOption,
--                tnIPFilterParamsTcpSyn,
--                tnIPFilterParamsTcpAck,
--                tnIPFilterParamsIcmpCode,
--                tnIPFilterParamsIcmpType,
--                tnIPFilterParamsCflowdSample,
--                tnIPFilterParamsCflowdIfSample,
--                tnIPFilterParamsForwardNHInterface,
--                tnIPFilterParamsIngressHitCount,
--                tnIPFilterParamsEgressHitCount,
--                tnIPFilterParamsLogInstantiated,
--                tnIPFilterParamsForwardRedPlcy,
--                tnIPFilterParamsActiveDest,
--                tnIPFilterParamsFwdSvcId,
--                tnIPFilterParamsFwdSapPortId,
--                tnIPFilterParamsFwdSapEncapVal,
--                tnIPFilterParamsFwdSdpBind,
--                tnIPFilterParamsRedirectURL,
--                tnIPFilterParamsSrcIpFullMask,
--                tnIPFilterParamsDestIpFullMask,
--                tnIPFilterParamsIngrHitByteCount,
--                tnIPFilterParamsEgrHitByteCount
--            }
--    STATUS    current
--    DESCRIPTION
--        "The group of objects supporting IP Filters
--         on Nokia 7x50 ESS/SR series systems 6.0 release."
--    ::= { tnFilterMIBGroups 22 }

-- tnMacFilterV6v0Group OBJECT-GROUP
--    OBJECTS {
--                tnMacFilterRowStatus,
--                tnMacFilterScope,
--                tnMacFilterDescription,
--                tnMacFilterDefaultAction,
--                tnMacFilterParamsRowStatus,
--                tnMacFilterParamsLogId,
--                tnMacFilterParamsDescription,
--                tnMacFilterParamsAction,
--                tnMacFilterParamsFrameType,
--                tnMacFilterParamsSrcMAC,
--                tnMacFilterParamsSrcMACMask,
--                tnMacFilterParamsDstMAC,
--                tnMacFilterParamsDstMACMask,
--                tnMacFilterParamsDot1pValue,
--                tnMacFilterParamsDot1pMask,
--                tnMacFilterParamsEtherType,
--                tnMacFilterParamsDsap,
--                tnMacFilterParamsDsapMask,
--                tnMacFilterParamsSsap,
--                tnMacFilterParamsSsapMask,
--                tnMacFilterParamsSnapPid,
--                tnMacFilterParamsSnapOui,
--                tnMacFilterParamsIngressHitCount,
--                tnMacFilterParamsEgressHitCount,
--                tnMacFilterParamsLogInstantiated,
--                tnMacFilterParamsFwdSvcId,
--                tnMacFilterParamsFwdSapPortId,
--                tnMacFilterParamsFwdSapEncapVal,
--                tnMacFilterParamsFwdSdpBind,
--                tnMacFilterParamsRedirectURL,
--                tnMacFilterParamsIngrHitByteCount,
--                tnMacFilterParamsEgrHitByteCount
--            }
--    STATUS    current
--    DESCRIPTION
--        "The group of objects supporting management of mac filter objects
--        on Nokia 7x50 SR series systems 6.0 release."
--    ::= { tnFilterMIBGroups 23 }

-- tnIPv6FilterV6v0Group OBJECT-GROUP
--    OBJECTS {
--                tnIPv6FilterRowStatus,
--                tnIPv6FilterScope,
--                tnIPv6FilterDescription,
--                tnIPv6FilterDefaultAction,
--                tnIPv6FilterParamsRowStatus,
--                tnIPv6FilterParamsLogId,
--                tnIPv6FilterParamsDescription,
--                tnIPv6FilterParamsAction,
--                tnIPv6FilterParamsForwardNH,
--                tnIPv6FilterParamsForwardNHIndirect,
--                tnIPv6FilterParamsRemarkDSCP,
--                tnIPv6FilterParamsRemarkDSCPMask,
--                tnIPv6FilterParamsRemarkDot1p,
--                tnIPv6FilterParamsSourceIpAddr,
--                tnIPv6FilterParamsSourceIpMask,
--                tnIPv6FilterParamsDestinationIpAddr,
--                tnIPv6FilterParamsDestinationIpMask,
--                tnIPv6FilterParamsNextHeader,
--                tnIPv6FilterParamsSourcePortValue1,
--                tnIPv6FilterParamsSourcePortValue2,
--                tnIPv6FilterParamsSourcePortOperator,
--                tnIPv6FilterParamsDestPortValue1,
--                tnIPv6FilterParamsDestPortValue2,
--                tnIPv6FilterParamsDestPortOperator,
--                tnIPv6FilterParamsDSCP,
--                tnIPv6FilterParamsTcpSyn,
--                tnIPv6FilterParamsTcpAck,
--                tnIPv6FilterParamsIcmpCode,
--                tnIPv6FilterParamsIcmpType,
--                tnIPv6FilterParamsCflowdSample,
--                tnIPv6FilterParamsCflowdIfSample,
--                tnIPv6FilterParamsForwardNHInterface,
--                tnIPv6FilterParamsIngressHitCount,
--                tnIPv6FilterParamsEgressHitCount,
--                tnIPv6FilterParamsLogInstantiated,
--                tnIPv6FilterParamsForwardRedPlcy,
--                tnIPv6FilterParamsActiveDest,
--                tnIPv6FilterParamsIngrHitByteCount,
--                tnIPv6FilterParamsEgrHitByteCount
--            }
--    STATUS    current
--    DESCRIPTION
--        "The group of objects supporting management of IPv6 filter objects
--        on Nokia 7x50 SR series systems."
--    ::= { tnFilterMIBGroups 24 }

END

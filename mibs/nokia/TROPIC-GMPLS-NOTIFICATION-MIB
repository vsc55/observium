TROPIC-GMPLS-NOTIFICATION-MIB DEFINITIONS ::= BEGIN

-- (c) Copyright 2021 Nokia Networks.  All rights reserved.
-- This software is the confidential and proprietary property of
-- Nokia and may only be used in accordance with the terms of the
-- license agreement provided with this software.

IMPORTS
      tnNotificationObjs,
      tnTrapTime,
      tnTrapObjectIDType,
      tnTrapObjectID,
      tnTrapCategory,
      tnTrapDescr,
      tnTrapData,
      tnTrapServiceAffecting,
      tnTrapEntityType,
      tnTrapCondition                         FROM TROPIC-NOTIFICATION-MIB
      MODULE-IDENTITY,
      NOTIFICATION-TYPE                       FROM SNMPv2-SMI
      tnGmplsMIBModules                       FROM TROPIC-GLOBAL-REG;

  tnGmplsNotificationMIBModule MODULE-IDENTITY
      LAST-UPDATED    "201802231200Z"
      ORGANIZATION    "Nokia"
      CONTACT-INFO    "Nokia
                       Attn: Jeff Donnelly
                       600 Mountain Avenue
                       New Providence, NJ 07974

                       Phone: +1 732 221 6408
                       Email: jeff.donnelly@nokia.com"

      DESCRIPTION "GMPLS Notifications."

      REVISION    "201802231200Z"
      DESCRIPTION "Updated the contact info."

      REVISION    "201611161200Z"
      DESCRIPTION "Updated the contact info."

      REVISION    "201306271200Z"
      DESCRIPTION "Initial version."

      ::= { tnGmplsMIBModules 5 }

---------------------------------------------------------------------------
-- Top Level Components of This MIB
---------------------------------------------------------------------------
  tnNotificationsGmpls           OBJECT IDENTIFIER ::= { tnNotificationObjs 8 }
  tnAlarmNotificationsGmpls      OBJECT IDENTIFIER ::= { tnNotificationsGmpls 1 }
  tnEventNotificationsGmpls      OBJECT IDENTIFIER ::= { tnNotificationsGmpls 2 }
  tnAlarmNotificationsGmplsNode  OBJECT IDENTIFIER ::= { tnAlarmNotificationsGmpls 1 }
--  tnAlarmNotificationsGmplsLink  OBJECT IDENTIFIER ::= { tnAlarmNotificationsGmpls 2 }
  tnAlarmNotificationsGmplsCpif  OBJECT IDENTIFIER ::= { tnAlarmNotificationsGmpls 3 }
  tnAlarmNotificationsGmplsLsp   OBJECT IDENTIFIER ::= { tnAlarmNotificationsGmpls 4 }
  tnEventNotificationsGmplsLsp   OBJECT IDENTIFIER ::= { tnEventNotificationsGmpls 1 }
  tnEventNotificationsGmplsDpif  OBJECT IDENTIFIER ::= { tnEventNotificationsGmpls 2 }
  tnEventNotificationsGmplsCpif  OBJECT IDENTIFIER ::= { tnEventNotificationsGmpls 3 }

-- **************************************************************************
-- Extensions for TROPIC-TC MIB
--   1. TnEntityType - Add gmplsNode, gmplsLsp, gmplsLink
--   2. TnCondition  - Add Node: RESTORATIONDISABLED, NODEDEG, INMIGRATION, SUBNODEUNREACHABLE,
--                               NEUNREACHBLE, OPTICALPARAMERR, EPTUPLOADERR
--                   - Add LSP: LSPFAILEDAPE, LSPFAILEDXC, LSPFAILEDPRE, LSPFAILEDTP,
--                              LSPFAILEDUNPROT, APEINPROGRESS, BACKUPUNAVAIL, CHANNELVIOLATION,
--                              COLORVIOLATION, FEASIBILITYVIOLATION, SRGDIVERSITY, LINKDIVERSITY,
--                              NUNVCOMM, NUNVCONFIG, NUNVINDETERMINED, NUNVREVERSION, NUNVTPBLOCKED,
--                              NUNVTRANSMISSION, READYTOREVERT, REROUTENOTPOSSIBLE, REROUTED,
--                              TESTMODE
--
--                   - Add link: ?
--                   - Add CP alarms: OSPF/RSVP/LMP/CPNbr degraded/down,
--                                 NetworkVersionMismatch
--
-- Extensions for TROPIC-NOTIFICATION-MIB
--   1. Valid gmpls objectIdTypes:
--      gmplsNodeObjectId     == 128
--      gmplsLspObjectId      == 129
--      gmplsDataLinkObjectId == 130
--      gmplsTELinkObjectId   == 131
--      gmplsCPNbrObjectId    == 132
--      gmplsOSPFObjectId     == 133
--      gmplsRSVPObjectId     == 134
--      gmplsLMPObjectId      == 135
--
--   2. tnTrapObjectId values
--
--        switch(objectIdType){
--              case gmplsNodeObjectId:
--                      nodeId = objectId;
--                      break;
--
--              case gmplsLspObjectId:
--                      lspId = objectId;
--                      break;
--
--              case gmplsDataLinkObjectId:
--                      dataLinkId = objectId
--                      break;
--
--              case gmplsTELinkObjectId:
--                      teLinkId = objectId;
--                      break;
--
--              case gmplsCPNbrObjectId:
--                      cpNbrId = (objectId & 0x0000FFFF);
--                      break;
--
--              case gmplsOSPFObjectId:
--                      ospfIfId = (objectId & 0x0000FFFF);
--                      break;
--
--              case gmplsRSVPObjectId:
--                      rsvpIfId = (objectId & 0x0000FFFF);
--                      break;
--
--              case gmplsLMPObjectId:
--                      lmpIfId = (objectId & 0x0000FFFF);
--                      break;
--        }

-- ------------------------------------------------------------
-- GMPLS Node alarms
-- ------------------------------------------------------------
    tnGmplsRestorationDisabledRaisedNotif NOTIFICATION-TYPE
        OBJECTS {
            tnTrapTime,
            tnTrapObjectIDType,
            tnTrapObjectID,
            tnTrapCategory,
            tnTrapDescr,
            tnTrapData,
            tnTrapEntityType,
            tnTrapCondition
        }
        STATUS         current
        DESCRIPTION    "."
        ::= { tnAlarmNotificationsGmplsNode 1 }

    tnGmplsRestorationDisabledClearedNotif NOTIFICATION-TYPE
        OBJECTS {
            tnTrapTime,
            tnTrapObjectIDType,
            tnTrapObjectID,
            tnTrapCategory,
            tnTrapDescr,
            tnTrapData,
            tnTrapEntityType,
            tnTrapCondition
        }
        STATUS         current
        DESCRIPTION    "."
        ::= { tnAlarmNotificationsGmplsNode 2 }

    tnGmplsNodeDegradedRaisedNotif NOTIFICATION-TYPE
        OBJECTS {
            tnTrapTime,
            tnTrapObjectIDType,
            tnTrapObjectID,
            tnTrapCategory,
            tnTrapDescr,
            tnTrapData,
            tnTrapEntityType,
            tnTrapCondition
        }
        STATUS         current
        DESCRIPTION    "."
        ::= { tnAlarmNotificationsGmplsNode 3 }

    tnGmplsNodeDegradedClearedNotif NOTIFICATION-TYPE
        OBJECTS {
            tnTrapTime,
            tnTrapObjectIDType,
            tnTrapObjectID,
            tnTrapCategory,
            tnTrapDescr,
            tnTrapData,
            tnTrapEntityType,
            tnTrapCondition
        }
        STATUS         current
        DESCRIPTION    "."
        ::= { tnAlarmNotificationsGmplsNode 4 }

    tnGmplsInMigrationRaisedNotif NOTIFICATION-TYPE
        OBJECTS {
            tnTrapTime,
            tnTrapObjectIDType,
            tnTrapObjectID,
            tnTrapCategory,
            tnTrapDescr,
            tnTrapData,
            tnTrapEntityType,
            tnTrapCondition
        }
        STATUS         current
        DESCRIPTION    "."
        ::= { tnAlarmNotificationsGmplsNode 5 }

    tnGmplsInMigrationClearedNotif NOTIFICATION-TYPE
        OBJECTS {
            tnTrapTime,
            tnTrapObjectIDType,
            tnTrapObjectID,
            tnTrapCategory,
            tnTrapDescr,
            tnTrapData,
            tnTrapEntityType,
            tnTrapCondition
        }
        STATUS         current
        DESCRIPTION    "."
        ::= { tnAlarmNotificationsGmplsNode 6 }

    tnGmplsSubnodeUnreachableRaisedNotif NOTIFICATION-TYPE
        OBJECTS {
            tnTrapTime,
            tnTrapObjectIDType,
            tnTrapObjectID,
            tnTrapCategory,
            tnTrapDescr,
            tnTrapData,
            tnTrapEntityType,
            tnTrapCondition
        }
        STATUS         current
        DESCRIPTION    "."
        ::= { tnAlarmNotificationsGmplsNode 7 }

    tnGmplsSubnodeUnreachableClearedNotif NOTIFICATION-TYPE
        OBJECTS {
            tnTrapTime,
            tnTrapObjectIDType,
            tnTrapObjectID,
            tnTrapCategory,
            tnTrapDescr,
            tnTrapData,
            tnTrapEntityType,
            tnTrapCondition
        }
        STATUS         current
        DESCRIPTION    "."
        ::= { tnAlarmNotificationsGmplsNode 8 }

    tnGmplsNeUnreachableRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnAlarmNotificationsGmplsNode 9 }

    tnGmplsNeUnreachableClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnAlarmNotificationsGmplsNode 10 }

    tnGmplsOpticalParameterFileErrRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnAlarmNotificationsGmplsNode 11 }

    tnGmplsOpticalParameterFileErrClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnAlarmNotificationsGmplsNode 12 }

    tnGmplsEptUploadErrRaisedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnAlarmNotificationsGmplsNode 13 }

    tnGmplsEptUploadErrClearedNotif NOTIFICATION-TYPE
        OBJECTS {
            tnTrapTime,
            tnTrapObjectIDType,
            tnTrapObjectID,
            tnTrapCategory,
            tnTrapDescr,
            tnTrapData,
            tnTrapServiceAffecting,
            tnTrapEntityType,
            tnTrapCondition
        }
        STATUS         current
        DESCRIPTION    "."
        ::= { tnAlarmNotificationsGmplsNode 14 }

-- ------------------------------------------------------------
-- GMPLS Link alarms
-- ------------------------------------------------------------

-- ------------------------------------------------------------
-- GMPLS CP interface alarms
-- ------------------------------------------------------------
    tnGmplsCPNbrCommunicationDownRaisedNotif NOTIFICATION-TYPE
        OBJECTS {
            tnTrapTime,
            tnTrapObjectIDType,
            tnTrapObjectID,
            tnTrapCategory,
            tnTrapDescr,
            tnTrapData,
            tnTrapEntityType,
            tnTrapCondition
        }
        STATUS         current
        DESCRIPTION    "."
        ::= { tnAlarmNotificationsGmplsCpif 1 }

    tnGmplsCPNbrCommunicationDownClearedNotif NOTIFICATION-TYPE
        OBJECTS {
            tnTrapTime,
            tnTrapObjectIDType,
            tnTrapObjectID,
            tnTrapCategory,
            tnTrapDescr,
            tnTrapData,
            tnTrapEntityType,
            tnTrapCondition
        }
        STATUS         current
        DESCRIPTION    "."
        ::= { tnAlarmNotificationsGmplsCpif 2 }

    tnGmplsCPNbrCommunicationDegradedRaisedNotif NOTIFICATION-TYPE
        OBJECTS {
            tnTrapTime,
            tnTrapObjectIDType,
            tnTrapObjectID,
            tnTrapCategory,
            tnTrapDescr,
            tnTrapData,
            tnTrapEntityType,
            tnTrapCondition
        }
        STATUS         current
        DESCRIPTION    "."
        ::= { tnAlarmNotificationsGmplsCpif 3 }

    tnGmplsCPNbrCommunicationDegradedClearedNotif NOTIFICATION-TYPE
        OBJECTS {
            tnTrapTime,
            tnTrapObjectIDType,
            tnTrapObjectID,
            tnTrapCategory,
            tnTrapDescr,
            tnTrapData,
            tnTrapEntityType,
            tnTrapCondition
        }
        STATUS         current
        DESCRIPTION    "."
        ::= { tnAlarmNotificationsGmplsCpif 4 }

    tnGmplsRsvpCommunicationDownRaisedNotif NOTIFICATION-TYPE
        OBJECTS {
            tnTrapTime,
            tnTrapObjectIDType,
            tnTrapObjectID,
            tnTrapCategory,
            tnTrapDescr,
            tnTrapData,
            tnTrapEntityType,
            tnTrapCondition
        }
        STATUS         current
        DESCRIPTION    "."
        ::= { tnAlarmNotificationsGmplsCpif 5 }

    tnGmplsRsvpCommunicationDownClearedNotif NOTIFICATION-TYPE
        OBJECTS {
            tnTrapTime,
            tnTrapObjectIDType,
            tnTrapObjectID,
            tnTrapCategory,
            tnTrapDescr,
            tnTrapData,
            tnTrapEntityType,
            tnTrapCondition
        }
        STATUS         current
        DESCRIPTION    "."
        ::= { tnAlarmNotificationsGmplsCpif 6 }

    tnGmplsRsvpCommunicationDegradedRaisedNotif NOTIFICATION-TYPE
        OBJECTS {
            tnTrapTime,
            tnTrapObjectIDType,
            tnTrapObjectID,
            tnTrapCategory,
            tnTrapDescr,
            tnTrapData,
            tnTrapEntityType,
            tnTrapCondition
        }
        STATUS         current
        DESCRIPTION    "."
        ::= { tnAlarmNotificationsGmplsCpif 7 }

    tnGmplsRsvpCommunicationDegradedClearedNotif NOTIFICATION-TYPE
        OBJECTS {
            tnTrapTime,
            tnTrapObjectIDType,
            tnTrapObjectID,
            tnTrapCategory,
            tnTrapDescr,
            tnTrapData,
            tnTrapEntityType,
            tnTrapCondition
        }
        STATUS         current
        DESCRIPTION    "."
        ::= { tnAlarmNotificationsGmplsCpif 8 }

    tnGmplsDprCommunicationDownRaisedNotif NOTIFICATION-TYPE
        OBJECTS {
            tnTrapTime,
            tnTrapObjectIDType,
            tnTrapObjectID,
            tnTrapCategory,
            tnTrapDescr,
            tnTrapData,
            tnTrapEntityType,
            tnTrapCondition
        }
        STATUS         current
        DESCRIPTION    "."
        ::= { tnAlarmNotificationsGmplsCpif 9 }

    tnGmplsDprCommunicationDownClearedNotif NOTIFICATION-TYPE
        OBJECTS {
            tnTrapTime,
            tnTrapObjectIDType,
            tnTrapObjectID,
            tnTrapCategory,
            tnTrapDescr,
            tnTrapData,
            tnTrapEntityType,
            tnTrapCondition
        }
        STATUS         current
        DESCRIPTION    "."
        ::= { tnAlarmNotificationsGmplsCpif 10 }

    tnGmplsDprCommunicationDegradedRaisedNotif NOTIFICATION-TYPE
        OBJECTS {
            tnTrapTime,
            tnTrapObjectIDType,
            tnTrapObjectID,
            tnTrapCategory,
            tnTrapDescr,
            tnTrapData,
            tnTrapEntityType,
            tnTrapCondition
        }
        STATUS         current
        DESCRIPTION    "."
        ::= { tnAlarmNotificationsGmplsCpif 11 }

    tnGmplsDprCommunicationDegradedClearedNotif NOTIFICATION-TYPE
        OBJECTS {
            tnTrapTime,
            tnTrapObjectIDType,
            tnTrapObjectID,
            tnTrapCategory,
            tnTrapDescr,
            tnTrapData,
            tnTrapEntityType,
            tnTrapCondition
        }
        STATUS         current
        DESCRIPTION    "."
        ::= { tnAlarmNotificationsGmplsCpif 12 }

    tnGmplsDprNetworkVersionMismatchRaisedNotif NOTIFICATION-TYPE
        OBJECTS {
            tnTrapTime,
            tnTrapObjectIDType,
            tnTrapObjectID,
            tnTrapCategory,
            tnTrapDescr,
            tnTrapData,
            tnTrapEntityType,
            tnTrapCondition
        }
        STATUS         current
        DESCRIPTION    "."
        ::= { tnAlarmNotificationsGmplsCpif 13 }

    tnGmplsDprNetworkVersionMismatchClearedNotif NOTIFICATION-TYPE
        OBJECTS {
            tnTrapTime,
            tnTrapObjectIDType,
            tnTrapObjectID,
            tnTrapCategory,
            tnTrapDescr,
            tnTrapData,
            tnTrapEntityType,
            tnTrapCondition
        }
        STATUS         current
        DESCRIPTION    "."
        ::= { tnAlarmNotificationsGmplsCpif 14 }

    tnGmplsLmpCommunicationDownRaisedNotif NOTIFICATION-TYPE
        OBJECTS {
            tnTrapTime,
            tnTrapObjectIDType,
            tnTrapObjectID,
            tnTrapCategory,
            tnTrapDescr,
            tnTrapData,
            tnTrapEntityType,
            tnTrapCondition
        }
        STATUS         current
        DESCRIPTION    "."
        ::= { tnAlarmNotificationsGmplsCpif 15 }

    tnGmplsLmpCommunicationDownClearedNotif NOTIFICATION-TYPE
        OBJECTS {
            tnTrapTime,
            tnTrapObjectIDType,
            tnTrapObjectID,
            tnTrapCategory,
            tnTrapDescr,
            tnTrapData,
            tnTrapEntityType,
            tnTrapCondition
        }
        STATUS         current
        DESCRIPTION    "."
        ::= { tnAlarmNotificationsGmplsCpif 16 }

    tnGmplsLmpCommunicationDegradedRaisedNotif NOTIFICATION-TYPE
        OBJECTS {
            tnTrapTime,
            tnTrapObjectIDType,
            tnTrapObjectID,
            tnTrapCategory,
            tnTrapDescr,
            tnTrapData,
            tnTrapEntityType,
            tnTrapCondition
        }
        STATUS         current
        DESCRIPTION    "."
        ::= { tnAlarmNotificationsGmplsCpif 17 }

    tnGmplsLmpCommunicationDegradedClearedNotif NOTIFICATION-TYPE
        OBJECTS {
            tnTrapTime,
            tnTrapObjectIDType,
            tnTrapObjectID,
            tnTrapCategory,
            tnTrapDescr,
            tnTrapData,
            tnTrapEntityType,
            tnTrapCondition
        }
        STATUS         current
        DESCRIPTION    "."
        ::= { tnAlarmNotificationsGmplsCpif 18 }

-- ------------------------------------------------------------
-- GMPLS Label Switched Path (LSP) alarms
-- ------------------------------------------------------------
    tnGmplsLspReroutedRaisedNotif NOTIFICATION-TYPE
        OBJECTS {
            tnTrapTime,
            tnTrapObjectIDType,
            tnTrapObjectID,
            tnTrapCategory,
            tnTrapDescr,
            tnTrapData,
            tnTrapEntityType,
            tnTrapCondition
        }
        STATUS         current
        DESCRIPTION    "."
        ::= { tnAlarmNotificationsGmplsLsp 1 }

    tnGmplsLspReroutedClearedNotif NOTIFICATION-TYPE
        OBJECTS {
            tnTrapTime,
            tnTrapObjectIDType,
            tnTrapObjectID,
            tnTrapCategory,
            tnTrapDescr,
            tnTrapData,
            tnTrapEntityType,
            tnTrapCondition
        }
        STATUS         current
        DESCRIPTION    "."
        ::= { tnAlarmNotificationsGmplsLsp 2 }

    tnGmplsLspReversionBlockedRaisedNotif NOTIFICATION-TYPE
        OBJECTS {
            tnTrapTime,
            tnTrapObjectIDType,
            tnTrapObjectID,
            tnTrapCategory,
            tnTrapDescr,
            tnTrapData,
            tnTrapEntityType,
            tnTrapCondition
        }
        STATUS         current
        DESCRIPTION    "."
        ::= { tnAlarmNotificationsGmplsLsp 3 }

    tnGmplsLspReversionBlockedClearedNotif NOTIFICATION-TYPE
        OBJECTS {
            tnTrapTime,
            tnTrapObjectIDType,
            tnTrapObjectID,
            tnTrapCategory,
            tnTrapDescr,
            tnTrapData,
            tnTrapEntityType,
            tnTrapCondition
        }
        STATUS         current
        DESCRIPTION    "."
        ::= { tnAlarmNotificationsGmplsLsp 4 }

    tnGmplsLspBackupUnavailRaisedNotif NOTIFICATION-TYPE
        OBJECTS {
            tnTrapTime,
            tnTrapObjectIDType,
            tnTrapObjectID,
            tnTrapCategory,
            tnTrapDescr,
            tnTrapData,
            tnTrapEntityType,
            tnTrapCondition
        }
        STATUS         current
        DESCRIPTION    "."
        ::= { tnAlarmNotificationsGmplsLsp 5 }

    tnGmplsLspBackupUnavailClearedNotif NOTIFICATION-TYPE
        OBJECTS {
            tnTrapTime,
            tnTrapObjectIDType,
            tnTrapObjectID,
            tnTrapCategory,
            tnTrapDescr,
            tnTrapData,
            tnTrapEntityType,
            tnTrapCondition
        }
        STATUS         current
        DESCRIPTION    "."
        ::= { tnAlarmNotificationsGmplsLsp 6 }

    tnGmplsLspActiveFailedRaisedNotif NOTIFICATION-TYPE
        OBJECTS {
            tnTrapTime,
            tnTrapObjectIDType,
            tnTrapObjectID,
            tnTrapCategory,
            tnTrapDescr,
            tnTrapData,
            tnTrapEntityType,
            tnTrapCondition
        }
        STATUS         current
        DESCRIPTION    "."
        ::= { tnAlarmNotificationsGmplsLsp 7 }

    tnGmplsLspActiveFailedClearedNotif NOTIFICATION-TYPE
        OBJECTS {
            tnTrapTime,
            tnTrapObjectIDType,
            tnTrapObjectID,
            tnTrapCategory,
            tnTrapDescr,
            tnTrapData,
            tnTrapEntityType,
            tnTrapCondition
        }
        STATUS         current
        DESCRIPTION    "."
        ::= { tnAlarmNotificationsGmplsLsp 8 }

    tnGmplsLspNominalUnavailRaisedNotif NOTIFICATION-TYPE
        OBJECTS {
            tnTrapTime,
            tnTrapObjectIDType,
            tnTrapObjectID,
            tnTrapCategory,
            tnTrapDescr,
            tnTrapData,
            tnTrapEntityType,
            tnTrapCondition
        }
        STATUS         current
        DESCRIPTION    "."
        ::= { tnAlarmNotificationsGmplsLsp 9 }

    tnGmplsLspNominalUnavailClearedNotif NOTIFICATION-TYPE
        OBJECTS {
            tnTrapTime,
            tnTrapObjectIDType,
            tnTrapObjectID,
            tnTrapCategory,
            tnTrapDescr,
            tnTrapData,
            tnTrapEntityType,
            tnTrapCondition
        }
        STATUS         current
        DESCRIPTION    "."
        ::= { tnAlarmNotificationsGmplsLsp 10 }

    tnGmplsLspActiveDegradedRaisedNotif NOTIFICATION-TYPE
        OBJECTS {
            tnTrapTime,
            tnTrapObjectIDType,
            tnTrapObjectID,
            tnTrapCategory,
            tnTrapDescr,
            tnTrapData,
            tnTrapEntityType,
            tnTrapCondition
        }
        STATUS         current
        DESCRIPTION    "."
        ::= { tnAlarmNotificationsGmplsLsp 11 }

    tnGmplsLspActiveDegradedClearedNotif NOTIFICATION-TYPE
        OBJECTS {
            tnTrapTime,
            tnTrapObjectIDType,
            tnTrapObjectID,
            tnTrapCategory,
            tnTrapDescr,
            tnTrapData,
            tnTrapEntityType,
            tnTrapCondition
        }
        STATUS         current
        DESCRIPTION    "."
        ::= { tnAlarmNotificationsGmplsLsp 12 }

    tnGmplsLspChannelViolationRaisedNotif NOTIFICATION-TYPE
        OBJECTS {
            tnTrapTime,
            tnTrapObjectIDType,
            tnTrapObjectID,
            tnTrapCategory,
            tnTrapDescr,
            tnTrapData,
            tnTrapEntityType,
            tnTrapCondition
        }
        STATUS         current
        DESCRIPTION    "."
        ::= { tnAlarmNotificationsGmplsLsp 13 }

    tnGmplsLspChannelViolationClearedNotif NOTIFICATION-TYPE
        OBJECTS {
            tnTrapTime,
            tnTrapObjectIDType,
            tnTrapObjectID,
            tnTrapCategory,
            tnTrapDescr,
            tnTrapData,
            tnTrapEntityType,
            tnTrapCondition
        }
        STATUS         current
        DESCRIPTION    "."
        ::= { tnAlarmNotificationsGmplsLsp 14 }

    tnGmplsLspColorViolationRaisedNotif NOTIFICATION-TYPE
        OBJECTS {
            tnTrapTime,
            tnTrapObjectIDType,
            tnTrapObjectID,
            tnTrapCategory,
            tnTrapDescr,
            tnTrapData,
            tnTrapEntityType,
            tnTrapCondition
        }
        STATUS         current
        DESCRIPTION    "."
        ::= { tnAlarmNotificationsGmplsLsp 15 }

    tnGmplsLspColorViolationClearedNotif NOTIFICATION-TYPE
        OBJECTS {
            tnTrapTime,
            tnTrapObjectIDType,
            tnTrapObjectID,
            tnTrapCategory,
            tnTrapDescr,
            tnTrapData,
            tnTrapEntityType,
            tnTrapCondition
        }
        STATUS         current
        DESCRIPTION    "."
        ::= { tnAlarmNotificationsGmplsLsp 16 }

    tnGmplsLspOpticalFeasibilityViolationRaisedNotif NOTIFICATION-TYPE
        OBJECTS {
            tnTrapTime,
            tnTrapObjectIDType,
            tnTrapObjectID,
            tnTrapCategory,
            tnTrapDescr,
            tnTrapData,
            tnTrapEntityType,
            tnTrapCondition
        }
        STATUS         current
        DESCRIPTION    "."
        ::= { tnAlarmNotificationsGmplsLsp 17 }

    tnGmplsLspOpticalFeasibilityViolationClearedNotif NOTIFICATION-TYPE
        OBJECTS {
            tnTrapTime,
            tnTrapObjectIDType,
            tnTrapObjectID,
            tnTrapCategory,
            tnTrapDescr,
            tnTrapData,
            tnTrapEntityType,
            tnTrapCondition
        }
        STATUS         current
        DESCRIPTION    "."
        ::= { tnAlarmNotificationsGmplsLsp 18 }

    tnGmplsLspSRGViolationRaisedNotif NOTIFICATION-TYPE
        OBJECTS {
            tnTrapTime,
            tnTrapObjectIDType,
            tnTrapObjectID,
            tnTrapCategory,
            tnTrapDescr,
            tnTrapData,
            tnTrapEntityType,
            tnTrapCondition
        }
        STATUS         current
        DESCRIPTION    "."
        ::= { tnAlarmNotificationsGmplsLsp 19 }

    tnGmplsLspSRGViolationClearedNotif NOTIFICATION-TYPE
        OBJECTS {
            tnTrapTime,
            tnTrapObjectIDType,
            tnTrapObjectID,
            tnTrapCategory,
            tnTrapDescr,
            tnTrapData,
            tnTrapEntityType,
            tnTrapCondition
        }
        STATUS         current
        DESCRIPTION    "."
        ::= { tnAlarmNotificationsGmplsLsp 20 }

    tnGmplsLspLinkDiversityViolationRaisedNotif NOTIFICATION-TYPE
        OBJECTS {
            tnTrapTime,
            tnTrapObjectIDType,
            tnTrapObjectID,
            tnTrapCategory,
            tnTrapDescr,
            tnTrapData,
            tnTrapEntityType,
            tnTrapCondition
        }
        STATUS         current
        DESCRIPTION    "."
        ::= { tnAlarmNotificationsGmplsLsp 21 }

    tnGmplsLspLinkDiversityViolationClearedNotif NOTIFICATION-TYPE
        OBJECTS {
            tnTrapTime,
            tnTrapObjectIDType,
            tnTrapObjectID,
            tnTrapCategory,
            tnTrapDescr,
            tnTrapData,
            tnTrapEntityType,
            tnTrapCondition
        }
        STATUS         current
        DESCRIPTION    "."
        ::= { tnAlarmNotificationsGmplsLsp 22 }

    tnGmplsLspApeInProgressRaisedNotif NOTIFICATION-TYPE
        OBJECTS {
            tnTrapTime,
            tnTrapObjectIDType,
            tnTrapObjectID,
            tnTrapCategory,
            tnTrapDescr,
            tnTrapData,
            tnTrapEntityType,
            tnTrapCondition
        }
        STATUS         current
        DESCRIPTION    "."
        ::= { tnAlarmNotificationsGmplsLsp 23 }

    tnGmplsLspApeInProgressClearedNotif NOTIFICATION-TYPE
        OBJECTS {
            tnTrapTime,
            tnTrapObjectIDType,
            tnTrapObjectID,
            tnTrapCategory,
            tnTrapDescr,
            tnTrapData,
            tnTrapEntityType,
            tnTrapCondition
        }
        STATUS         current
        DESCRIPTION    "."
        ::= { tnAlarmNotificationsGmplsLsp 24 }

    tnGmplsLspTestModeRaisedNotif NOTIFICATION-TYPE
        OBJECTS {
            tnTrapTime,
            tnTrapObjectIDType,
            tnTrapObjectID,
            tnTrapCategory,
            tnTrapDescr,
            tnTrapData,
            tnTrapEntityType,
            tnTrapCondition
        }
        STATUS         current
        DESCRIPTION    "."
        ::= { tnAlarmNotificationsGmplsLsp 25 }

    tnGmplsLspTestModeClearedNotif NOTIFICATION-TYPE
        OBJECTS {
            tnTrapTime,
            tnTrapObjectIDType,
            tnTrapObjectID,
            tnTrapCategory,
            tnTrapDescr,
            tnTrapData,
            tnTrapEntityType,
            tnTrapCondition
        }
        STATUS         current
        DESCRIPTION    "."
        ::= { tnAlarmNotificationsGmplsLsp 26 }

    tnGmplsLspReadyToRevertRaisedNotif NOTIFICATION-TYPE
        OBJECTS {
            tnTrapTime,
            tnTrapObjectIDType,
            tnTrapObjectID,
            tnTrapCategory,
            tnTrapDescr,
            tnTrapData,
            tnTrapEntityType,
            tnTrapCondition
        }
        STATUS         current
        DESCRIPTION    "."
        ::= { tnAlarmNotificationsGmplsLsp 27 }

    tnGmplsLspReadyToRevertClearedNotif NOTIFICATION-TYPE
        OBJECTS {
            tnTrapTime,
            tnTrapObjectIDType,
            tnTrapObjectID,
            tnTrapCategory,
            tnTrapDescr,
            tnTrapData,
            tnTrapEntityType,
            tnTrapCondition
        }
        STATUS         current
        DESCRIPTION    "."
        ::= { tnAlarmNotificationsGmplsLsp 28 }

    tnGmplsLspEndpointFailureRaisedNotif NOTIFICATION-TYPE
        OBJECTS {
            tnTrapTime,
            tnTrapObjectIDType,
            tnTrapObjectID,
            tnTrapCategory,
            tnTrapDescr,
            tnTrapData,
            tnTrapEntityType,
            tnTrapCondition
        }
        STATUS         current
        DESCRIPTION    "."
        ::= { tnAlarmNotificationsGmplsLsp 29 }

    tnGmplsLspEndpointFailureClearedNotif NOTIFICATION-TYPE
        OBJECTS {
            tnTrapTime,
            tnTrapObjectIDType,
            tnTrapObjectID,
            tnTrapCategory,
            tnTrapDescr,
            tnTrapData,
            tnTrapEntityType,
            tnTrapCondition
        }
        STATUS         current
        DESCRIPTION    "."
        ::= { tnAlarmNotificationsGmplsLsp 30 }

-- ------------------------------------------------------------
-- GMPLS LSP Events
-- ------------------------------------------------------------
    tnGmplsLspCreatedNotif NOTIFICATION-TYPE
        OBJECTS {
            tnTrapTime,
            tnTrapObjectIDType,
            tnTrapObjectID,
            tnTrapCategory,
            tnTrapDescr,
            tnTrapData
        }
        STATUS         current
        DESCRIPTION    "."
        ::= { tnEventNotificationsGmplsLsp 1 }

    tnGmplsLspDeletedNotif NOTIFICATION-TYPE
        OBJECTS {
            tnTrapTime,
            tnTrapObjectIDType,
            tnTrapObjectID,
            tnTrapCategory,
            tnTrapDescr,
            tnTrapData
        }
        STATUS         current
        DESCRIPTION    "."
        ::= { tnEventNotificationsGmplsLsp 2 }

-- ------------------------------------------------------------
-- GMPLS DPIF Events
-- ------------------------------------------------------------
    tnGmplsDBLinkCreatedNotif NOTIFICATION-TYPE
        OBJECTS {
            tnTrapTime,
            tnTrapObjectIDType,
            tnTrapObjectID,
            tnTrapCategory,
            tnTrapDescr,
            tnTrapData
        }
        STATUS         current
        DESCRIPTION    "."
        ::= { tnEventNotificationsGmplsDpif 1 }

    tnGmplsDBLinkDeletedNotif NOTIFICATION-TYPE
        OBJECTS {
            tnTrapTime,
            tnTrapObjectIDType,
            tnTrapObjectID,
            tnTrapCategory,
            tnTrapDescr,
            tnTrapData
        }
        STATUS         current
        DESCRIPTION    "."
        ::= { tnEventNotificationsGmplsDpif 2 }

    tnGmplsTELinkCreatedNotif NOTIFICATION-TYPE
        OBJECTS {
            tnTrapTime,
            tnTrapObjectIDType,
            tnTrapObjectID,
            tnTrapCategory,
            tnTrapDescr,
            tnTrapData
        }
        STATUS         current
        DESCRIPTION    "."
        ::= { tnEventNotificationsGmplsDpif 3 }

    tnGmplsTELinkDeletedNotif NOTIFICATION-TYPE
        OBJECTS {
            tnTrapTime,
            tnTrapObjectIDType,
            tnTrapObjectID,
            tnTrapCategory,
            tnTrapDescr,
            tnTrapData
        }
        STATUS         current
        DESCRIPTION    "."
        ::= { tnEventNotificationsGmplsDpif 4 }

-- ------------------------------------------------------------
-- GMPLS CPIF Events
-- ------------------------------------------------------------
    tnGmplsCPNbrCreatedNotif NOTIFICATION-TYPE
        OBJECTS {
            tnTrapTime,
            tnTrapObjectIDType,
            tnTrapObjectID,
            tnTrapCategory,
            tnTrapDescr,
            tnTrapData
        }
        STATUS         current
        DESCRIPTION    "."
        ::= { tnEventNotificationsGmplsCpif 1 }

    tnGmplsCPNbrDeletedNotif NOTIFICATION-TYPE
        OBJECTS {
            tnTrapTime,
            tnTrapObjectIDType,
            tnTrapObjectID,
            tnTrapCategory,
            tnTrapDescr,
            tnTrapData
        }
        STATUS         current
        DESCRIPTION    "."
        ::= { tnEventNotificationsGmplsCpif 2 }

    tnGmplsRsvpIfCreatedNotif NOTIFICATION-TYPE
        OBJECTS {
            tnTrapTime,
            tnTrapObjectIDType,
            tnTrapObjectID,
            tnTrapCategory,
            tnTrapDescr,
            tnTrapData
        }
        STATUS         current
        DESCRIPTION    "."
        ::= { tnEventNotificationsGmplsCpif 3 }

    tnGmplsRsvpIfDeletedNotif NOTIFICATION-TYPE
        OBJECTS {
            tnTrapTime,
            tnTrapObjectIDType,
            tnTrapObjectID,
            tnTrapCategory,
            tnTrapDescr,
            tnTrapData
        }
        STATUS         current
        DESCRIPTION    "."
        ::= { tnEventNotificationsGmplsCpif 4 }

    tnGmplsDprIfCreatedNotif NOTIFICATION-TYPE
        OBJECTS {
            tnTrapTime,
            tnTrapObjectIDType,
            tnTrapObjectID,
            tnTrapCategory,
            tnTrapDescr,
            tnTrapData
        }
        STATUS         current
        DESCRIPTION    "."
        ::= { tnEventNotificationsGmplsCpif 5 }

    tnGmplsDprIfDeletedNotif NOTIFICATION-TYPE
        OBJECTS {
            tnTrapTime,
            tnTrapObjectIDType,
            tnTrapObjectID,
            tnTrapCategory,
            tnTrapDescr,
            tnTrapData
        }
        STATUS         current
        DESCRIPTION    "."
        ::= { tnEventNotificationsGmplsCpif 6 }

    tnGmplsLmpIfCreatedNotif NOTIFICATION-TYPE
        OBJECTS {
            tnTrapTime,
            tnTrapObjectIDType,
            tnTrapObjectID,
            tnTrapCategory,
            tnTrapDescr,
            tnTrapData
        }
        STATUS         current
        DESCRIPTION    "."
        ::= { tnEventNotificationsGmplsCpif 7 }

    tnGmplsLmpIfDeletedNotif NOTIFICATION-TYPE
        OBJECTS {
            tnTrapTime,
            tnTrapObjectIDType,
            tnTrapObjectID,
            tnTrapCategory,
            tnTrapDescr,
            tnTrapData
        }
        STATUS         current
        DESCRIPTION    "."
        ::= { tnEventNotificationsGmplsCpif 8 }

END -- DEFINITION OF TROPIC-GMPLS-NOTIFICATION-MIB

--MibName=raisecomBanner
-- *****************************************************************
-- RAISECOM-BANNER-MIB.MIB:  raisecom Banner MIB file
-- July 2012, Wangmingzhou
--
-- Copyright (c) 2012 by raisecom, Inc.
-- All rights reserved.
-- *****************************************************************
RAISECOM-BANNER-MIB  DEFINITIONS ::= BEGIN

IMPORTS   
        RowStatus                               FROM SNMPv2-TC 
        raisecomAgent	            	        FROM RAISECOM-BASE-MIB 
        EnableVar                               FROM SWITCH-TC;  
        
	    raisecomBanner  MODULE-IDENTITY
        LAST-UPDATED    "201207260000Z"
        ORGANIZATION    "raisecom, Inc."
        CONTACT-INFO
                "       Raise Systems

                Postal: Beijing, China

                   Tel: 86-010-82884499

                E-mail: support@raisecom.com"
        DESCRIPTION
                "description of raisecomBanner object."  
                REVISION   "201207260000Z"
                DESCRIPTION
                "Configure Banner information."
                ::= { raisecomAgent 81}  

  raisecomBannerNotifications       OBJECT IDENTIFIER ::={ raisecomBanner 1 }
  raisecomBannerObjects             OBJECT IDENTIFIER ::={ raisecomBanner 2 }
  raisecomBannerConformance         OBJECT IDENTIFIER ::={ raisecomBanner 3 }  
  
-- -------------------------------------------------------------
-- scalar in the MIB
-- -------------------------------------------------------------

  raisecomBannerGlobalGroup         OBJECT IDENTIFIER ::={ raisecomBannerObjects 1 }
  raisecomBannerMessageTableGroup   OBJECT IDENTIFIER ::={ raisecomBannerObjects 2 }
  
  raisecomBannerEnable              OBJECT-TYPE 
        SYNTAX   EnableVar
        ACCESS	 read-write
        STATUS   current
        DESCRIPTION
                 "If the banner is enable."
        ::= { raisecomBannerGlobalGroup 1}    
         
  raisecomBannerCmd                 OBJECT-TYPE 
        SYNTAX   INTEGER  { 
                            none(0)
                            clear(1)
                          }        
        ACCESS	 read-write
        STATUS   current
        DESCRIPTION
                 "Operation command, only support clear now."
        ::= { raisecomBannerGlobalGroup 2}   
        
  raisecomBannerMessageTableCount   OBJECT-TYPE 
        SYNTAX   INTEGER
        ACCESS	 read-only
        STATUS   current
        DESCRIPTION
                 "The count of total banner message tables."
        ::= { raisecomBannerGlobalGroup 3}  


-- ---------------------------------------------------------------------------       
-- raisecomBannerMessageTable  
-- ---------------------------------------------------------------------------
  raisecomBannerMessageTable      OBJECT-TYPE 
        SYNTAX   SEQUENCE OF raisecomBannerMessageEntry
        ACCESS	 not-accessible
        STATUS   current
        DESCRIPTION
                 "Banner message information."
        ::= { raisecomBannerMessageTableGroup   1 }
        
  raisecomBannerMessageEntry      OBJECT-TYPE
        SYNTAX   raisecomBannerMessageEntry
        ACCESS   not-accessible
        STATUS   current
        DESCRIPTION
                 "An entry in raisecomBannerMessageTable"
        INDEX { raisecomBannerType,
                raisecomBannerIndex}
        ::= { raisecomBannerMessageTable  1 } 
      
  raisecomBannerMessageEntry ::= SEQUENCE {
		raisecomBannerType	          INTEGER,
		raisecomBannerIndex           INTEGER,
		raisecomBannerDescribe        OCTET STRING,
		raisecomBannerRowstatus       RowStatus
  }

  
  raisecomBannerType       OBJECT-TYPE 
        SYNTAX   INTEGER{
                         motd (0),
                         login(1),
                         exec(2)
                        }
        ACCESS	 read-create
        STATUS   current
        DESCRIPTION
                 "Banner type, only support login now."
        ::= { raisecomBannerMessageEntry 1}    
         
  raisecomBannerIndex      OBJECT-TYPE 
        SYNTAX   INTEGER(1..10)
        ACCESS	 read-create
        STATUS   current
        DESCRIPTION
                 "One banner message support 2560 characters, so it needs to create 10 message tables,
                 this number is the table index."
        ::= { raisecomBannerMessageEntry 2}   
        
  raisecomBannerDescribe      OBJECT-TYPE 
        SYNTAX   OCTET STRING(SIZE(1..256))
        ACCESS	 read-create
        STATUS   current
        DESCRIPTION
                 "Banner message that input by user." 
        ::= { raisecomBannerMessageEntry 3}       
        
  raisecomBannerRowstatus      OBJECT-TYPE 
        SYNTAX   RowStatus
        ACCESS	 read-create
        STATUS   current
        DESCRIPTION
    "This object permits management of the table by
 	facilitating actions such as row creation,
 	construction, and destruction.
 	
 	The value of this object has no effect on
 	whether other objects in this conceptual row can be
 	modified." 
        ::= { raisecomBannerMessageEntry 4} 
        
  END

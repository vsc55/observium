-- File: RAISECOM-OPCOM3500-RCRMC-MIB.my
-- Changes:
-- author:Wang H.L.
--remote RC601VC,RC601VE,RC501,RC511FE,RC511-4FE
-- RCRMC: RaiseCom Optical Tranceiver Series

RAISECOM-OPT-REMOTE-RMC-MIB DEFINITIONS ::= BEGIN

IMPORTS
		
		OBJECT-TYPE, MODULE-IDENTITY,  NOTIFICATION-TYPE,Integer32,Counter32              
                  
        	FROM SNMPv2-SMI
		DisplayString,TruthValue		
			FROM SNMPv2-TC
  		MODULE-COMPLIANCE, OBJECT-GROUP,
  		NOTIFICATION-GROUP                FROM SNMPv2-CONF
		rcNotifsTrapLocation                  
		    FROM RAISECOM-NOTIFICATION-MIB	
		optSysModules                                               
            FROM RAISECOM-BASE-MIB 
        RcOptModuleType, RcOptIfModuleType
                FROM RAISECOM-OPTICAL-MODULE-TYPE-MIB    
	    rcEntPhysicalID
            FROM RAISECOM-OPTICAL-ENTITY-MIB;
  	

raisecomOptRemoteRmcMib MODULE-IDENTITY
    LAST-UPDATED "1303071705Z" 
    ORGANIZATION "RaiseCom Technology CO.,LTD"
    CONTACT-INFO
        "
       www.raisecom.com
        "
    DESCRIPTION
        "MIB for opcom3500 remote rc equipment."
    REVISION      "0506130000Z"
    DESCRIPTION
        ""
    REVISION      "0707160000Z"
    DESCRIPTION
        "
        1.add rcRemoteRmcReqInfo
        by Liu.X.M.
        "
    REVISION      "0905110000Z"
    DESCRIPTION
        "
        1.add 
             rcRemoteRmcLPBBeing      			INTEGER,
             rcRemoteRmcLPBInsideOutside      	INTEGER,
             rcRemoteRmcLPBMacAddrExch      	INTEGER,
             rcRemoteRmcLPBCrcRecal      		INTEGER,
             rcRemoteRmcLPBUtility      		INTEGER,
             rcRemoteRmcLPBFrameLength      	INTEGER，
             rcRemoteRmcLPBTime      			INTEGER

			rcRemoteRmcAdminCmd增加了2个命令项
          							  fxloopbackexternal(5), 
          							  fxloopbackinternal(6)  
        by zhuleilei
        "            
    REVISION      "0906080000Z"
    DESCRIPTION
        "
        1.add 
                   rcRemoteRmcQoSEnable                 INTEGER,
                   rcRemoteRmcQueuesPolicy              INTEGER,
                   rcRemoteRmcQoSPolicy              	INTEGER,
                   rcRemoteRmcBaseCOS                	INTEGER
                   
                   rcRemoteRmcEthFePriority			INTEGER
 
                   rcRemoteRmcVLANIndex				INTEGER,
                   rcRemoteRmcVLANStatus			INTEGER,
                   rcRemoteRmcVID					INTEGER,                
                   rcRemoteRmcVLANMember			INTEGER
			rcRemoteRmcVlantype增加了枚举值
          							  tagvlan(3) 
          	rcRemoteRmcAdminCmd增加了1个命令项
          							  versionnotice(7)--删掉了 
        by huxuehai
        "
    REVISION      "2010030300Z"
    DESCRIPTION
        "  根据评审意见调整了2010-2-8的顺序
        1.rcRemoteRmcSystemEntry add
                   rcRemoteRmcVersionInformation        OCTET STRING,
                   rcRemoteRmcDeviceMode				INTEGER,
                   rcRemoteRmcRemManage					INTEGER,
                   rcRemoteRmcRemotePowerDown			INTEGER,
                   rcRemoteRmcRemoteSeriousAlarm        INTEGER,
                   rcRemoteRmcOAMConnect                INTEGER,
         
                   rcRemoteRmcMacAging                  INTEGER,
                   rcRemoteRmcQosCfgQueueWeight         OCTET STRING,
                   rRemoteRmcQosCosToQueueQueue			OCTET STRING,
                   rcRemoteRmcQinQDirection             INTEGER,
                   rcRemoteRmcQinQTagMode               INTEGER,
                   rcRemoteRmcQinQDtOuterVID            INTEGER,
                   rcRemoteRmcQinQDtOuterTpid           INTEGER
				   rcRemoteRmcMaxPktsLength增加了枚举值	
				          								length2k(3)
														length9k(4)
 
		           rcRemoteRmcAdminCmd增加了1个命令项
					          							fxoamloopback(7)  
					          							syncStatustoCfg(8)
		           rcRemoteRmcQueuesPolicy增加了枚举值
					          							wrr(5)
					          							onespthreewrr(6)
					          							twosptwowrr(7)
		2.rcRemoteRmcEthFxEntry add
					rcRemoteRmcEthFxAttribute				INTEGER,
                    rcRemoteRmcEthFxCosOverrideEn           INTEGER,
                    rcRemoteRmcEthFxDefCos                  INTEGER,
                    rcRemoteRmcEthFxFlowControl             INTEGER,
                    rcRemoteRmcEthFxAutoNegotiate           INTEGER,
                    rcRemoteRmcEthFxSpeedStatus             INTEGER,
                    rcRemoteRmcEthFxDuplexStatus            INTEGER,
                    rcRemoteRmcEthFxLoopStatus              INTEGER,
                    rcRemoteRmcEthFxTxBandWidthControl      INTEGER,
                    rcRemoteRmcEthFxRxBandWidthControl      INTEGER,
                    rcRemoteRmcEthFxType                    INTEGER
		3.rcRemoteRmcVLANEntry add
					rcRemoteRmcTrunkUntag			      	INTEGER
 
        4. 修改了编译错误
        by wuyanxiong
        "
    REVISION      "2010051300Z"
    DESCRIPTION
    
         "  增加 以太网统计时间戳 节点
         	rcRemoteRmcEthFxTimeStamp				INTEGER
         	by wuyanxiong
         "
    REVISION      "2010052100Z"
    DESCRIPTION   
    
         "  修改 rcRemoteRmcEthFxDownIsForSnmpShutdown  属性为read-write
         	且根据代码，修改注释 1：网管关闭，2：网管打开
         	                  
         	by wuyanxiong
         "
    REVISION      "2010060700Z"
    DESCRIPTION   
    
         "  根据RC552-GEF-A需求增加节点 支持的SFP速率类型
            rcRemoteRmcEthFxSFPSpeedType
         	by wuyanxiong
         " 
    REVISION      "2010092000Z"
    DESCRIPTION
    
        "
        1.rcRemoteRmcSystemEntry add 
        			rcRemoteRmcAdminCmd增加了枚举值
                                           		channeltestStart(9)
                                            	channeltestOver(10)  
                    rcRemoteRmcQoSPolicy增加了枚举值
                    							disable(3)
        			rcRemoteRmcMAClearn			INTEGER，
        			rcRemoteRmcFaultPass		INTEGER，
        			rcRemoteRmcLPBResult		INTEGER 
        			
        2.rcRemoteRmcEthFeTable add 
        			rcRemoteRmcEthFeDefCos		INTEGER,
        			rcRemoteRmcEthFeAdminCmd	INTEGER,
        			rcRemoteRmcEthFeVCTStatus	INTEGER,
        			rcRemoteRmcEthFeVCTMDIPairResult			OCTET STRING,
        			rcRemoteRmcEthFeVCTMDIPairFaultDistance 	OCTET STRING,
        			rcRemoteRmcEthFeTimeStamp	INTEGER		
        			       		    			           				                             
        by hejuan
        "    
        
  	REVISION      "201011250000Z"
    DESCRIPTION
    
        "
        1.rcRemoteRmcSystemEntry add 
        			rcRemoteRmcRemotePowerDown修改了枚举值
                                           		powerdown(1)
                                           		normal(2)		
        			       		    			           				                             
        by hejuan
        "  
        
    REVISION      "2011042000Z"
    DESCRIPTION
    
        "
        1.rcRemoteRmcSystemEntry add 
        			rcRemoteRmcSerialNumber		OCTET STRING
        			
        2.rcRemoteRmcEthFeSpeed
          rcRemoteRmcEthFeSpeedStatus增加了枚举值
          										speed1000(3) 
 												other(4) 		
        			       		    			           				                             
        by hejuan
        " 
        
  	REVISION      "201104131130Z"
    DESCRIPTION   
    
         "  增加 RMC保护表rcRemoteRmcApsTable 
         	包括成员：	rcRemoteRmcAPSType
         	         	rcRemoteRmcApsForceSwitch
         				rcRemoteRmcApsActiveLine
         				rcRemoteRmcApsRevertive  
         	by yangbintao 
          "  
          
    REVISION      "201104191405Z"
    DESCRIPTION   
    
         "  在RMC保护表rcRemoteRmcApsTable中添加 
         	成员： 返回时间：rcRemoteRmcApsWaitToRestore  
         	by yangbintao 
          "   
          
    REVISION      "201104271856Z"
    DESCRIPTION   
    
         "  添加rcRemoteRmcAdminCmd命令节点值softreset(11)
            添加成员rcRemoteRmcEthFxSpeed，用来配置速率
            by yangbintao 
          "
  		
  	REVISION      "1107190000Z"
	DESCRIPTION            
		"
			rcRemoteRmcEthFeTxBytes       Integer32-->  Counter64   
			rcRemoteRmcEthFeRxBytes       Integer32-->  Counter64
										----by hejuan
		"     
	REVISION      "1112230944Z"
	DESCRIPTION            
		"
			add	rcRemoteRmcRmdStatus  
										----by yangbintao
		" 
	REVISION      "1209281447Z"
	DESCRIPTION            
		"
			add	rcRemoteRmcDeviceLedStatus
			add rcRemoteRmcAlarmShieldStatus
			add rcRemoteRmcAlarmShieldConfig
			add rcRemoteRmcEthFeTxFaultFramesThreshold
			add rcRemoteRmcEthFeRxFaultFramesThreshold
			
										----by lixun
		" 

 	REVISION      "1303071705Z"
	DESCRIPTION            
		"
			add	rcRemoteRmcFlowControl
			add rcRemoteRmcFlowControlStatus
						
										----by lixun
		"        
    ::= { optSysModules 19 }
    


 --对象定义
    rcRemoteRmcSysObjects 		OBJECT IDENTIFIER ::= { raisecomOptRemoteRmcMib 1 }

    rcRemoteRmcEth         		OBJECT IDENTIFIER ::= { raisecomOptRemoteRmcMib 2 }
    
    rcRemoteRmcNotifications       OBJECT IDENTIFIER ::= { raisecomOptRemoteRmcMib 3 } 
    
    rcRemoteRmcVLAN         		OBJECT IDENTIFIER ::= { raisecomOptRemoteRmcMib 5 }
    rcRemoteRmcAps         		OBJECT IDENTIFIER ::= { raisecomOptRemoteRmcMib 6 }     

 -- 系统配置表
 		rcRemoteRmcSystemTable OBJECT-TYPE
              SYNTAX  SEQUENCE OF RcRemoteRmcSystemEntry
              MAX-ACCESS  not-accessible
              STATUS  current
              DESCRIPTION
                 "The RCRemoteRmc System table."
             ::= { rcRemoteRmcSysObjects 1 }

    rcRemoteRmcSystemEntry OBJECT-TYPE
              SYNTAX  RcRemoteRmcSystemEntry
              MAX-ACCESS  not-accessible
              STATUS  current
              DESCRIPTION
                 "
                 An entry in the rc system table.
                
                 "
              INDEX   { rcEntPhysicalID }
             ::= { rcRemoteRmcSystemTable 1 }

     RcRemoteRmcSystemEntry ::=
              SEQUENCE {
                   rcRemoteRmcDeviceExist			INTEGER,
                   rcRemoteRmcDeviceDescr			DisplayString,
                   rcRemoteRmcDeviceType			RcOptModuleType,
                   rcRemoteRmcSysTemperature		INTEGER,
                   rcRemoteRmcSysVoltageStatus		INTEGER,
                   rcRemoteRmcVlantype				INTEGER,
                   rcRemoteRmcMaxPktsLength      	INTEGER,
                   rcRemoteRmcAdminCmd      		INTEGER,
                   rcRemoteRmcOpticalModuleType	RcOptIfModuleType, 
                   rcRemoteRmcReqInfo      		INTEGER,
                  
                   rcRemoteRmcLPBBeing      			INTEGER,
                   rcRemoteRmcLPBInsideOutside      	INTEGER,
                   rcRemoteRmcLPBMacAddrExch      		INTEGER,
                   rcRemoteRmcLPBCrcRecal      			INTEGER,
                   rcRemoteRmcLPBUtility      			INTEGER,
                   rcRemoteRmcLPBFrameLength      		INTEGER,
                   rcRemoteRmcLPBTime		      		INTEGER,
                   
                   rcRemoteRmcQoSEnable                 INTEGER,
                   rcRemoteRmcQueuesPolicy              INTEGER,
                   rcRemoteRmcQoSPolicy              	INTEGER,
                   rcRemoteRmcBaseCOS                	INTEGER,

                   rcRemoteRmcVersionInformation        OCTET STRING,
                   rcRemoteRmcDeviceMode				INTEGER,
                   rcRemoteRmcRemManage					INTEGER,
                   rcRemoteRmcRemotePowerDown			INTEGER,
                   rcRemoteRmcRemoteSeriousAlarm        INTEGER,
                   rcRemoteRmcOAMConnect                INTEGER,

                   rcRemoteRmcMacAging                  INTEGER,
                   rcRemoteRmcQosCfgQueueWeight         OCTET STRING,
                   rcRemoteRmcQosCosToQueueQueue		OCTET STRING,
                   rcRemoteRmcQinQDirection             INTEGER,
                   rcRemoteRmcQinQTagMode               INTEGER,
                   rcRemoteRmcQinQDtOuterVID            INTEGER,
                   rcRemoteRmcQinQDtOuterTpid           INTEGER,
                   rcRemoteRmcMAClearn					INTEGER,
                   rcRemoteRmcFaultPass					INTEGER,
                   rcRemoteRmcLPBResult					INTEGER,
                   rcRemoteRmcSerialNumber				OCTET STRING,
                   rcRemoteRmcRemManageStatus			INTEGER,
                   rcRemoteRmcDeviceLedStatus			INTEGER,
                   rcRemoteRmcAlarmShieldStatus			INTEGER,
                   rcRemoteRmcAlarmShieldConfig			INTEGER,
                   rcRemoteRmcFlowControl				INTEGER,
                   rcRemoteRmcFlowControlStatus			INTEGER
               }
            
       
		rcRemoteRmcDeviceExist OBJECT-TYPE
           SYNTAX      INTEGER {
          							exist(1),
          							notExist(2) 
        						}
           MAX-ACCESS  read-only
           STATUS      current
           DESCRIPTION
           "
          	远端设备是否在位
           "
        ::= { rcRemoteRmcSystemEntry 2 }
        
         rcRemoteRmcDeviceDescr OBJECT-TYPE
           SYNTAX      DisplayString
           MAX-ACCESS  read-only
           STATUS      current
           DESCRIPTION
           "
          	远端设备描述
           "
        ::= { rcRemoteRmcSystemEntry 3 }
        
        rcRemoteRmcDeviceType OBJECT-TYPE
           SYNTAX      RcOptModuleType 
           MAX-ACCESS  read-only
           STATUS      current
           DESCRIPTION
           "
          	远端设备类型
           "
        ::= { rcRemoteRmcSystemEntry 4 }
        
     
         
        
         rcRemoteRmcSysTemperature OBJECT-TYPE
           SYNTAX      INTEGER (-25..125)
           MAX-ACCESS  read-only
           STATUS      current
           DESCRIPTION
           "
          	远端设备温度
           "
        ::= { rcRemoteRmcSystemEntry 8 }
        
        rcRemoteRmcSysVoltageStatus OBJECT-TYPE
           SYNTAX     INTEGER {
          										  normal(1),
          										  toohigh(2),
          										  toolow(3)
        						}
           MAX-ACCESS  read-only
           STATUS      current
           DESCRIPTION
           "
          	远端设备电压状态
           "
        ::= { rcRemoteRmcSystemEntry 9 }
        
       rcRemoteRmcVlantype OBJECT-TYPE
          SYNTAX     INTEGER {
         						 portvlan(1),
         						 novlan(2),
         						 tagvlan(3)
       						}
          MAX-ACCESS  read-write
          STATUS      current
          DESCRIPTION
          "
         	远端设备Vlan的类型
          "
       ::= { rcRemoteRmcSystemEntry 10 }
        

        
        rcRemoteRmcMaxPktsLength OBJECT-TYPE
           SYNTAX      INTEGER {
          										  length1916(1),
          										  length1536(2),
          										  length2k(3),
          										  length9k(4) 
        												}
           MAX-ACCESS  read-write
           STATUS      current
           DESCRIPTION
           "
          	远端设备最大包长，若为其他，表示实际包长度值
          "
        ::= { rcRemoteRmcSystemEntry 11 }
        
       rcRemoteRmcAdminCmd OBJECT-TYPE
           SYNTAX      INTEGER {
          										  reset(1),
          										  reqInfoStart(2),
          										  reqInfoOver(3),
          										  ready(4), 
          										  fxloopbackexternal(5), 
          										  fxloopbackinternal(6),
          										  fxoamloopback(7),
          										  syncstatustocfg(8),
          										  channeltestStart(9),
          										  channeltestOver(10), 
          										  softreset(11)      										          										   
        												}
           MAX-ACCESS  read-write
           STATUS      current
           DESCRIPTION
           "
          	远端设备命令字，每个设备都有自己固定的命令字
                    1:复位 ，2：开始查询信息，3：结束查询信息  4：就绪
                    5. 光口外环
                    6. 光口内环 
                    其中2，3只有531,532, 552设备支持
                    5、6 只有552 支持 
                    7.oam环回
                    8.同步板卡console口配置到板卡
                    注：防止网管下发配置覆盖console口的配置。要等console口配置生效，状态改变后进行同步。
                    9.网管通道环回测试
                    10.取消网管通道环回测试
                    注:9、10只有局端设备支持                                     
                    11.软复位芯片，只有OPCOM200-OCPF支持
           "
        ::= { rcRemoteRmcSystemEntry 12 }  
     
         
        rcRemoteRmcOpticalModuleType OBJECT-TYPE
           SYNTAX  RcOptIfModuleType 
           MAX-ACCESS  read-only
           STATUS      current
           DESCRIPTION
           "
          	远端设备光模块类型。RC501,RC511,RC601,RC601E,RC5114FE,RC531,RC532中实现。
           "
        ::= { rcRemoteRmcSystemEntry 13 }

        rcRemoteRmcReqInfo OBJECT-TYPE
           SYNTAX      INTEGER {
          										  enable(1),
          										  disable(2) 
        												}
           MAX-ACCESS  read-only
           STATUS      current
           DESCRIPTION
           "
          	远端设备统计信息查询状态，只有531，532设备支持
           "
        ::= { rcRemoteRmcSystemEntry 14 }

        rcRemoteRmcLPBBeing OBJECT-TYPE
           SYNTAX      INTEGER {
          										  yes(1),
          										  no(2) 
        												}
           MAX-ACCESS  read-only
           STATUS      current
           DESCRIPTION
           "
          	环回  是否正处于环回状态，只有RC552FE设备支持
           "
        ::= { rcRemoteRmcSystemEntry 15 }
        
        rcRemoteRmcLPBInsideOutside OBJECT-TYPE
           SYNTAX      INTEGER {
          										  internal(1),
          										  external(2) 
        												}
           MAX-ACCESS  read-write
           STATUS      current
           DESCRIPTION
           "
          	环回  光口外环还是光口内环，只有RC552FE设备支持
           "
        ::= { rcRemoteRmcSystemEntry 16 }
        
        rcRemoteRmcLPBMacAddrExch OBJECT-TYPE
           SYNTAX      INTEGER {
          										  yes(1),
          										  no(2) 
        												}
           MAX-ACCESS  read-write
           STATUS      current
           DESCRIPTION
           "
          	环回  是否交换MAC地址，只有RC552FE设备支持
           "
        ::= { rcRemoteRmcSystemEntry 17 }
        
        rcRemoteRmcLPBCrcRecal OBJECT-TYPE
           SYNTAX      INTEGER {
          										  yes(1),
          										  no(2) 
        												}
           MAX-ACCESS  read-write
           STATUS      current
           DESCRIPTION
           "
          	环回  是否重新计算CRC，只有RC552FE设备支持
           "
        ::= { rcRemoteRmcSystemEntry 18 }
        
        rcRemoteRmcLPBUtility OBJECT-TYPE
           SYNTAX      INTEGER {
          										  utility100(1),
          										  utility10(2) 
        												}
           MAX-ACCESS  read-write
           STATUS      current
           DESCRIPTION
           "
          	环回  测试数据的速率值，只有RC552FE设备支持
           "
        ::= { rcRemoteRmcSystemEntry 19 }
        
        rcRemoteRmcLPBFrameLength OBJECT-TYPE
           SYNTAX      INTEGER {
          										  length1518(1),
          										  length64(2) 
        												}
           MAX-ACCESS  read-write
           STATUS      current
           DESCRIPTION
           "
          	 环回  测试数据的帧长度，只有RC552FE设备支持
           "
        ::= { rcRemoteRmcSystemEntry 20 }
        
        
        rcRemoteRmcLPBTime OBJECT-TYPE
           SYNTAX      INTEGER {
				  min1(1), 
				  min2(2), 
				  min4(3), 
				  min8(4), 
				  min15(5), 
				  min30(6), 
				  min60(7), 
				  frame2(18), 
				  frame5(19), 
				  frame10(20), 
				  frame20(21), 
				  frame50(22), 
				  frame100(23), 
				  end(32), 
				  start(33)
								}
           MAX-ACCESS  read-write
           STATUS      current
           DESCRIPTION
           "
          	 环回  测试时间设置，只有RC552FE设备支持
           "
        ::= { rcRemoteRmcSystemEntry 21 }
        
		rcRemoteRmcQoSEnable OBJECT-TYPE
           SYNTAX      INTEGER {
          							enable(1),
          							disable(2) 
        						}
           MAX-ACCESS  read-write
           STATUS      current
           DESCRIPTION
           "
          	QOS使能设置
           "
        ::= { rcRemoteRmcSystemEntry 22 }
        
		rcRemoteRmcQueuesPolicy OBJECT-TYPE
           SYNTAX      INTEGER {
          							strictPriority(1),
          							weightedCycle10vs1(2),
          							weightedCycle5vs1(3),
          							weightedCycle2vs1(4),
          							wrr(5),
          							onespthreewrr(6),
          							twosptwowrr(7) 
        						}
           MAX-ACCESS  read-write
           STATUS      current
           DESCRIPTION
           "
          	队列调度策略：
	      	   	1:严格优先
				2：加权循环（高：低）10:1；
				3：加权循环（高：低）5:1；
				4：加权循环（高：低）2:1；
				5: 加权循环；
				6：队列4绝对优先，队列3-1加权循环；
				7：队列4-3绝对有限，队列2-1加权循环；

           "
        ::= { rcRemoteRmcSystemEntry 23 }  
        
		rcRemoteRmcQoSPolicy OBJECT-TYPE
           SYNTAX      INTEGER {
          							portBased(1),
          							cosBased(2),
          							disable(3) 
        						}
           MAX-ACCESS  read-write
           STATUS      current
           DESCRIPTION
           "
          	QOS策略：
	      	   	1:基于端口；
				2：基于COS；
				3：cos禁止
           "
        ::= { rcRemoteRmcSystemEntry 24 }

		rcRemoteRmcBaseCOS OBJECT-TYPE
           SYNTAX      INTEGER 
           MAX-ACCESS  read-write
           STATUS      current
           DESCRIPTION
           "
          	COS界限，取值0~7
           "
        ::= { rcRemoteRmcSystemEntry 25 }

    	rcRemoteRmcVersionInformation OBJECT-TYPE
        SYNTAX OCTET STRING(SIZE (0..100))
        MAX-ACCESS read-only
        STATUS    current
        DESCRIPTION 
        "
            rmc设备版本信息 透传mcu ASCII码
        "  
        ::={ rcRemoteRmcSystemEntry 26 }
        
    	rcRemoteRmcDeviceMode OBJECT-TYPE
        SYNTAX  INTEGER
			{
      			master(1),
     			slave(2)
 			} 

        MAX-ACCESS read-only
        STATUS    current
        DESCRIPTION 
        "
            -- rmc设备主从模式
            1：主； 2：从

        "  
        ::={ rcRemoteRmcSystemEntry 27 }

    	rcRemoteRmcRemManage OBJECT-TYPE
        SYNTAX  INTEGER
			{
      			enable(1), 
				disable(2)
 			} 

        MAX-ACCESS read-write
        STATUS    current
        DESCRIPTION 
        "
            -- rmc设备远端管理功能
              	1：使能;2：禁止
              	注：远端设备无效

        "  
        ::={ rcRemoteRmcSystemEntry 28 }

    	rcRemoteRmcRemotePowerDown OBJECT-TYPE
        SYNTAX  INTEGER
			{
      			powerdown(1),
     			normal(2)
			} 

        MAX-ACCESS read-only
        STATUS    current
        DESCRIPTION 
        "
            rmc远端设备掉电 
            1 Powerdown：掉电, 2 Normal：正常
            注：远端设备无效
        "  
        ::={ rcRemoteRmcSystemEntry 29 }

    	rcRemoteRmcRemoteSeriousAlarm OBJECT-TYPE
        SYNTAX  INTEGER
			{
      			nothappenned(1),
				happenned (2)
 			} 

        MAX-ACCESS read-only
        STATUS    current
        DESCRIPTION 
        "
            -- rmc设备远端严重事件告警是否发生
               1：没有发生;2：发生
               注：远端设备无效
        "  
        ::={ rcRemoteRmcSystemEntry 30 }

    	rcRemoteRmcOAMConnect OBJECT-TYPE
        SYNTAX  INTEGER
			{
      			unconnected(1),
				connect(2)
 			} 

        MAX-ACCESS read-only
        STATUS    current
        DESCRIPTION 
        "
            Udrmc设备OAM连接是否建立
            1 没有建立连接; 2 建立连接;
        "  
        ::={ rcRemoteRmcSystemEntry 31 }
        
        rcRemoteRmcMacAging OBJECT-TYPE
        SYNTAX  INTEGER
			{
      			normal-200s(1), 
				accelerate-2s(2) 
 			} 

        MAX-ACCESS read-write
        STATUS    current
        DESCRIPTION 
        "
            -- MAC老化时间
            	1:正常（300s）
				2：加速（2s）

        "  
        ::={ rcRemoteRmcSystemEntry 32 }
                
    	rcRemoteRmcQosCfgQueueWeight OBJECT-TYPE
        SYNTAX      OCTET STRING
        MAX-ACCESS  read-write
        STATUS      current
        DESCRIPTION
            "Queue 1 to 4 maps to the wrr weight, the weight value ranges from 0 to 55
            |队列1权重值|队列2权重值|队列3权重值|队列4权重值|，每个队列权重值占用一个字节；
             "
        ::= { rcRemoteRmcSystemEntry 33 } 

		rcRemoteRmcQosCosToQueueQueue OBJECT-TYPE
        SYNTAX      OCTET STRING(SIZE(8))
        MAX-ACCESS  read-write
        STATUS      current
        DESCRIPTION
            "COS from 0 to 7 maps to the queue id,the queue id ranges from 1 to 4."
        ::= { rcRemoteRmcSystemEntry 34}
        

    	rcRemoteRmcQinQDirection OBJECT-TYPE
        SYNTAX  INTEGER
			{
      			clienttoline(1),
     			linetoclient(2)
 			} 

        MAX-ACCESS read-write
        STATUS    current
        DESCRIPTION 
        "
            --VLAN-TAG方向
            1：CLIENT口到LINE口
			2：LINE口到CLIENT口

        "  
        ::={ rcRemoteRmcSystemEntry 35 }

    	rcRemoteRmcQinQTagMode OBJECT-TYPE
        SYNTAX  INTEGER
			{
      			transparent(1),
     			singletag(2),
     			doubletag(3)

 			} 

        MAX-ACCESS read-write
        STATUS    current
        DESCRIPTION 
        "
            -- QinQ模式
               1：透传; 2：单Tag; 3：双Tag


        "  
        ::={ rcRemoteRmcSystemEntry 36 }

    	rcRemoteRmcQinQDtOuterVID OBJECT-TYPE
        SYNTAX  INTEGER
        MAX-ACCESS read-write
        STATUS    current
        DESCRIPTION 
        "
            -- OuterTag VID
            	1～4094

        "  
        ::={ rcRemoteRmcSystemEntry 37 }

    	rcRemoteRmcQinQDtOuterTpid OBJECT-TYPE
        SYNTAX  INTEGER
        MAX-ACCESS read-write
        STATUS    current
        DESCRIPTION 
        "
            -- OuterTag TPID
               	1～0xfffe，16进制
        "  
        ::={ rcRemoteRmcSystemEntry 38 }  
        
        rcRemoteRmcMAClearn OBJECT-TYPE
        SYNTAX  INTEGER
			{
      			enable(1),
     			disable(2)
 			} 

        MAX-ACCESS read-write
        STATUS    current
        DESCRIPTION 
        "
            -- MAC地址学习功能
               1：打开；2：关闭

        "  
        ::={ rcRemoteRmcSystemEntry 39 }     
        
        rcRemoteRmcFaultPass OBJECT-TYPE
        SYNTAX  INTEGER
        MAX-ACCESS read-write
        STATUS    current
        DESCRIPTION 
        "
            -- 故障转移功能功能
               bit1：光口到电口				1：使能；0：禁止
               bit0：电口到光口				1：使能；0：禁止
        "  
        ::={ rcRemoteRmcSystemEntry 40 }  
                
        rcRemoteRmcLPBResult OBJECT-TYPE
        SYNTAX  INTEGER
			{
      			success(1),
     			failure(2)
 			} 

        MAX-ACCESS read-only
        STATUS    current
        DESCRIPTION 
        "
            -- 网管通道环回测试结果
               1：成功；2：失败

        "  
        ::={ rcRemoteRmcSystemEntry 41 }  
        
        rcRemoteRmcSerialNumber OBJECT-TYPE
        SYNTAX OCTET STRING(SIZE (0..64))
        MAX-ACCESS read-only
        STATUS    current
        DESCRIPTION 
        "
            rmc设备产品序列号 透传mcu ASCII码
        "  
        ::={ rcRemoteRmcSystemEntry 42 }  
        
        rcRemoteRmcRemManageStatus OBJECT-TYPE
        SYNTAX  INTEGER
			{
      			normal(1), 
				abnormal(2)
 			} 

        MAX-ACCESS read-only
        STATUS    current
        DESCRIPTION 
        "
            -- rmc设备远端管理指示灯状态
              	1：连接正常;2：连接异常
        "  
        ::={ rcRemoteRmcSystemEntry 43 }

        rcRemoteRmcDeviceLedStatus OBJECT-TYPE
        SYNTAX  INTEGER
        MAX-ACCESS read-only
        STATUS    current
        DESCRIPTION 
        "
            -- rmc设备指示灯状态
               BIT0：电源指示灯1
               BTI1：电源指示灯2
               BIT2：告警指示灯
               以上各BIT值含义均为0熄灭；1点亮
        "  
        ::={ rcRemoteRmcSystemEntry 44 }

        rcRemoteRmcAlarmShieldStatus OBJECT-TYPE
        SYNTAX  INTEGER
        MAX-ACCESS read-only
        STATUS    current
        DESCRIPTION 
        "
            -- rmc设备告警端子屏蔽状态
               BIT0:温度告警
			   BIT1:光口LINK DOWN
			   BIT2:电口LINK DOWN
 			   BIT3:电源电压超限告警
			   以上各BIT值含义均为0禁止屏蔽；1使能屏蔽
        "  
        ::={ rcRemoteRmcSystemEntry 45 }

        rcRemoteRmcAlarmShieldConfig OBJECT-TYPE
        SYNTAX  INTEGER
        MAX-ACCESS read-write
        STATUS    current
        DESCRIPTION
        "
            -- rmc设备告警端子屏蔽状态
               BIT0:温度告警
			   BIT1:光口LINK DOWN
			   BIT2:电口LINK DOWN
 			   BIT3:电源电压超限告警
			   以上各BIT值含义均为0禁止屏蔽；1使能屏蔽
        "  
        ::={ rcRemoteRmcSystemEntry 46 }
        
        rcRemoteRmcFlowControl OBJECT-TYPE
        SYNTAX  INTEGER
        	{
        		on(1),
        		off(2)
        	}
        MAX-ACCESS read-write
        STATUS    current
        DESCRIPTION
        "
            -- rmc设备流控配置
            1:打开; 2:关闭	   
        "  
        ::={ rcRemoteRmcSystemEntry 47 }
        
        rcRemoteRmcFlowControlStatus OBJECT-TYPE
        SYNTAX  INTEGER
        	{
        		on(1),
        		off(2)
        	}
        MAX-ACCESS read-only
        STATUS    current
        DESCRIPTION
        "
            -- rmc设备流控配置
            1:打开; 2:关闭	   
        "  
        ::={ rcRemoteRmcSystemEntry 48 }

----------------------------------------------------------------------------
------------------RCRemoteRmc FX table
----------------------------------------------------------------------------        



        rcRemoteRmcEthFxTable OBJECT-TYPE
              SYNTAX  SEQUENCE OF RcRemoteRmcEthFxEntry
              MAX-ACCESS  not-accessible
              STATUS  current
              DESCRIPTION
                 "The RCRemoteRmc FX Port table."
             ::= { rcRemoteRmcEth 2 }

   			rcRemoteRmcEthFxEntry OBJECT-TYPE
              SYNTAX  RcRemoteRmcEthFxEntry
              MAX-ACCESS  not-accessible
              STATUS  current
              DESCRIPTION
                 "
                 An entry in the Fx Port config table.
                 
                 "
              INDEX   { rcEntPhysicalID, rcRemoteRmcEthFxIndex }
             ::= { rcRemoteRmcEthFxTable 1 }
             
          RcRemoteRmcEthFxEntry ::=
              SEQUENCE {
                    rcRemoteRmcEthFxIndex                       Integer32,
                    rcRemoteRmcEthFxDescr						DisplayString,
                    rcRemoteRmcEthFxRLK                     INTEGER,
          			rcRemoteRmcEthFxTLK                     INTEGER,
          			rcRemoteRmcEthFxSD           			INTEGER,
          			rcRemoteRmcEthFxTxPowerAbnormal			INTEGER,
					rcRemoteRmcEthFxRxSensitiveAbnormal     INTEGER,
					rcRemoteRmcEthFxLaserAbnormal           INTEGER,
					rcRemoteRmcEthFxToFeFaultPass                  INTEGER,
					rcRemoteRmcEthFxALSEnable										INTEGER,
					rcRemoteRmcEthFxDownIsForEthFeLinkDown			TruthValue,
					rcRemoteRmcEthFxDownIsForEthFxNoRxSignal    TruthValue,
		      rcRemoteRmcEthFxDownIsForSnmpShutdown       TruthValue,
		      rcRemoteRmcEthFxTxBytes					Counter32,
					rcRemoteRmcEthFxRxBytes					Counter32,
					rcRemoteRmcEthFxTxFrames					Counter32,
					rcRemoteRmcEthFxRxFrames					Counter32,
					rcRemoteRmcEthFxTxFaultFrames					Counter32,
					rcRemoteRmcEthFxRxFaultFrames					Counter32,
					rcRemoteRmcEthFxTag						INTEGER,
					rcRemoteRmcEthFxPVID					INTEGER,
					rcRemoteRmcEthFxAttribute				INTEGER,
                    rcRemoteRmcEthFxCosOverrideEn           INTEGER,
                    rcRemoteRmcEthFxDefCos                  INTEGER,
                    rcRemoteRmcEthFxFlowControl             INTEGER,
                    rcRemoteRmcEthFxAutoNegotiate           INTEGER,
                    rcRemoteRmcEthFxSpeedStatus             INTEGER,
                    rcRemoteRmcEthFxDuplexStatus            INTEGER,
                    rcRemoteRmcEthFxLoopStatus              INTEGER,
                    rcRemoteRmcEthFxTxBandWidthControl      INTEGER,
                    rcRemoteRmcEthFxRxBandWidthControl      INTEGER,
                    rcRemoteRmcEthFxType                    INTEGER,
                    rcRemoteRmcEthFxTimeStamp               INTEGER,
                    rcRemoteRmcEthFxSFPSpeedType			INTEGER,
                    rcRemoteRmcEthFxSpeed		            INTEGER
                   }
                   
          rcRemoteRmcEthFxIndex OBJECT-TYPE
          SYNTAX  Integer32
          MAX-ACCESS  read-only
          STATUS  current
          DESCRIPTION
                 "光口索引  
                 "
          
		  ::= { rcRemoteRmcEthFxEntry 1 }
     
          rcRemoteRmcEthFxDescr OBJECT-TYPE
          SYNTAX  DisplayString
          MAX-ACCESS  read-only
          STATUS  current
          DESCRIPTION
                 "接口描述  
                 "
          
		  ::= { rcRemoteRmcEthFxEntry 2 }    
                   
         rcRemoteRmcEthFxRLK OBJECT-TYPE
          SYNTAX  INTEGER {
                    linkup (1),
                    linkdown    (2)
                    }
          MAX-ACCESS  read-only
          STATUS  current
          DESCRIPTION
                 "光口RLK  
                 "
          
		  ::= { rcRemoteRmcEthFxEntry 3 }

   		  rcRemoteRmcEthFxTLK OBJECT-TYPE
          SYNTAX  INTEGER {
                       linkup(1),
                       linkdown(2)
                 }
          MAX-ACCESS  read-only
          STATUS  current
          DESCRIPTION
                 "
                	光口TLK
                 "
                
          ::= { rcRemoteRmcEthFxEntry 4 }
          
          
        rcRemoteRmcEthFxSD OBJECT-TYPE
          SYNTAX  INTEGER {
                    normal (1),
                    sd (2)
                    }
          MAX-ACCESS  read-only
          STATUS  current
          DESCRIPTION
                 "
                 	光口SD异常
                 "

		  ::= { rcRemoteRmcEthFxEntry 5 }

  
			rcRemoteRmcEthFxTxPowerAbnormal OBJECT-TYPE
          SYNTAX  INTEGER {
                    normal (1),
                    abnormal (2)
                    }
          MAX-ACCESS  read-only
          STATUS  current
          DESCRIPTION
                 "
                 发送功率异常
                 "

          
		  ::= { rcRemoteRmcEthFxEntry 6 }
		  
		 rcRemoteRmcEthFxRxSensitiveAbnormal OBJECT-TYPE
          SYNTAX  INTEGER  {
                    normal (1),
                    abnormal (2)
                    }
          MAX-ACCESS  read-only
          STATUS  current
          DESCRIPTION
                 "
                 接收灵敏度异常
                 "
          
		  ::= { rcRemoteRmcEthFxEntry 7 }
		  
		  rcRemoteRmcEthFxLaserAbnormal OBJECT-TYPE
          SYNTAX  INTEGER {
                    normal (1),
                    abnormal (2)
                    }
          MAX-ACCESS  read-only
          STATUS  current
          DESCRIPTION
                 "
                 光激光管工作异常
                 "

          
		  ::= { rcRemoteRmcEthFxEntry 8 }
		  
		  rcRemoteRmcEthFxToFeFaultPass OBJECT-TYPE
           SYNTAX      INTEGER {
          						  enable(1),
          						  disable(2)
          						}
           MAX-ACCESS  read-write
           STATUS      current
           DESCRIPTION
           "
          	远端设备FX到FE故障转移设置
           "
        ::= { rcRemoteRmcEthFxEntry 9 }
        
		  
			  rcRemoteRmcEthFxALSEnable OBJECT-TYPE
           SYNTAX      INTEGER {
          						  enable(1),
          						  disable(2)
          						}
           MAX-ACCESS  read-write
           STATUS      current
           DESCRIPTION
           "
          	光口接收故障转移到发送使能
           "
        ::= { rcRemoteRmcEthFxEntry 10 }
        
       rcRemoteRmcEthFxDownIsForEthFeLinkDown			OBJECT-TYPE
           SYNTAX      TruthValue 
           MAX-ACCESS  read-only
           STATUS      current
           DESCRIPTION
           "
            如果该位置1，表明光口发送被关闭的原因是：当电口LINK-DOWN,并且光口到电口的故障转移功能被使能
            否则该位置0
           "
        ::= { rcRemoteRmcEthFxEntry 11 }
        
       rcRemoteRmcEthFxDownIsForEthFxNoRxSignal OBJECT-TYPE
           SYNTAX      TruthValue
           MAX-ACCESS  read-only
           STATUS      current
           DESCRIPTION
           "
          	如果该位置1，表明光口发送被关闭的原因是：当光口无接收信号,并且光口接收到光口发送的故障转移功能被使能
          	否则该位置0
           "
        ::= { rcRemoteRmcEthFxEntry 12 }
        
        rcRemoteRmcEthFxDownIsForSnmpShutdown OBJECT-TYPE
           SYNTAX      TruthValue
           MAX-ACCESS  read-write
           STATUS      current
           DESCRIPTION
           "
            网管关闭光口时为1，否则为2。
            即 1：网管关闭，2：网管打开。
           "
        ::= { rcRemoteRmcEthFxEntry 13 }
        
        rcRemoteRmcEthFxTxBytes OBJECT-TYPE
           SYNTAX      Counter32 
           MAX-ACCESS  read-only
           STATUS      current
           DESCRIPTION
           "
            光端口发送字节数
           "
        ::= { rcRemoteRmcEthFxEntry 14 }
        

				rcRemoteRmcEthFxRxBytes OBJECT-TYPE
           SYNTAX      Counter32 
           MAX-ACCESS  read-only
           STATUS      current
           DESCRIPTION
           "
            光端口接收字节数
           "
        ::= { rcRemoteRmcEthFxEntry 15 }
        

	     rcRemoteRmcEthFxTxFrames OBJECT-TYPE
           SYNTAX      Counter32 
           MAX-ACCESS  read-only
           STATUS      current
           DESCRIPTION
           "
            光端口发送帧数
           "
        ::= { rcRemoteRmcEthFxEntry 16 }
        
				
				rcRemoteRmcEthFxRxFrames OBJECT-TYPE
           SYNTAX      Counter32 
           MAX-ACCESS  read-only
           STATUS      current
           DESCRIPTION
           "
            光端口接收帧数
           "
        ::= { rcRemoteRmcEthFxEntry 17 }
        

			rcRemoteRmcEthFxTxFaultFrames OBJECT-TYPE
           SYNTAX      Counter32 
           MAX-ACCESS  read-only
           STATUS      current
           DESCRIPTION
           "
            光端口发送错误帧数
           "
        ::= { rcRemoteRmcEthFxEntry 18 }
        
									
         
       rcRemoteRmcEthFxRxFaultFrames OBJECT-TYPE
           SYNTAX      Counter32 
           MAX-ACCESS  read-only
           STATUS      current
           DESCRIPTION
           "
            光端口接收错误帧数
           "
        ::= { rcRemoteRmcEthFxEntry 19 }  
        
       rcRemoteRmcEthFxTag OBJECT-TYPE
           SYNTAX      INTEGER  {
           						tag(1),
           						untag(2)
           						}            
           MAX-ACCESS  read-write
           STATUS      current
           DESCRIPTION
           "
            光端口输出帧是否带tag标识
           "
        ::= { rcRemoteRmcEthFxEntry 20 }
        
       rcRemoteRmcEthFxPVID OBJECT-TYPE
           SYNTAX      INTEGER              
           MAX-ACCESS  read-write
           STATUS      current
           DESCRIPTION
           "
            光端口VID值，为无tag的包打tag标签时使用
           "
        ::= { rcRemoteRmcEthFxEntry 21 }   
        
    	rcRemoteRmcEthFxAttribute OBJECT-TYPE
        SYNTAX  INTEGER
        {
			access(1),
			trunk (2)
		}
        MAX-ACCESS read-write
        STATUS    current
        DESCRIPTION 
        "
			端口的VLAN属性            
			1：access
			2：trunk
        "  
        ::={ rcRemoteRmcEthFxEntry 22 }
       
    	rcRemoteRmcEthFxCosOverrideEn OBJECT-TYPE
        SYNTAX  INTEGER
        {
        	enable(1),
        	diable(2)
        }
        MAX-ACCESS read-write
        STATUS    current
        DESCRIPTION 
        "
			端口CoS 赋值使能
		"  
        ::={ rcRemoteRmcEthFxEntry 23 }


    	rcRemoteRmcEthFxDefCos OBJECT-TYPE
        SYNTAX  INTEGER
        MAX-ACCESS read-write
        STATUS    current
        DESCRIPTION 
        "
			默认CoS值 (0～7)        
		"  
        ::={ rcRemoteRmcEthFxEntry 24 }

    	rcRemoteRmcEthFxFlowControl OBJECT-TYPE
        SYNTAX  INTEGER
        {
        	on(1),
        	off(2)
        }
        MAX-ACCESS read-write
        STATUS    current
        DESCRIPTION 
        "
			端口流控设置
		"  
        ::={ rcRemoteRmcEthFxEntry 25 }

    	rcRemoteRmcEthFxAutoNegotiate OBJECT-TYPE
        SYNTAX  INTEGER
        {
        	enable(1),
        	diable(2)
        }
        MAX-ACCESS read-write
        STATUS    current
        DESCRIPTION 
        "
			端口自协商设置
		"  
        ::={ rcRemoteRmcEthFxEntry 26 }

    	rcRemoteRmcEthFxSpeedStatus OBJECT-TYPE
        SYNTAX  INTEGER
        {
        	speed10(1),
			speed100(2),
			speed1000(3),	
			other(4)
        }
        MAX-ACCESS read-only
        STATUS    current
        DESCRIPTION 
        "
			Eth端口速率

		"  
        ::={ rcRemoteRmcEthFxEntry 27 }
        
   	rcRemoteRmcEthFxDuplexStatus OBJECT-TYPE
        SYNTAX  INTEGER
        {
			full-duplex(1),
			half-duplex(2)
        }
        MAX-ACCESS read-only
        STATUS    current
        DESCRIPTION 
        "
			Eth双工模式

		"  
        ::={ rcRemoteRmcEthFxEntry 28 }  

    	rcRemoteRmcEthFxLoopStatus OBJECT-TYPE
        SYNTAX  INTEGER
        {
			localoutsideloop(1),
			remoteoutsideloop(2),
			localinsideloop(3),
			oamloop(4),
			
			normal(100)			
        }
        MAX-ACCESS read-only
        STATUS    current
        DESCRIPTION 
        "
			端口的环回状态
			1: 端口本地外环  
			2：端口远端外环
			3：端口本地内环 
			4：OAM环
			100：无环回

		"  
        ::={ rcRemoteRmcEthFxEntry 29 }


   		rcRemoteRmcEthFxTxBandWidthControl OBJECT-TYPE
        SYNTAX  INTEGER
        MAX-ACCESS read-write
        STATUS    current
        DESCRIPTION 
        "
			以太网端口发送限定速率

		"  
        ::={ rcRemoteRmcEthFxEntry 30 }

   		rcRemoteRmcEthFxRxBandWidthControl OBJECT-TYPE
        SYNTAX  INTEGER
        MAX-ACCESS read-write
        STATUS    current
        DESCRIPTION 
        "
			太网端口接收限定速率
		"  
        ::={ rcRemoteRmcEthFxEntry 31 }

   		rcRemoteRmcEthFxType OBJECT-TYPE
        SYNTAX  INTEGER
        {
			electrical(1), 
			optical(2)
        }
        MAX-ACCESS read-only
        STATUS    current
        DESCRIPTION 
        "
			以太网端口的类型 
			1: electrical(1) 
			2: optical(2)

		"  
        ::={ rcRemoteRmcEthFxEntry 32 }       
        
   		rcRemoteRmcEthFxTimeStamp OBJECT-TYPE
        SYNTAX  INTEGER
        MAX-ACCESS read-only
        STATUS    current
        DESCRIPTION 
        "
         	以太网流量统计上报时间戳
		"  
        ::={ rcRemoteRmcEthFxEntry 33 }  

   		rcRemoteRmcEthFxSFPSpeedType OBJECT-TYPE
        SYNTAX  INTEGER 
        {
        	speed-1000M(1),
        	speed-auto(2)
        }
        MAX-ACCESS read-only
        STATUS    current
        DESCRIPTION 
        "
         	以太网端口支持的SFP速率类型
         	1:1000M
         	2:自协商接口
         "  
        ::={ rcRemoteRmcEthFxEntry 34 }  
        
    	rcRemoteRmcEthFxSpeed OBJECT-TYPE
        SYNTAX  INTEGER
        {
        	speed10(1),
			speed100(2),
			speed1000(3),	
			other(4)
        }
        MAX-ACCESS read-write
        STATUS    current
        DESCRIPTION 
        "
			Eth端口速率配置

		"  
        ::={ rcRemoteRmcEthFxEntry 35 }
                     
----------------------------------------------------------------------------
------------------RCRemoteRmc FE table
----------------------------------------------------------------------------          
          
      --   Fe Current table
	     rcRemoteRmcEthFeTable OBJECT-TYPE
              SYNTAX  SEQUENCE OF RcRemoteRmcEthFeEntry
              MAX-ACCESS  not-accessible
              STATUS  current
              DESCRIPTION
                 "The RCRemoteRmc Fe Port table."
             ::= { rcRemoteRmcEth 1 }

   			rcRemoteRmcEthFeEntry OBJECT-TYPE
              SYNTAX  RcRemoteRmcEthFeEntry
              MAX-ACCESS  not-accessible
              STATUS  current
              DESCRIPTION
                 "
                 An entry in the Fe Port config table.
                 
                 "
              INDEX   { rcEntPhysicalID,  rcRemoteRmcEthFeIndex }
             ::= { rcRemoteRmcEthFeTable 1 }
             
          RcRemoteRmcEthFeEntry ::=
              SEQUENCE {
              			rcRemoteRmcEthFeIndex                     	Integer32,
              			rcRemoteRmcEthFeDescr						DisplayString,
                    	rcRemoteRmcEthFeLinkStatus                	INTEGER,
          			    rcRemoteRmcEthFeShutDown                  	INTEGER,
          			    rcRemoteRmcEthFeAutoNegotiate           	INTEGER,
          			    rcRemoteRmcEthFeSpeed                	  	INTEGER,
          			    rcRemoteRmcEthFeSpeedStatus               	INTEGER,
						rcRemoteRmcEthFeDuplex                    	INTEGER,
						rcRemoteRmcEthFeDuplexStatus              	INTEGER,
						rcRemoteRmcEthFeToFxFaultPass              	INTEGER,
						rcRemoteRmcEthFeTxBandWidthControl          INTEGER,
						rcRemoteRmcEthFeRxBandWidthControl          INTEGER,
						rcRemoteRmcEthFeTxBytes					Counter64,
						rcRemoteRmcEthFeRxBytes					Counter64,
						rcRemoteRmcEthFeTxFrames					Counter32,
						rcRemoteRmcEthFeRxFrames					Counter32,
						rcRemoteRmcEthFeTxFaultFrames					Counter32,
						rcRemoteRmcEthFeRxFaultFrames					Counter32,
						rcRemoteRmcEthFeDownIsForReEthfeFault      TruthValue,
						rcRemoteRmcEthFeDownIsForEthFxFault        TruthValue,
						rcRemoteRmcEthFeTag               INTEGER,
						rcRemoteRmcEthFePVID               INTEGER,
						rcRemoteRmcEthFePriority			INTEGER,
						rcRemoteRmcEthFeDefCos				INTEGER,
						rcRemoteRmcEthFeAdminCmd			INTEGER,
						rcRemoteRmcEthFeVCTStatus			INTEGER,
						rcRemoteRmcEthFeVCTMDIPairResult	OCTET STRING,
						rcRemoteRmcEthFeVCTMDIPairFaultDistance		OCTET STRING,
						rcRemoteRmcEthFeTimeStamp			INTEGER,
						rcRemoteRmcEthFeTxFaultFramesThreshold		INTEGER,
						rcRemoteRmcEthFeRxFaultFramesThreshold		INTEGER
						
									}
									
       
	    
	    rcRemoteRmcEthFeIndex OBJECT-TYPE
					SYNTAX Integer32
					MAX-ACCESS read-only
					STATUS current
					DESCRIPTION
						"
						以太网电口端口索引
						"
					::= { rcRemoteRmcEthFeEntry 1 }
	  
	  	rcRemoteRmcEthFeDescr OBJECT-TYPE
					SYNTAX DisplayString
					MAX-ACCESS read-only
					STATUS current
					DESCRIPTION
						"
						以太网电口端口描述
						"
					::= { rcRemoteRmcEthFeEntry 2 }
	   
	   rcRemoteRmcEthFeLinkStatus OBJECT-TYPE
					SYNTAX INTEGER{
													linkup(1),
													linkdown(2)	
												}
					MAX-ACCESS read-only
					STATUS current
					DESCRIPTION
						"
						以太网电口的link状态
						"
					::= { rcRemoteRmcEthFeEntry 3 }
					
	 		rcRemoteRmcEthFeShutDown OBJECT-TYPE
					SYNTAX INTEGER{
													enable(1),
													disable(2)	
												}
					MAX-ACCESS read-write
					STATUS current
					DESCRIPTION
						"
									Eth端口关闭
						"
					::= { rcRemoteRmcEthFeEntry 4 }
					
		 rcRemoteRmcEthFeAutoNegotiate OBJECT-TYPE
					SYNTAX INTEGER{
													enable(1),
													disable(2)	
												}
					MAX-ACCESS read-write
					STATUS current
					DESCRIPTION
						"
									Eth自协商设置,rc601不支持
						"
					::= { rcRemoteRmcEthFeEntry 5 }
					
		 rcRemoteRmcEthFeSpeed OBJECT-TYPE
					SYNTAX INTEGER{
													speed10(1),
													speed100(2),
													speed1000(3),
													other(4)	
												}
					MAX-ACCESS read-write
					STATUS current
					DESCRIPTION
						"
									Eth端口速率设置,rc601不支持
						"
					::= { rcRemoteRmcEthFeEntry 6 }
					
		 rcRemoteRmcEthFeSpeedStatus OBJECT-TYPE
					SYNTAX INTEGER{
													speed10(1),
													speed100(2),
													speed1000(3),
													other(4)	
												}
					MAX-ACCESS read-only
					STATUS current
					DESCRIPTION
						"
									Eth端口速率
						"
					::= { rcRemoteRmcEthFeEntry 7 }
					
		 rcRemoteRmcEthFeDuplex OBJECT-TYPE
					SYNTAX INTEGER
					{
							full-duplex(1),
							half-duplex(2)		
					}
					MAX-ACCESS read-write
					STATUS current
					DESCRIPTION
						"
									Eth双工模式设置， rc601不支持
						"
					::= { rcRemoteRmcEthFeEntry 8 }
					
		 rcRemoteRmcEthFeDuplexStatus OBJECT-TYPE
					SYNTAX INTEGER
					{
							full-duplex(1),
							half-duplex(2)	
					}
					MAX-ACCESS read-only
					STATUS current
					DESCRIPTION
						"
									Eth双工模式
						"
					::= { rcRemoteRmcEthFeEntry 9 }
					
		 rcRemoteRmcEthFeToFxFaultPass OBJECT-TYPE
           SYNTAX      INTEGER {
          						  enable(1),
          						  disable(2)
          						}
           MAX-ACCESS  read-write
           STATUS      current
           DESCRIPTION
           "
          	远端设备FE到FX故障转移设置，所有的设备都不支持，现在只支持FX到FE的故障转移
           "
        ::= { rcRemoteRmcEthFeEntry 10 }
        
        
     rcRemoteRmcEthFeTxBandWidthControl	OBJECT-TYPE
				SYNTAX	INTEGER
				MAX-ACCESS	read-write
				STATUS	current
				DESCRIPTION
					"
						远端设备以太网端口接收限定速率：
						(n * value；n = 0,1,2....., rc511-4FE,rc5322FE,value = 32kb/s,rc531FE,rc532FE,value = 64kb/s).
					"
			 ::= { rcRemoteRmcEthFeEntry 11 }	
			 
		rcRemoteRmcEthFeRxBandWidthControl	OBJECT-TYPE
				SYNTAX	INTEGER
				MAX-ACCESS	read-write
				STATUS	current
				DESCRIPTION
					"
						远端设备以太网端口接收限定速率：
						(n * value；n = 0,1,2....., rc511-4FE,rc5322FE,value = 32kb/s,rc531FE,rc532FE,value = 64kb/s).
					"
			 ::= { rcRemoteRmcEthFeEntry 12 }	
			 
			 
		 rcRemoteRmcEthFeTxBytes	OBJECT-TYPE
				SYNTAX	Counter64
				MAX-ACCESS	read-only
				STATUS	current
				DESCRIPTION
					"
						fe端口发送字节流量统计
					"
			 ::= { rcRemoteRmcEthFeEntry 13 }
			 
		 rcRemoteRmcEthFeRxBytes	OBJECT-TYPE
				SYNTAX	Counter64
				MAX-ACCESS	read-only
				STATUS	current
				DESCRIPTION
					"
						fe端口接收字节流量统计
					"
			 ::= { rcRemoteRmcEthFeEntry 14 }	 
			 
		 rcRemoteRmcEthFeTxFrames	OBJECT-TYPE
				SYNTAX	Counter32
				MAX-ACCESS	read-only
				STATUS	current
				DESCRIPTION
					"
						fe端口发送帧流量统计
					"
			 ::= { rcRemoteRmcEthFeEntry 15 }
			 
		 rcRemoteRmcEthFeRxFrames	OBJECT-TYPE
				SYNTAX	Counter32
				MAX-ACCESS	read-only
				STATUS	current
				DESCRIPTION
					"
						fe端口接收流量统计
					"
			 ::= { rcRemoteRmcEthFeEntry 16 }
			
	  rcRemoteRmcEthFeTxFaultFrames	OBJECT-TYPE
				SYNTAX	Counter32
				MAX-ACCESS	read-only
				STATUS	current
				DESCRIPTION
					"
						fe端口发送错误帧统计
					"
			 ::= { rcRemoteRmcEthFeEntry 17 }
			 
	 rcRemoteRmcEthFeRxFaultFrames	OBJECT-TYPE
				SYNTAX	Counter32
				MAX-ACCESS	read-only
				STATUS	current
				DESCRIPTION
					"
						fe端口接收错误帧统计
					"
			 ::= { rcRemoteRmcEthFeEntry 18 }
			
			
			rcRemoteRmcEthFeDownIsForReEthfeFault OBJECT-TYPE
				SYNTAX	TruthValue
				MAX-ACCESS	read-only
				STATUS	current
				DESCRIPTION
					"
						如果该位置1,表明本地电口被关闭的原因是：当远端电口出现故障,并且光口到电口的故障转移功能被使能、
						否则该位置0																		
					"
			 ::= { rcRemoteRmcEthFeEntry 19 }
			
			rcRemoteRmcEthFeDownIsForEthFxFault	OBJECT-TYPE
				SYNTAX  TruthValue
				MAX-ACCESS	read-only
				STATUS	current
				DESCRIPTION
					"
						如果该位置1,表明本地电口被关闭的原因是：当光口出现故障,并且光口到电口的故障转移功能被使能
					  否则该位置0
					"
			 ::= { rcRemoteRmcEthFeEntry 20 }
			 
      rcRemoteRmcEthFeTag	OBJECT-TYPE
				SYNTAX	INTEGER{
          						  tag(1),
          						  un-tag(2)
          						 }
				MAX-ACCESS	read-write
				STATUS	current
				DESCRIPTION
					"
						设置TAG
					"
			 ::= { rcRemoteRmcEthFeEntry 21 }

      rcRemoteRmcEthFePVID	OBJECT-TYPE
				SYNTAX	INTEGER
				MAX-ACCESS	read-write
				STATUS	current
				DESCRIPTION
					"
						设置以太网电口PVID值，为输出包打tag标识时使用
					"
			 ::= { rcRemoteRmcEthFeEntry 22 } 
			 
       rcRemoteRmcEthFePriority OBJECT-TYPE
           SYNTAX      INTEGER  {
           						high(1),
           						low(2)
           						}            
           MAX-ACCESS  read-write
           STATUS      current
           DESCRIPTION
           "
            设置端口优先级
           "
        ::= { rcRemoteRmcEthFeEntry 23 } 	
        
      rcRemoteRmcEthFeDefCos	OBJECT-TYPE
				SYNTAX	INTEGER
				MAX-ACCESS	read-write
				STATUS	current
				DESCRIPTION
					"
						设置以太网电口default cos值（0-7）
					"
			 ::= { rcRemoteRmcEthFeEntry 24 } 
			 
      rcRemoteRmcEthFeAdminCmd	OBJECT-TYPE
           		SYNTAX      INTEGER  {
           						reset(1),
           						VirtualCableTest(2)
           						} 				
           		MAX-ACCESS	read-write
				STATUS	current
				DESCRIPTION
					"
						电口命令字
						1：复位；2：电口线路诊断命令
					"
			 ::= { rcRemoteRmcEthFeEntry 25 } 
			 
      rcRemoteRmcEthFeVCTStatus	OBJECT-TYPE
           		SYNTAX      INTEGER  {
           						none(1),
           						in(2),
           						over(3)    						
           						} 
				MAX-ACCESS	read-only
				STATUS	current
				DESCRIPTION
					"
						电口线路诊断状态
					"
			 ::= { rcRemoteRmcEthFeEntry 26 } 

      rcRemoteRmcEthFeVCTMDIPairResult	OBJECT-TYPE
				SYNTAX	OCTET STRING
				MAX-ACCESS	read-only
				STATUS	current
				DESCRIPTION
					"
						线对1-4诊断结果
							short(1)，open(2)，normal(3)
						|线对4结果|线对3结果|线对2结果|线对1结果|
						每个线对结果占1个字节，最低位字节表示线对1结果
					"
			 ::= { rcRemoteRmcEthFeEntry 27 }   

      rcRemoteRmcEthFeVCTMDIPairFaultDistance	OBJECT-TYPE
				SYNTAX	OCTET STRING
				MAX-ACCESS	read-only
				STATUS	current
				DESCRIPTION
					"
						线对1-4故障距离
						|线对4|线对3|线对2|线对1|
						每个线对故障距离占4个字节，最低位4个字节表示线对1故障距离，单位：m
					"
			 ::= { rcRemoteRmcEthFeEntry 28 } 			 
			 
      rcRemoteRmcEthFeTimeStamp	OBJECT-TYPE
				SYNTAX	INTEGER
				MAX-ACCESS	read-only
				STATUS	current
				DESCRIPTION
					"
						电口流量统计上报时间戳
					"
			 ::= { rcRemoteRmcEthFeEntry 29 } 		 
			 
      rcRemoteRmcEthFeTxFaultFramesThreshold	OBJECT-TYPE
				SYNTAX	INTEGER
				MAX-ACCESS	read-write
				STATUS	current
				DESCRIPTION
					"
						电口发送失败超限告警阈值配置
					"
			 ::= { rcRemoteRmcEthFeEntry 30 }

      rcRemoteRmcEthFeRxFaultFramesThreshold	OBJECT-TYPE
				SYNTAX	INTEGER
				MAX-ACCESS	read-write
				STATUS	current
				DESCRIPTION
					"
						电口接收错误超限告警阈值配置
					"
			 ::= { rcRemoteRmcEthFeEntry 31 }
			 
    rcRemoteRmcNotificationPrefix     OBJECT IDENTIFIER ::= { rcRemoteRmcNotifications 0 }             	
	
			 
		rcRemoteRmcVoltageTooHighTrap NOTIFICATION-TYPE
		OBJECTS { rcNotifsTrapLocation, rcEntPhysicalID }
		STATUS             current
		DESCRIPTION
		"
			远端收发器电压过高通知信号.
		"
		::= { rcRemoteRmcNotificationPrefix 1301 }	 
			 
		rcRemoteRmcVoltageTooHighTrapOk NOTIFICATION-TYPE
		OBJECTS { rcNotifsTrapLocation, rcEntPhysicalID }
		STATUS             current
		DESCRIPTION
		"
			远端收发器电压过高恢复通知信号.
		"
		::= { rcRemoteRmcNotificationPrefix 1302 }		 
			 
		rcRemoteRmcVoltageTooLowTrap NOTIFICATION-TYPE
		OBJECTS { rcNotifsTrapLocation, rcEntPhysicalID }
		STATUS             current
		DESCRIPTION
		"
			远端收发器电压过低通知信号.
		"
		::= { rcRemoteRmcNotificationPrefix 1303 }	 
			 
		rcRemoteRmcVoltageTooLowTrapOk NOTIFICATION-TYPE
		OBJECTS { rcNotifsTrapLocation, rcEntPhysicalID }
		STATUS             current
		DESCRIPTION
		"
			远端收发器电压过低恢复通知信号.
		"
		::= { rcRemoteRmcNotificationPrefix 1304 }			 
			 
		 
			 
	
		rcRemoteRmcEthFeLinkdownTrap NOTIFICATION-TYPE
		OBJECTS { rcNotifsTrapLocation, rcEntPhysicalID ,rcRemoteRmcEthFeIndex }
		STATUS             current
		DESCRIPTION
		"
			以太网电口linkdown通知信号.
		"
		::= { rcRemoteRmcNotificationPrefix 1305 }	 
			 
		rcRemoteRmcEthFeLinkupTrap NOTIFICATION-TYPE
		OBJECTS { rcNotifsTrapLocation, rcEntPhysicalID ,rcRemoteRmcEthFeIndex }
		STATUS             current
		DESCRIPTION
		"
			以太网电口linkup通知信号.
		"
		::= { rcRemoteRmcNotificationPrefix 1306 }		
		
 		rcRemoteRmcEthFxRLinkdownTrap NOTIFICATION-TYPE
		OBJECTS { rcNotifsTrapLocation, rcEntPhysicalID ,rcRemoteRmcEthFxIndex }
		STATUS             current
		DESCRIPTION
		"
			以太网光口接收linkdown通知信号.
		"
		::= { rcRemoteRmcNotificationPrefix 1307 }	 
			 
		rcRemoteRmcEthFxRLinkupTrap NOTIFICATION-TYPE
		OBJECTS { rcNotifsTrapLocation, rcEntPhysicalID ,rcRemoteRmcEthFxIndex }
		STATUS             current
		DESCRIPTION
		"
			以太网光口接收linkup通知信号.
		"
		::= { rcRemoteRmcNotificationPrefix 1308 }			
		
		
		rcRemoteRmcEthFxTLinkdownTrap NOTIFICATION-TYPE
		OBJECTS { rcNotifsTrapLocation, rcEntPhysicalID ,rcRemoteRmcEthFxIndex }
		STATUS             current
		DESCRIPTION
		"
			以太网光口发送linkdown通知信号.
		"
		::= { rcRemoteRmcNotificationPrefix 1309 }	 
			 
		rcRemoteRmcEthFxTLinkupTrap NOTIFICATION-TYPE
		OBJECTS { rcNotifsTrapLocation, rcEntPhysicalID ,rcRemoteRmcEthFxIndex }
		STATUS             current
		DESCRIPTION   
		"
			以太网光口发送linkup通知信号.
		"
		::= { rcRemoteRmcNotificationPrefix 1310 }		
		
		rcRemoteRmcEthFxSDTrap NOTIFICATION-TYPE
		OBJECTS { rcNotifsTrapLocation, rcEntPhysicalID ,rcRemoteRmcEthFxIndex }
		STATUS             current
		DESCRIPTION
		"
			以太网光口SD异常通知信号.
		"
		::= { rcRemoteRmcNotificationPrefix 1311 }	 
			 
		rcRemoteRmcEthFxSDTrapOk NOTIFICATION-TYPE
		OBJECTS { rcNotifsTrapLocation, rcEntPhysicalID ,rcRemoteRmcEthFxIndex }
		STATUS             current
		DESCRIPTION
		"
			以太网光口SD异常恢复通知信号.
		"
		::= { rcRemoteRmcNotificationPrefix 1312 }		
			 
		rcRemoteRmcEthFxTxPowerAbnormalTrap NOTIFICATION-TYPE
		OBJECTS { rcNotifsTrapLocation, rcEntPhysicalID ,rcRemoteRmcEthFxIndex }
		STATUS             current
		DESCRIPTION
		"
			以太网光口发送功率异常通知信号.
		"
		::= { rcRemoteRmcNotificationPrefix 1313 }	 
			 
		rcRemoteRmcEthFxTxPowerAbnormalTrapOk NOTIFICATION-TYPE
		OBJECTS { rcNotifsTrapLocation, rcEntPhysicalID ,rcRemoteRmcEthFxIndex }
		STATUS             current
		DESCRIPTION
		"
			以太网光口发送功率正常通知信号.
		"
		::= { rcRemoteRmcNotificationPrefix 1314 }			 
			 
		rcRemoteRmcEthFxRxSensitiveAbnormalTrap NOTIFICATION-TYPE
		OBJECTS { rcNotifsTrapLocation, rcEntPhysicalID ,rcRemoteRmcEthFxIndex }
		STATUS             current
		DESCRIPTION
		"
			以太网光口接收灵敏度异常通知信号.
		"
		::= { rcRemoteRmcNotificationPrefix 1315 }	 
			 
		rcRemoteRmcEthFxRxSensitiveAbnormalTrapOk NOTIFICATION-TYPE
		OBJECTS { rcNotifsTrapLocation, rcEntPhysicalID ,rcRemoteRmcEthFxIndex }
		STATUS             current
		DESCRIPTION
		"
			以太网光口接收灵敏度正常通知信号.
		"
		::= { rcRemoteRmcNotificationPrefix 1316 }


		rcRemoteRmcEthFxLaserAbnormalTrap NOTIFICATION-TYPE
		OBJECTS { rcNotifsTrapLocation, rcEntPhysicalID ,rcRemoteRmcEthFxIndex }
		STATUS             current
		DESCRIPTION
		"
			以太网光口光激光管工作异常异常通知信号.
		"
		::= { rcRemoteRmcNotificationPrefix 1317 }	 
			 
		rcRemoteRmcEthFxLaserAbnormalTrapOk NOTIFICATION-TYPE
		OBJECTS { rcNotifsTrapLocation, rcEntPhysicalID ,rcRemoteRmcEthFxIndex }
		STATUS             current
		DESCRIPTION
		"
			以太网光口光激光管工作正常通知信号.
		"
		::= { rcRemoteRmcNotificationPrefix 1318 }



			 
-- conformance information
	rcRmcConformance	OBJECT IDENTIFIER ::= { raisecomOptRemoteRmcMib 4 }
	rcRmcGroups 		OBJECT IDENTIFIER ::= { rcRmcConformance 1 }	 
	rcRmcDevices 	 OBJECT IDENTIFIER ::= { rcRmcConformance 2 }
-- units of conformance
      rc501Objects    OBJECT-GROUP
          OBJECTS {
			
			rcRemoteRmcDeviceExist,
			rcRemoteRmcDeviceDescr,	
			rcRemoteRmcDeviceType,
			rcRemoteRmcSysTemperature,
			rcRemoteRmcSysVoltageStatus,
			rcRemoteRmcAdminCmd,
			rcRemoteRmcOpticalModuleType,
			  
			  
			rcRemoteRmcEthFeIndex,
			rcRemoteRmcEthFeDescr, 
			rcRemoteRmcEthFeLinkStatus,
			rcRemoteRmcEthFeShutDown,
			rcRemoteRmcEthFeAutoNegotiate,
			rcRemoteRmcEthFeSpeed,
			rcRemoteRmcEthFeSpeedStatus,
			rcRemoteRmcEthFeDuplex,
			rcRemoteRmcEthFeDuplexStatus,
			
			
 			rcRemoteRmcEthFxIndex,
			rcRemoteRmcEthFxDescr,
			rcRemoteRmcEthFxRLK,
			rcRemoteRmcEthFxTLK,
			rcRemoteRmcEthFxSD,
			rcRemoteRmcEthFxTxPowerAbnormal,
			rcRemoteRmcEthFxRxSensitiveAbnormal,
			rcRemoteRmcEthFxLaserAbnormal,
			rcRemoteRmcEthFxToFeFaultPass			
             }
          STATUS     current
          DESCRIPTION
              "
              		rc501设备管理对象
              "
      ::= { rcRmcGroups 1 }  

      rc601VCObjects    OBJECT-GROUP
          OBJECTS {
			
			rcRemoteRmcDeviceExist,
			rcRemoteRmcDeviceDescr,	
			rcRemoteRmcDeviceType,
			rcRemoteRmcSysTemperature,
			rcRemoteRmcSysVoltageStatus,
			rcRemoteRmcAdminCmd,
			rcRemoteRmcOpticalModuleType,
			   
			rcRemoteRmcEthFeIndex,
			rcRemoteRmcEthFeDescr,
			rcRemoteRmcEthFeLinkStatus,
			rcRemoteRmcEthFeShutDown,
			rcRemoteRmcEthFeSpeedStatus,
			rcRemoteRmcEthFeDuplexStatus,
			
			rcRemoteRmcEthFxIndex,
			rcRemoteRmcEthFxDescr,
			rcRemoteRmcEthFxRLK,
			rcRemoteRmcEthFxTLK,
			rcRemoteRmcEthFxSD,
			rcRemoteRmcEthFxToFeFaultPass
		
             }
          STATUS     current
          DESCRIPTION
              "
              		rc601VC设备管理对象
              "
      ::= { rcRmcGroups 2 } 


 rc601VEObjects    OBJECT-GROUP
          OBJECTS {
			
			rcRemoteRmcDeviceExist,
			rcRemoteRmcDeviceDescr,	
			rcRemoteRmcDeviceType,
			rcRemoteRmcSysTemperature,
			rcRemoteRmcSysVoltageStatus,
			rcRemoteRmcAdminCmd,
			rcRemoteRmcOpticalModuleType,
			   
			rcRemoteRmcEthFeIndex,
			rcRemoteRmcEthFeDescr,
			rcRemoteRmcEthFeLinkStatus,
			rcRemoteRmcEthFeShutDown,
			rcRemoteRmcEthFeSpeedStatus,
			rcRemoteRmcEthFeDuplexStatus,
			
			rcRemoteRmcEthFxIndex,
			rcRemoteRmcEthFxDescr,
			rcRemoteRmcEthFxRLK,
			rcRemoteRmcEthFxTLK,
			rcRemoteRmcEthFxSD,
			rcRemoteRmcEthFxToFeFaultPass			
             }
          STATUS     current
          DESCRIPTION
              "
              		rc601VE设备管理对象
              "
      ::= { rcRmcGroups 3 } 
      
      
      -- units of conformance
      rc511Objects    OBJECT-GROUP
          OBJECTS {
			
			rcRemoteRmcDeviceExist,
			rcRemoteRmcDeviceDescr,	
			rcRemoteRmcDeviceType,
			rcRemoteRmcSysTemperature,
			rcRemoteRmcSysVoltageStatus,
			rcRemoteRmcAdminCmd,
			rcRemoteRmcOpticalModuleType,
			  
			  
			rcRemoteRmcEthFeIndex,
			rcRemoteRmcEthFeDescr, 
			rcRemoteRmcEthFeLinkStatus,
			rcRemoteRmcEthFeShutDown,
			rcRemoteRmcEthFeAutoNegotiate,
			rcRemoteRmcEthFeSpeed,
			rcRemoteRmcEthFeSpeedStatus,
			rcRemoteRmcEthFeDuplex,
			rcRemoteRmcEthFeDuplexStatus,
			
			
 			rcRemoteRmcEthFxIndex,
			rcRemoteRmcEthFxDescr,
			rcRemoteRmcEthFxRLK,
			rcRemoteRmcEthFxTLK,
			rcRemoteRmcEthFxSD,
			rcRemoteRmcEthFxTxPowerAbnormal,
			rcRemoteRmcEthFxRxSensitiveAbnormal,
			rcRemoteRmcEthFxLaserAbnormal,
			rcRemoteRmcEthFxToFeFaultPass
			
             }
          STATUS     current
          DESCRIPTION
              "
              		rc511设备管理对象
              "
      ::= { rcRmcGroups 4 }  
      

      rc511-4FEObjects    OBJECT-GROUP
          OBJECTS {
			
			rcRemoteRmcDeviceExist,
			rcRemoteRmcDeviceDescr,	
			rcRemoteRmcDeviceType,
			rcRemoteRmcSysTemperature,
			rcRemoteRmcSysVoltageStatus,
			rcRemoteRmcMaxPktsLength,
			rcRemoteRmcAdminCmd,
			rcRemoteRmcOpticalModuleType,
			   
			rcRemoteRmcEthFeIndex,
			rcRemoteRmcEthFeDescr,
			rcRemoteRmcEthFeLinkStatus,
			rcRemoteRmcEthFeShutDown,
			rcRemoteRmcEthFeAutoNegotiate,
			rcRemoteRmcEthFeSpeed,
			rcRemoteRmcEthFeSpeedStatus,
			rcRemoteRmcEthFeDuplex,
			rcRemoteRmcEthFeDuplexStatus,
			rcRemoteRmcEthFeTxBandWidthControl,
			rcRemoteRmcEthFeRxBandWidthControl,
			rcRemoteRmcEthFeTxBytes,
			rcRemoteRmcEthFeRxBytes,
			
			
 			rcRemoteRmcEthFxIndex,
 			rcRemoteRmcEthFxDescr,
			rcRemoteRmcEthFxRLK,
			rcRemoteRmcEthFxTLK,
			rcRemoteRmcEthFxSD,
			rcRemoteRmcEthFxToFeFaultPass
             }
          STATUS     current
          DESCRIPTION
              "
              		rc511-4FE设备管理对象
              "
      ::= { rcRmcGroups 5 } 
      
      
      rc531-FEObjects    OBJECT-GROUP
          OBJECTS {
			
			rcRemoteRmcDeviceExist,
			rcRemoteRmcDeviceDescr,	
			rcRemoteRmcDeviceType,
			rcRemoteRmcSysTemperature,
			rcRemoteRmcSysVoltageStatus,
			rcRemoteRmcAdminCmd,
			rcRemoteRmcOpticalModuleType,
			   
			rcRemoteRmcEthFeIndex,
			rcRemoteRmcEthFeDescr,
			rcRemoteRmcEthFeLinkStatus,
			rcRemoteRmcEthFeShutDown,
			rcRemoteRmcEthFeAutoNegotiate,
			rcRemoteRmcEthFeSpeed,
			rcRemoteRmcEthFeSpeedStatus,
			rcRemoteRmcEthFeDuplex,
			rcRemoteRmcEthFeDuplexStatus,
			rcRemoteRmcEthFeTxBandWidthControl,
			rcRemoteRmcEthFeRxBandWidthControl,
			rcRemoteRmcEthFeTxBytes,
			rcRemoteRmcEthFeRxBytes,
			rcRemoteRmcEthFeTxFrames,
			rcRemoteRmcEthFeRxFrames,
			rcRemoteRmcEthFeTxFaultFrames,
			rcRemoteRmcEthFeRxFaultFrames,
			rcRemoteRmcEthFeDownIsForReEthfeFault,
			rcRemoteRmcEthFeDownIsForEthFxFault,
			
			
 			rcRemoteRmcEthFxIndex,
 			rcRemoteRmcEthFxDescr,
			rcRemoteRmcEthFxRLK,
			rcRemoteRmcEthFxTLK,
			rcRemoteRmcEthFxSD,
			rcRemoteRmcEthFxToFeFaultPass,
      rcRemoteRmcEthFxALSEnable,										
			rcRemoteRmcEthFxDownIsForEthFeLinkDown,                   
		  rcRemoteRmcEthFxDownIsForEthFxNoRxSignal 
             }
          STATUS     current
          DESCRIPTION
              "
              		rc531-FE设备管理对象
              "
      ::= { rcRmcGroups 6 }
      
      rc532-FEObjects    OBJECT-GROUP
          OBJECTS {
			
			rcRemoteRmcDeviceExist,
			rcRemoteRmcDeviceDescr,	
			rcRemoteRmcDeviceType,
			rcRemoteRmcSysTemperature,
			rcRemoteRmcSysVoltageStatus,
			rcRemoteRmcVlantype,
			rcRemoteRmcMaxPktsLength,
			rcRemoteRmcAdminCmd,
			rcRemoteRmcOpticalModuleType,
			   
			rcRemoteRmcEthFeIndex,
			rcRemoteRmcEthFeDescr,
			rcRemoteRmcEthFeLinkStatus,
			rcRemoteRmcEthFeShutDown,
			rcRemoteRmcEthFeAutoNegotiate,
			rcRemoteRmcEthFeSpeed,
			rcRemoteRmcEthFeSpeedStatus,
			rcRemoteRmcEthFeDuplex,
			rcRemoteRmcEthFeDuplexStatus,
			rcRemoteRmcEthFeTxBandWidthControl,
			rcRemoteRmcEthFeRxBandWidthControl,
			rcRemoteRmcEthFeTxBytes,
			rcRemoteRmcEthFeRxBytes,
			rcRemoteRmcEthFeTxFrames,
			rcRemoteRmcEthFeRxFrames,
			rcRemoteRmcEthFeTxFaultFrames,
			rcRemoteRmcEthFeRxFaultFrames,
			rcRemoteRmcEthFeDownIsForReEthfeFault,
			rcRemoteRmcEthFeDownIsForEthFxFault,
			
 			rcRemoteRmcEthFxIndex,
 			rcRemoteRmcEthFxDescr,
			rcRemoteRmcEthFxRLK,
			rcRemoteRmcEthFxTLK,
			rcRemoteRmcEthFxSD,
			rcRemoteRmcEthFxToFeFaultPass,
      rcRemoteRmcEthFxALSEnable,										
			rcRemoteRmcEthFxDownIsForEthFeLinkDown,                   
		  rcRemoteRmcEthFxDownIsForEthFxNoRxSignal 
		               }
          STATUS     current
          DESCRIPTION
              "
              		rc532-FE设备管理对象
              "
      ::= { rcRmcGroups 7 }
      
      
      
      notificationsGroup NOTIFICATION-GROUP
        NOTIFICATIONS {
	  		rcRemoteRmcVoltageTooHighTrap,
	  		rcRemoteRmcVoltageTooHighTrapOk,
	  		rcRemoteRmcVoltageTooLowTrap,
	  		rcRemoteRmcVoltageTooLowTrapOk,
			
	  		rcRemoteRmcEthFeLinkdownTrap,
	  		rcRemoteRmcEthFeLinkupTrap,			
			
	  		rcRemoteRmcEthFxRLinkdownTrap,
	  		rcRemoteRmcEthFxRLinkupTrap,
	  		rcRemoteRmcEthFxTLinkdownTrap,
	  		rcRemoteRmcEthFxTLinkupTrap,
	  		rcRemoteRmcEthFxSDTrap,
	  		rcRemoteRmcEthFxSDTrapOk,
	  		rcRemoteRmcEthFxTxPowerAbnormalTrap,
	  		rcRemoteRmcEthFxTxPowerAbnormalTrapOk,
	  		rcRemoteRmcEthFxRxSensitiveAbnormalTrap,
	  		rcRemoteRmcEthFxRxSensitiveAbnormalTrapOk,
	  		rcRemoteRmcEthFxLaserAbnormalTrap,
	  		rcRemoteRmcEthFxLaserAbnormalTrapOk
           }
        STATUS        current
        DESCRIPTION
            "The collection of the notifications."
    ::= { rcRmcGroups 8 }
    	  
 
   -- compliance statements

       rc501-0x0c MODULE-COMPLIANCE
          STATUS  current
          DESCRIPTION
              "
              	rc501卡式收发器
              "

          MODULE  -- this module
          MANDATORY-GROUPS
             {
             rc501Objects,notificationsGroup
             }
      ::= { rcRmcDevices 0 }	
 
   	
 	    rc601VC-0x09 MODULE-COMPLIANCE
          STATUS  current
          DESCRIPTION
              "
              	rc601VC收发器
              "

          MODULE  -- this module
          MANDATORY-GROUPS
             {
             rc601VCObjects,notificationsGroup
             }
      ::= { rcRmcDevices 2 }
      
        rc601VE-0x6f MODULE-COMPLIANCE
          STATUS  current
          DESCRIPTION
              "
              	rc601VE收发器
              "

          MODULE  -- this module
          MANDATORY-GROUPS
             {
             rc601VEObjects,notificationsGroup
             }
      ::= { rcRmcDevices 3 }
      
       rc511Card-0x3e MODULE-COMPLIANCE
          STATUS  current
          DESCRIPTION
              "
              	rc511卡式收发器
              "

          MODULE  -- this module
          MANDATORY-GROUPS
             {
             rc511Objects,notificationsGroup
             }
      ::= { rcRmcDevices 4 }
   
        rc511Device-0x6c MODULE-COMPLIANCE
          STATUS  current
          DESCRIPTION
              "
              	rc511台式收发器
              "

          MODULE  -- this module
          MANDATORY-GROUPS
             {
             rc511Objects,notificationsGroup
             }
      ::= { rcRmcDevices 5 }
      
       rc511-4FE-0xfc05 MODULE-COMPLIANCE
          STATUS  current
          DESCRIPTION
              "
              	rc511-4FE收发器
              "

          MODULE  -- this module
          MANDATORY-GROUPS
             {
             rc511-4FEObjects,notificationsGroup
             }
      ::= { rcRmcDevices 6 }
      
      rc531-FE-0x48 MODULE-COMPLIANCE
          STATUS  current
          DESCRIPTION
              "
              	rc531-FE收发器
              "

          MODULE  -- this module
          MANDATORY-GROUPS
             {
             rc531-FEObjects,notificationsGroup
             }
      ::= { rcRmcDevices 7 }
      
      rc532-FE-0x4d MODULE-COMPLIANCE
          STATUS  current
          DESCRIPTION
              "
              	rc532-FE收发器
              "

          MODULE  -- this module
          MANDATORY-GROUPS
             {
             rc532-FEObjects,notificationsGroup
             }
      ::= { rcRmcDevices 8 }
      
 



----------------------------------------------------------------------------
------------------RCRemoteRmc VLAN table
----------------------------------------------------------------------------    
 -- 系统配置表
 		rcRemoteRmcVLANTable OBJECT-TYPE
              SYNTAX  SEQUENCE OF RcRemoteRmcVLANEntry
              MAX-ACCESS  not-accessible
              STATUS  current
              DESCRIPTION
                 "The RCRemoteRmc VLAN table."
             ::= { rcRemoteRmcVLAN 1 }

    rcRemoteRmcVLANEntry OBJECT-TYPE
              SYNTAX  RcRemoteRmcVLANEntry
              MAX-ACCESS  not-accessible
              STATUS  current
              DESCRIPTION
                 "
                 An entry in the RRMC VLAN table.
                
                 "
              INDEX   { rcEntPhysicalID,rcRemoteRmcVLANIndex }
             ::= { rcRemoteRmcVLANTable 1 }

     RcRemoteRmcVLANEntry ::=
              SEQUENCE {
                   rcRemoteRmcVLANIndex				INTEGER,
                   rcRemoteRmcVLANStatus			INTEGER,
                   rcRemoteRmcVID					INTEGER,              
                   rcRemoteRmcVLANMember			INTEGER,
                   rcRemoteRmcTrunkUntag			INTEGER
        
                       } 
 
	rcRemoteRmcVLANIndex OBJECT-TYPE
          SYNTAX      INTEGER 
          MAX-ACCESS  read-only
          STATUS      current
          DESCRIPTION
          "
         	VLAN索引，取值1~16
          "
       ::= { rcRemoteRmcVLANEntry 1 } 
 
	rcRemoteRmcVLANStatus OBJECT-TYPE
          SYNTAX      INTEGER 
          {
                activated(1),
                nonactivated(2)
          }
          MAX-ACCESS  read-write
          STATUS      current
          DESCRIPTION
          "
         	VLAN激活状态
          "
       ::= { rcRemoteRmcVLANEntry 2 } 
 
	rcRemoteRmcVID OBJECT-TYPE
          SYNTAX      INTEGER 
          MAX-ACCESS  read-write
          STATUS      current
          DESCRIPTION
          "
         	VLAN ID，取值1~4094
          "
       ::= { rcRemoteRmcVLANEntry 3 } 
 
	rcRemoteRmcVLANMember OBJECT-TYPE
          SYNTAX      INTEGER 
          MAX-ACCESS  read-write
          STATUS      current
          DESCRIPTION
          "
     		bit31~0对应第32路~第1路EthFe口，第n位为1表示第n+1端口为该该VLAN成员。
			目前RC511-4FEE1-REV-B设备只有4路EthFe。
			例如：bit3=1，bit0=1，表示端口4和端口1为该VLAN的成员。
          "
       ::= { rcRemoteRmcVLANEntry 4 } 
       
	rcRemoteRmcTrunkUntag OBJECT-TYPE
          SYNTAX      INTEGER 
          MAX-ACCESS  read-write
          STATUS      current
          DESCRIPTION
          "
     		Bit 31~0对应第32路～第1路端口。
			例如：bit3=1，bit0=1，表示从端口4和端口1发出都去掉此VLAN TAG

          "
       ::= { rcRemoteRmcVLANEntry 5 }        
 
 
       
 	rcRemoteRmcApsTable OBJECT-TYPE
              SYNTAX  SEQUENCE OF RcRemoteRmcApsEntry
              MAX-ACCESS  not-accessible
              STATUS  current
              DESCRIPTION
                 "The RCRemoteRmc Ptotect table."
             ::= { rcRemoteRmcAps 1 }

    rcRemoteRmcApsEntry OBJECT-TYPE
              SYNTAX  RcRemoteRmcApsEntry
              MAX-ACCESS  not-accessible
              STATUS  current
              DESCRIPTION
                 "
                 An entry in the rc protect table.
                
                 "
              INDEX   { rcEntPhysicalID }
             ::= { rcRemoteRmcApsTable 1 }

    RcRemoteRmcApsEntry ::=
              SEQUENCE {
                   rcRemoteRmcApsType				INTEGER,
                   rcRemoteRmcApsForceSwitch		INTEGER,
                   rcRemoteRmcApsActiveLine			INTEGER,
                   rcRemoteRmcApsRevertive        	INTEGER,
                   rcRemoteRmcApsWaitToRestore		INTEGER 
               }
            
       
		rcRemoteRmcApsType OBJECT-TYPE
           SYNTAX INTEGER {
							onePlusOneProtectSwitch(1),
			                oneForOneProtectSwitch(2)
			              }
           MAX-ACCESS  read-write
           STATUS      current
           DESCRIPTION
           "
             	保护倒换模式,1+1 or  1:1
           "
        ::= { rcRemoteRmcApsEntry 1 }
        
         rcRemoteRmcApsForceSwitch OBJECT-TYPE
           SYNTAX INTEGER {
							auto(1),
			                toPriLine(2),
			                toSecLine(3),
			                reserved(4)
			               }
           MAX-ACCESS  read-write
           STATUS      current
           DESCRIPTION
           "
          		线路侧倒换模式,自动,强制到主,强制到备,保留
           "
        ::= { rcRemoteRmcApsEntry 2 }
        
        rcRemoteRmcApsActiveLine OBJECT-TYPE
           SYNTAX INTEGER {
							priChannel(1),
			                secChannel(2)
			              }
           MAX-ACCESS  read-only
           STATUS      current
           DESCRIPTION
           "
          	  	当前工作通道,主通道,备通道
           "
        ::= { rcRemoteRmcApsEntry 3 }
        
         rcRemoteRmcApsRevertive  OBJECT-TYPE
		   SYNTAX INTEGER {
			                 nonrevertive(1),
			                 revertive(2)
			              }           
		   MAX-ACCESS  read-write
           STATUS      current
           DESCRIPTION
           "
           		返回模式,非自动返回,自动返回
           "
        ::= { rcRemoteRmcApsEntry 4 }    
        
         rcRemoteRmcApsWaitToRestore  OBJECT-TYPE
		   SYNTAX	INTEGER          
		   MAX-ACCESS  read-write
           STATUS      current
           DESCRIPTION
           "
           		返回时间0-255,以分钟为单位,默认为12分钟
           "
        ::= { rcRemoteRmcApsEntry 5 }  

    
 
 END

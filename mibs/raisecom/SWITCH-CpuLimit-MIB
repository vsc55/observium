--MibName=SWITCH-CPUPRO-MIB
-- *****************************************************************
-- RAISECOM-CPUPRO-MIB.mib:  Raisecom CPUPro MIB file
--
-- Apr 2010, wangzhongfei huochao
--
-- Copyright (c) 1994-2006 by Raisecom Technology Co., Ltd.
-- All rights reserved.
--
-- *****************************************************************

-- *****************************************************************
-- Modi Report：Format: <number>, <time>, <author>, <desc>
-- 01,20110815,huochao,将节点rcCpuProPacketIndex的取值"all"去掉，这种设计不合理
--                     "all"的配置和获取可以通过遍历的方式进行
-- *****************************************************************


SWITCH-CpuLimit-MIB  DEFINITIONS ::= BEGIN

IMPORTS
    MODULE-IDENTITY, NOTIFICATION-TYPE,
    OBJECT-TYPE                         FROM SNMPv2-SMI

    MODULE-COMPLIANCE,
    NOTIFICATION-GROUP,
    OBJECT-GROUP                        FROM SNMPv2-CONF  
      
    EnableVar                           FROM SWITCH-TC
    iscomSwitch	                        FROM RAISECOM-BASE-MIB;
   

rcCpuLimit MODULE-IDENTITY
        LAST-UPDATED    "201004010000Z"
        ORGANIZATION    "Raisecom Technology Co., Ltd."
        CONTACT-INFO
                "Raisecom Systems

                Postal: No.617/619 Haitai Tower,
                229 Fourth North Loop Middle Road,
                Haidian District, Beijing, PRC

                Tel: +86-10-82884499

                E-mail: wangzhongfei@raisecom.com"
        DESCRIPTION
         "The MIB module is for configuration of Cpu Limitation
         feature."
        REVISION   "201004010000Z"
        DESCRIPTION
            "The initial revision of this MIB module."
        ::= { iscomSwitch 61 }

------------------------------------------------------------------------------
-- define groups in rcCpuPro
------------------------------------------------------------------------------
    rcCpuLimitGroup   OBJECT IDENTIFIER ::= { rcCpuLimit 1 }

------------------------------------------------------------------------------
-- begin rcCpuProGroup  rcCpuProPortTable-----
------------------------------------------------------------------------
rcCpuLimitEnable OBJECT-TYPE 
        SYNTAX EnableVar
        MAX-ACCESS read-write
        STATUS current
        DESCRIPTION
            "Enable or disable cpu rate limit.It may cause hight cpu utilization if disable."  
        ::= { rcCpuLimitGroup 1 }           
       
END

--MibName=raisecomMplsQosMIB
-- *****************************************************************
-- RAISECOM-MPLS-OS-MIB.MIB:  Raisecom Mpls QOS MIB file
--
-- May. 2011, huochao
--
-- Copyright (c) 1994-2011 by Raisecom, Inc.
-- All rights reserved.
-- 01,20111231,yangkewei,ROS00008218,advent mib编译检查
-- *****************************************************************
RAISECOM-MPLS-QOS-MIB  DEFINITIONS ::= BEGIN

IMPORTS                      
	MODULE-IDENTITY, OBJECT-TYPE,
        Integer32, Counter64                    FROM SNMPv2-SMI
        
        TruthValue, RowStatus
        					FROM SNMPv2-TC
        EnableVar,ObjName
        					FROM SWITCH-TC
        MODULE-COMPLIANCE, OBJECT-GROUP         FROM SNMPv2-CONF    
        
        SnmpAdminString
           FROM SNMP-FRAMEWORK-MIB          -- RFC3411

        raisecomQosMIB
                FROM RAISECOM-QOS-MIB; 
                 
    
	raisecomMplsQosMIB MODULE-IDENTITY
        LAST-UPDATED    "201105040000Z"
        ORGANIZATION    "Raisecom, Inc."
        CONTACT-INFO
                "       Raise Systems
                        
                Postal: Beijing,
                        China

                   Tel: 86-010-82884499

                E-mail: huochao@raisecom.com"
        DESCRIPTION
                "Description of Mpls QOS object."     
                
        REVISION   "201105040000Z"  
        DESCRIPTION                       
        "Mpls qos is a submodule of qos.Mpls qos processes the qos priority information between user's network and provider's network.
        Including the following details:
        1.Mapping the qos information of user's network to provider's,including internal priority to Tunnel EXP and VC EXP.
        2.Mapping the qos information of provider's network to user's,including Tunnel EXP and VC EXP to internel priority.
        3.Mannul config the Tunenl EXP,VC EXP value."
                ::= { raisecomQosMIB 4 }   
------------------------------------------------------------------------------
--  define groups in raisecomQosMIB
------------------------------------------------------------------------------
    rcMplsQosNotifications     OBJECT IDENTIFIER ::={ raisecomMplsQosMIB 1 } 
    rcMplsQosObjects           OBJECT IDENTIFIER ::={ raisecomMplsQosMIB 2 }
    rcMplsQosConformance       OBJECT IDENTIFIER ::={ raisecomMplsQosMIB 3 }   
    
    rcMplsQosScalerObject      OBJECT IDENTIFIER ::={ rcMplsQosObjects 1 }       
------------------------------------------------------------------------------
----rcMplsQosObjects group------------
----rcMplsQosScalerObject group scale MIB--
------------------------------------             
rcMplsQosLocalPriMappingToIpPrecedenceEnable OBJECT-TYPE
        SYNTAX  EnableVar
        MAX-ACCESS  read-write
        STATUS      current
        DESCRIPTION
            "Indicates whether the internal priority mapping to IP precedence is enabled on the device.
            enable(1) means that the mapping is enabled on this device.
            disable(2) means that the mapping is disabled." 
        DEFVAL { disable }
        ::= { rcMplsQosScalerObject 1 }

     
rcMplsQosLocalPriMappingToDscpEnable OBJECT-TYPE
        SYNTAX  EnableVar
        MAX-ACCESS  read-write
        STATUS      current
        DESCRIPTION
            "Indicates whether the internal priority mapping to dscp is enabled on the device.
            enable(1) means that the mapping is enabled on this device.
            disable(2) means that the mapping is disabled." 
        DEFVAL { disable }
        ::= { rcMplsQosScalerObject 2 }     
                
----------------------------------------------
----rcMplsQosObjects group rcMplsQosLocalPriMappingTable----
----------------------------------------------
rcMplsQosLocalPriMappingTable OBJECT-TYPE
        SYNTAX SEQUENCE OF RcMplsQosLocalPriMappingEntry
        MAX-ACCESS not-accessible
        STATUS current
        DESCRIPTION
            "A mapping table of local priority to EXP,including tunnel EXP and VC EXP."
        ::= { rcMplsQosObjects 2 }

rcMplsQosLocalPriMappingEntry OBJECT-TYPE
        SYNTAX RcMplsQosLocalPriMappingEntry
        MAX-ACCESS not-accessible
        STATUS current
        DESCRIPTION
            "Table entry for the internal priority maping to EXP table."
        INDEX { rcMplsQosLocalPriMappingLocalPriority }
        ::= { rcMplsQosLocalPriMappingTable 1 }

RcMplsQosLocalPriMappingEntry ::= SEQUENCE {
        rcMplsQosLocalPriMappingLocalPriority   INTEGER, 
        rcMplsQosLocalPriMappingTunnelExp       INTEGER,
        rcMplsQosLocalPriMappingVcExp	     	INTEGER, 
        rcMplsQosLocalPriMappingIpPrecedence    INTEGER, 
        rcMplsQosLocalPriMappingDscp            INTEGER
        }

rcMplsQosLocalPriMappingLocalPriority OBJECT-TYPE
        SYNTAX INTEGER(0..7)
        MAX-ACCESS not-accessible
        STATUS current
        DESCRIPTION
            "the local priority for mapping."
        ::= { rcMplsQosLocalPriMappingEntry 1}

rcMplsQosLocalPriMappingTunnelExp OBJECT-TYPE
        SYNTAX      INTEGER(0..7)
        MAX-ACCESS  read-write
        STATUS      current
        DESCRIPTION
            "the tunnel EXP value of the mpls packet."   
        DEFVAL { 0 }
        ::= { rcMplsQosLocalPriMappingEntry 2}   

rcMplsQosLocalPriMappingVcExp OBJECT-TYPE
        SYNTAX      INTEGER(0..7)
        MAX-ACCESS  read-write
        STATUS      current
        DESCRIPTION
            "the VC EXP value of the mpls packet."  
        DEFVAL { 0 }
        ::= { rcMplsQosLocalPriMappingEntry 3}  
                                                            
rcMplsQosLocalPriMappingIpPrecedence OBJECT-TYPE
        SYNTAX      INTEGER(0..7)
        MAX-ACCESS  read-write
        STATUS      current
        DESCRIPTION
            "the IP precedence value." 
        DEFVAL { 0 }
        ::= { rcMplsQosLocalPriMappingEntry 4}  
                           
rcMplsQosLocalPriMappingDscp OBJECT-TYPE
        SYNTAX      INTEGER(0..63)
        MAX-ACCESS  read-write
        STATUS      current
        DESCRIPTION
            "the dscp value." 
        DEFVAL { 0 }
        ::= { rcMplsQosLocalPriMappingEntry 5}  
                           
                           
-----------------------------------------------------------   
 ----rcMplsQosObjects group rcMplsQosTunnelExpConfigTable----
-----------------------------------------------------------
rcMplsQosTunnelExpConfigTable OBJECT-TYPE
        SYNTAX SEQUENCE OF RcMplsQosTunnelExpConfigEntry
        MAX-ACCESS not-accessible
        STATUS current
        DESCRIPTION
            "This table describes the tunnel exp configuration based on tunnel label."
        ::= { rcMplsQosObjects 3}

rcMplsQosTunnelExpConfigEntry OBJECT-TYPE
        SYNTAX RcMplsQosTunnelExpConfigEntry
        MAX-ACCESS not-accessible
        STATUS current
        DESCRIPTION
            "Table entry for tunnel EXP configuration."
        INDEX { rcMplsQosTunnelExpConfigTunnelName }
        ::= { rcMplsQosTunnelExpConfigTable 1 }           

RcMplsQosTunnelExpConfigEntry ::= SEQUENCE {
        rcMplsQosTunnelExpConfigTunnelName	   SnmpAdminString,
        rcMplsQosTunnelExpConfigExp            INTEGER, 
        rcMplsQosTunnelExpConfigMode           INTEGER,
        rcMplsQosTunnelExpConfigRowStatus      RowStatus
    }

rcMplsQosTunnelExpConfigTunnelName OBJECT-TYPE
        SYNTAX      SnmpAdminString(SIZE(1..255))

        MAX-ACCESS  not-accessible
        STATUS      current
        DESCRIPTION
            "The tunnel name."
        ::= { rcMplsQosTunnelExpConfigEntry 1}
        
rcMplsQosTunnelExpConfigExp OBJECT-TYPE
        SYNTAX 		INTEGER(0..7)
        MAX-ACCESS read-write
        STATUS     current
        DESCRIPTION
            "The tunnel EXP value." 
        DEFVAL { 0 }
        ::= { rcMplsQosTunnelExpConfigEntry 2 } 
           
rcMplsQosTunnelExpConfigMode OBJECT-TYPE
        SYNTAX 		INTEGER{fixed(0),mapping(1)}
        MAX-ACCESS read-write
        STATUS     current
        DESCRIPTION
            "The tunnel EXP generate mode,
            fixed(0) means using the config exp value,
            mapping(1) means using local priority mapping to exp." 
        DEFVAL { mapping }
        ::= { rcMplsQosTunnelExpConfigEntry 3 } 

rcMplsQosTunnelExpConfigRowStatus OBJECT-TYPE
        SYNTAX 		RowStatus
        MAX-ACCESS read-create
        STATUS     current
        DESCRIPTION
            "This object allows entries to be created and deleted in the rcMplsQosTunnelExpConfigTable."
        ::= { rcMplsQosTunnelExpConfigEntry 4 }   
                 
-----------------------------------------------------------   
 ----rcMplsQosObjects group rcMplsQosVcExpConfigTable----
-----------------------------------------------------------
rcMplsQosVcExpConfigTable OBJECT-TYPE
        SYNTAX SEQUENCE OF RcMplsQosVcExpConfigEntry
        MAX-ACCESS not-accessible
        STATUS current
        DESCRIPTION
            "This table describes the VC EXP configuration based on VC label."
        ::= { rcMplsQosObjects 4 }

rcMplsQosVcExpConfigEntry OBJECT-TYPE
        SYNTAX RcMplsQosVcExpConfigEntry
        MAX-ACCESS not-accessible
        STATUS current
        DESCRIPTION
            "Table entry for VC EXP configuration."
        INDEX { rcMplsQosVcExpConfigVcId }
        ::= { rcMplsQosVcExpConfigTable 1 }           

RcMplsQosVcExpConfigEntry ::= SEQUENCE {
        rcMplsQosVcExpConfigVcId	       INTEGER,
        rcMplsQosVcExpConfigExp            INTEGER,     
        rcMplsQosVcExpConfigMode           INTEGER,
        rcMplsQosVcExpConfigRowStatus      RowStatus
    }

rcMplsQosVcExpConfigVcId OBJECT-TYPE
        SYNTAX      INTEGER(0..1048575)
        MAX-ACCESS  not-accessible
        STATUS      current
        DESCRIPTION
            "The VC id value."
        ::= { rcMplsQosVcExpConfigEntry 1}
        
rcMplsQosVcExpConfigExp OBJECT-TYPE
        SYNTAX 		INTEGER(0..7)
        MAX-ACCESS read-write
        STATUS     current
        DESCRIPTION
            "The VC EXP value." 
        DEFVAL { 0 }
        ::= { rcMplsQosVcExpConfigEntry 2 }   
        
rcMplsQosVcExpConfigMode OBJECT-TYPE
        SYNTAX 		INTEGER{fixed(0),mapping(1)}
        MAX-ACCESS read-write
        STATUS     current
        DESCRIPTION
            "The VC EXP generate mode,
            fixed(0) means using the config exp value,
            mapping(1) means using local priority mapping to exp."  
        DEFVAL { mapping }
        ::= { rcMplsQosVcExpConfigEntry 3 } 


rcMplsQosVcExpConfigRowStatus OBJECT-TYPE
        SYNTAX 		RowStatus
        MAX-ACCESS read-create
        STATUS     current
        DESCRIPTION
            "This object allows entries to be created and deleted in the rcMplsQosVcExpConfigTable."
        ::= { rcMplsQosVcExpConfigEntry 4 }  
         
-----------------------------------------------------------   
 ----rcMplsQosObjects group rcMplsQosTunnelExpMappingTable----
-----------------------------------------------------------   
rcMplsQosTunnelExpMappingTable OBJECT-TYPE
        SYNTAX SEQUENCE OF RcMplsQosTunnelExpMappingEntry
        MAX-ACCESS not-accessible
        STATUS current
        DESCRIPTION
            "A mapping table of tunnel EXP to local priority."
        ::= { rcMplsQosObjects 5 }

rcMplsQosTunnelExpMappingEntry OBJECT-TYPE
        SYNTAX RcMplsQosTunnelExpMappingEntry
        MAX-ACCESS not-accessible
        STATUS current
        DESCRIPTION
            "Table entry for tunnel EXP to local priority mapping table."
        INDEX { rcMplsQosTunnelExpMappingExp }
        ::= { rcMplsQosTunnelExpMappingTable 1 }           

RcMplsQosTunnelExpMappingEntry ::= SEQUENCE {
        rcMplsQosTunnelExpMappingExp	              INTEGER,
        rcMplsQosTunnelExpMappingLocalPriority        INTEGER,  
        rcMplsQosTunnelExpMappingColor                INTEGER
       }

rcMplsQosTunnelExpMappingExp OBJECT-TYPE
        SYNTAX      INTEGER(0..7)
        MAX-ACCESS  not-accessible
        STATUS      current
        DESCRIPTION
            "The tunnel EXP value for mapping."
        ::= { rcMplsQosTunnelExpMappingEntry 1}
        
rcMplsQosTunnelExpMappingLocalPriority OBJECT-TYPE
        SYNTAX 		INTEGER(0..7)
        MAX-ACCESS read-write
        STATUS     current
        DESCRIPTION
            "The local priority."  
        DEFVAL { 0 }
        ::= { rcMplsQosTunnelExpMappingEntry 2 }    

rcMplsQosTunnelExpMappingColor OBJECT-TYPE
        SYNTAX 	   INTEGER {green(1),yellow(2),red(3)}	
        MAX-ACCESS read-write
        STATUS     current
        DESCRIPTION
            "The color value."
        DEFVAL { null }
        ::= { rcMplsQosTunnelExpMappingEntry 3 } 

-----------------------------------------------------------   
 ----rcMplsQosObjects group rcMplsQosVcExpMappingTable----
-----------------------------------------------------------
rcMplsQosVcExpMappingTable OBJECT-TYPE
        SYNTAX SEQUENCE OF RcMplsQosVcExpMappingEntry
        MAX-ACCESS not-accessible
        STATUS current
        DESCRIPTION
            "A mapping table of VC EXP to local priority."
        ::= { rcMplsQosObjects 6 }

rcMplsQosVcExpMappingEntry OBJECT-TYPE
        SYNTAX RcMplsQosVcExpMappingEntry
        MAX-ACCESS not-accessible
        STATUS current
        DESCRIPTION
            "Table entry for VC EXP to local priority mapping table."
        INDEX { rcMplsQosVcExpMappingExp }
        ::= { rcMplsQosVcExpMappingTable 1 }           

RcMplsQosVcExpMappingEntry ::= SEQUENCE {
        rcMplsQosVcExpMappingExp	           INTEGER,
        rcMplsQosVcExpMappingLocalPriority     INTEGER,  
        rcMplsQosVcExpMappingColor             INTEGER
       }

rcMplsQosVcExpMappingExp OBJECT-TYPE
        SYNTAX      INTEGER(0..7)
        MAX-ACCESS  not-accessible
        STATUS      current
        DESCRIPTION
            "The VC EXP value."
        ::= { rcMplsQosVcExpMappingEntry 1}
        
rcMplsQosVcExpMappingLocalPriority OBJECT-TYPE
        SYNTAX 		INTEGER(0..7)
        MAX-ACCESS read-write
        STATUS     current
        DESCRIPTION
            "The local priority." 
        DEFVAL { 0 }
        ::= { rcMplsQosVcExpMappingEntry 2 }    
        
rcMplsQosVcExpMappingColor OBJECT-TYPE
        SYNTAX 	   INTEGER {green(1),yellow(2),red(3)}	
        MAX-ACCESS read-write
        STATUS     current
        DESCRIPTION
            "the color value."  
        DEFVAL { null }
        ::= { rcMplsQosVcExpMappingEntry 3 } 


-----------------------------------------------------------   
----rcMplsQosObjects group rcMplsQosTunnelLocalPriConfigTable---- 
-----------------------------------------------------------
 rcMplsQosTunnelLocalPriConfigTable OBJECT-TYPE
        SYNTAX SEQUENCE OF RcMplsQosTunnelLocalPriConfigEntry
        MAX-ACCESS not-accessible
        STATUS current
        DESCRIPTION
            "The local priority configuration based on tunnel label."
        ::= { rcMplsQosObjects 7}

rcMplsQosTunnelLocalPriConfigEntry OBJECT-TYPE
        SYNTAX RcMplsQosTunnelLocalPriConfigEntry
        MAX-ACCESS not-accessible
        STATUS current
        DESCRIPTION
            "table entry for local priority configuration based on tunnel label."
        INDEX { rcMplsQosTunnelLocalPriConfigTunnelName }
        ::= {rcMplsQosTunnelLocalPriConfigTable 1 }           

RcMplsQosTunnelLocalPriConfigEntry ::= SEQUENCE {
        rcMplsQosTunnelLocalPriConfigTunnelName	       SnmpAdminString,
        rcMplsQosTunnelLocalPriConfigLocalPriority     INTEGER, 
        rcMplsQosTunnelLocalPriConfigMode              INTEGER,
        rcMplsQosTunnelLocalPriConfigRowStatus         RowStatus
       }

rcMplsQosTunnelLocalPriConfigTunnelName OBJECT-TYPE
        SYNTAX      SnmpAdminString(SIZE(1..255))
        MAX-ACCESS  not-accessible
        STATUS      current
        DESCRIPTION
            "the tunnel name."
        ::= { rcMplsQosTunnelLocalPriConfigEntry 1}
        
rcMplsQosTunnelLocalPriConfigLocalPriority OBJECT-TYPE
        SYNTAX 	   INTEGER(0..7)	
        MAX-ACCESS read-create
        STATUS     current
        DESCRIPTION
            "the local priority." 
        DEFVAL { 0 }
        ::= { rcMplsQosTunnelLocalPriConfigEntry 2 }   
        
rcMplsQosTunnelLocalPriConfigMode OBJECT-TYPE
        SYNTAX 	   INTEGER{not-change(0),fixed(1),mapping(2)}
        MAX-ACCESS read-create
        STATUS     current
        DESCRIPTION
            "the local priority generate mode,
            not-change(0) means not change the local priority,
            fixed(1) means using the static config local priority value,
            mapping(2) means using exp mapping to local priority." 
        DEFVAL { mapping }
        ::= { rcMplsQosTunnelLocalPriConfigEntry 3 } 
        
rcMplsQosTunnelLocalPriConfigRowStatus OBJECT-TYPE
        SYNTAX 	   RowStatus
        MAX-ACCESS read-write
        STATUS     current
        DESCRIPTION
            "This object allows entries to be created and deleted in the rcMplsQosTunnelLocalPriConfigTable."
        ::= { rcMplsQosTunnelLocalPriConfigEntry 4 } 

-----------------------------------------------------------   
 ----rcMplsQosObjects group rcMplsQosVcLocalPriConfigTable---- 
-----------------------------------------------------------
 rcMplsQosVcLocalPriConfigTable OBJECT-TYPE
        SYNTAX SEQUENCE OF RcMplsQosVcLocalPriConfigEntry
        MAX-ACCESS not-accessible
        STATUS current
        DESCRIPTION
            "The local priority configuration based on VC label."
        ::= { rcMplsQosObjects 8}

rcMplsQosVcLocalPriConfigEntry OBJECT-TYPE
        SYNTAX RcMplsQosVcLocalPriConfigEntry
        MAX-ACCESS not-accessible
        STATUS current
        DESCRIPTION
            "table entry for local priority configuration based on VC label."
        INDEX { rcMplsQosVcLocalPriConfigVcId }
        ::= {rcMplsQosVcLocalPriConfigTable 1 }           

RcMplsQosVcLocalPriConfigEntry ::= SEQUENCE {
        rcMplsQosVcLocalPriConfigVcId	            INTEGER,
        rcMplsQosVcLocalPriConfigLocalPriority      INTEGER,  
        rcMplsQosVcLocalPriConfigMode               INTEGER, 
        rcMplsQosVcLocalPriConfigRowStatus          RowStatus
       }

rcMplsQosVcLocalPriConfigVcId OBJECT-TYPE
        SYNTAX      INTEGER(0..1048575)
        MAX-ACCESS  not-accessible
        STATUS      current
        DESCRIPTION
            "the VC id value."
        ::= { rcMplsQosVcLocalPriConfigEntry 1}
        
rcMplsQosVcLocalPriConfigLocalPriority OBJECT-TYPE
        SYNTAX 	   INTEGER(0..7)	
        MAX-ACCESS read-write
        STATUS     current
        DESCRIPTION
            "the local priority."  
        DEFVAL { 0 }
        ::= { rcMplsQosVcLocalPriConfigEntry 2 } 

rcMplsQosVcLocalPriConfigMode OBJECT-TYPE
        SYNTAX 	   INTEGER{not-change(0),fixed(1),mapping(2)}	
        MAX-ACCESS read-write
        STATUS     current
        DESCRIPTION
            "the local priority generate mode,
            not-change(0) means not change the local priority,
            fixed(1) means using the static config local priority value,
            mapping(2) means using exp mapping to local priority." 
        DEFVAL { mapping }
        ::= { rcMplsQosVcLocalPriConfigEntry 3 } 


rcMplsQosVcLocalPriConfigRowStatus OBJECT-TYPE
        SYNTAX 	   RowStatus
        MAX-ACCESS read-write
        STATUS     current
        DESCRIPTION
            "the local priority configuration based on VC label table row status."
        ::= { rcMplsQosVcLocalPriConfigEntry 4 }    
        
        
 -----------------------------------------------------------   
 ----rcMplsQosObjects group rcMplsQosPortStatusConfigTable---- 
-----------------------------------------------------------
 rcMplsQosPortStatusConfigTable OBJECT-TYPE
        SYNTAX SEQUENCE OF rcMplsQosPortStatusConfigEntry
        MAX-ACCESS not-accessible
        STATUS current
        DESCRIPTION
            "The enable/disable of local pri to dscp or ip precedence in port."
        ::= { rcMplsQosObjects 9}

rcMplsQosPortStatusConfigEntry OBJECT-TYPE
        SYNTAX rcMplsQosPortStatusConfigEntry
        MAX-ACCESS not-accessible
        STATUS current
        DESCRIPTION
            "table entry for the enable/disable of local pri to dscp or ip precedence in port."
        INDEX { rcMplsQosPortId }
        ::= {rcMplsQosPortStatusConfigTable 1 }           

rcMplsQosPortStatusConfigEntry ::= SEQUENCE {
        rcMplsQosPortId	            INTEGER,
        rcMplsQosPortLocalPriMappingToIpPrecedenceEnable      INTEGER,  
        rcMplsQosPortLocalPriMappingToDscpEnable               INTEGER
             }

rcMplsQosPortId OBJECT-TYPE
        SYNTAX      INTEGER
        MAX-ACCESS  not-accessible
        STATUS      current
        DESCRIPTION
        	"An index that uniquely identifies a configuration about mpls qos."
        ::= { rcMplsQosPortStatusConfigEntry 1}
        
rcMplsQosPortLocalPriMappingToIpPrecedenceEnable OBJECT-TYPE
        SYNTAX 	   EnableVar	
        MAX-ACCESS read-write
        STATUS     current
        DESCRIPTION
            "Indicates whether the internal priority mapping to IP precedence is enabled on the port.
            enable(1) means that the mapping is enabled on this device.
            disable(2) means that the mapping is disabled." 

        DEFVAL { disable }
        ::= { rcMplsQosPortStatusConfigEntry 2 } 

rcMplsQosPortLocalPriMappingToDscpEnable OBJECT-TYPE
        SYNTAX 	   EnableVar	
        MAX-ACCESS read-write
        STATUS     current
        DESCRIPTION
            "Indicates whether the internal priority mapping to IP dscp is enabled on the port.
            enable(1) means that the mapping is enabled on this device.
            disable(2) means that the mapping is disabled." 
        DEFVAL { disable }
        ::= { rcMplsQosPortStatusConfigEntry 3 }    
        
        
 -----------------------------------------------------------   
 ----rcMplsQosObjects group rcMplsQosPortLocalPriMappingConfigTable---- 
-----------------------------------------------------------
 rcMplsQosPortLocalPriMappingConfigTable OBJECT-TYPE
        SYNTAX SEQUENCE OF rcMplsQosPortLocalPriMappingConfigEntry
        MAX-ACCESS not-accessible
        STATUS current
        DESCRIPTION
            "The enable/disable of local pri to dscp or ip precedence in port."
        ::= { rcMplsQosObjects 10}

rcMplsQosPortLocalPriMappingConfigEntry OBJECT-TYPE
        SYNTAX rcMplsQosPortLocalPriMappingConfigEntry
        MAX-ACCESS not-accessible
        STATUS current
        DESCRIPTION
            "table entry for the enable/disable of local pri to dscp or ip precedence in port."
        INDEX { rcMplsQosPortLocalPriMappingPortId, rcMplsQosPortLocalPriMappingLocalPri }
        ::= {rcMplsQosPortLocalPriMappingConfigTable 1 }           

rcMplsQosPortLocalPriMappingConfigEntry ::= SEQUENCE {
        rcMplsQosPortLocalPriMappingPortId	            INTEGER,
        rcMplsQosPortLocalPriMappingLocalPri      INTEGER,  
        rcMplsQosPortLocalPriMappingDscp               INTEGER ,
        rcMplsQosPortLocalPriMappingIpPre          INTEGER 

             }

rcMplsQosPortLocalPriMappingPortId OBJECT-TYPE
        SYNTAX      INTEGER
        MAX-ACCESS  not-accessible
        STATUS      current
        DESCRIPTION
        	"An index that uniquely identifies a configuration about mpls qos."
        ::= { rcMplsQosPortLocalPriMappingConfigEntry 1}
        
rcMplsQosPortLocalPriMappingLocalPri OBJECT-TYPE
        SYNTAX 	   INTEGER(0..7)
        MAX-ACCESS not-accessible
        STATUS     current
        DESCRIPTION
        	"An index that uniquely identifies a configuration about mpls qos."
        ::= { rcMplsQosPortLocalPriMappingConfigEntry 2 } 

rcMplsQosPortLocalPriMappingDscp OBJECT-TYPE
        SYNTAX 	   INTEGER(0..63)	
        MAX-ACCESS read-write
        STATUS     current
        DESCRIPTION
            "the dscp value." 
        DEFVAL { 0 }
        ::= { rcMplsQosPortLocalPriMappingConfigEntry 3 } 
        
rcMplsQosPortLocalPriMappingIpPre OBJECT-TYPE
        SYNTAX 	   INTEGER(0..7)	
        MAX-ACCESS read-write
        STATUS     current
        DESCRIPTION
            "the IP precedence value." 
        DEFVAL { 0 }
        ::= { rcMplsQosPortLocalPriMappingConfigEntry 4 }     

 
END

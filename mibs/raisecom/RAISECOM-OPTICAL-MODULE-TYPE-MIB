-- file: RAISECOM-OPTICAL-MODULE-TYPE-MIB.my
-- Changes:

-- 


RAISECOM-OPTICAL-MODULE-TYPE-MIB DEFINITIONS ::= BEGIN
     
    IMPORTS
        MODULE-IDENTITY, OBJECT-TYPE
                FROM SNMPv2-SMI
        TEXTUAL-CONVENTION          
                FROM SNMPv2-TC
        optSysModules
                FROM RAISECOM-BASE-MIB;
             
     raisecomOptModuleTypeMIB   MODULE-IDENTITY
     
        LAST-UPDATED "1403171408Z"
        ORGANIZATION "RC006 Software Working Group"
        CONTACT-INFO
           "           "
        DESCRIPTION
              "The MIB module defines module types used in Raisecom Optical Group.
              Modules include cards, devices, and sub modules, etc."
       REVISION      "0603011400Z"
       DESCRIPTION
               "Add RcOptIfModuleType"
       REVISION      "0604132200Z"
       DESCRIPTION
               "modify module type for all pdh subm card"
       REVISION      "0605121100Z"
       DESCRIPTION
               "add RC801/3/5-480B series, RCMS2811-120/240/480FE-BL series
               modify description for rcOptTypeSS13 and rcOptTypeSS23 "
       REVISION      "0605191700Z"
       DESCRIPTION
               "add RC002 series RMC and optical modem"
       REVISION      "0605261700Z"
       DESCRIPTION
               "modify rc511-fe-rev-a and rc511-fe-c-rev-a type"
       REVISION      "0606011700Z"
       DESCRIPTION
               "add remote RIC type"
       REVISION      "0607171700Z"
       DESCRIPTION
               "add OPCOM3500-P240EOS, RC3000, RC3000-OPT-2E1"
       REVISION      "0608211700Z"
       DESCRIPTION
               "add rc953 serias RIC and RC3101 PCM device(RC002 protocol)"
       REVISION      "0608221700Z"
       DESCRIPTION
               "add rc3201/3202"
       REVISION      "0609071100Z"
       DESCRIPTION
               "add rc531-fe-rev-a, rc532-fe-rev-a, rc532-2fe-rev-a device"
       REVISION      "0609221800Z"
       DESCRIPTION
               "add rc802-30b,rc804-30b,rc806-30b,rc802-60b,rc804-60b,rc806-60b device"
       REVISION      "0609261200Z"
       DESCRIPTION
               "add opcom3500-eos-8fx device"
       REVISION      "0610121500Z"
       DESCRIPTION
               "add rc801/5-30b-fv35-rev-m, rc802/4/6-30b-fv35-rev-m, 
                    rc801/3/5-30b-fv35-rev-n, rc802/4/6-30b-fv35-rev-n, 
                    rc801/5-60b-fv35-rev-m, rc801/3/5-60b-fv35-rev-n device"
       REVISION      "0612131100Z"
       DESCRIPTION
               "add rc954-fe4e1-rev-a and rc954-fx4e1-rev-a"
       REVISION      "0612181100Z"
       DESCRIPTION
               "add opcom3500e-nms"
       REVISION      "0612301100Z"
       DESCRIPTION
               "add opcom100-olp-a, rc832-120-rev-a, rc832-240-rev-a, 
               rc832-120-s-rev-a, rc832-240-s-rev-a, etc."
       REVISION      "0701161100Z"
       DESCRIPTION
               "add opcom3500-120eosx4"
       REVISION      "0701281100Z"
       DESCRIPTION
               "add rc513-fe-rev-a and rc513-fe-c-rev-a"
       REVISION      "0705091700Z"
       DESCRIPTION
               "add rc956-fx8e1-r"
       REVISION      "0706211700Z"
       DESCRIPTION
               "add 7017 series devices and RC3000-15 cards
               "
       REVISION      "0706071500Z"
       DESCRIPTION
               "modify opcom3500e-120feX4-ge device type
               "
       REVISION      "0707151500Z"
       DESCRIPTION
               "add opcom3500-eop-fe8e1"
       REVISION      "0707301500Z"
       DESCRIPTION
               "add e-subm-fv35"
       REVISION      "0708171100Z"
       DESCRIPTION
               "add opcom3105"
       REVISION      "0709141700Z"
       DESCRIPTION
               "add rc3000-15-16fxs, rc3000-15-16fxo, rc3000-15-16fxs-16fxo, rc3000-15-fxso"
       REVISION      "0709171600Z"
       DESCRIPTION
               "add  rcvs1000-601ax3, rcvs1000-501a, rcvs1000-801a"
       REVISION      "0709281700Z"
       DESCRIPTION
               "add  rcvs1000-50x, rcvs1000-60x
                modify rc511-fe-c-rev-a as rc511-fe-rev-b
                modify rc513-fe-c-rev-a as rc513-fe-rev-b
                add rc512-fe-s, rc512-fe-s-single, rc512-fe-c,rc512-fe-c-single
               "
       REVISION      "0710090930Z"
       DESCRIPTION
               "add  opcom3500-eos-4fe, opcom3500-eose-4fx"
       REVISION      "0710100930Z"
       DESCRIPTION
               "RcOptIfModuleType add type notExist"
       REVISION      "0711021730Z"
       DESCRIPTION
               "add opcom100-oau,opcom3500-4eos-4fe"
       REVISION      "0711261800Z"
       DESCRIPTION
               "add RcOptIfPortType"
       REVISION      "0712041800Z"
       DESCRIPTION
               "update RcOptIfModuleType with company standard"
       REVISION      "0712281800Z"
       DESCRIPTION
               "add opcom100-oau-1b, opcom100-oau-2b, rc006-16rs232, ms3esw-ge-t, ms3esw-ge-f
                ms3esw-2ge-t, ms3esw-2ge-f, opcom600-omu, opcom600-odu, opcom600-omd, opcom600-oad-d,
                opcom600-oad-s, rc832-120x2, opcom3500e-p480fe, opcom3500e-240hx2,
                opcom3500-eop-fee1X8, rc3000-15-480fe-opt, rc3000-15-p480fe-opt, rc3000-15-8v24,
                rc3000-15-shdsl-2wX8, rc3000-15-240fe-opt,rc3000-15-p240fe-opt"
       REVISION      "0802021600Z"
       DESCRIPTION
               "add rcvs1000-601b, rcvs1000-602b, rcvs1000-501b, rcvs1000-502b,
               rcms2802-480ge, rcms2802-480ge-s"
       REVISION      "0803131800Z"
       DESCRIPTION
               "change name rcms2802-480ge to rcms2802-480ge-bl , rcms2802-480ge-s to rcms2802-480ge-bl-s
               add rcms2802-240ge-bl, rcms2802-240ge-bl-s, opcom3500-4eos-4fx-esw, opcom3500-4eos-4fx-eos,
               rc959-4fe16e1"
       REVISION      "0803201000Z"
       DESCRIPTION
               "add rc1101-fev35e1-rev-a, rc1102-e1-rev-b0, rc1102-e1-rev-b1,rc1102-e1-rev-b2,
               rc1102-e1-bl-rev-b0, rc1102-e1-bl-rev-b1,rc1102-e1-bl-rev-b2, 
               rc1102-fe-rev-a, rc1102-fe-rev-b, rc1102-v35-rev-a"
       REVISION      "0803311700Z"
       DESCRIPTION
               "fix module id for rc512-fe-c and rc512-fe-c-single"
       REVISION      "0804171700Z"
       DESCRIPTION
               "add opcom3500e-nms-stm1, opcom3500e-8v35, opcom3500e-8v24, opcom3500e-dxc-ds0, 
               opcom3500e-shdsl-2wx8, rc1106-fe-2wx8, rc1106-fe-2wx8-s, rc1106-fe-2wx8-s,
               rc3000-15-shdsl-2wx8, rcvs1000-601b-s, rcvs1000-602b-s, rcvs1000-608b, rcvs1000-808b,
               rcvs1000-808b-s"
       REVISION      "0805281100Z"
       DESCRIPTION
               "add opcom3500-4fx, rc532-feX4, changed opcom3500-4eos-4fx-esw and opcom3500-4eos-4fx-eos id"
       REVISION      "0806171000Z"
       DESCRIPTION
               "add rcOptTypeS15 in RcOptIfModuleType"
       REVISION      "0807241700Z"
       DESCRIPTION
               "add opcom600-2gemp, opcom600-2gemp-s, opcom600-otu1-1, opcom600-otu1-2, opcom600-otu1-4,
               opcom600-ocp1-1, opcom600-ocp1-2, opcom3500e-b-2stm4-m, opcom3500e-p480fx, rc3000-15-8ethp"
       REVISION      "0808251500Z"
       DESCRIPTION
               "change module type of rc1101-fev35e1-rev-a. add rc1102-v35-rev-a1, rc1102-fe-4w-rev-a"
       REVISION      "0811181500Z"
       DESCRIPTION
               "add opcom3500e-b-nms-stm1, opcom600-olp-b, rc3000-15-8rs485, rc3000-15-16c64k, rc3000-15-fe16e1,
               rcvs1000-600b-master, rcvs1000-600b-slave, rcvs1000-600b-remote, rc959-gestm1, rc802-16e1e3-bl"
       REVISION      "0812311500Z"
       DESCRIPTION
               "add rc832-30-fv35-rev-b, rc832-30-fv35-rev-a1, rc831-30-fv35-rev-a1, rc831-60-fv35-rev-a1,rcms2801-30-fv35_rev-a1
               rcms2801-60-fv35_rev-a1"
       REVISION      "0901121600Z"
       DESCRIPTION
               "add rc954-fe4e1-bl-rev-a, rc954-fx4e1-bl-rev-a"
       REVISION      "0902021500Z"
       DESCRIPTION
               "add e-subm-fv35-rev-b, e-subm-2fv35-rev-b"
       REVISION      "0902261600Z"
       DESCRIPTION
               "add rc3000-15-8rs232h, rc3000-6-4e1, rc3000-6-4e1-bl, rc3000-15-8e1-c, rc3000-15-8e&m, 
                 rc3000-15-4e&m, rc3000-6-dxc, rc3000-15-4fxso, rc3000-15-8fxso, rc3000-15-16fxso"
       REVISION      "0903121100Z"
       DESCRIPTION
               "add rcvs1000-616-v-master,rcvs1000-616-vd-master,rcvs1000-616-ve-master, rcvs1000-816-v-slave,
               rcvs1000-816-vd-slave, rcvs1000-816-ve-slave, rcvs1000-816-v-remote, rcvs1000-816-vd-remote,
               rcvs1000-816-ve-remote, rcvs1000-a08f, rcvs1000-501u"
       REVISION      "0903231500Z"
       DESCRIPTION
               "add rc1102-v35-rev-b"
       REVISION      "0904141600Z"
       DESCRIPTION
               "add opcom3500e-4v35, rcvs1000-a04f, rc3000-15-8v24h"
       REVISION      "0907151500Z"
       DESCRIPTION
               "add opcom600-2gemp-slave, opcom600-olp-a, opcom600-olp-b-rev-b, opcom600-olp-b5-rev-a,
               opcom3103-sub-2stm1, opcom3500e-4stm1-m, rcms2911-480fe-rev-a, rcms2911-480fe-rev-a-e1-remote,
               e-subm-4fxso, rc3000-6-240fe-opt, rc3000e, rc1201-4fe4e1t1, rc3000-sub-10fxso, rc3000-sub-8em,
               opcom3103-stm1-bl
               "
       REVISION      "0908131030Z"
       DESCRIPTION
               "add rc3000-15-ht-8fe16e1, opcom3500e-ht-6fe24e1
               "
        
        REVISION      "0908171500Z"
       DESCRIPTION
               "add rc512-fe-rev-a, rc512-fe-ss-slave
               "
        REVISION      "0912171500Z"
       DESCRIPTION
               "add opcom600-otu1-1-rev-b, opcom600-otu1-2-rev-b, opcom600-otu1-4-rev-b-10, opcom3500-b-stm1-s,
               opcom3500e-fe8rs, rc905g-4fe16e1, rc3000-15-8e1-sh-rev-b, rc3000-15-8e1-lh-rev-b, rcvs1000-a-series,
               rcms2802-2t1-fe-rev-a, rcms2802-4t1-fe-rev-a, rcms2802-8t1-fe-rev-a, rcms2802-60-fx-rev-a               
               "
       REVISION      "0912241500Z"
       DESCRIPTION
               "add rc3000e,dlcom2096 sub-modules
               "

       REVISION      "1008120000Z"
       DESCRIPTION
               "add  rcOptTypeSFP(15)
               "
       REVISION      "1009011100Z"
       DESCRIPTION
               "add opcom600-otu2
               "
       REVISION      "1102181447Z"
       DESCRIPTION
               "add opcom600-olp-b-rev-ae, opcom600-olp-b-rev-be5
               "
       REVISION      "1104120000Z"
       DESCRIPTION
               "add opcom600-otu2e-master, opcom600-otu2e-slave, opcom600-otu2e-remote
               "   
       REVISION      "1105170000Z"
       DESCRIPTION
               "change name from 'opcom600-otu2e' to  'opn600-otu2e'
               "
        
       REVISION      "1111020000Z"
       DESCRIPTION
               "
               	add    opcom3500e-240gex4l, opcom3500e-120eosx4l,rcms2903-4e1-4ge
               "
        
       REVISION      "1202290000Z"
       DESCRIPTION
               "
				add OPCOM3500E-BSSH, OPCOM3500E-DSPH, OPCOM3500E-DFPS, RC602-GE(C),iTN125
               "
       
       REVISION      "1203010000Z"
       DESCRIPTION
               "
				add RC3K15H-MULTI
               "
       
       REVISION      "1203050000Z"
       DESCRIPTION
               "
				add RCVS1000-600AL-2FE、RCVS1000-601AL-2FE、Gazelle RM904-PE1（C.00）
                "

       REVISION      "1203221700Z"
       DESCRIPTION
               "
				add OPCOM3500E-EOPFE 、OPCOM3500E-EOP8FX
               "

       REVISION      "1203231130Z"
       DESCRIPTION
               "
				add RP3000H-2IGC、RP3000H-8V24、RP3000H-16E1、RP3000H-32E1-BL、RP3000H-32E1、RP3000H-16E1-REV-C、RP3000H-240Hx2
               "

       REVISION      "1205291500Z"
       DESCRIPTION        
              "
				add ms3esw-2ge-combo、opcom3500e-c-4stm1-m、rc1201-2ge16e1t1-sub-4ge、itn2100-ces-16e1、
				itn2100-16gf、opcom3107-16e1-bl(b.00)、opcom3500e-3ds3e3-slave、opcom3500e-3ds3e3-remote        
               "       

       REVISION      "1206081010Z"
       DESCRIPTION        
              "
				add itn2100-ntu-4gf
              "       
 
       REVISION      "1206261050Z"
       DESCRIPTION        
              "
				exchange module type e-subm-2fv35-rev-b(6427)\e-subm-fv35-rev-b(6428)     
				add RCVS1000-M8R8N(0x200F)、RCVS1000-M8R8U(0x1B3A)
              "       
       REVISION      "1206291550Z"
       DESCRIPTION        
              "
				add itn2100-8gf,itn2100-16fx
              "       
       REVISION      "1207061650Z"
       DESCRIPTION        
              "
				add rh2901-2rs2e1-2fe,opcom3500e-12mt
              "       
       REVISION      "1208071850Z"
       DESCRIPTION        
              "
				add RC956G-FEE1(B),RC956G-FXE1(B),RC956G-FE4E1(A),RC956G-FX4E1(A),RC956G-FE8E1(A),RC956G-FX8E1(A)
				add iTN2100-NTU-2XG
              "   			
       REVISION      "1208231500Z"
       DESCRIPTION        
              "   
			 add TYPE for MSAP JICAI：
					RC956G-FE/FX4E1(B),RC956G-FE/FX8E1(B)
			 add iTN2100-4STM1-GC、OPCOM3500E-8EOS-GC、RC3000-15-DRYC
			 add iTN remote type：
					iTN125-4FE:0x2201
					iTN123-FE:0x2202
					iTN123-4FE:0x2203
					iTN161-GE:0x2204
					iTN161-4GE:0x2205
					iTN161-4GEF:0x2206
					iTN162:0x2207
					iTN163:0x2208 
					iTN165-6GEFS:0x2209
					iTN165-4GE4E1:0x220a
					iTN165-4GEE1:0x220b
					iTN165-4GEV35:0x220c
					iTN165-6GEF:0x220d
					iTN201:0x2210
					iTN201-4GEF:0x2211
					iTN201-2XG:0x2212 
					iTN311-T:0x2213
					iTN311-C:0x2214
					iTN311-W:0x2215 
					RC551E-GE:0x2216
					RC551E-4GE:0x2217
					RC551E-4GEF:0x2218 
					RC551B-FE:0x2219
					RC551B-4FE:0x221a
					RC552-GE(D)：0x221b
			 add OTN type：NXCU,AO2D，EM2D
              "   			
       REVISION      "1208281200Z"
       DESCRIPTION        
              "
				add RC904-PE1(B.10)       
				  RC904-PE1（B.10）-MSTER 0xF4FB 
				  RC904-PE1（B.10）-SLAVE 0xF4FC  
				  RC904-PE1（B.10）-REMOTE 0xF4FD 
             "   			
       REVISION      "1209120930Z"
       DESCRIPTION        
              "
			 add TYPE for MSAP JICAI：
			    iTN2100-WDMCARD(0x1888)
			    iTN2100-GB(0x106E)
			    OPCOM3500E-HSEE(0x130D)			
            "              
       REVISION      "1209131030Z"
       DESCRIPTION        
              "
			add type for MSAP JICAI：
			8B <==>B8 ：RC512_FE_DUAL(REV.B)<==>RC513_FE_DUAL(REV.B)
			AE <==>B9 ：RC512_FE_SINGLE(REV.B)<==>RC513_FE_SINGLE(REV.B)
            "              
       REVISION      "1209131830Z"
       DESCRIPTION        
              "
			add RC581-GE(REV.A) 0x221c
            "              
       REVISION      "1209171330Z"
       DESCRIPTION        
              "
			add type for MSAP JICAI：
			OPCOM600-OMD4(0x1022)<==>iTN2100-4SU-D（0x106F）
			OPCOM600-OMU8(0x1020)<==>iTN2100-8SU-S(0x1070)   
			delete iTN2100-WDMCARD(0x1888)
            "   
       REVISION      "1210151600Z"
       DESCRIPTION        
            "
            add opcom3203 0x2013
            "           
       REVISION      "1210261530Z"
       DESCRIPTION        
            "
            add ITN2100_8EOS_8GF 0x1D06
            "           
       REVISION      "1301061530Z"
       DESCRIPTION        
            "
            add OPCOM3500E-DSEE 0x130E
            "           
       REVISION      "1301231530Z"
       DESCRIPTION        
            "
            add iTN203-4GF 0x221D
            add iTN203-2XG 0x221E
            modify iTN201-4GEF =》iTN201-4GF 
            "           
       REVISION      "1301281530Z"
       DESCRIPTION        
            "
            add RC3000-SUB-RS24  0x1C35
           "           
       REVISION      "1302221630Z"
       DESCRIPTION        
            "
            add MSG series device type.
           "           
       REVISION      "1302251730Z"
       DESCRIPTION        
            "
            add iTN165-4GE4E1S、iTN165-4GEE1S、iTN165-4GEV35S、opcom3500e-8mt  
           "           
       REVISION      "1302271730Z"
       DESCRIPTION        
            "
            add MSG2110-2W
           "           
       REVISION      "1303111800Z"
       DESCRIPTION        
            "
            add SLT8600、SLT8500
            "
       REVISION      "1304171800Z"
       DESCRIPTION        
            "
            add iTN165-4GE4E1-BL、iTN165-4GE4E1S-BL、iTN8600 serials card
            "
       REVISION      "1304271630Z"
       DESCRIPTION        
            "
            add iTN2100-2STM16-M、iTN2100-4STM4-S
            "
       REVISION      "1305211730Z"
       DESCRIPTION        
            "
            add iTN8000-PG16E(A.00)
            "
       REVISION      "1305221630Z"
       DESCRIPTION        
            "
            modify iTN2100-4STM4-S module number。
            "
       REVISION      "1307261630Z"
       DESCRIPTION        
            "
		    1、HSEEC （原型 eose-8fx（REV.C））
			2、iTN167系列：
				iTN167-4GE-L
				iTN167-4GC4E1- BL-S
				iTN167-4GC4E1-BL-L
				iTN167-4GC
				iTN167-4GC4E1-S
				iTN167-4GC4E1-L
			3、iTN8600系统的设备类型：
				电源盘：0x3081
				风扇盘：0x3082
           " 
        REVISION      "1307311630Z"
        DESCRIPTION        
          "
			分配设备类型：             
			iTN 125-4FE-B              
			iTN 123-FE-B               
			iTN 123-4FE-B              
			iTN 161-GE-B               
			iTN 161-4GE-B              
			iTN 161-4GE-B              
			RC551E-GE-B                
			RC551E-4GE-B               
			RC551E-4GE-B               
			RC551B-FE-B                
			RC551B-4FE-B               
			                           
			RC1201_GESTM1              
			ITN2100_CES_STM1           
			ITN2100_CES_STM4           
			ITN2100_CES_SDHM_4VC4      
			ITN2100_CES_SDHM_VC4       
			iTN2100-CES-16E1T1-UNBL    
           
           "     
       REVISION      "1308021130Z"
       DESCRIPTION        
              "
			add RC581-GE(REV.B) 0x2235
            "              
       REVISION      "1308211130Z"
       DESCRIPTION        
              "
			add iTN165-4GE 0x2236
            "              
       REVISION      "1312231746Z"
       DESCRIPTION        
              "
			SLT8500-IAD   (0x1604  或者 5636)
            "              
       REVISION      "1401021628Z"
       DESCRIPTION        
              "
			(0x223C ~ 0x2241: 8764~8769)
			iTN151-DDENL
			iTN151-DDESL
			iTN151-DDDNL
			iTN151-DDDSL
			iTN151-DDVNL
			iTN151-DDVSL
			
            "              
       REVISION      "1401031554Z"
       DESCRIPTION        
              "
			RC3000-SUB-DMT (0x1C36或7222)
            "              
       REVISION      "1401071434Z"
       DESCRIPTION        
              "
			itn401-dblbh(8770或0x2242)
			itn401-bclbh(8771或0x2243)
			iTN8600-PE16(0x1B8D或7053)
			iTN8600-PS4(0x1B8E或7054)
            "              
       REVISION      "1402261106Z"
       DESCRIPTION        
              "
			OPCOM3500E-IAD   (0x1605  或者 5637)
            "              
       REVISION      "1403041006Z"
       DESCRIPTION        
            "
            add ITN2100_8EOS_8GF_622MCARD 0x1D07
            "           
       REVISION      "1403121000Z"
       DESCRIPTION        
            "
            add 　	iTN165-4GE-PWR	0x2254 8788
            "           
       REVISION      "1403171408Z"
       DESCRIPTION        
            "
            add 　	rc152-h(45365)  0xB135
            "           
          ::= { optSysModules 1 }      
 
   RcOptModuleType ::= TEXTUAL-CONVENTION
       STATUS       current
       DESCRIPTION
               "  RAISECOM device module type defination. "
       SYNTAX  INTEGER {      
                notExist(0),
                unknowType(1),

                -- 网管、交换、交叉等独立单盘
                opcom3500-nms(4097),          -- OPCOM3500-NMS OPCOM3500网管盘  0x1001
                rc006-nms(4098),              -- RC006-NMS RC006网管盘  0x1002
                rc006-esw-2ge(4099),          -- RC006-ESW-2GE 以太网汇聚盘 0x1003
                opcom3500e-nms(4100),         -- OPCOM3500-NMS OPCOM3500E网管盘 0x1004
                opcom3500e-nms-stm1(4101),    -- OPCOM3500E-NMS-STM1	OPCOM3500-6网管盘 0x1005
                opcom3500e-b-nms-stm1(4102),  -- OPCOM3500E-B-NMS-STM1	OPCOM3500-6网管盘 0x1006
                opcom3500e-c-nms(4103),       -- OPCOM3500E-C-NMS	OPCOM3500E C版网管盘 0x1007   
                slt8600-b(4104),              -- 原型产品：OPCOM3500E-C-NMS	OPCOM3500E C版网管盘 0x1008   
                slt8500-a(4105),              -- 原型产品：OPCOM3500E-B-NMS	OPCOM3500E B版网管盘 0x1009   
                opcom100-olp-a(4112),         -- OPCOM100-OLP-A 1+1光线路保护卡 0x1010
                opcom100-oau-1b(4113),        -- OPCOM100-OAU-1B 单路光放大卡 0x1011
                opcom600-oau-2b(4114),        -- OPCOM600-OAU-2b 双路光放大卡 0x1012
                rc006-16rs232(4115),          -- RC006-16RS232 16路串口网管卡 0x1013
                ms3esw-ge-t(4116),            -- OPCOM3500E-6 3U机箱以太网汇聚盘，一电 0x1014
                ms3esw-ge-f(4117),            -- OPCOM3500E-6 3U机箱以太网汇聚盘，一光 0x1015
                ms3esw-2ge-t(4118),           -- OPCOM3500E-6 3U机箱以太网汇聚盘，两电 0x1016
                ms3esw-2ge-f(4119),           -- OPCOM3500E-6 3U机箱以太网汇聚盘，两光 0x1017
                sub-pwrm-dc(4120),            --智能电源盘     0x1018
                sub-pwr-dc(4121),	          --非智能电源盘   0x1019
                ms3esw-2ge-combo(4122), 	  --MS3ESW-2GE(REV.B)	OPCOM3500E-6 3U机箱以太网汇聚盘，2个千兆Combo口	0x101A

                opcom600-omu(4128),           -- 光合波卡 0x1020
                opcom600-odu(4129),           -- 光分波卡 0x1021
                opcom600-omd(4130),           -- 光合分波一体卡 0x1022
                sub-ptu-4ge(4131),            -- SUB-PTU-4GE 0x1023
                opcom600-oad-d(4132),         -- 双向光上下路卡 0x1024
                opcom600-oad-s(4133),         -- 单向光上下路卡 0x1025
                opcom600-2gemp(4134),         -- 带保护功能的双千兆子速率复用卡 0x1026
                opcom600-2gemp-s(4135),       -- 带保护功能的双千兆子速率复用卡(远端) 0x1027
                opcom600-otu1-1(4136),        -- 局端1路SFP光转换卡 0x1028
                opcom600-otu1-2(4137),        -- 局端2路SFP光转换卡 0x1029
                opcom600-otu1-4(4138),        -- 局端4路SFP光转换卡 0x102A
                opcom600-ocp1-1(4139),        -- 1路SFP光通道保护卡, 局端 0x102B
                opcom600-ocp1-2(4140),        -- 2路SFP光通道保护卡, 局端 0x102C
                opcom600-olp-b(4141),         -- 1:1光线路保护卡, 局端 0x102D
                opcom600-olp-be5(4142),       -- 1:1光线路保护卡, 局端 0x102E
                
                opcom3500e-8v35(4144),        -- OPCOM3500E-8V35 OPCOM3500E平台的8路V35数据业务盘 0x1030
                opcom3500e-8v24(4145),        -- OPCOM3500E-8V24 OPCOM3500E平台的8路V24数据业务盘 0x1031
                opcom3500e-dxc-ds0(4146),     -- OPCOM3500E-DXC-DS0 OPCOM3500E平台的DS0交叉盘 0x1032
                opcom3500e-4v35(4147),        -- OPCOM3500E-4V35 OPCOM3500E平台的4路V35数据业务盘（带握手信号） 0x1033
                opcom600-2gemp-slave(4148),   -- OPCOM600-2GEMP-SLAVE 带保护功能的双千兆子速率复用卡(局端从) 0x1034
                opcom600-olp-a(4149),         -- OPCOM600-OLP-A 0x1035
                opcom600-olp-b-rev-b(4150),   -- OPCOM600-OLP-B(REV.B) 0x1036
                opcom600-olp-b5-rev-a(4151),  -- OPCOM600-OLP-B5(REV A) 0x1037
                opcom600-otu1-1-rev-b(4152),  -- OPCOM600-OTU1-1(REV B) 0x1038
                opcom600-otu1-2-rev-b(4153),  -- OPCOM600-OTU1-2(REV B) 0x1039
                opcom600-otu1-4-rev-b(4154),  -- OPCOM600-OTU1-4(REV B) 0x103A
                opcom600-olp-b-rev-b10(4155), -- OPCOM600-OLP-B(B.10)0x103B   
                opcom600-olp-b-rev-ae(4156),  -- OPCOM600_OLP_AE 0x103C    
                opcom600-8gem-master(4157),   -- OPCOM600_8GEM,局端主  0x103D
                opcom600-8gem-slave(4158),    -- OPCOM600_8GEM,局端从  0x103E
                opcom600-8gem(4159),  	      -- OPCOM600_8GEM,远端  0x103F
                opcom600-8gemp-master(4160),  -- OPCOM600_8GEMP,局端主  0x1041
                opcom600-8gemp-slave(4161),   -- OPCOM600_8GEMP,局端从  0x1042
                opcom600-8gemp(4162),  	      -- OPCOM600_8GEMP,远端  0x1043
                opcom600-4gemp-master(4163),  -- OPCOM600_8GEMP,局端主  0x1044
                opcom600-4gemp-slave(4164),   -- OPCOM600_8GEMP,局端从  0x1045
                opcom600-4gemp(4165),         -- OPCOM600_8GEMP,远端  0x1046 
                itn2100-gb(4166),             -- iTN2100-WDMCARD(0x1888)对应原型号：WDMCARD(0x1887)
                
                iscom5800-2ge(4192),          -- ISCOM5800-2GE	2GE EPON设备	0x1060
                iscom5800-4e1(4193),          -- ISCOM5800-4E1	4E1 EPON设备	0x1061
                sub-pwrm-ac(4194),	          -- SUB-PWRM-AC		0x1062
                opcom600-otm4(4195),          -- OPCOM600-OTM4		0x1063
                rpd1361-48s12-dc(4196),       -- RPD1361-48S12-DC	iMS100电源盘	0x1064
                rpd1361-48s12-ac(4197),       -- RPD1361-48S12-AC	iMS100电源盘	0x1065
                ipn2100-2igc(4198),           -- iPN2100-2IGC		0x1066
                sub-pwrii-ac(4199),           -- SUB-PWRII-AC		0x1067
                rc002-nms-rev-b(4200),        -- RC002-NMS(B)	MPC852网管盘(扩容)	0x1068
                rc002-nms-rev-c(4201),        -- RC002-NMS(C)	ARM7网管盘(扩容)	0x1069
                sub-pwrmf-dc(4202),           -- SUB-PWRMF-DC		0x106A
                itn2100-tsu(4203),            -- iTN2100-TSU	iTN2100时钟盘	0x106B
                rp3000h-2igc(4204),           -- RP3000H-2IGC	原型产品为：iTN2100-2IGC(0x1066)	0x106C
                rp3000h-8v24(4205),           -- RP3000H-8V24	原型产品为：OPCOM3500E-8V24(0x1031)	0x106D
                itn2100-gb(4206),           -- iTN2100-GB	原型产品为：OPCOM600-OTM4(0x1063)	0x106E
                itn2100-4su-d(4207),           -- iTN2100-4SU-D	原型产品为：OPCOM600-OMD4(0x1022)	0x106E
                itn2100-8su-s(4208),           -- iTN2100-8SU-S	原型产品为：OPCOM600-OMU8(0x1020)	0x1070

                -- SDH盘
                opcom3500-stm1-m(4353),       -- OPCOM3500-STM1-M STM1群路盘  0x1101
                opcom3500-stm4-m(4354),       -- OPCOM3500-STM4-M STM4群路盘  0x1102
                opcom3500-stm1-s(4355),       -- OPCOM3500-STM1-S STM1支路盘  0x1103
                opcom3500-stm4-s(4356),       -- OPCOM3500-STM4-S STM4支路盘  0x1104
                opcom3500e-stm1-m(4357),      -- OPCOM3500-STM4-S STM4支路盘  0x1105
                opcom3500e-stm4-m(4358),      -- OPCOM3500-STM4-S STM4支路盘  0x1106
                opcom3500e-b-stm1-m(4359),    -- OPCOM3500-STM4-S STM4支路盘  0x1107
                opcom3500e-b-stm4-m(4360),    -- OPCOM3500-STM4-S STM4支路盘  0x1108
                opcom3500e-b-2stm4-m(4361),   -- OPCOM3500E-B-2STM4-M STM4双口群路盘  0x1109
                opcom3103-sub-2stm1(4362),    -- OPCOM3103-SUB-2STM1 0x110A
                opcom3500e-4stm1-m(4363),     -- OPCOM3500E-4STM1-M 0x110B
                opcom3500e-b-stm1-s(4364),    -- OPCOM3500E-B-STM1-S STM1支路盘 0x110C
                opcom3500e-c-2stm1-m(4365),   -- OPCOM3500E-C-2STM1-M STM1群路盘 0x110D
                opcom3500e-c-2stm4-m(4366),   -- OPCOM3500E-C-2STM4-M STM4群路盘 0x110E
                opcom3500e-c-stm1-s(4367),    -- OPCOM3500E-C-STM1-S		0x110F
                opcom3500e-4stm1-s(4368),     -- OPCOM3500E-4STM1-S		0x1110
                opcom3500e-c-4stm1-m(4369),   -- OPCOM3500E-C-4STM1-M 0x1111
                
                opcom3500e-fe8rs(4384),       -- OPCOM3500E-FE8RS 0x1120                         																						
                opcom3500e-eot-gestm4(4385),  -- OPCOM3500E-EOT-GESTM4		0x1121                 
                opcom3500e-eot-gestm1(4386),  -- OPCOM3500E-EOT-GESTM1		0x1122                 
                opcom3500e-eot-ge(4387),      -- OPCOM3500E-EOT-GE		0x1123                     																						
                opcom3500e-bssh(4388),        -- 原型产品为：OPCOM3500E-C-STM1-S (0x110F)	0x1124 	   
                
                iTN2100-2STM16-M(4389),   	  -- 2.5G群路盘 0x1125
                iTN2100-4STM4-S(4400),        -- 4口STM4支路板卡 0x1130
                                              
                -- E1盘                       
                opcom3500-16e1(4609),         -- OPCOM3500-16E1   16路E1电支路盘  0x1201
                opcom3500-32e1(4610),         -- OPCOM3500-32E1   32路E1电支路盘  0x1202
                opcom3500e-32e1(4611),        -- OPCOM3500E-32E1	32路E1电支路盘（非平衡）	0x1203
                opcom3500e-3ds3e3-om(4612),   -- OPCOM3500E-3DS3E3-OM		0x1204
                opcom3500e-3ds3e3-p(4613),     -- OPCOM3500E-3DS3E3-P		0x1205
                opcom3500e-3ds3e3(4614),       -- OPCOM3500E-3DS3E3		0x1206
                opcom3500e-16e1-rev-c(4615),  -- OPCOM3500E-16E1-REV-C	16路E1电支路盘（REV.C）	0x1207
                rp3000h-16e1(4616),           -- RP3000H-16E1 	原型产品为：OPCOM3500-16E1(0x1201) 	0x1208
                rp3000h-32e1-bl(4617),        -- RP3000H-32E1-BL	原型产品为：OPCOM3500E-32E1-BL(0x1202)	0x1209
                rp3000h-32e1(4618),           -- RP3000H-32E1	原型产品为：OPCOM3500E-32E1(0x1203)	0x1210
                rp3000h-16e1-rev-c(4619),     -- RP3000H-16E1-REV-C	原型产品为：OPCOM3500E-16E1-REV-C(0x1207)	0x1211

                -- G.SHDSL盘 
                opcom3500e-shdsl-2wx8(4737),  -- OPCOM3500E-SHDSL-2Wx8	G.SHDSL设备	0x1281
                rc1106-fe-2wx8(4738),         -- RC1106-FE-2Wx8 带反向复用，2线对，8单元的G.SHDSL设备	0x1282
                rc1106-fe-2wx8-s(4739),       -- RC1106-FE-2Wx8-S G.SHDSL设备（从模式）	0x1283
                rc3000-15-shdsl-2wx8(4740),   -- RC3000-15-SHDSL-2Wx8	G.SHDSL设备	0x1284
                rc1106e-fe-2wx4(4741),        -- RC1106E-FE-2Wx4 带反向复用，2线对，4单元的G.SHDSL设备	0x1285
                rc1106e-fe-2wx4-s(4742),      -- RC1106E-FE-2Wx4-S G.SHDSL设备（从模式）	0x1286    
                rc1106e-fe-2wx8(4743),        -- RC1106E-FE-2Wx8 带反向复用，2线对，4单元的G.SHDSL设备	0x1287
                rc1106e-fe-2wx8-s(4744),      -- RC1106E-FE-2Wx8-S G.SHDSL设备（从模式）	0x1288                 
                rc1108-shdsl-2wx8(4745),      -- RC1108-SHDSL-2W×8		0x1289
                rc3000-15-16multi(4746),      -- RC3000-15-16MULTI	RC3000-15/6-综合PCM业务盘	0x128A
                rc1103-gshdsl-4w(4747),       -- RC1103-GSHDSL-4W	盒式G.SHDSL设备	0x128B
                rc1103-gshdsl-4w-s(4748),     -- RC1103-GSHDSL-4W-S	盒式G.SHDSL设备（从模式）	0x128C
                
                -- EOS盘
                opcom3500-eos-8fe(4865),      -- OPCOM3500-EOS-8FE 8口EOS电支路盘 0x1301
                opcom3500-eos-8fx(4866),      -- OPCOM3500-EOS-8FE 8口EOS电支路盘 0x1302
                opcom3500-eose-8fx(4867),     -- OPCOM3500-EOSE-8FE 增强型8口EOS光支路盘  0x1303
                opcom3500-8eos-fx(4868),      -- OPCOM3500-8EOS-FX 8口带交换EOS 0x1304
                opcom3500-8eos-fe(4869),      -- OPCOM3500-8EOS-FE 8口带交换EOS 0x1305
                opcom3500-eos-4fe(4870),      -- OPCOM3500-EOS-4FE 4口带交换EOS 0x1306
                opcom3500-eose-4fx(4871),     -- OPCOM3500-EOSE-4FX 增强型的EOS支路盘 0x1307
                opcom3500-4eos-4fe(4872),     -- OPCOM3500-4EOS-4FE 增强型4口EOS光支路盘 0x1308
                opcom3500-4eos-4fx-eos(4873), -- OPCOM3500-4EOS-4FX-EOS 4口带交换EOS电支路盘 0x1309
                opcom3500-4eos-4fx-esw(4874), -- OPCOM3500-4EOS-4FX-ESW 4口带交换EOS电支路盘 0x130A
                opcom3500e-120eosx4l(4875),   -- OPCOM3500-120EOSx4L   0x130b  
                opcom3500e-8eos-gc(4876),     -- OPCOM3500E-8EOS-GC    0x130c
                opcom3500e-hsee(4877),        -- OPCOM3500E-HSEE(0x130D)对应原型号：OPCOM3500-EOSE-8FX (0x1303)															
                opcom3500e-dsse(4878),        -- OPCOM3500E-DSEE（0x130E)原型产品为：OPCOM3500E-EOSE-4FX（B)(0x1307)														
                opcom3500e-hseec(4879),        -- OPCOM3500E-HSEE(0x130F)对应原型号：OPCOM3500-EOSE-8FX (0x1303)															

                -- DSLAM业务盘或设备
                dlcom2096-24adsl(4993),       -- DLCOM2096 24口ADSL卡 0x1381
                dlcom2096-48pots(4994),       -- DLCOM2096 48口POTS卡 0x1382
                dlcom2096-16fe(4995),	      -- DLCOM2096 16口FE卡 0x1383
                dlcom2096-smc-2ge(4997),      -- DLCOM2096 上联子卡，一光一电口 0x1385
                dlcom2096-smc-2ge-t(4998),    -- DLCOM2096 上联子卡，双电口 0x1386
                dlcom2096-smc-2ge-f(4999),    -- DLCOM2096 上联子卡，双光口 0x1387
                dlcom2096-smc-epon(5000),     -- DLCOM2096 上联子卡 EPON 0x1388
                dlcom2096_16vdsl_17a(5001),   -- DLCOM2096_16VDSL_17A	16口类型为17A的VDSL板卡	0x1389																																																																																												
                dlcom2096_16vdsl_30a(5002),   -- DLCOM2096_16VDSL_30A	16口类型为30A的VDSL板卡	0x138A																																																																																												
                dlcom2096_24pots(5003),       -- DLCOM2096_24POTS	24口的POTS板卡	0x138B            																																																																																												
                
                -- 光端机(PDH) 
                rc812-120x2(5121),          -- RC812-120x2  PDH支路盘 0x1401
                rc812-240(5122),            -- RC812 240  PDH支路盘 0x1402
                opcom3500-240x2(5123),      -- OPCOM3500-240x2  PDH支路盘 0x1403
                opcom3500-120x4(5124),      -- OPCOM3500-120x4  PDH支路盘 0x1404
                opcom3500-120hx4(5125),     -- OPCOM3500-120Hx4 PDH支路盘 0x1405
                rc832-120(5126),            -- RC832-120 0x1406
                rc832-240(5127),            -- RC832-240 0x1407
                rc832-120-s(5128),          -- RC832-120 0x1408
                rc832-240-s(5129),          -- RC832-240 0x1409
                rc832-120x2(5130),          -- RC832-120x2 双端口PDH支路盘	0x140A
--                rc832-120x2-s(5131),         RC832-120x2-S 双端口PDH支路盘（作为远端模块）	0x140B
                opcom3500e-p480fe(5132),    -- OPCOM3500E-P480FE 0x140C
                opcom3500e-240hx2(5133),    -- OPCOM3500E-240Hx2 0x140D
                opcom3500e-p480fx(5134),    -- OPCOM3500E-P480FX 0x140E
                rc802-16e1e3-bl(5135),      -- RC802-16E1E3-BL 0x140F
                opcom3500e-240gex4l(5136),	-- OPCOM3500E_240GEx4L 0x1410
                opcom3500e-120x8l(5137),	-- OPCOM3500E-120x8L         0x1411 
                opcom3500e-120fex8l-ge(5138),-- OPCOM3500E-120FE×8L-GE   0x1412       
                opcom3500e-dsph(5139),      -- 	原型产品为：OPCOM3500-120Hx4(0x1405)	0x1413
                rp3000h-240hx2(5140),       -- 	原型产品为：OPCOM3500E-240Hx2(0x140D)	0x1414

                
                -- 光猫业务盘或设备
                opcom3500-30x8(5249),       -- OPCOM3500-30x8 8端口光猫支路盘 0x1481
                
                -- 以太网复用器盘
                rcms2812-120fe(5377),       -- RCMS2812-120FE(Rev A) 0x1501
                rcms2812-240fe(5378),       -- RCMS2812-240FE(Rev A) 0x1502
                rcms2812-480fe(5379),       -- RCMS2812-480FE(Rev A) 0x1503
                opcom3500-p240eos(5380),    -- OPCOM3500-P240EOS(Rev A) 0x1504
                rcms2812-120fe-s(5381),     -- RCMS2812-120FE-S(Rev A) 0x1505
                rcms2812-240fe-s(5382),     -- RCMS2812-240FE-S(Rev A) 0x1506
                rcms2812-480fe-s(5383),     -- RCMS2812-480FE-S(Rev A) 0x1507
                opcom3500-120eosx4(5384),   -- OPCOM3500-120EOSx4(Rev A) 0x1508
                rcms2802-120fe(5385),       -- RCMS2802-120FE(Rev A) 0x1509
                rcms2802-240fe(5386),       -- RCMS2802-240FE(Rev A) 0x150A
                rcms2802-120fe-s(5387),     -- RCMS2802-120FE-S(Rev A) 0x150B
                rcms2802-240fe-s(5388),     -- RCMS2802-240FE-S(Rev A) 0x150C
                opcom3500-p240fe(5389),     -- OPCOM3500-P240FE(Rev A) 0x150D
                opcom3500e-120feX4-ge(5390),-- OPCOM3500E-120FEx4-GE(Rev A) 0x150E
                rcms2802-480ge-bl(5391),    -- RCMS2802-480GE-BL(Rev A) 0x150F
                rcms2802-480ge-bl-s(5392),  -- RCMS2802-480GE-BL-S(Rev A) 0x1510
                rcms2802-240ge-bl(5393),    -- RCMS2802-240GE-BL(Rev A) 0x1511
                rcms2802-240ge-bl-s(5394),  -- RCMS2802-240GE-BL-S(Rev A) 0x1512
                opcom3500e-dfps(5395),      -- 对应原型号：OPCOM3500-120EOSx4(0x1508)	0x1513

                -- PCM盘
                rc3102(5633),               -- RC3102   PCM支路盘 0x1601
                rc3202(5634),               -- RC3202   PCM支路盘 0x1602
                rcma502(5635),              -- PCM支路盘，原型号：RC3202	0x1603
                slt8500-iad(5636),          -- SLT8500-IAD,可以插在ITN2100、OPCOM3500E-12、OPCOM2500E-6、SLT8500、SLT8600中
                opcom3500e-iad(5637),       -- SLT8500-IAD的原型板卡

                -- 协转盘
                opcom3500-eop-fxe1x8(5889), -- OPCOM3500-EOP-FXE1x8   协转支路盘  0x1701
                opcom3500-eop-fe16e1(5890), -- OPCOM3500-EOP-FE16E1   协转支路盘  0x1702
                opcom3500-eops-8e1(5891),   -- OPCOM3500-EOPS-8E1     协转支路盘  0x1703
                opcom3500-eop-fe8e1(5892),  -- OPCOM3500-EOP-FE8E1    协转支路盘  0x1704                
                opcom3500-eop-fee1X8(5893), -- OPCOM3500-EOP-FEE1x8	协转支路盘	0x1705
                opcom3500e-ht-6fe24e1(5894), -- OPCOM3500E-HT-6FE24E1 0x1706
                opcom3500e-eop3fe(5895),    -- OPCOM3500E-EOP3FE 0x1707
                opcom3500e-eopfe(5896),     -- OPCOM3500E-EOPFE 0x1708
                opcom3500e-eop8fx(5897),    -- OPCOM3500E-EOP8FX 0x1709
                                        
                -- 收发器业务盘
                opcom3500-4fx(6017),         -- OPCOM3500-4FX   4口光纤收发器（上交换盘） 0x1781
                rc532-feX4(6018),            -- RC532-FEx4   四路可远端管理的10/100M以太网光纤收发器 0x1782
                opcom3500e-8fx(6019),        -- OPCOM3500E-8FX 8口光纤收发器（上交换盘） 0x1783

                -- 反向复用器
                opcom3500-eop-fe8e1x2-r(6145),  -- OPCOM3500-EOP-FE8E1x2-R  8E1反向复用器 0x1801
                rc956-fe4e1-r(6146),            -- RC956-FE4E1-R  4E1反向复用器 0x1802
                rc956-fe8e1-r(6147),            -- RC956-FE8E1-R  8E1反向复用器 0x1803
                rc953e-3fe16e1(6148),           -- RC953E-3FE16E1 反向复用器  0x1804
                rc956-fx8e1-r(6149),            -- RC956-FX8E1-R  8E1反向复用器 0x1805
                rc959-4fe16e1(6150),            -- RC959-4FE16E1  4FE 16E1台式反向复用器 0x1806
                rc905g-4fe16e1(6151),           -- RC905G-4FE16E1  与RC959-4FE16E1完全相同的定制设备 0x1807
                rc956-fe8e1-rev-b(6152),        -- RC956-FE8E1(REV B)		0x1808
                ipn2100-8fx(6153),              -- iPN2100-8FX					0x1809
                rc959-gestm1-rev-b(6154),       -- RC959-GESTM1(REV B)	0x180A
	
                -- CWDM/OTN系列                
                opcom600-otu2(6273),           -- 10G业务速率的光转换卡, 一路, XFP模块 0x1881
                opn600-otu2e-master(6274),   -- 带FEC功能的10G OTN光转发器，局端主, 0x1882
                opn600-otu2e-slave(6275),    -- 带FEC功能的10G OTN光转发器，局端从，0x1883
                opn600-otu2e-remote(6276),   -- 带FEC功能的10G OTN光转发器，远端，0x1884
                opcom600-obp-a(6277),        -- OPCOM600-OBP-A		0x1885
                opcom600-obp-b(6278),        -- OPCOM600-OBP-B		0x1886
                wdmcard(6279),               -- WDMCARD				0x1887    

                -- 光端机扩展槽子模块
                subm-4e1(6401),             -- SUBM-4E1 非智能4E1支路子模块 0x1901
                e-subm-2e1(6402),           -- E-SUBM-2E1 非智能2E1支路子模块 0x1902
                e-subm-4e1-bl(6403),        -- E-SUBM-4E1-BL 非智能4E1支路子模块  0x1903
                subm-e(6416),               -- SUBM-E 成帧10BASE-T子模块  0x1910
                subm-fe(6417),              -- SUBM-FE  10/100BASE-T子模块  0x1911
                subm-v35(6418),             -- SUBM-V35   V35子模块 0x1912
                subm-fv35-rev-a(6419),      -- SUBM-FV35(REV.A)   成帧V35子模块 0x1913
                subm-e-rev-b(6420),         -- SUBM-E(REV.B)  以太网子模块  0x1914
                subm-fv35-rev-b(6421),      -- SUBM-FV35(REV.B)   成帧V35子模块 0x1915
                e-subm-2fv35(6422),         -- E-SUBM-2FV35(REV.A) 0x1916
                e-subm-2fe(6423),           -- E-SUBM-2FE(REV.A)   0x1917
                e-subm-fe4e1(6424),         -- E-SUBM-FE4E1(REV.A) 0x1918
                e-subm-fv35(6425),          -- E-SUBM-FV35(REV.A) 0x1919
                e-subm-fv35-rev-b(6427),   -- E-SUBM-FV35(REV.B) 0x191B
                e-subm-2fv35-rev-b(6428),    -- E-SUBM-2FV35(REV.B) 0x191C
                e-subm-4fxso(6429),         --  E-SUBM-4FXSO 0x191D

                -- RC3000-15设备局端板卡
                rc3000-15-dxc(6657),        -- 交叉盘 0x1A01
                rc3000-15-8e1(6658),        -- 8个E1的接入板卡  0x1A02
                rc3000-15-240X1-opt(6659),  -- 单光口8E1接入板卡  0x1A03
                rc3000-15-120X2-opt(6660),  -- 双光口2x4E1接入板卡  0x1A04
                rc3000-15-30X8-opt(6661),   -- 8光口8x1E1接入板卡 0x1A05
                rc3000-15-32fxs(6662),      -- 32路语音用户FXS接口卡  0x1A06  
                rc3000-15-32fxo(6663),      -- 32路语音中继FX0接口卡  0x1A07
                rc3000-15-16e-m2-4(6664),   -- 16路语音中继E&M 2线和4线接口卡 0x1A08
                rc3000-15-8v35(6665),       -- 8路V35数据接口卡 0x1A09
                rc3000-15-8eth(6666),       -- 8端口8方向以太网接口卡 0x1A0A            
                rc3000-15-16rs232(6667),    -- 16路RS232串行数据接口卡  0x1A0B          
                rc3000-15-16rs422(6668),    -- 16路RS422串行数据接口卡  0x1A0C          
                rc3000-15-16rs485(6669),    -- 16路RS485串行数据接口卡  0x1A0D          
                rc3000-15-30X4-g(6670),     -- 4路G.接口卡（8路可以放下时为8路）  0x1A0E
                rc3000-15-16fxs(6671),      -- 16路语音用户FXS接口卡  0x1A0F  
                rc3000-15-16fxo(6672),      -- 16路语音中继FX0接口卡  0x1A10
                rc3000-15-16fxs-16fxo(6673), -- 16路语音用户FXS接口卡+16路语音中继FX0接口卡  0x1A11
                rc3000-15-fxso(6674),       -- FXS/FSO接口卡,路数由订货信息确定  0x1A12
                rc3000-15-480fe-opt(6675),  -- RC3000-15-480FE-OPT	16路E1+1路以太网	0x1A13
                rc3000-15-p480fe-opt(6676), -- RC3000-15-P480FE-OPT	6路E1+1路以太网(带保护倒换功能)	0x1A14
                rc3000-15-8v24(6677),       -- RC3000-15-8V24	8路V24接口卡	0x1A15
                rc3000-15-shdsl-2wX8(6678), -- RC3000-15-SHDSL-2Wx8	8路SHDSL接入板	0x1A16
                rc3000-15-240fe-opt(6679),  -- RC3000-15-240FE-OPT	8路E1+1路以太网	0x1A17
                rc3000-15-p240fe-opt(6680), -- RC3000-15-P240FE-OPT	8路E1+1路以太网（具有保护倒换功能）	0x1A18
                rc3000-15-8rs485(6681),     -- RC3000-15-8RS485	8路RS485串行数据接口卡	0x1A19
                rc3000-15-16c64k(6682),     -- 同向64k接口盘	0x1A1A
                rc3000-15-8rs232h(6683),    -- 8路支持握手信号的RS-232数据盘	0x1A1B
                rc3000-6-4e1(6684),         -- 4E1接口盘	0x1A1C
                rc3000-6-4e1-bl(6685),      -- 4E1平衡口接口盘	0x1A1D
                rc3000-15-8v24h(6686),      -- 0x1A1E
                rc3000-6-240fe-opt(6687),   -- RC3000-6-240FE-OPT 0x1A1F 
                rc3000-15-ht-8fe16e1(6688),   -- RC3000-15-HT-8FE16E1 0x1A20
                
                rc3000-15-v5(6704),         -- 有8个E1接口，可支持V5.2协议  0x1A30      
                rc3000-15-stm1(6705),       -- 155M SDH 上联接口盘支持32E1  0x1A31  
                rc3000-15-8ethp(6706),      -- 0x1A32
                rc3000-15-fe16e1(6707),     -- 16路以太网汇聚到前面板FE电接口，或通过背板向ESW-2GE盘汇聚	0x1A33
                rc3000-15-8e1-c(6708),      -- 0x1A34
                rc3000-15-8e-m(6709),       -- RC3000-15-8E&M, 0x1A35
                rc3000-15-4e-m(6710),       -- RC3000-15-4E&M, 0x1A36
                rc3000-6-dxc(6711),         -- RC3000-6-DXC, 0x1A37
                rc3000-15-4fxso(6712),      -- RC3000-15-4FXSO, 0x1A38
                rc3000-15-8fxso(6713),      -- RC3000-15-8FXSO, 0x1A39
                rc3000-15-16fxso(6714),     -- RC3000-15-16FXSO, 0x1A3A
                rc3000e(6715),              -- RC3000E, 0x1A3B 
                rc3000-15-8e1-sh-rev-b(6716), -- RC3000-15-8E1-SH(REV.B), 8个E1的接入板卡（短距）0x1A3C
                rc3000-15-8e1-lh-rev-b(6717), -- RC3000-15-8E1-LH(REV.B), 8个E1的接入板卡（长距）0x1A3D
                rc3000-15-p240-4fe(6718),  		-- RC3000-15-P240-4FE	RC3000-15-P240FE-OPT的升级产品，增加了向用户提供4端口以太业务的功能	0x1A3E
                rc3000-15-dxc-rev-h(6719),    -- RC3000-15-DXC(H)		0x1A3F
                rc3000-15-2stm1-m-rev-h(6720),-- RC3000-15-2STM1-M(H)		0x1A40
                rc3000-15-2stm4-m-rev-h(6721),-- RC3000-15-2STM4-M(H)		0x1A41
                rc3000-15-esw-4ge(6722),   		-- RC3000-15-ESW-4GE		0x1A42
                rc3000-15-12mt(6723),      		-- RC3000-15-12MT		0x1A43
                rc3000-15-p240x2l(6724),   		-- RC3000-15-P240x2L		0x1A44
                rc3000-rev-c(6725),           -- RC3000(C)		0x1A45  
                rc3000-15-multi-rev-h(6726),  -- RC3K15H-MULTI  0x1A46
                rc3000-15-stm1-rev-b(6727),   -- RC3000-15-STM1(B)		0x1A47
                opcom3500e-12mt(6728),        -- OPCOM3500E-12MT		0x1A48
                opcom3500e-15-dryc(6729),     --  RC3000-15-DRYC		0x1A49
                opcom3500e-8mt(6730),         -- OPCOM3500E-8MT		0x1A4A

                
                -- RCMA5xxx系列
                rcma5115-dxc(6736),           -- 对应原型号RC3000-15-DXC	0x1A50
                rcma5115-120x2-opt(6737),     -- 对应原型号RC3000-15-120×2-OP	0x1A51
                rcma5115-16em(6738),          -- 对应原型号RC3000-15-16E&M	0x1A52
                rcma5115-8em(6739),           -- 对应原型号RC3000-15-8E&M	0x1A53
                rcma5115-4em(6740),           -- 对应原型号RC3000-15-4E&M	0x1A54
                rcma5115-32fxo(6741),          -- 对应原型号RC3000-15-32FXO	0x1A55
                rcma5115-32fxs(6742),          -- 对应原型号RC3000-15-32FXS	0x1A56
                rcma5115-16fxs16o(6743),       -- 对应原型号RC3000-15-16FXS16O	0x1A57
                rcma5115-16fxo(6744),          -- 对应原型号RC3000-15-16FXO	0x1A58
                rcma5115-16fxs(6745),          -- 对应原型号RC3000-15-16FXS	0x1A59
                rcma5115-fxso(6746),           -- 对应原型号RC3000-15-FXSO	0x1A5A
                rcma5115-16fxso(6747),         -- 对应原型号RC3000-15-16FXSO	0x1A5B
                rcma5115-8fxso(6748),          -- 对应原型号RC3000-15-8FXSO	0x1A5C
                rcma5115-4fxso(6749),          -- 对应原型号RC3000-15-4FXSO	0x1A5D
                rcma5115-8e1(6750),            -- 对应原型号RC3000-15-8E1	0x1A5E
                rcma5115-8e1c(6751),           -- 对应原型号RC3000-15-8E1C	0x1A5F
                rcma5115-8e1-sh(6752),         -- 对应原型号RC3000-15-8E1-SH	0x1A60
                rcma5115-8e1-lh(6753),         -- 对应原型号RC3000-15-8E1-LH	0x1A61
                rcma5115-8eth(6754),           -- 对应原型号RC3000-15-8ETH	0x1A62
                rcma5115-8ethp(6755),          -- 对应原型号RC3000-15-8ETHP	0x1A63
                rcma5115-16rs232(6756),        -- 对应原型号RC3000-15-16RS232	0x1A64
                rcma5115-8rs485(6757),         -- 对应原型号RC3000-15-8RS485	0x1A65
                rcma5115-8v24(6758),           -- 对应原型号RC3000-15-8V24	0x1A66
                rcma5115-8v35(6759),           -- 对应原型号RC3000-15-8V35	0x1A67
                rcma5115-fe16e1(6760),         -- 对应原型号RC3000-15-FE16E1	0x1A68
                rcma5115-ht-8fe16e1(6761),     -- 对应原型号RC3000-15-HT-8FE16E1	0x1A69
                rcma5115-stm1(6762),           -- 对应原型号RC3000-15-STM1	0x1A6A
                rcma5106-4e1(6763),            -- 对应原型号RC3000-6-4E1	0x1A6B
                rcma5106-4e1-bl	(6764),        -- 对应原型号RC3000-6-4E1-BL	0x1A6C
                rcma5106-dxc(6765),            -- 对应原型号RC3000-6-DXC	0x1A6D
                
                -- 视频光端机
                rcvs1000-601ax3(6913),       -- RCVS1000-601A×3  0x1B01, 三路RCVS1000局端卡式视频光端机
                rcvs1000-60x(6914),          -- RCVS1000-60x  0x1B02, RCVS1000局端多层卡式视频光端机
                rcvs1000-50x(6915),          -- RCVS1000-50x  0x1B03, RCVS1000远端多层台式视频光端机
                rcvs1000-601b(6916),         -- RCVS1000-601B  0x1B04, 视频光端机
                rcvs1000-602b(6917),         -- RCVS1000-602B  0x1B05, 视频光端机
                rcvs1000-501b(6918),         -- RCVS1000-501B  0x1B06, 远端视频光端机
                rcvs1000-502b(6919),         -- RCVS1000-502B  0x1B07, 远端视频光端机
                rcvs1000-601b-s(6920),       -- RCVS1000-601B-S	0x1B08 视频光端卡式接收机, 无扩展卡, 1路视频(远端)	
                rcvs1000-602b-s(6921),       -- RCVS1000-602B-S	0x1B09 视频光端卡式接收机, 无扩展卡, 2路视频(远端)	
                rcvs1000-608b(6922),         -- RCVS1000-608B  0x1B0A, 远端视频光端机
                rcvs1000-808b(6923),         -- RCVS1000-808B  0x1B0B, 远端视频光端机
                rcvs1000-808b-s(6924),       -- RCVS1000-808B-S  0x1B0C, 远端视频光端机
                rcvs1000-600b-master(6925),  -- RCVS1000-600B-MASTER  0x1B0D, RCVS1000-600B主设备作为局端
                rcvs1000-600b-slave(6926),   -- RCVS1000-600B-SLAVE  0x1B0E, RCVS1000-600B从设备作为局端
                rcvs1000-600b-remote(6927),  -- RCVS1000-600B-REMOTE  0x1B0F, RCVS1000-600B从设备作为远端
                rcvs1000-616-v-master(6928), -- RCVS1000-616-V-MASTER  0x1B10
                rcvs1000-616-vd-master(6929), -- RCVS1000-616-VD-MASTER  0x1B11
                rcvs1000-616-ve-master(6930), -- RCVS1000-616-VE-MASTER  0x1B12
                rcvs1000-816-v-slave(6931),  -- RCVS1000-816-V-SLAVE  0x1B13
                rcvs1000-816-vd-slave(6932), -- RCVS1000-816-VD-SLAVE  0x1B14
                rcvs1000-816-ve-slave(6933), -- RCVS1000-816-VE-SLAVE  0x1B15
                rcvs1000-816-v-remote(6934), -- RCVS1000-816-V-REMOTE  0x1B16
                rcvs1000-816-vd-remote(6935), -- RCVS1000-816-VD-REMOTE  0x1B17
                rcvs1000-816-ve-remote(6936), -- RCVS1000-816-VE-REMOTE  0x1B18
                rcvs1000-a08f(6937),         -- RCVS1000-A08F  0x1B19
                rcvs1000-501u(6938),         -- RCVS1000-501U  0x1B1A
                rcvs1000-a04f(6939),         -- RCVS1000-A04F  0x1B1B
                rcvs1000-a-series(6940),     -- RCVS1000-A-Series 0x1B1C
               rcvs1000-616ap-master(6941), -- RCVS1000-616AP-MASTER	局端主	0x1B1D
               rcvs1000-616ap-slave(6942),  -- RCVS1000-616AP-SLAVE	局端从	0x1B1E
               rcvs1000-616ap-remote(6943), -- RCVS1000-616AP-REMOTE	远端从	0x1B1F
               rcvs1000-a16fp-master(6944), -- RCVS1000-A16FP-MASTER	局端主	0x1B20
               rcvs1000-a16fp-slave(6945),  -- RCVS1000-A16FP-SLAVE	局端从	0x1B21
               rcvs1000-a16fp-remote(6946), -- RCVS1000-A16FP-REMOTE	远端从	0x1B22
               rcvs1000-d0r0a-master(6947), -- RCVS1000-D0R0A-MASTER	数据扩展盘局端主	0x1B23
               rcvs1000-d0r0a-slave(6948),  -- RCVS1000-D0R0A- SLAVE	数据扩展盘局端从	0x1B24
               rcvs1000-d8r0a-master(6949), -- RCVS1000-D8R0A-MASTER	视频扩展盘局端主	0x1B25
               rcvs1000-d8r0a-slave(6950),  -- RCVS1000-D8R0A- SLAVE	视频扩展盘局端从	0x1B26
               rcvs1000-c0r0np-up-2dd5-2fe-master(6951),        -- RCVS1000-C0R0NP/UP-2DD5-2FE- MASTER	独立基盘局端主	0x1B27
               rcvs1000-c0r0np-up-2dd5-2fe-slave(6952),         -- RCVS1000-C0R0NP/UP-2DD5-2FE- SLAVE	独立基盘局端从	0x1B28
               rcvs1000-c0r0np-up-2dd5-16e1-2fe-ge-master(6953),-- RCVS1000-C0R0NP/UP- 2DD5-16E1-2FE-GE-MASTER	基盘+E1扩展盘局端主	0x1B29
               rcvs1000-c0r0np-up-2dd5-16e1-2fe-ge-slave(6954), -- RCVS1000-C0R0NP/UP- 2DD5-16E1-2FE-GE-SLAVE	基盘+E1扩展盘局端从	0x1B2A
               rcvs1000-cxdx(6955),         -- RCVS1000-CXDX	RCVS1000-C0R0AP作为远端设备（包括基盘）	0x1B2B
               rcvs1000-501a-fe(6956),      -- RCVS1000-501A-FE		0x1B2C
               rcvs1000-501a-fe-1rd5(6958), -- RCVS1000-501A-FE-1RD5		0x1B2E
               rcvs1000-601al-fe(6959),     -- RCVS1000-601AL-FE		0x1B2F
               rcvs1000-601al-fe-1rd5(6960),-- RCVS1000-601AL-FE-1RD5		0x1B30
               rcvs1000-501a-4fe(6961),     -- RCVS1000-501A-4FE		0x1B31
               rcvs1000-500a-fe(6962),      -- RCVS1000-500A-FE		0x1B32
               rcvs1000-500a-4fe(6964),     -- RCVS1000-500A-4FE		0x1B34
               rcvs1000-600al-fe(6965),     -- RCVS1000-600AL-FE		0x1B35
               rcvs1000-500a-fe-1rd5(6966), -- RCVS1000-500A-FE-1RD5		0x1B36
               rcvs1000-600al-fe-1rd5(6967),-- RCVS1000-600AL-FE-1RD5		0x1B37
               rcvs1000-500a-8fe(6968),      -- RCVS1000-500A-8FE	台式数据光端机	0x1B38
               rcvs1000-501a-8fe(6969),      -- RCVS1000-501A-8FE	单路视频发射机	0x1B39     
               rcvs1000-m8r8u(6970),         -- RCVS1000-M8R8U,台式警用多业务光端机,被RCVS1000-M8R8N管理  0x1B3A
                            
                -- TDMoIP
                rc1201-4fe4e1t1(7041),        -- RC1201-4FE4E1T1 0x1B81
               rc1201-2fev35(7042),           -- RC1201-2FEV35		0x1B82
               rc1201-2fee1t1(7043),          -- RC1201-2FEE1T1		0x1B83
               rc1201-2ge16e1t1(7044),        -- RC1201-2GE16E1T1	0x1B84
               rc1201-2ge16e1t1-sub-4ge(7045),-- RC1201-2GE16E1T1-SUB-4GE		0x1B85
               itn2100-ces-16e1(7046),        -- iTN2100-CES-16E1		0x1B86
			   rc1201_gestm1(7047),             
			   itn2100_ces_stm1(7048),          
			   itn2100_ces_stm4(7049),          
			   itn2100_ces_sdhm_4vc4(7050),     
			   itn2100_ces_sdhm_vc4(7051),      
			   itn2100-ces-16e1t1-unbl(7052),   
			   itn8600-pe16(7053),   
			   itn8600-ps4(7054),   

                
                -- 映射RC3000E子卡
                rc3000e-up-4e1(7169),        --RC3000E-UP-4E1 上行接口卡类型	0x1C01
                rc3000e-up-4e1-bl(7170),     --RC3000E-UP-4E1-BL 上行接口卡类型	0x1C02
                rc3000e-up-8e1(7171),        --RC3000E-UP-8E1 上行接口卡类型	0x1C03
                rc3000e-up-8e1-bl(7172),     --RC3000E-UP-8E1-BL 上行接口卡类型	0x1C04
                
                rc3000e-up-opt-fe(7189),     --RC3000E-UP-OPT-FE 上行接口卡类型	0x1C15
                rc3000e-up-opt-fe2e1(7190),  --RC3000E-UP-OPT-FE2E1 上行接口卡类型	0x1C16
                rc3000e-up-opt-fe4e1(7191),  --RC3000E-UP-OPT-FE4E1 上行接口卡类型	0x1C17
                
                rc3ke-sub-empty(7200),       --空卡 0X1c20
                rc3ke-sub-fxs-8(7201),       --8FXS卡 0X1c21
                rc3ke-sub-fxo-8(7202),       --8FXO卡 0X1c22
                rc3ke-sub-fxo-fxs-8(7203),   --8FXSO卡 0X1c23
                rc3ke-sub-em2-8(7204),       --8EM2 0X1c24
                rc3ke-sub-em4-4(7205),       --4EM4 0X1c25
                rc3ke-sub-v35-1(7206),       --DV35卡 0X1c26
                rc3ke-sub-v24-4(7207),       --DV24卡 0X1c27
                rc3ke-sub-eth10m-1(7208),    --ETH10M 0X1c28
                rc3ke-sub-rs232-8(7209),     --8RS232 0X1c29
                rc3ke-sub-rs422-8(7210),     --8RS422 0X1c2a
                rc3ke-sub-magtele-8(7211),   --8MAGTELE卡 0X1c2b
                rc3ke-sub-dsr-8(7212),       --fxs极性可反转卡8通道24v 0X1c2c
                rc3ke-sub-rs485-8(7213),     --8452 0X1c2d
                rc3ke-sub-dsr-4(7214),       --fxs极性可反转卡4通道48v 0X1c2e
                rc3ke-sub-eth10-100m-1(7215),--ETH10-100卡 0X1c2f
                rc3ke-sub-eth10-100m-2(7216),--2ETH10-100卡 0X1c30
                rc3ke-sub-dc64k-4(7217),     --c64k卡 0X1c31
                rc3000-sub-10fxso(7218),     -- RC3000-SUB-10FXSO 下行接口卡类型 0x1C32
                rc3000-sub-8em(7219),        -- RC3000-SUB-8EM 下行接口卡类型 0x1C33
                rc3000-sub-dethx2(7220),     -- RC3000-SUB-DETHX2  0x1C34  
                rc3000-sub-rs24(7221),       -- RC3000-SUB-RS24 0x1C35
                rc3000-sub-dmt(7222),       -- RC3000-SUB-DMT 0x1C36
                
                -- itn2100业务子卡
                itn2100-16gf(7424),          --	iTN2100-16GF		0x1D00   
                itn2100-ntu-4gf(7425),       -- iTN2100-NTU-4GF     0x1D01        
                itn2100-8gf(7426),           -- iTN2100-8GF         0x1D02
                itn2100-16fx(7427),          -- iTN2100-16FX        0x1D03
                itn2100-ntu-2xg(7428),       -- iTN2100-NTU-2XG     0x1D04
                itn2100-4STM1-GC(7429),      -- iTN2100-4STM1-GC    0x1D05   
                itn2100-8eos-8gf(7430),      -- ITN2100_8EOS_8GF    0x1D06  
                itn2100-8eos-8gf-622m(7431),      -- ITN2100_8EOS_8GF_622MCARD    0x1D07  
                
                -- 带有IPRAN功能的板卡业务子卡
                iTN8000-PG16E(7680),         -- iTN8000-PG16E(A.00) 0x1E00
                
                -- 独立台式设备
                rc702c(8193),                -- RC702 REV.C 单口EOS设备 0x2001
                opcom3105(8194),             -- OPCOM3105 小型MSAP设备 0x2002
                rc702-ge-stm4(8195),         -- 0x2003
                opcom3107(8196),             -- 0x2004
                rc959-gestm1(8197),          -- 0x2005
                opcom3103-stm1-bl(8198),     -- OPCOM3103-STM1-BL 0x2006
                opcom3100(8199),              -- OPCOM3100		0x2007
                opcom3101(8200),              -- OPCOM3101		0x2008
                opcom3102(8201),              -- OPCOM3102		0x2009
                opcom3109(8202),              -- OPCOM3109		0x200A
                opcom3103-sub-8eos-2ge(8203), -- OPCOM3103-SUB-8EOS-2GE		0x200B
                rc953eb-gestm1(8204),         -- RC953EB-GESTM1	rc953e-gestm1 B版设备	0x200C
                opcom3103-sub-2ds3e3(8205),   -- OPCOM3103-SUB-2DS3E3		0x200D
                opcom3105-155-8e1-rev-b(8206),-- OPCOM3105-155-8E1（REV.B）		0x200E
                rcvs1000-m8r8n(8207),         -- RCVS1000-M8R8N,台式警用多业务光端机,独立网元 0x200F
                opcom3107-16e1-bl(8209),      -- OPCOM3107-16E1-BL (B.00)		0x2011
                opcom3109-8e1(8210),		  -- OPCOM3109-8E1（REV.A)		0x2012
                opcom3203(8211),		      -- opcom3203（REV.A)		0x2013

                
                -- 网关产品（软件六部开发的）
                msg2110-4w(8449),               -- MSG2110	企业网关2/4线	0x2101
                msg2110-8w(8450),               -- MSG2110	企业网关8线	0x2102
                msg2300-2gf-ac(8451),	        -- 光口上行     0x2103		
                msg2200-2gf-ac(8452),	        -- 光口上行     0x2104		
                msg2210-c-ac(8453),		        -- 光口上行     0x2105		
                msg2210-w-ac(8454),		        -- 光口上行     0x2106		
                msg2210-t-ac(8455),		        -- 光口上行     0x2107		
                msg2210-gf-cdma2-11n-ac(8456),  -- 光口上行     0x2108		
                msg2210-gf-wcdma-11n-ac(8457),	-- 光口上行     0x2109		
                msg2210-gf-td-11n-ac(8458),		-- 光口上行     0x210A		
                msg2210-gf-tdlte-11n-ac(8459),	-- 光口上行     0x210B		
                msg2100e-gf-8v(8460), 		    -- 光口上行     0x210C		
                msg1200-gec(8461),	            -- 可电可光上行 0x210D		
                msg2100-gec-8v-b(8462),	        -- 可电可光上行 0x210E		
                msg2200-gegf-ac(8463),	        -- 可电可光上行 0x210F		
                msg2300-gegf-ac(8464), 	        -- 可电可光上行 0x2110		
                msg2300-bm3-gegf(8465),	        -- 可电可光上行 0x2111		
                msg2300-2ge-ac(8466),	        -- 电口上行	   0x2112		
                msg2200-2ge-g-ac(8467),	        -- 电口上行	   0x2113		
                msg2200-2ge-ac(8468),	        -- 电口上行	   0x2114		
                msg2100e-ge-8v(8469), 	        -- 电口上行	   0x2115		
                msg2100(8470),	                -- 电口上行	   0x2116		
                msg2200-t1(8471),	            -- 电口上行	   0x2117		
                msg2200-t1-b(8472),	            -- 电口上行	   0x2118		
                msg2300-bm3-2ge(8473), 	        -- 电口上行	   0x2119		
                msg2110-2w(8474),               -- MSG2110	企业网关2线	0x211A
               
                -- EDD设备
                itn125-4fe(8705),                 -- iTN125	0x2201 
                itn123-fe(8706),                  -- iTN123-FE:0x2202
                itn123-4fe(8707),                 -- iTN123-4FE:0x2203
                itn161-ge(8708),                  -- iTN161-GE:0x2204
                itn161-4ge(8709),                 -- iTN161-4GE:0x2205
                itn161-4gef(8710),                -- iTN161-4GEF:0x2206
                itn162(8711),                     -- iTN162:0x2207
                itn163(8712),                     -- iTN163:0x2208 
                itn165-6gefs(8713),               -- iTN165-6GEFS:0x2209
                itn165-4ge4e1(8714),              -- iTN165-4GE4E1:0x220a
                itn165-4gee1(8715),               -- iTN165-4GEE1:0x220b
                itn165-4gev35(8716),              -- iTN165-4GEV35:0x220c
                itn165-6gef(8717),                -- iTN165-6GEF:0x220d
                itn201(8720),                     -- iTN201:0x2210
                itn201-4gf(8721),                 -- iTN201-4GF:0x2211
                itn201-2xg(8722),                 -- iTN201-2XG:0x2212 
                itn311-t(8723),                   -- iTN311-T:0x2213
                itn311-c(8724),                   -- iTN311-C:0x2214
                itn311-w(8725),                   -- iTN311-W:0x2215 
                rc551e-ge(8726),                  -- RC551E-GE:0x2216
                rc551e-4ge(8727),                 -- RC551E-4GE:0x2217
                rc551e-4gef(8728),                -- RC551E-4GEF:0x2218 
                rc551b-fe(8729),                  -- RC551B-FE:0x2219
                rc551b-4fe(8730),                 -- RC551B-4FE:0x221a
                rc552-ge-d(8731),                 -- RC552-GE(D)：0x221b
                rc581-ge(8732),                   -- 原型号 RC551E-GE: 0x2216
                itn203-4gf(8733),                 -- iTN203-4GF:0x221d
                itn203-2xg(8734),                 -- iTN203-2XG:0x221e 
                itn165-4ge4e1s(8735),             -- iTN165-4GE4E1S:0x221f
                itn165-4gee1s(8736),              -- iTN165-4GEE1S:0x2220
                itn165-4gev35s(8737),             -- iTN165-4GEV35S:0x2221
                itn165-4ge4e1-bl(8738),           -- iTN165-4GE4E1:0x2222
                itn165-4ge4e1s-bl(8739),          -- iTN165-4GE4E1S:0x2223
                itn167-4ge-l(8740),               -- iTN167-4GE-L:0x2224
   				itn167-4gc4e1-bl-s(8741),         -- iTN167-4GC4E1-BL-S:0x2225
   			    itn167-4gc411-bl-l(8742),         -- iTN167-4GC4E1-BL-L:0x2226  
                itn167-4gc(8743),                 -- iTN167-4GC:0x2227
                itn167-4gc4e1-s(8744),            -- iTN167-4GC4E1-S:0x2228
                itn167-4gc4e1-l(8745),            -- iTN167-4GC4E1-L:0x2229
                itn125-4fe-b(8746),            
                itn123-fe-b(8747),             
                itn123-4fe-b(8748),            
                itn161-ge-b(8749),             
                itn161-4ge-b(8750),            
                itn161-4ge-b(8751),            
                rc551e-ge-b(8752),              
                rc551e-4ge-b(8753),             
                rc551e-4ge-b(8754),             
                rc551b-fe-b(8755),              
                rc551b-4fe-b(8756),             
                rc581-ge-b(8757),
                itn165-4ge(8758),                  
                itn165-4ge-b(8763),                  
                itn151-ddenl(8764),
                itn151-ddesl(8765),
                itn151-dddnl(8766),
                itn151-dddsl(8767),
                itn151-ddvnl(8768),
                itn151-ddvsl(8769),
                itn401-dblbh(8770),
                itn401-bclbh(8771),
                itn165-4ge-pwr(8788),                  
           
                -- OTN系统业务板卡 
                iTN8600-NXU(12289),				  --  iTN8600网管交换板	    	0x3001 
                iTN8600-PWR(12417),				  --  iTN8600电源盘 	    	0x3002 
                iTN8600-FAN(12418),				  --  iTN8600风扇盘 	    	0x3003
                iTN8600-A-NXU(12295),             --  iTN8600-A网管交换盘		0x3007    
                iTN8000-AO2D (12545),			  --  8路ANY业务汇聚OTU2板 		0x3101 
                iTN8000-XD2D(12546),			  --  2路10G业务OTN转发板  		0x3102
                iTN8600-OTU5E(12552),             --  5路增强型双向波长转换单板	0x3108
                iTN8000-EM2D (13057),			  --  以太业务汇聚OTU2板 		0x3301
                iTN8000-PG8(13058),				  --  8路GE业务接口板 	    	0x3302
                iTN8000-PX2(13059),				  --  2路10GE业务接口板  		0x3303
                iTN8000-SG16(13569),			  --  8/16路FE/GE EOS板	    	0x3501
				iTN8000-SH2(13570),				  --  2路STM-16群路板    		0x3502
				iTN8000-SS4-STM4(13571),		  --  4路STM-1/4支路板			0x3504
				iTN8000-SS4-STM1(13572),		  --  4路STM-1/4支路板			0x3505
				iTN8000-SS8-STM4(13573),		  --  8路STM-1/4支路板			0x3506
				iTN8000-SS8-STM1(13574),		  --  8路STM-1/4支路板			0x3507
				iTN8000-DM16E-DD16E(14081),	      --  16波DWDM合分波板			0x3701
				iTN8000-OMD8-DAD1D(14082),		  --  8波CWDM合分波板	    	0x3702
				iTN8000-OLP(14083),				  --  光线路1+1保护板 			0x3703                                                                       
                                                                                       
                -- RC004 类型
                rcms2104-240b-rev-b(57354),     -- RCMS2104-240B(Rev B) 0xE00A
                rcms2504-240b-rev-b(57355),     -- RCMS2504-240B(Rev B) 0xE00B
                rcms2104-120b-rev-a(57356),     -- RCMS2104-120B(Rev A) 0xE00C
                rcms2504-120b-rev-a(57357),     -- RCMS2504-120B(Rev A) 0xE00D
                rc801-240b-rev-m(57366),        -- RC801-240B(Rev M) 0xE016
                rc803-240b-rev-m(57367),        -- RC803-240B(Rev M) 0xE017
                rc805-240b-rev-m(57368),        -- RC805-240B(Rev M) 0xE018
                rc801-120b-rev-m(57373),        -- RC801-120B(Rev M) 0xE01D
                rc803-120b-rev-m(57374),        -- RC803-120B(Rev M) 0xE01E
                rc805-120b-rev-m(57375),        -- RC805-120B(Rev M) 0xE01F
                rc801-480b-rev-m(57378),        -- RC801-480B(Rev M) 0xE022
                rc803-480b-rev-m(57379),        -- RC803-480B(Rev M) 0xE023
                rc805-480b-rev-m(57380),        -- RC805-480B(Rev M) 0xE024
                rc3000(57381),                  -- RC3000(REV.A)综合复用器  0xE025
                rc3000-opt-2e1(57384),          -- RC3000-OPT-2E1综合复用器 0xE028
                rc3101(57385),                  -- RC3101 经济型PCM   0xE029
                rcms2811-120fe(57387),          -- RCMS2811-120FE(Rev A) 0xE02B
                rcms2811-240fe(57388),          -- RCMS2811-240FE(Rev A) 0xE02C
                rcms2811-480fe(57389),          -- RCMS2811-480FE(Rev A) 0xE02D
                rc3201(57390),                  -- RC3201 经济型PCM   0xE02E
                rc801-240e(57393),              -- RC801-240E 0xE031
                rc831-120(57394),               -- RC831-120 0xE032
                rc831-240(57395),               -- RC831-240 0xE033
                rc831-240e(57396),              -- RC831-240E 0xE034
                rc831-30-fv35(57397),           -- RC831-30-FV35 0xE035
                rc831-60-fv35(57398),           -- RC831-60-FV35 0xE036  
                rc832-30(57399),                -- RC832-30 0xE037
                rc832-30-fv35(57400),           -- RC832-30-FV35(REV A) 0xE038    
                rc832-60(57401),                -- RC832-60 0xE039        
                rc832-120l(57402),              -- RC832-120L 0xE03A      
                rc832-240l(57403),              -- RC832-240L 0xE03B      
                rcms2801-30fe-fv35(57404),      -- RCMS2801-30FE-FV35 0xE03C
                rcms2801-60fe-fv35(57405),      -- RCMS2801-60FE-FV35 0xE03D
                rcms2801-120fe(57406),          -- RCMS2801-120FE 0xE03E 
                rcms2801-240fe(57407),          -- RCMS2801-240FE 0xE03F 
                rcms2801-240efe(57408),         -- RCMS2801-240EFE 0xE040
                rcms2802-30fe(57409),           -- RCMS2802-30FE 0xE041  
                rcms2802-60fe(57410),           -- RCMS2802-60FE 0xE042    
                rcms2811-240efe(57413),         -- RCRCMS2811-240EFE 0xE045
                rcms2802-120lfe(57414),         -- RCMS2802-120LFE 0xE046
                rcms2802-240lfe(57415),         -- RCMS2802-240LFE 0xE047
                rc832-30-fv35-rev-b(57416),     -- RC832-30-FV35(REV B) 0xE048
                rc832-30-fv35-rev-a1(57419),    -- RC832-30-FV35(REV A1) 0xE04B
                rc831-30-fv35-rev-a1(57420),    -- RC831-30-FV35(REV A1) 0xE04C
                rc831-60-fv35-rev-a1(57421),    -- RC831-60-FV35(REV A1) 0xE04D
                rcms2801-30-fv35-rev-a1(57422), -- RCMS2801-30-FV35(REV A1) 0xE04E
                rcms2801-60-fv35-rev-a1(57423), -- RCMS2801-60-FV35(REV A1) 0xE04F
                rcms2802-2t1-fe-rev-a(57425),   -- RCMS2802-2T1-FE(REV A) 0xE051
                rcms2802-4t1-fe-rev-a(57426),   -- RCMS2802-4T1-FE(REV A) 0xE052
                rcms2802-8t1-fe-rev-a(57427),   -- RCMS2802-8T1-FE(REV A) 0xE053
                rcms2802-60-fx-rev-a(57428),    -- RCMS2802-60-FX(REV A) 0xE054
                rc800-120(57431),               -- RC800-120 0xE057
                rcms2000(57432),               -- RC800-120 0xE058
                                                   
                -- RC002 类型                                  
                -- RMC                  
                rc601-fe-rev-c(61705),        -- RC601-FE (REV.C)100M可远端管理模块 0xF109
                rc601-fe-rev-e(61807),        -- RC601-FE (REV.E)100M可远端管理模块 0xF16F
                rc501-fe-rev-c(61708),        -- RC501-FE（REV.C）10/100M可远端管理模块 0xF10C
                rc511-fe-rev-a(61758),        -- RC511-FE（REV.A）10/100M可远端管理具带宽限定功能的以太网光纤收发器远端设备
                                              -- 0xF13E
                rc511-fe-rev-b(61804),        -- RC511-FE（REV.B）10/100M可远端管理具带宽限定功能的以太网光纤收发器
                                              -- 0xF16C
                rc511-4FE(61957),             -- RC511-4FE 10/100M可远端管理具带宽限定功能的4口以太网光纤收发器
                                              -- 0xF205
                rc532-2fe-rev-a(62021),       -- RC532-2FE(REV.A)(SLAVE)10/100M可远端管理具带宽限定功能的以太网光纤收发器用户端设备
                                              -- 0xF245
                rc531-fe-rev-a(62024),        -- RC531-FE(REV.A)10/100M可远端管理具带宽限定功能的以太网光纤收发器
                                              -- 0xF248
                rc532-fe-rev-a(62029),        -- RC532-FE(REV.A)(SLAVE)10/100M可远端管理具带宽限定功能的以太网光纤收发器用户端设备
                                              -- 0xF24D
                rc513-fe-rev-a(61762),        -- RC513-FE（REV.A）10/100M可远端管理具带宽限定功能的单芯以太网光纤收发器（对应RC511-FE （REV.C））
                                              -- 0xF142
                rc513-fe-rev-b(61805),        -- RC513-FE（REV.B）10/100M可远端管理具带宽限定功能的单芯以太网光纤收发器
                                              -- 0xF16D
                rc512-fe-s(61864),            -- RC512-FE-S 10/100M可远端管理具带宽限定功能的以太网光纤收发器远端台式设备(双芯)
                                              -- 0xF1A8
                rc512-fe-s-single(61865),     -- RC512-FE-S 10/100M可远端管理具带宽限定功能的以太网单芯光纤收发器远端台式设备
                                              -- 0xF1A9
                rc512-fe-c(61867),            -- RC512-FE-C 10/100M可远端管理具带宽限定功能的以太网光纤收发器远端卡式设备(双芯)
                                              -- 0xF1AB
                rc512-fe-c-single(61868),     -- RC512-FE-C 10/100M可远端管理具带宽限定功能的以太网单芯光纤收发器远端卡式设备
                                              -- 0xF1AC
                rc512-fe-ss-slave(61870),     -- RC512-FE-SS-SLAVE（远端卡式设备）(对应RC512-FE -SLAVE，有SS13、SS23，光头类型为2和3；为SS34时，光头类型为4；光头类型1无意义)
                                              -- 0xF1AE        
                rc512-fe-rev-a(61835),        -- RC512-FE 10/100M可局/远端管理具带宽限定功能的以太网单芯光纤收发器卡式设备
                                              -- 0xF18B         
                rc513-fe-rev-b-master(61880), -- 为MSAP电信集采分配收发器设备类型 0xF1B8,原型号为：RC512-FE-S(REV.B) 0xF18B
                rc513-fe-rev-b-slave(61881),  -- 为MSAP电信集采分配收发器设备类型 0xF1B9,原型号为：RC512-FE-S(REV.B) 0xF1AE
                rc500-fe(62141),              -- RC50010/100M可远端管理具带宽限定功能的以太网光纤收发器用户端设备
                                              -- 0xF2BD(双纤）
                                              
                -- RIC
                rc952-fxe1-rev-a(62000),      -- RC952-FXE1(A) 0xF230
                rc952-fee1-rev-a(62001),      -- RC952-FEE1(A) 0xF231
                rc951-fee1-rev-a(62007),      -- RC951-FEE1(A) 0xF237
                rc953-fe8e1-rev-a(62045),     -- RC953-FE8E1(A) 0xF25D
                rc953-fx8e1-rev-a(62046),     -- RC953-FX8E1(A) 0xF25E
                rc953-fe8e1-bl-rev-a(62047),  -- RC953-FE8E1-BL(A) 0xF25F
                rc953-fx8e1-bl-rev-a(62048),  -- RC953-FX8E1-BL(A) 0xF260
                rc953-fx4e1-rev-a(62055),     -- RC953-FX4E1(A) 0xF267
                rc953-fe4e1-rev-a(62056),     -- RC953-FE4E1(A) 0xF268                
                rc954-fe4e1-rev-a(62078),     -- RC954-FE4E1(A) 0xF27E
                rc954-fx4e1-rev-a(62079),     -- RC954-FX4E1(A) 0xF27F                
                rc954-fe4e1-bl-rev-a(62098),     -- RC954-FE4E1(A) 0xF292
                rc954-fx4e1-bl-rev-a(62099),     -- RC954-FX4E1(A) 0xF293                
                
                -- OM
                rc852-30-rev-a(62008),        -- RC852-30(REV.A)单路E1光端机模块 0xF238
                rc852-30-fv35-rev-a(62009),   -- RC852-30-FV35(REV.A)单路V35光端机模块 0xF239
                rc851-30-fv35-rev-a(62032),   -- RC851-30-FV35(REV.A)单路V35光端机 0xF250
                rc852-30-bl-rev-a(62038),     -- RC852-30-BL(REV.A) 单路E1平衡接口光端机模块 0xF256
                
                --PCM
                rc3101-002(62010),            -- RC3101经济型PCM模块(RC002协议) 0xF23A
                
                --PDH
                rc802-30b-rev-m(61822),       -- RC802-30B(REV.M)单路E1光端机模块 0xF17E
                rc804-30b-rev-m(61823),       -- RC804-30B(REV.M)单路E1光端机模块 0xF17F
                rc806-30b-rev-m(61824),       -- RC806-30B(REV.M)单路E1光端机模块 0xF180
                rc802-60b-rev-m(61836),       -- RC802-60B(REV.M) 可远端网管双路E1光端机模块 0xF18C
                rc804-60b-rev-m(61837),       -- RC804-60B(REV.M) 可远端网管单芯1310双路E1光端机模块 0xF18D
                rc806-60b-rev-m(61838),       -- RC806-60B(REV.M) 可远端网管单芯1310双路E1光端机模块 0xF18E
                rc802-30b-fv35-rev-m(61800),  -- RC802-30B-FV35(REV.M)可远端管理V.35口光端机 0xF168
                rc804-30b-fv35-rev-m(61803),  -- RC804-30B-FV35(REV.M) 单芯1310可远端管V.35口光端机模块 0xF16B
                rc806-30b-fv35-rev-m(61830),  -- RC806-30B-FV35(REV.M)单芯1550单路V35光Modem 0xF186
                rc801-30b-fv35-rev-m(61799),  -- RC801-30B-FV35(REV.M)可远端管理V.35口光端机 0xF167
                rc805-30b-fv35-rev-m(61802),  -- RC805-30B-FV35(REV.M) 单芯1550可远端管理V.35口光端机 0xF16A
                rc801-60b-fv35-rev-m(61839),  -- RC801-60B-FV35(REV.M)可远端网管1V35+1E1光端机 0xF18F
                rc805-60b-fv35-rev-m(61840),  -- RC805-60B-FV35(REV.M)可远端网管单芯1550 1V35+1E1光端机 0xF190
                rc802-30b-fv35-rev-n(61852),  -- RC802-30B-FV35(REV.N) 可网管具时隙分配功能的V35光端机 0xF19C
                rc804-30b-fv35-rev-n(61853),  -- RC804-30B-FV35(REV.N) 单纤1310可网管具时隙分配功能的V35光端机 0xF19D
                rc806-30b-fv35-rev-n(61854),  -- RC806-30B-FV35(REV.N) 单纤1550可网管具时隙分配功能的V35光端机 0xF19E
                rc801-30b-fv35-rev-n(61855),  -- RC801-30B-FV35(REV.N) 可网管具时隙分配功能的V35光端机 0xF19F
                rc803-30b-fv35-rev-n(61856),  -- RC803-30B-FV35(REV.N) 单纤1310可网管具时隙分配功能的V35光端机 0xF1A0
                rc805-30b-fv35-rev-n(61857),  -- RC805-30B-FV35(REV.N) 单纤1550可网管具时隙分配功能的V35光端机 0xF1A1
                rc801-60b-fv35-rev-n(61858),  -- RC801-60B-FV35(REV.N) 可网管具时隙分配功能的V35光端机 0xF1A2
                rc803-60b-fv35-rev-n(61859),  -- RC803-60B-FV35(REV.N) 单纤1310可网管具时隙分配功能的V35光端机 0xF1A3
                rc805-60b-fv35-rev-n(61860),  -- RC805-60B-FV35(REV.N) 单纤1550可网管具时隙分配功能的V35光端机 0xF1A4

                -- 视频光端机
                rcvs1000-801a(62083),         -- RCVS1000-801A视频光端机(RC002协议)  0xF283     
                rcvs1000-501a(62094),         -- RCVS1000-501A视频光端机(RC002协议)  0xF28E     

                -- G.SHDSL设备
                rc1101-fev35e1-rev-a(62212),  -- RC1101-FEV35E1 0xF304 
                rc1102-e1-rev-b0(61983),      -- RC1102-E1 0xF21F
                rc1102-e1-rev-b1(62068),      -- RC1102-E1-A-NEW 0xF274
                rc1102-fe-rev-a(61975),       -- RC1102-FE-A 0xF217
                rc1102-v35-rev-a(62004),      -- RC1102-V35-A 0xF234
                rc1102-v35-rev-b(62016),      -- RC1102-V35-B 0xF240
                rc1102-v35-rev-a1(62061),     -- RC1102-V35-A 0xF26D
                rc1102-e1-rev-b2(62091),      -- RC1102-E1-B2 0xF28B
                rc1102-e1-bl-rev-a0(62022),   -- RC1102-E1-BL-A 0xF246
                rc1102-e1-bl-rev-a1(62073),   -- RC1102-E1-BL-A-NEW 0xF279
                rc1102-e1-bl-rev-a2(62060),   -- RC1102-E1-BL-B2() 0xF26C
                rc1102-fe-rev-b(62213),       -- RC1102-FE-B 0xF305                
                rc1102-fe-4w-rev-a(62214),    -- RC1102-FE-4W 0xF306
                rc1101-fev35e1-rev-b(62215),  -- RC1101-FEV35E1 0xF307
                -- 映射RC002约定3的扩展类型，对应约定3类型为0xB1
                rc906h-fee1-rev-b(45313),       -- RC906H-FEE1（REV.B） 	对应RC952-FEE1（B）	0xB101
                rc906h-fxe1-rev-c(45314),       -- RC906H-FXE1（REV.C）	对应RC952-FXE1（C）	0xB102
                rc602-gef-rev-c-master(45315),  -- RC602-GEF(C)-MASTER		0xB103
                rc602-gef-rev-c-remote(45316),  -- RC602-GEF(C)-REMOTE		0xB104
                rc952-fxe1-rev-c(45317),        -- RC952-FXE1（REV.C）		0xB105
                rc952-fee1-rev-b(45318),        -- RC952-FEE1（REV.B）		0xB106
                -- 符合中移动标准的其他厂家协转类型 0xB107
                rc954-fx8e1-master(45320),      -- RC954-FX8E1-MASTER（REV.A）		0xB108
                rc954-fx8e1-slave(45321),       -- RC954-FX8E1-SLAVE（REV.A）		0xB109
                rc953-4fe4e1t1-bl-slave(45322), -- RC953-4FE4E1T1-BL-SLAVE（REV.A）		0xB10A
                rc953-4fe8e1t1-bl-slave(45323), -- RC953-4FE8E1T1-BL-SLAVE（REV.A）		0xB10B
                rc953-4fe4e1-slave(45324),      -- RC953-4FE4E1-SLAVE（REV.A）		0xB10C
                rc953-4fe8e1-slave(45325),      -- RC953-4FE8E1-SLAVE（REV.A）		0xB10D
                opcom200-feu1-rev-b-master(45326),      -- OPCOM200-FEU1-MASTER (REV.B)		0xB10E
                opcom200-feu1-rev-b-slave(45328),       -- OPCOM200-FEU1-SLAVE (REV.B)		0xB110
                rc951e-4fee1(45330),            -- RC951E-4FEE1		0xB112
                rc951-2fe2e1-8rs232h(45331),    -- RC951-2FE2E1-8RS232H	串口服务器	0xB113
                rc532e-fe-master(45334),        -- RC532E-FE-MASTER		0xB116
                rc532e-fe-slave(45335),         -- RC532E-FE-SLAVE		0xB117
                rc532e-fe-remote(45336),        -- RC532E-FE-REMOTE		0xB118
                rc112-ge-rev-b(45337),          -- RC112-GE(B)	SFP改造型号	0xB119
                rc212-ge-rev-b(45338),          -- RC212-GE(B)	SFP改造型号	0xB11A
                opcom200-ocpf-master(45339),    -- OPCOM200-OCPF-MASTER		0xB11B
                opcom200-ocpf-slave(45340),     -- OPCOM200-OCPF-SLAVE		0xB11C
                opcom200-ocpf-remote(45341),    -- OPCOM200-OCPF -REMOTE		0xB11D
                rc531-fe-rev-b(45343),          -- RC531-FE(B)		0xB11F
                rc512-fe-s-rev-c(45344),        -- RC512-FE-S(C)		0xB120
                rc112-fe-rev-c(45345),          -- RC112-FE(C) 		0xB121
                rc316-fe-rev-c(45347),          -- RC316-FE(C)		0xB123
                rc953-8fe8e1t1-rev-bl-slave(45350),      -- RC953-8FE8E1T1-BL-SLAVE		0xB126
                rc532-fe-rev-b-master(45351),   -- RC532-FE-MASTER（B）		0xB127
                rc532-fe-rev-b-slave(45352),    -- RC532-FE-SLAVE（B）		0xB128
                rc532-fe-rev-b-remote(45353),   -- RC532-FE-REMOTE（B）		0xB129
                rc512-fe-rev-c-master(45354),   -- RC512-FE-MASTER（C）		0xB12A
                rc512-fe-rev-c-slave(45355),    -- RC512-FE-SLAVE（C）		0xB12B
                rc512-fe-rev-b-remote(45356),   -- RC512-FE-REMOTE（C）		0xB12C
                rc802-ds3e3-rev-b-master(45358),-- RC802-DS3E3-MASTER			0xB12E
                rc802-ds3e3-rev-b-slave(45359), -- RC802-DS3E3-SLAVE	    0xB12F
                rc802-ds3e3-rev-b-remote(45360),-- RC802-DS3E3-REMOTE			0xB130
                rc602-ge-rev-c-master(45361),   -- RC602-GE-MASTER (C)		0xB131
                rc602-ge-rev-c-slave(45362),    -- RC602-GE-SLAVE (C)			0xB132
                rc602-ge-rev-c-remote(45364),   -- RC602-GE-REMOTE (C)		0xB134
                rc152-h(45365),   		-- RC152(H)		0xB135
                
                -- RC002约定5设备类型
                rcvs1000-604al(62466),          -- RCVS1000-604AL	增强型RC002可网管卡式4路多功能非压缩视频发射机	0xF402
                rcvs1000-602bl(62467),          -- RCVS1000-602BL	双层RC002两路视频接收子卡	0xF403
                rcvs1000-601bl(62468),          -- RCVS1000-601BL	单路视频接收子卡，由602BL衍生。	0xF404
                rcms2802-60ge-bl-rev-b-master(62469), 	-- RCMS2802-60GE-BL-MASTER (REV.B)		0xF405
                rcms2802-60ge-bl-rev-b-slave(62470),   	-- RCMS2802-60GE-BL-SLAVE (REV.B)		0xF406
                rcms2802-60ge-bl-rev-b-remote(62471),  	-- RCMS2802-60GE-BL-REMOTE (REV.B)		0xF407
                rc952-2fe2e1(62480),            -- RC952-2FE2E1		0xF410
                rc952-2fe2e1-8rs232(62481),     -- RC952-2FE2E1-8RS232		0xF411
                rc951-2fe2e1-8rs232(62482),     -- RC951-2FE2E1-8RS232		0xF412
                rc904-pe1-mster(62512),         -- RC904－PE1-MSTER		0xF430
                rc904-pe1-slave(62513),         -- RC904－PE1-SLAVE		0xF431
                rc904-pe1-remote(62514),        -- RC904－PE1-REMOTE		0xF432
                rcms2802-120lge-bl-rev-b-master(62516), -- RCMS2802-120LGE-BL-MASTER (REV.B)		0xF434
                rcms2802-120lge-bl-rev-b-slave(62517),  -- RCMS2802-120LGE-BL-SLAVE (REV.B)		0xF435
                rcms2802-120lge-bl-rev-b-remote(62518), -- RCMS2802-120LGE-BL-REMOTE (REV.B)		0xF436
                rcms2802-240lge-bl-rev-b-master(62519), -- RCMS2802-240LGE-BL-MASTER (REV.B)		0xF437
                rcms2802-240lge-bl-rev-b-slave(62520),  -- RCMS2802-240LGE-BL-SLAVE (REV.B)		0xF438
                rcms2802-240lge-bl-rev-b-remote(62521), -- RCMS2802-240LGE-BL-REMOTE (REV.B)		0xF439
                rc958-fe4e1-master(62523),       -- RC958-FE4E1-MASTER		0xF43B
                rc958-fe4e1-slave(62525),        -- RC958-FE4E1-SLAVE		0xF43D
                rc958-fe4e1-remote(62526),       -- RC958-FE4E1-REMOTE		0xF43E
                rc958-fe8e1-master(62527),       -- RC958-FE8E1-MASTER		0xF43F
                rc958-fe8e1-slave(62528),        -- RC958-FE8E1-SLAVE		0xF440
                rc958-fe8e1-remote(62529),       -- RC958-FE8E1-REMOTE		0xF441
                rc958-fx4e1-master(62530),       -- RC958-FX4E1-MASTER		0xF442
                rc958-fx4e1-slave(62531),        -- RC958-FX4E1-SLAVE		0xF443
                rc958-fx4e1-remote(62533),       -- RC958-FX4E1-REMOTE		0xF445
                rc958-fx8e1-master(62534),       -- RC958-FX8E1-MASTER		0xF446
                rc958-fx8e1-slave(62535),        -- RC958-FX8E1-SLAVE		0xF447
                rc958-fx8e1-remote(62536),       -- RC958-FX8E1-REMOTE		0xF448
                rc908-fev35-master(62537),       -- RC908-FEV35-MASTER		0xF449
                rc908-fev35-slave(62538),        -- RC908-FEV35-SLAVE		0xF44A
                rc908-fev35-remote(62540),       -- RC908-FEV35-REMOTE		0xF44C
                rc958-fee1-master(62541),        -- RC958-FEE1-MASTER		0xF44D
                rc958-fee1-slave(62542),         -- RC958-FEE1-SLAVE		0xF44E
                rc958-fee1-remote(62543),        -- RC958-FEE1-REMOTE		0xF44F
                rc958-fxe1-master(62544),        -- RC958-FXE1-MASTER		0xF450
                rc958-fxe1-slave(62545),         -- RC958-FXE1-SLAVE		0xF451
                rc958-fxe1-remote(62546),        -- RC958-FXE1-REMOTE		0xF452
                rc906g-fe4e1-master(62547),      -- RC906G-FE4E1-MASTER		0xF453
                rc906g-fe4e1-slave(62548),       -- RC906G-FE4E1-SLAVE		0xF454
                rc906g-fe4e1-remote(62550),      -- RC906G-FE4E1-REMOTE		0xF456
                rc906g-fx4e1-master(62551),      -- RC906G-FX4E1-MASTER		0xF457
                rc906g-fx4e1-slave(62552),       -- RC906G-FX4E1-SLAVE		0xF458
                rc906g-fx4e1-remote(62553),      -- RC906G-FX4E1-REMOTE		0xF459
                rc906g-fee1-master(62555),       -- RC906G-FEE1-MASTER		0xF45B
                rc906g-fee1-slave(62556),        -- RC906G-FEE1-SLAVE		0xF45C
                rc906g-fee1-remote(62557),       -- RC906G-FEE1-REMOTE		0xF45D
                rc906g-fxe1-master(62558),       -- RC906G-FXE1-MASTER		0xF45E
                rc906g-fxe1-slave(62559),        -- RC906G-FXE1-SLAVE		0xF45F
                rc906g-fxe1-remote(62560),       -- RC906G-FXE1-REMOTE		0xF460
                rc906g-fe8e1-master(62561),      -- RC906G-FE8E1-MASTER		0xF461
                rc906g-fe8e1-slave(62562),       -- RC906G-FE8E1-SLAVE		0xF462
                rc906g-fe8e1-remote(62563),      -- RC906G-FE8E1-REMOTE		0xF463
                rc906g-fx8e1-master(62564),      -- RC906G-FX8E1-MASTER		0xF464
                rc906g-fx8e1-slave(62565),       -- RC906G-FX8E1-SLAVE		0xF465
                rc906g-fx8e1-remote(62567),      -- RC906G-FX8E1-REMOTE		0xF467
                rc414-rev-b(62568),              -- RC414(REV B)		0xF468
                rcvs1000-901nl(62570),           -- RCVS1000-901NL	局端设备	0xF46A
                rcvs1000-901ul-remote(62571),    -- RCVS1000-901UL(REMOTE)	远端设备	0xF46B
                rcvs1000-901ul-slave(62572),     -- RCVS1000-901UL(SLAVE)	局端从设备	0xF46C
                rcms2912-4t1e1ge-master(62573),  -- RCMS2912-4T1E1GE（MASTER）		0xF46D
                rcms2912-4t1e1ge-slave(62574),   -- RCMS2912-4T1E1GE（SLAVE）		0xF46E
                rcms2912-4t1e1ge-remote(62575),  -- RCMS2912-4T1E1GE（REMOTE）		0xF46F
                rcms2912-8t1e1ge-master(62576),  -- RCMS2912-8T1E1GE（MASTER）		0xF470
                rcms2912-8t1e1ge-slave(62577),   -- RCMS2912-8T1E1GE（SLAVE）		0xF471
                rcms2912-8t1e1ge-remote(62578),  -- RCMS2912-8T1E1GE（REMOTE）		0xF472
                opcom200-otu1-rev-a20(62579),    -- OPCOM200-OTU1(REV A.20)		0xF473
                rc952-se1m-master(62580),        -- RC952-SE1M-MASTER	局端设备	0xF474
                rc952-se1m-slave(62581),         -- RC952-SE1M-SLAVE	局端从设备	0xF475
                rc952-se1m-remote(62582),        -- RC952-SE1M-REMOTE	远端设备	0xF476
                rcvs1000-501c(62585),            -- RCVS1000-501C	局端设备	0xF479
                rcvs1000-601c(62586),            -- RCVS1000-601C	远端设备	0xF47A
                rcms2902-120lfe-bl-master(62587),-- RCMS2902-120LFE(-BL)-MASTER	单光口4E1以太网复用器	0xF47B
                rcms2902-120lfe-bl-slave(62588), -- RCMS2902-120LFE(-BL)-SLAVE		0xF47C
                rcms2902-120lfe-bl-remote(62589),-- RCMS2902-120LFE(-BL)-REMOTE		0xF47D
                rcms2902-240lfe-bl-master(62590),-- RCMS2902-240LFE(-BL)-MASTER	单光口8E1以太网复用器	0xF47E
                rcms2902-240lfe-bl-slave(62591), -- RCMS2902-240LFE(-BL)-SLAVE			0xF47F
                rcms2902-240lfe-bl-remote(62592),-- RCMS2902-240LFE(-BL)-REMOTE		0xF480
                rcms2902-60fe-bl-master(62593),	 -- RCMS2902-60FE-BL-MASTER		单光口2E1以太网复用器	0xF481
                rcms2902-60fe-bl-slave(62594),   -- RCMS2902-60FE-BL-SLAVE		0xF482
                rcms2902-60fe-bl-remote(62595),  -- RCMS2902-60FE-BL-REMOTE		0xF483
                rc862-60-bl-master(62596),	     -- RC862-60-BL-MASTER		单光口2E1光端机	0xF484
                rc862-60-bl-slave(62597),        -- RC862-60-BL-SLAVE		0xF485
                rc862-60-bl-remote(62598),       -- RC862-60-BL-REMOTE		0xF486
                rc862-30-bl-master(62601),       -- RC862-30-BL-MASTER	单光口单E1光端机	0xF489
                rc862-30-bl-slave(62602),        -- RC862-30-BL-SLAVE		0xF48A
                rc862-30-bl-remote(62603),       -- RC862-30-BL-REMOTE		0xF48B
                rc952-cse1m-master(62604),       -- RC952-CSE1M-MASTER	局端设备	0xF48C
                rc952-cse1m-slave(62605),        -- RC952-CSE1M-SLAVE	局端从设备	0xF48D
                rc952-cse1m-remote(62606),       -- RC952-CSE1M-REMOTE	远端设备	0xF48E
                rcms2911-480fe(62607),           -- RCMS2911-480FE(REV.A)		0xF48F
                rcms2911-120fe(62608),           -- RCMS2911-120FE(REV.A)		0xF490
                rcms2912-480fe-mater(62609),     -- RCMS2912-480FE-MATER(REV.A)	局端主	0xF491
                rcms2912-480fe-slave(62610),     -- RCMS2912-480FE-SLAVE(REV.A)	局端从	0xF492
                rcms2912-480fe-remote(62611),    -- RCMS2912-480FE-REMOTE (REV.A)	远端从	0xF493
                rcms2912-240fe-mater(62612),     -- RCMS2912-240FE-MATER(REV.A)	局端主	0xF494
                rcms2912-240fe-slave(62613),     -- RCMS2912-240FE-SLAVE(REV.A)	局端从	0xF495
                rcms2912-240fe-remote(62614),    -- RCMS2912-240FE-REMOTE (REV.A)	远端从	0xF497
                rcms2901-480efe(62615),          -- RCMS2901-480EFE		0xF498
                rc861-480e(62618),               -- RC861-480E		0xF49A
                rcms2901-60fe-fv35(62619),       -- RCMS2901-60FE-FV35		0xF49B
                rc861-60-fv35(62620),            -- RC861-60-FV35		0xF49C
                rcms2903-4e1-4ge(62621),         -- RCMS2903-4E1-4GE(REV.A)		0xF49D
                rc958-fee1-rev-b-slave(62622),   -- RC958-FEE1-SLAVE(B)		0xF49E
                rc958-fee1-rev-b-remote(62623),  -- RC958-FEE1-REMOTE(B)		0xF49F
                rc958-fxe1-rev-b-master(62624),  -- RC958-FXE1-MASTER(B)		0xF4A0
                rc958-fxe1-rev-b-slave(62625),   -- RC958-FXE1-SLAVE(B)		0xF4A1
                rc958-fxe1-rev-b-remote(62626),  -- RC958-FXE1-REMOTE(B)		0xF4A2
                rc958-fe4e1-rev-b-master(62627), -- RC958-FE4E1-MASTER(B)		0xF4A3
                rc958-fe4e1-rev-b-slave(62628),  -- RC958-FE4E1-SLAVE(B)		0xF4A4
                rc958-fe4e1-rev-b-remote(62630), -- RC958-FE4E1-REMOTE(B)		0xF4A6
                rc958-fx4e1-rev-b-master(62631), -- RC958-FX4E1-MASTER(B)		0xF4A7
                rc958-fx4e1-rev-b-slave(62632),  -- RC958-FX4E1-SLAVE(B)		0xF4A8
                rc958-fx4e1-rev-b-remote(62633), -- RC958-FX4E1-REMOTE(B)		0xF4A9
                rc958-fe8e1-rev-b-master(62635), -- RC958-FE8E1-MASTER(B)		0xF4AB
                rc958-fe8e1-rev-b-slave(62636),  -- RC958-FE8E1-SLAVE(B)		0xF4AC
                rc958-fe8e1-rev-b-remote(62637), -- RC958-FE8E1-REMOTE(B)		0xF4AD
                rc958-fx8e1-rev-b-master(62638), -- RC958-FX8E1-MASTER(B)		0xF4AE
                rc958-fx8e1-rev-b-slave(62639),  -- RC958-FX8E1-SLAVE(B)		0xF4AF
                rc958-fx8e1-rev-b-remote(62640), -- RC958-FX8E1-REMOTE(B)		0xF4B0
                rc906g-fee1-rev-b-master(62641), -- RC906G-FEE1-MASTER(B)		0xF4B1
                rc906g-fee1-rev-b-slave(62642),  -- RC906G-FEE1-SLAVE(B)		0xF4B2
                rc906g-fee1-rev-b-remote(62643), -- RC906G-FEE1-REMOTE(B)		0xF4B3
                rc906g-fxe1-rev-b-master(62645), -- RC906G-FXE1-MASTER(B)		0xF4B5
                rc906g-fxe1-rev-b-slave(62646),  -- RC906G-FXE1-SLAVE(B)		0xF4B6
                rc906g-fxe1-rev-b-remote(62647), -- RC906G-FXE1-REMOTE(B)		0xF4B7
                rc906g-fe4e1-rev-b-master(62648),-- RC906G-FE4E1-MASTER(B)		0xF4B8
                rc906g-fe4e1-rev-b-slave(62649), -- RC906G-FE4E1-SLAVE(B)		0xF4B9
                rc906g-fe4e1-rev-b-remote(62650),-- RC906G-FE4E1-REMOTE(B)		0xF4BA
                rc906g-fx4e1-rev-b-master(62652),-- RC906G-FX4E1-MASTER(B)		0xF4BC
                rc906g-fx4e1-rev-b-slave(62653), -- RC906G-FX4E1-SLAVE(B)		0xF4BD
                rc906g-fx4e1-rev-b-remote(62654),-- RC906G-FX4E1-REMOTE(B)		0xF4BE
                rc906g-fe8e1-rev-b-master(62655),-- RC906G-FE8E1-MASTER(B)		0xF4BF
                rc906g-fe8e1-rev-b-slave(62656), -- RC906G-FE8E1-SLAVE(B)		0xF4C0
                rc906g-fe8e1-rev-b-remote(62657),-- RC906G-FE8E1-REMOTE(B)		0xF4C1
                rc906g-fx8e1-rev-b-master(62658),-- RC906G-FX8E1-MASTER(B)		0xF4C2
                rc906g-fx8e1-rev-b-slave(62660), -- RC906G-FX8E1-SLAVE(B)		0xF4C4
                rc906g-fx8e1-rev-b-remote(62661),-- RC906G-FX8E1-REMOTE(B)		0xF4C5
                rcms2901-240fe(62662),           -- RCMS2901-240FE		0xF4C6
                rcms2901-120fe(62663),           -- RCMS2901-120FE		0xF4C7
                rc861-240(62664),                -- RC861-240		0xF4C8
                rc861-120(62665),                -- RC861-120		0xF4C9
                rc862-30-fv35-master(62666),     -- RC862-30-FV35-MASTER		0xF4CA
                rc862-30-fv35-slave(62667),      -- RC862-30-FV35-SLAVE		0xF4CB
                rc862-30-fv35-remote(62669),     -- RC862-30-FV35-REMOTE		0xF4CD
                rc958-fee1-rev-b-master(62670),  -- RC958-FEE1-MASTER(B)		0xF4CE
                rcvs1000-600al-2fe(62671),       -- RCVS1000-600AL-2FE              
                rcvs1000-601al-2fe(62672),       -- RCVS1000-601AL-2FE              
                rm904-pe1-rev-c-mster(62673),    -- Gazelle RM904-PE1（C.00）-MSTER  0xF4D1 
                rm904-pe1-rev-c-slave(62675),    -- Gazelle RM904-PE1（C.00）-SLAVE  0xF4D3
                rm904-pe1-rev-c-remote(62676),   -- Gazelle RM904-PE1（C.00）-REMOTE 0xF4D4
                rcms2902-2e1ge-master(62677),    -- RCMS2902-2E1GE-MASTER  0xF4D5
                rcms2902-2e1ge-slave(62678),     -- RCMS2902-2E1GE-SLAVE   0xF4D6
                rcms2902-2e1ge-remote(62679),    -- RCMS2902-2E1GE-REMOTE  0xF4D7
                rh2901-2rs2e1-2fe(62680),        -- RH2901-2RS2E1-2FE  0xF4D8				               

                rc956g-fee1-rev-b-master(62681), -- RC956G-FEE1-REV-B-MASTER	0xF4D9
                rc956g-fee1-rev-b-slave(62682),  -- RC956G-FEE1-REV-B-SLAVE		0xF4DA
                rc956g-fee1-rev-b-remote(62683), -- RC956G-FEE1-REV-B-REMOTE	0xF4DB
                rc956g-fxe1-rev-b-master(62684), -- RC956G-FXE1-REV-B-MASTER	0xF4DC
                rc956g-fxe1-rev-b-slave(62686),  -- RC956G-FXE1-REV-B-SLAVE		0xF4DE
                rc956g-fxe1-rev-b-remote(62687), -- RC956G-FXE1-REV-B-REMOTE	0xF4DF
                rc956g-fe4e1-master(62688),      -- RC956G-FE4E1-MASTER		0xF4E0
                rc956g-fe4e1-slave(62690),       -- RC956G-FE4E1-SLAVE		0xF4E2
                rc956g-fe4e1-remote(62691),      -- RC956G-FE4E1-REMOTE		0xF4E3
                rc956g-fx4e1-master(62692),      -- RC956G-FX4E1-MASTER		0xF4E4
                rc956g-fx4e1-slave(62693),       -- RC956G-FX4E1-SLAVE		0xF4E5
                rc956g-fx4e1-remote(62694),      -- RC956G-FX4E1-REMOTE		0xF4E6
                rc956g-fe8e1-master(62695),      -- RC956G-FE8E1-MASTER		0xF4E7
                rc956g-fe8e1-slave(62696),       -- RC956G-FE8E1-SLAVE		0xF4E8
                rc956g-fe8e1-remote(62697),      -- RC956G-FE8E1-REMOTE		0xF4E9
                rc956g-fx8e1-master(62698),      -- RC956G-FX8E1-MASTER		0xF4EA
                rc956g-fx8e1-slave(62699),       -- RC956G-FX8E1-SLAVE		0xF4EB
                rc956g-fx8e1-remote(62700),      -- RC956G-FX8E1-REMOTE		0xF4EC
                rc956g-fe4e1-rev-b-master(62701),      -- RC956G-FE4E1-MASTER		0xF4ED
                rc956g-fe4e1-rev-b-slave(62703),       -- RC956G-FE4E1-SLAVE		0xF4EF
                rc956g-fe4e1-rev-b-remote(62705),      -- RC956G-FE4E1-REMOTE		0xF4F1
                rc956g-fx4e1-rev-b-master(62706),      -- RC956G-FX4E1-MASTER		0xF4F2
                rc956g-fx4e1-rev-b-slave(62707),       -- RC956G-FX4E1-SLAVE		0xF4F3
                rc956g-fx4e1-rev-b-remote(62708),      -- RC956G-FX4E1-REMOTE		0xF4F4
                rc956g-fe8e1-rev-b-master(62709),      -- RC956G-FE8E1-MASTER		0xF4F5
                rc956g-fe8e1-rev-b-slave(62710),       -- RC956G-FE8E1-SLAVE		0xF4F6
                rc956g-fe8e1-rev-b-remote(62711),      -- RC956G-FE8E1-REMOTE		0xF4F7
                rc956g-fx8e1-rev-b-master(62712),      -- RC956G-FX8E1-MASTER		0xF4F8
                rc956g-fx8e1-rev-b-slave(62713),       -- RC956G-FX8E1-SLAVE		0xF4F9
                rc956g-fx8e1-rev-b-remote(62714),      -- RC956G-FX8E1-REMOTE		0xF4FA 
                rc904-pe1-rev-b-master(62715),		   -- RC904-PE1（B.10）-MSTER   0xF4FB 
                rc904-pe1-rev-b-slave(62716),		     -- RC904-PE1（B.10）-SLAVE   0xF4FC  
                rc904-pe1-rev-b-remote(62717),		   -- RC904-PE1（B.10）-REMOTE  0xF4FD 

                -- iTN8600设备类型
                rcvs1000-604al(62466),          -- RCVS1000-604AL	增强型RC002可网管卡式4路多功能非压缩视频发射机	0xF402
 
                
                deviceAll(65535)                
                }
                
    RcOptIfModuleType  ::= TEXTUAL-CONVENTION
       STATUS       current
       DESCRIPTION
               "   RAISECOM Optical Module typde defination. "
       SYNTAX  INTEGER {      
                unknowType(0),         
                rcOptTypeM(1),      -- 双芯多模1310nm波长，0－2km（155M）
                                    -- 双芯多模850nm波长，0－0.55km（GE）
                rcOptTypeS1(2),     -- 双芯单模1310nm波长，0－25km
                rcOptTypeS2(3),     -- 双芯单模1310nn波长，10－60km（155M）
                                    -- 双芯单模1550nn波长，10－60km（GE）
                rcOptTypeS3(4),     -- 双芯单模光纤1550nm波长，15－120km（155M）
                                    -- 双芯单模光纤1550nm波长，25－100km（GE）
                rcOptTypeSS13(5),   -- 单芯单模双波长，0-25km，发射波长1310nm
                                    -- 双光模块、且固定1＋1保护的设备,第一个光模块为SS13，
                                    -- 第二个光模块为SS15
                rcOptTypeS15(12),   -- 双芯单模1550nm波长，0－25km
                rcOptTypeSS15(6),   -- 单芯单模双波长，0-25km，发射波长1550nm
                rcOptTypeSS23(7),   -- 单芯单模双波长，10-50km，发射波长1310nm（155M）
                                    -- 双光模块、且固定1＋1保护的设备,第一个光模块为SS23/24，
                                    -- 第二个光模块为SS25
                rcOptTypeSS25(8),   -- 单芯单模双波长，10-50km，发射波长1550nm（155M）
                                    -- 单芯单模双波长，10-60km，发射波长1550nm（GE）
                rcOptTypeSS34(9),   -- 单芯单模双波长，15-100km，发射波长1490nm（155M）
                                    -- 双光模块、且固定1＋1保护的设备,第一个光模块为SS34，
                                    -- 第二个光模块为SS35
                rcOptTypeSS35(10),  -- 单芯单模双波长，15-100km，发射波长1550nm（155M）
                rcOptTypeSFP(15),	-- SFP模块
                rcOptTypeSS24(23),  -- 单芯单模双波长，10-60km，发射波长1490nm（GE）
                rcOptTypeAS1(34),   -- 
                rcOptTypeAS2(35),   -- 
                rcOptTypeAS3(36),   --
                notExist(255)       -- 不存在
                }

    RcOptIfPortType  ::= TEXTUAL-CONVENTION
       STATUS       current
       DESCRIPTION
               "Definatione for portType in ifIndex. portType occupies bit18 to bit22 in ifIndex"
       SYNTAX  INTEGER {      
                unknowType(0),         
                ifPortTypeE1(1),      -- E1接口
                ifPortTypeEth(2),     -- ETH：以太网电口
                ifPortTypeEthFx(3),   -- ETH-FX：以太网光口
                ifPortTypeEthGe(4),   -- ETH-GE：以太网千兆电口
                ifPortTypeEthGeFx(5), -- ETH-GE-FX：以太网千兆光口
                ifPortTypeEos(6),     -- EOS：EOS电接口
                ifPortTypeEosFx(7),   -- EOS-FX：EOS光接口
                ifPortTypePdh(8),     -- PDH：PDH电接口 
                ifPortTypePdhOpt(9),  -- PDH-OPT：PDH光接口
                ifPortTypeStm1(10),   -- STM1电接口
                ifPortTypeStm1Opt(11),-- STM1光接口
                ifPortTypeStm4(12),   -- STM4电接口
                ifPortTypeStm4Opt(13),-- STM4光接口
                ifPortTypeV35(14),    -- V35电接口
                ifPortTypeV35F(15),   -- V35光接口
                ifPortTypeGhdsl(16),  -- GHDSL接口
                ifPortTypeRs(17),     -- RS232接口
                ifPortTypeUserOpt(18),-- 用户侧透明光通道
                ifPortTypeLineOpt(19),-- 线路侧透明光通道
                ifPortTypeUserE(20),  -- 用户侧透明电通道
                ifPortTypeLineE(21),  -- 线路侧透明电通道
                ifPortTypeCtrlData(22),-- 控制数据口
                ifPortTypeVideo(23),  -- 视频接口类型   
                ifPortTypeEopdh(24),  -- 支持GFP封装的EOP端口接口类型   
                ifPortTypeEot(25),    -- 同时支持EOS和EOP的端口接口类型   
                ifPortTypeSfp(26),    -- SFP接口类型
                ifPortTypeAll(31)     -- 所有接口类型
                }
                
END

--MibName=RAISECOM-VRRP-MIB
-- *****************************************************************
-- RAISECOM-VRRP-MIB.mib:  Raisecom VRRP MIB file
--
-- 20110726,tangyoucan 
--
--
-- Copyright (c) 2000-2011 by Raisecom Technology Co., Ltd. 
-- All rights reserved.
-- 
-- *****************************************************************

RAISECOM-VRRP-MIB DEFINITIONS ::= BEGIN

 IMPORTS
     MODULE-IDENTITY, OBJECT-TYPE,
     NOTIFICATION-TYPE, Counter32,
     Integer32, IpAddress, mib-2         FROM SNMPv2-SMI

     TEXTUAL-CONVENTION, RowStatus, 
     MacAddress, TruthValue   FROM SNMPv2-TC

     MODULE-COMPLIANCE, OBJECT-GROUP,
     NOTIFICATION-GROUP                  FROM SNMPv2-CONF
     ifIndex                             FROM IF-MIB
     vrrpOperVrId                        FROM VRRP-MIB
     raisecomAgent                       FROM RAISECOM-BASE-MIB; 

	 raisecomVrrp MODULE-IDENTITY
        LAST-UPDATED    "201107260000Z"
        ORGANIZATION    "Raisecom Technology Co., Ltd."
        CONTACT-INFO
                "Raisecom Science & Technology Co., ltd.
                 E-mail: support@raisecom.com"
        DESCRIPTION
         "This MIB module is designed for vrrp config."
        REVISION   "201107260000Z"
        DESCRIPTION
            "version 1.0.0"
        ::= { raisecomAgent 41 }  

-- *******************************************************************
--  RAISECOM VRRP MIB Groups
-- *******************************************************************

    raisecomVrrpNotifications   OBJECT IDENTIFIER ::= { raisecomVrrp 0 }
    raisecomVrrpObjects       OBJECT IDENTIFIER ::= { raisecomVrrp 1 }

    raisecomVrrpScalarObjects OBJECT IDENTIFIER ::= { raisecomVrrpObjects 1 }
    raisecomVrrpConformance     OBJECT IDENTIFIER ::= { raisecomVrrp 2 }

-- *******************************************************************
--  Start of MIB objects
-- *******************************************************************

 raisecomVrrpPing  OBJECT-TYPE
     SYNTAX       TruthValue
     MAX-ACCESS   read-write
     STATUS       current
     DESCRIPTION
        "ICMP echo enable or disable of virtual router."   
     DEFVAL { true }
     ::= { raisecomVrrpScalarObjects 1 }

 raisecomVrrpStatisticsClear  OBJECT-TYPE
     SYNTAX       TruthValue
     MAX-ACCESS   read-write
     STATUS       current
     DESCRIPTION
        "action of clear statistics of VRRP, when the statistics clear, 
         it will change to false."   
     DEFVAL { false }
     ::= { raisecomVrrpScalarObjects 2 }

-- *******************************************************************
--  VRRP Operations Table
-- *******************************************************************

 raisecomVrrpOperTable OBJECT-TYPE
     SYNTAX       SEQUENCE OF RaisecomVrrpOperEntry
     MAX-ACCESS   not-accessible
     STATUS       current
     DESCRIPTION
         "Operations table for a VRRP router to set desciption , preempt delay."

     ::= { raisecomVrrpObjects 2 }

 raisecomVrrpOperEntry OBJECT-TYPE
     SYNTAX       RaisecomVrrpOperEntry
     MAX-ACCESS   not-accessible
     STATUS       current
     DESCRIPTION
         "An entry in the raisecomVrrpOperTable containing the operational
          characteristics of a virtual router. On a VRRP router,
          a given virtual router is identified by a combination
          of the IF index and VRID."

     INDEX    { ifIndex, vrrpOperVrId }
     ::= { raisecomVrrpOperTable 1 }

 RaisecomVrrpOperEntry ::= SEQUENCE {
         raisecomVrrpOperDesc   OCTET STRING,
         raisecomVrrpOperPreemptDelay   INTEGER
         }

 raisecomVrrpOperDesc OBJECT-TYPE
     SYNTAX       OCTET STRING (SIZE(0..32))
     MAX-ACCESS   read-write
     STATUS       current
     DESCRIPTION
         "The description of the virtual router. "
     ::= { raisecomVrrpOperEntry 1 }

 raisecomVrrpOperPreemptDelay OBJECT-TYPE
     SYNTAX INTEGER (0..255) 
     UNITS        "second"    
     MAX-ACCESS   read-write
     STATUS       current
     DESCRIPTION
         "The preempt delay of the virtual router."  
     DEFVAL { 0 }
     ::= { raisecomVrrpOperEntry 2 }

-- *******************************************************************
--  VRRP track if Table
-- *******************************************************************

 raisecomVrrpTrackIfTable OBJECT-TYPE
     SYNTAX       SEQUENCE OF RaisecomVrrpTrackIfEntry
     MAX-ACCESS   not-accessible
     STATUS       current
     DESCRIPTION
         "VRRP track table for a VRRP router to monitor such interface."

     ::= { raisecomVrrpObjects 3 }

 raisecomVrrpTrackIfEntry OBJECT-TYPE
     SYNTAX       RaisecomVrrpTrackIfEntry
     MAX-ACCESS   not-accessible
     STATUS       current
     DESCRIPTION
         "An entry in the raisecomVrrpTrackTable containing track if of VRRP router."

     INDEX    { ifIndex, vrrpOperVrId , raisecomVrrpTrackIf}
     ::= { raisecomVrrpTrackIfTable 1 }

 RaisecomVrrpTrackIfEntry ::= SEQUENCE {
         raisecomVrrpTrackIf            INTEGER,  
         raisecomVrrpTrackIfPriChg      INTEGER,
         raisecomVrrpTrackIfRowStatus   RowStatus         
         }

 raisecomVrrpTrackIf OBJECT-TYPE
     SYNTAX INTEGER        
     MAX-ACCESS   not-accessible
     STATUS       current
     DESCRIPTION
         "The track if of the virtual router. "
     ::= { raisecomVrrpTrackIfEntry 1 }

 raisecomVrrpTrackIfPriChg OBJECT-TYPE
     SYNTAX INTEGER        
     MAX-ACCESS   read-create
     STATUS       current
     DESCRIPTION
         "The track interface down, then the virtual router priority will reduce this value."
     ::= { raisecomVrrpTrackIfEntry 2 }
     
raisecomVrrpTrackIfRowStatus OBJECT-TYPE
     SYNTAX       RowStatus
     MAX-ACCESS   read-create
     STATUS       current
     DESCRIPTION
         "The row status this entry.used for create/del this entry."
     ::= { raisecomVrrpTrackIfEntry 3 }

END

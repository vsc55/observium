--MibName=BFD
-- *****************************************************************
-- RAISECOM-BFD-MIB.mib:  Raisecom BFD MIB file
--
-- 20110420,tangyoucan 
--
--
-- Copyright (c) 2000-2011 by Raisecom Technology Co., Ltd. 
-- All rights reserved.
-- 01,20111231,ROS00008218,advent mib编译检查
-- *****************************************************************

RAISECOM-BFD-MIB  DEFINITIONS ::= BEGIN

IMPORTS
   MODULE-IDENTITY, OBJECT-TYPE, NOTIFICATION-TYPE,
   Integer32, Unsigned32, Gauge32,
   TimeTicks, Counter32, Counter64,
   IpAddress, Opaque, mib-2,
   zeroDotZero
       FROM SNMPv2-SMI                 -- [RFC2578]
    MODULE-COMPLIANCE,
    NOTIFICATION-GROUP,
    OBJECT-GROUP                        FROM SNMPv2-CONF      
    EnableVar		                    FROM SWITCH-TC 
    TruthValue, RowStatus, StorageType, TimeStamp
        FROM SNMPv2-TC            
    InterfaceIndexOrZero
        FROM IF-MIB
    InetAddress, InetAddressType, InetPortNumber
            FROM INET-ADDRESS-MIB    -- [RFC3291] 

    raisecomAgent                       FROM RAISECOM-BASE-MIB; 

	raisecomBfd MODULE-IDENTITY
        LAST-UPDATED    "201104200000Z"
        ORGANIZATION    "Raisecom Technology Co., Ltd."
        CONTACT-INFO
                "Raisecom Science & Technology Co., ltd.
                 E-mail: support@raisecom.com"
        DESCRIPTION
         "This MIB module is designed for bfd config."
        REVISION   "201104200000Z"
        DESCRIPTION
            "version 1.0.0"
        ::= { raisecomAgent 35 }  
        
--bfd type define start here  
-- draft-ietf-bfd-tc-mib-00.txt  
    BfdSessIndexTC ::= TEXTUAL-CONVENTION
    DISPLAY-HINT   "d"
    STATUS         current
    DESCRIPTION
        "An index used to uniquely identify BFD sessions."
    SYNTAX Unsigned32 (1..4294967295)

    BfdIntervalTC ::= TEXTUAL-CONVENTION
    DISPLAY-HINT  "d"
    STATUS        current
    DESCRIPTION
        "The BFD interval in microseconds."
    SYNTAX Unsigned32 (0..4294967295)

    BfdMultiplierTC ::= TEXTUAL-CONVENTION
    DISPLAY-HINT    "d"
    STATUS          current
    DESCRIPTION
        "The BFD failure detection multiplier."
    SYNTAX Unsigned32 (1..255)

    BfdDiagTC ::= TEXTUAL-CONVENTION
    STATUS       current
    DESCRIPTION
        "A common BFD diagnostic code."
    SYNTAX INTEGER {
        noDiagnostic(0),
        controlDetectionTimeExpired(1),
        echoFunctionFailed(2),
        neighborSignaledSessionDown(3),
        forwardingPlaneReset(4),
        pathDown(5),
        concatenatedPathDown(6),
        administrativelyDown(7),
        reverseConcatenatedPathDown(8)
    }

    BfdSessTypeTC ::= TEXTUAL-CONVENTION
    STATUS        current
    DESCRIPTION
        "BFD session type"

    REFERENCE
        "RFC5880, RFC5881, RFC5883"
    SYNTAX INTEGER {
        singleHop(1),
        multiHopTotallyArbitraryPaths(2),
        multiHopOutOfBandSignaling(3),
        multiHopUnidirectionalLinks(4),
        multiPointHead(5),
        multiPointTail(6)
    }

    BfdSessOperModeTC ::= TEXTUAL-CONVENTION
    STATUS            current
    DESCRIPTION
        "BFD session operating mode"
    REFERENCE
        "RFC5880, Section 3.2"
    SYNTAX INTEGER {
        asyncModeWEchoFunction(1),
        asynchModeWOEchoFunction(2),
        demandModeWEchoFunction(3),
        demandModeWOEchoFunction(4)
    }

    BfdCtrlDestPortNumberTC ::= TEXTUAL-CONVENTION
    DISPLAY-HINT            "d"
    STATUS                  current
    DESCRIPTION
        "UDP destination port number of BFD control packets.
         3784 represents single hop BFD session.
         4784 represents multi hop BFD session.
         However, syntax is left open to wider range of values
         purposely for two reasons:
         1. implementation uses non-compliant port number for
            valid proprietary reason.
         2. potential future extension drafts."
    REFERENCE
        "Port 3784 (RFC5881) and Port 4784 (RFC5883)"
    SYNTAX Unsigned32 (0..65535)

    BfdCtrlSourcePortNumberTC ::= TEXTUAL-CONVENTION
    DISPLAY-HINT              "d"
    STATUS                    current
    DESCRIPTION
        "UDP source port number of BFD control packets.
         However, syntax is left open to wider range of values
         purposely for two reasons:
         1. implementation uses non-compliant port number for
            valid proprietary reason.

         2. potential future extension drafts."
    REFERENCE
        "Port 49152..65535 (RFC5881)"
    SYNTAX Unsigned32 (0..65535)

    BfdSessStateTC ::= TEXTUAL-CONVENTION
    STATUS         current
    DESCRIPTION
        "BFD session state. State failing(5) is only applicable if
         corresponding session is running in BFD version 0."
    REFERENCE
        "draft-katz-ward-bfd-02.txt, RFC5880"
    SYNTAX INTEGER {
        adminDown(1),
        down(2),
        init(3),
        up(4),
        failing(5)
    }

    BfdSessAuthenticationTypeTC ::= TEXTUAL-CONVENTION
    STATUS                      current
    DESCRIPTION
        "BFD authentication type"
    REFERENCE
        "RFC5880, Sections 4.2 - 4.4"
    SYNTAX INTEGER {
        noAuthentication(-1),
        reserved(0),
        simplePassword(1),
        keyedMD5(2),
        meticulousKeyedMD5(3),
        keyedSHA1(4),
        meticulousKeyedSHA1(5)
    }

    BfdSessionAuthenticationKeyTC ::= TEXTUAL-CONVENTION
    DISPLAY-HINT                  "1x "
    STATUS                        current
    DESCRIPTION
        "BFD authentication key type.
    
         A BfdSessionAuthenticationKeyTC is always interpreted within
         the context of an BfdSessAuthenticationTypeTC value.  Every
         usage of the BfdSessionAuthenticationTypeTC textual
         convention is required to specify the the
         BfdSessionAuthenticationKeyTC object that provides the
         context.  It is suggested that the
         BfdSessionAuthentcationTypeTC object be logically registered
         before the object(s) that use the
         BfdSessionAuthenticationKeyTC textual convention, if they
         appear in the same logical row.

         The value of a BfdSessionAuthenticationKeyTC must always be
         consistent with the value of the associated
         BfdSessionAuthencationTypeTC object.  Attempts to set a
         BfdSessionAuthenticationKeyTC object to a value inconsistent
         with the associated BfdSessionAuthenticationTypeTC must fail
         with an inconsistentValue error.

         The following size constraints for a
         BfdSessionAuthenticationKeyTC object are defined for the
         associated BfdSessionAuthenticationTypeTC values show below:

         noAuthentication(-1): SIZE(0)
         reserved(0): SIZE(0)
         simplePassword(1): SIZE(1..16)
         keyedMD5(2): SIZE(16)
         meticulousKeyedMD5(3): SIZE(16)
         keyedSHA1(4): SIZE(20)
         meticulousKeyedSHA1(5): SIZE(20)

         When this textual convention is used as the syntax of an
         index object, there may be issues with the limit of 128
         sub-identifiers specified in SMIv2, STD 58.  In this case,
         the object definition MUST include a 'SIZE' clause to limit
         the number of potential instance sub-identifiers; otherwise
         the applicable constraints MUST be stated in the appropriate
         conceptual row DESCRIPTION clauses, or in the surrounding
         documentation if there is no single DESCRIPTION clause that
         is appropriate."
    REFERENCE
        "RFC5880, Sections 4.2 - 4.4"
    SYNTAX OCTET STRING(SIZE(0..252))

--bfd type define end
--draft-ietf-bfd-tc-mib-00.txt
--bfd mib define start
--draft-ietf-bfd-mib-10.txt
-- Top level components of this MIB module.

    raisecomBfdNotifications OBJECT IDENTIFIER ::= { raisecomBfd 0 }

    raisecomBfdObjects       OBJECT IDENTIFIER ::= { raisecomBfd 1 }
    
    raisecomBfdScalarObjects OBJECT IDENTIFIER ::= { raisecomBfdObjects 1 }
    raisecomBfdConformance   OBJECT IDENTIFIER ::= { raisecomBfd 2 }
 -- BFD General Variables

 -- These parameters apply globally to the Systems'
 -- BFD Process.

    raisecomBfdAdminStatus OBJECT-TYPE
        SYNTAX     INTEGER {
            enabled(1),
            disabled(2)
        }
        MAX-ACCESS read-write
        STATUS     current
        DESCRIPTION
            "The global administrative status of BFD in this router.
             The value 'enabled' denotes that the BFD Process is
             active on at least one interface; 'disabled' disables
             it on all interfaces."
        DEFVAL { enabled }
        ::= { raisecomBfdScalarObjects 1 }

    raisecomBfdSessNotificationsEnable OBJECT-TYPE
        SYNTAX     TruthValue
        MAX-ACCESS read-write
        STATUS     current
        DESCRIPTION
            "If this object is set to true(1), then it enables
             the emission of bfdSessUp and bfdSessDown
             notifications; otherwise these notifications are not
             emitted."
        REFERENCE
            "See also RFC3413 for explanation that
             notifications are under the ultimate control of the
             MIB modules in this document."
        DEFVAL { false }
        ::= { raisecomBfdScalarObjects 2 }  
        
 raisecomBfdRoleMode   OBJECT-TYPE
      SYNTAX      INTEGER 
      {
         activeRole(1),
         passiveRole(2)
      }
      MAX-ACCESS  read-write
      STATUS      current
      DESCRIPTION
         "A system may take either an Active role or a Passive role in session
          initialization.  A system taking the Active role MUST send BFD
          Control packets for a particular session, regardless of whether it
          has received any BFD packets for that session.  A system taking the
          Passive role MUST NOT begin sending BFD packets for a particular
          session until it has received a BFD packet for that session, and thus
          has learned the remote system's discriminator value.  At least one
          system MUST take the Active role (possibly both). "
     DEFVAL { activeRole }
     ::= { raisecomBfdScalarObjects 3 } 
      
raisecomBfdEchoSourceIpType  OBJECT-TYPE
      SYNTAX      InetAddressType
      MAX-ACCESS  read-write
      STATUS      current
      DESCRIPTION
         "This object specifies IP address type of the source IP
             address of echo packet. Only values
             ipv4(1), ipv6(2)have to be supported."
      ::= { raisecomBfdScalarObjects 4 }

raisecomBfdEchoSourceIpAddr  OBJECT-TYPE
      SYNTAX      InetAddress
      MAX-ACCESS  read-write
      STATUS      current
      DESCRIPTION
         "This object specifies the source IP address of echo packet."
      ::= { raisecomBfdScalarObjects 5 }   

raisecomBfdAllSessionsStatisticsClear  OBJECT-TYPE
      SYNTAX      EnableVar
      MAX-ACCESS  read-write
      STATUS      current
      DESCRIPTION
         "This object specifies the the action to clear all sessions statistics.
         set to enable to clear, and then it will change to disable."
      DEFVAL { disable }
      ::= { raisecomBfdScalarObjects 6 } 

 -- BFD Session Table
 -- The BFD Session Table specifies BFD session specific
 -- information.

    raisecomBfdSessTable OBJECT-TYPE
        SYNTAX     SEQUENCE OF RaisecomBfdSessEntry
        MAX-ACCESS not-accessible
        STATUS     current
        DESCRIPTION
            "The BFD Session Table describes the BFD sessions."
        REFERENCE
            "BFD Version 0 (draft-katz-ward-bfd-02.txt) and
             BFD Version 1 (RFC5880)"
        ::= { raisecomBfdObjects 2 }

    raisecomBfdSessEntry OBJECT-TYPE
        SYNTAX     RaisecomBfdSessEntry
        MAX-ACCESS not-accessible
        STATUS     current
        DESCRIPTION
            "The BFD Session Entry describes BFD session."
        INDEX { raisecomBfdSessIndex }
        ::= { raisecomBfdSessTable 1 }

    RaisecomBfdSessEntry ::= SEQUENCE {
        raisecomBfdSessIndex                    BfdSessIndexTC,
        raisecomBfdSessVersionNumber            Unsigned32,
        raisecomBfdSessType                     BfdSessTypeTC,
        raisecomBfdSessDiscriminator            Unsigned32,
        raisecomBfdSessRemoteDiscr              Unsigned32,
        raisecomBfdSessDestinationUdpPort       BfdCtrlDestPortNumberTC,
        raisecomBfdSessSourceUdpPort            BfdCtrlSourcePortNumberTC,
        raisecomBfdSessEchoSourceUdpPort        InetPortNumber,
        raisecomBfdSessAdminStatus              INTEGER,
        raisecomBfdSessState                    BfdSessStateTC,
        raisecomBfdSessRemoteHeardFlag          TruthValue,
        raisecomBfdSessDiag                     BfdDiagTC,
        raisecomBfdSessOperMode                 BfdSessOperModeTC,
        raisecomBfdSessDemandModeDesiredFlag    TruthValue,
        raisecomBfdSessControlPlaneIndepFlag    TruthValue,
        raisecomBfdSessMultipointFlag           TruthValue,
        raisecomBfdSessInterface                InterfaceIndexOrZero,
        raisecomBfdSessSrcAddrType              InetAddressType,
        raisecomBfdSessSrcAddr                  InetAddress,
        raisecomBfdSessDstAddrType              InetAddressType,
        raisecomBfdSessDstAddr                  InetAddress,
        raisecomBfdSessGTSM                     TruthValue,
        raisecomBfdSessGTSMTTL                  Unsigned32,
        raisecomBfdSessDesiredMinTxInterval     BfdIntervalTC,
        raisecomBfdSessReqMinRxInterval         BfdIntervalTC,
        raisecomBfdSessReqMinEchoRxInterval     BfdIntervalTC,
        raisecomBfdSessDetectMult               BfdMultiplierTC,
        raisecomBfdSessNegotiatedInterval       BfdIntervalTC,
        raisecomBfdSessNegotiatedEchoInterval   BfdIntervalTC,
        raisecomBfdSessNegotiatedDetectMult     BfdMultiplierTC,
        raisecomBfdSessAuthPresFlag             TruthValue,
        raisecomBfdSessAuthenticationType       BfdSessAuthenticationTypeTC,
        raisecomBfdSessAuthenticationKeyID      Integer32,
        raisecomBfdSessAuthenticationKey        BfdSessionAuthenticationKeyTC,
        raisecomBfdSessStorType                 StorageType,
        raisecomBfdSessRowStatus                RowStatus,
        raisecomBfdSessTemplateName             OCTET STRING
    }

    raisecomBfdSessIndex OBJECT-TYPE
        SYNTAX     BfdSessIndexTC
        MAX-ACCESS not-accessible
        STATUS     current
        DESCRIPTION
            "This object contains an index used to represent a
             unique BFD session on this device."
        ::= { raisecomBfdSessEntry 1 }

    raisecomBfdSessVersionNumber OBJECT-TYPE
        SYNTAX     Unsigned32 (0..7)
        MAX-ACCESS read-create
        STATUS     current
        DESCRIPTION
            "The version number of the BFD protocol that this session
             is running in. Write access is available for this object
             to provide ability to set desired version for this
             BFD session."
        REFERENCE
            "BFD Version 0 (draft-katz-ward-bfd-02.txt) and
             BFD Version 1 (RFC5880)"
        DEFVAL { 1 }
        ::= { raisecomBfdSessEntry 2 }

    raisecomBfdSessType OBJECT-TYPE
        SYNTAX     BfdSessTypeTC
        MAX-ACCESS read-create
        STATUS     current
        DESCRIPTION
            "This object specifies the type of this BFD session."
        ::= { raisecomBfdSessEntry 3 }

    raisecomBfdSessDiscriminator OBJECT-TYPE
        SYNTAX     Unsigned32 (1..4294967295)
        MAX-ACCESS read-only
        STATUS     current
        DESCRIPTION
            "This object specifies the local discriminator for this BFD
             session, used to uniquely identify it."
        ::= { raisecomBfdSessEntry 4 }

    raisecomBfdSessRemoteDiscr OBJECT-TYPE
        SYNTAX     Unsigned32 (0 | 1..4294967295)
        MAX-ACCESS read-only
        STATUS     current
        DESCRIPTION
            "This object specifies the session discriminator chosen
             by the remote system for this BFD session.  The value may
             be zero(0) if the remote discriminator is not yet known
             or if the session is in the down or adminDown(1) state."
        REFERENCE
            "RFC5880, Section 6.8.6"
        ::= { raisecomBfdSessEntry 5 }

    raisecomBfdSessDestinationUdpPort OBJECT-TYPE
        SYNTAX     BfdCtrlDestPortNumberTC
        MAX-ACCESS read-create
        STATUS     current
        DESCRIPTION
            "This object specifies the destination UDP port number
             used for this BFD session's control packets. The value
             may be zero(0) if the session is in adminDown(1) state."
        DEFVAL { 0 }
        ::= { raisecomBfdSessEntry 6 }

    raisecomBfdSessSourceUdpPort OBJECT-TYPE
        SYNTAX     BfdCtrlSourcePortNumberTC
        MAX-ACCESS read-create
        STATUS     current
        DESCRIPTION
            "This object specifies the source UDP port number used
             for this BFD session's control packets. The value may be
             zero(0) if the session is in adminDown(1) state. Upon
             creation of a new BFD session via this MIB, the value of
             zero(0) specified would permit the implementation to
             chose its own source port number."
        DEFVAL { 0 }
        ::= { raisecomBfdSessEntry 7 }

    raisecomBfdSessEchoSourceUdpPort OBJECT-TYPE
        SYNTAX     InetPortNumber
        MAX-ACCESS read-create
        STATUS     current
        DESCRIPTION
            "This object specifies the source UDP port number used for
             this BFD session's echo packets. The value may be zero(0)
             if the session is not running in the echo mode, or the
             session is in adminDown(1) state. Upon creation of a new
             BFD session via this MIB, the value of zero(0) would
             permit the implementation to chose its own source port
             number."
        DEFVAL { 0 }
        ::= { raisecomBfdSessEntry 8 }

    raisecomBfdSessAdminStatus OBJECT-TYPE
        SYNTAX     INTEGER {
                            stop(1),
                            start(2)
                   }
        MAX-ACCESS read-create
        STATUS     current
        DESCRIPTION
                "A transition from 'stop' to 'start' will start
                 the BFD state machine for the session. The state
                 machine will have an initial state of down.
                 A transition from 'start' to 'stop' will cause
                 the BFD sesssion to be brought down to
                 adminDown(1). Care should be used in providing
                 write access to this object without adequate
                 authentication."
        DEFVAL { 2 }
        ::= { raisecomBfdSessEntry 9 }

    raisecomBfdSessState OBJECT-TYPE
        SYNTAX     BfdSessStateTC
        MAX-ACCESS read-only
        STATUS     current
        DESCRIPTION
            "BFD session state."
        DEFVAL { 2 }
        ::= { raisecomBfdSessEntry 10 }

    raisecomBfdSessRemoteHeardFlag OBJECT-TYPE
        SYNTAX     TruthValue
        MAX-ACCESS read-only
        STATUS     current
        DESCRIPTION
            "This object specifies status of BFD packet reception from
             the remote system. Specifically, it is set to true(1) if
             the local system is actively receiving BFD packets from the
             remote system, and is set to false(2) if the local system
             has not received BFD packets recently (within the detection
             time) or if the local system is attempting to tear down
             the BFD session."
        REFERENCE
            "BFD Version 0 (draft-katz-ward-bfd-02.txt) and
             BFD Version 1 (RFC5880)"
        DEFVAL { false }
        ::= { raisecomBfdSessEntry 11 }

    raisecomBfdSessDiag OBJECT-TYPE
        SYNTAX     BfdDiagTC
        MAX-ACCESS read-only
        STATUS     current
        DESCRIPTION
            "A diagnostic code specifying the local system's reason
             for the last transition of the session from up(4)
             to some other state."
        ::= { raisecomBfdSessEntry 12 }

    raisecomBfdSessOperMode OBJECT-TYPE
        SYNTAX     BfdSessOperModeTC
        MAX-ACCESS read-create
        STATUS     current
        DESCRIPTION
            "This object specifies current operating mode that BFD
             session is operating in."
        ::= { raisecomBfdSessEntry 13 }

    raisecomBfdSessDemandModeDesiredFlag OBJECT-TYPE
        SYNTAX     TruthValue
        MAX-ACCESS read-create
        STATUS     current
        DESCRIPTION
            "This object indicates that the local system's
             desire to use Demand mode. Specifically, it is set
             to true(1) if the local system wishes to use
             Demand mode or false(2) if not"
        DEFVAL { false }
        ::= { raisecomBfdSessEntry 14 }

    raisecomBfdSessControlPlaneIndepFlag OBJECT-TYPE
        SYNTAX     TruthValue
        MAX-ACCESS read-create
        STATUS     current
        DESCRIPTION
            "This object indicates that the local system's
             ability to continue to function through a disruption of
             the control plane. Specifically, it is set
             to true(1) if the local system BFD implementation is
             independent of the control plane. Otherwise, the
             value is set to false(2)"
        DEFVAL { false }
        ::= { raisecomBfdSessEntry 15 }

    raisecomBfdSessMultipointFlag OBJECT-TYPE
        SYNTAX     TruthValue
        MAX-ACCESS read-create
        STATUS     current
        DESCRIPTION
            "This object indicates the Multipoint (M) bit for this
             session. It is set to true(1) if Multipoint (M) bit is
             set to 1. Otherwise, the value is set to false(2)"
        DEFVAL { false }
        ::= { raisecomBfdSessEntry 16 }

    raisecomBfdSessInterface OBJECT-TYPE
        SYNTAX     InterfaceIndexOrZero
        MAX-ACCESS read-create
        STATUS     current
        DESCRIPTION
            "This object contains an interface index used to indicate
             the interface which this BFD session is running on. This
             value can be zero if there is no interface associated
             with this BFD session."
        ::= { raisecomBfdSessEntry 17 }

    raisecomBfdSessSrcAddrType OBJECT-TYPE
        SYNTAX     InetAddressType
        MAX-ACCESS read-create
        STATUS     current
        DESCRIPTION
            "This object specifies IP address type of the source IP
             address of this BFD session. Only values unknown(0),
             ipv4(1), ipv6(2), or ipv6z(4) have to be supported.
             The value of unknown(0) is allowed only when the session
             is singleHop(1) and the source IP address of this BFD
             session is drived from the outgoing interface, or when
             the BFD session is not associated with a specific
             interface. If any other unsupported values are attempted
             in a set operation, the agent MUST return an
             inconsistentValue error."
      ::= { raisecomBfdSessEntry 18 }

    raisecomBfdSessSrcAddr OBJECT-TYPE
        SYNTAX     InetAddress
        MAX-ACCESS read-create
        STATUS     current
        DESCRIPTION
            "This object specifies the source IP address of this BFD
             session."
        ::= { raisecomBfdSessEntry 19 }

    raisecomBfdSessDstAddrType OBJECT-TYPE
        SYNTAX     InetAddressType
        MAX-ACCESS read-create
        STATUS     current
        DESCRIPTION
            "This object specifies IP address type of the neighboring IP
             address which is being monitored with this BFD session.
             Only values unknown(0), ipv4(1), ipv6(2), or ipv6z(4)
             have to be supported. The value of unknown(0) is allowed
             only when the session is singleHop(1) and the outgoing
             interface is of type point-to-point, or when the BFD
             session is not associated with a specific interface. If any
             other unsupported values are attempted in a set operation,
             the agent MUST return an inconsistentValue error."
      ::= { raisecomBfdSessEntry 20 }

    raisecomBfdSessDstAddr OBJECT-TYPE
        SYNTAX     InetAddress
        MAX-ACCESS read-create
        STATUS     current
        DESCRIPTION
            "This object specifies the neighboring IP address which is
             being monitored with this BFD session."
        ::= { raisecomBfdSessEntry 21 }

    raisecomBfdSessGTSM OBJECT-TYPE
        SYNTAX  TruthValue
        MAX-ACCESS read-create
        STATUS current
        DESCRIPTION
           "Setting the value of this object to true(1) will enable GTSM
            protection of the BFD session.  GTSM MUST be enabled on a
            singleHop(1) session if no authentication is in use."
        REFERENCE
           "RFC5082, The Generalized TTL Security Mechanism (GTSM).
            RFC5881, Section 5"
        DEFVAL { false }
        ::= { raisecomBfdSessEntry 22 }

    raisecomBfdSessGTSMTTL OBJECT-TYPE
        SYNTAX Unsigned32 (0..255)
        MAX-ACCESS read-create
        STATUS current
        DESCRIPTION
            "This object is valid only when bfdSessGTSM protection is
             enabled on the system. This object specifies the minimum
             allowed TTL for received BFD control packets. For
             singleHop(1) session, if GTSM protection is enabled,
             this object SHOULD be set to maximum TTL allowed for
             single hop. The value of zero(0) indicates that
             bfdSessGTSM is disabled."
        REFERENCE
           "RFC5082, The Generalized TTL Security Mechanism (GTSM).
            RFC5881, Section 5"
        DEFVAL { 0 }
        ::= { raisecomBfdSessEntry 23 }

    raisecomBfdSessDesiredMinTxInterval OBJECT-TYPE
        SYNTAX     BfdIntervalTC
        MAX-ACCESS read-create
        STATUS     current
        DESCRIPTION
            "This object specifies the minimum interval, in
             microseconds, that the local system would like to use
             when transmitting BFD Control packets. The value of
             zero(0) is reserved, and should not be used."
        REFERENCE
            "RFC5880, Section 4.1"
        ::= { raisecomBfdSessEntry 24 }

    raisecomBfdSessReqMinRxInterval OBJECT-TYPE
        SYNTAX     BfdIntervalTC
        MAX-ACCESS read-create
        STATUS     current
        DESCRIPTION
            "This object specifies the minimum interval, in
             microseconds, between received  BFD Control packets the
             local system is capable of supporting. The value of
             zero(0) can be specified when the transmitting system
             does not want the remote system to send any periodic BFD
             control packets."
        REFERENCE
            "RFC5880, Section 4.1"
        ::= { raisecomBfdSessEntry 25 }

    raisecomBfdSessReqMinEchoRxInterval OBJECT-TYPE
        SYNTAX     BfdIntervalTC
        MAX-ACCESS read-create
        STATUS     current
        DESCRIPTION
            "This object specifies the minimum interval, in
             microseconds, between received BFD Echo packets that this
             system is capable of supporting. Value must be zero(0) if
             this is a multihop BFD session."
        ::= { raisecomBfdSessEntry 26 }

    raisecomBfdSessDetectMult OBJECT-TYPE
        SYNTAX     BfdMultiplierTC
        MAX-ACCESS read-create
        STATUS     current
        DESCRIPTION
            "This object specifies the Detect time multiplier."
        ::= { raisecomBfdSessEntry 27 }

    raisecomBfdSessNegotiatedInterval OBJECT-TYPE
        SYNTAX     BfdIntervalTC
        MAX-ACCESS read-only
        STATUS     current
        DESCRIPTION
            "This object specifies the negotiated interval, in
             microseconds, that the local system is transmitting
             BFD Control packets."
        ::= { raisecomBfdSessEntry 28 }

    raisecomBfdSessNegotiatedEchoInterval OBJECT-TYPE
        SYNTAX     BfdIntervalTC
        MAX-ACCESS read-only
        STATUS     current
        DESCRIPTION
            "This object specifies the negotiated interval, in
             microseconds, that the local system is transmitting
             BFD echo packets. Value is expected to be zero if
             the sessions is not running in echo mode."
        ::= { raisecomBfdSessEntry 29 }

    raisecomBfdSessNegotiatedDetectMult OBJECT-TYPE
        SYNTAX     BfdMultiplierTC
        MAX-ACCESS read-only
        STATUS     current
        DESCRIPTION
            "This object specifies the Detect time multiplier."
        ::= { raisecomBfdSessEntry 30 }

    raisecomBfdSessAuthPresFlag OBJECT-TYPE
        SYNTAX     TruthValue
        MAX-ACCESS read-create
        STATUS     current
        DESCRIPTION
            "This object indicates that the local system's
             desire to use Authentication. Specifically, it is set
             to true(1) if the local system wishes the session
             to be authenticated or false(2) if not."
        REFERENCE
            "RFC5880, Sections 4.2 - 4.4"
        DEFVAL { false }
        ::= { raisecomBfdSessEntry 31 }

    raisecomBfdSessAuthenticationType OBJECT-TYPE
        SYNTAX     BfdSessAuthenticationTypeTC
        MAX-ACCESS read-create
        STATUS     current
        DESCRIPTION
            "The Authentication Type used for this BFD session.
             This field is valid only when the Authentication
             Present bit is set. Max-access to this object as well as
             other authentication related objects are set to
             read-create in order to support management of a single
             key ID at a time, key rotation is not handled. Key update
             in practice must be done by atomic update using a set
             containing all affected objects in the same varBindList
             or otherwise risk the session dropping. Value -1
             indicates that no authentication is in use for this
             session."
        REFERENCE
            "RFC5880, Sections 4.2 - 4.4"
        DEFVAL { -1 }
        ::= { raisecomBfdSessEntry 32 }

    raisecomBfdSessAuthenticationKeyID OBJECT-TYPE
        SYNTAX     Integer32 (-1 | 0..255)
        MAX-ACCESS read-create
        STATUS     current
        DESCRIPTION
            "The authentication key ID in use for this session.  This
             object permits multiple keys to be active simultaneously.
             When bfdSessAuthPresFlag is false(2), then the value
             of this object MUST be -1.  The value -1 indicates that
             no Authentication Key ID will be present in the optional
             BFD Authentication Section."
        REFERENCE
            "RFC5880, Sections 4.2 - 4.4"
        DEFVAL { -1 }
        ::= { raisecomBfdSessEntry 33 }

    raisecomBfdSessAuthenticationKey OBJECT-TYPE
        SYNTAX     BfdSessionAuthenticationKeyTC
        MAX-ACCESS read-create
        STATUS     current
        DESCRIPTION
            "The authentication key.  When the
             bfdSessAuthenticationType is simplePassword(1), the value
             of this object is the password present in the BFD packets.

             When the bfdSessAuthentication type is one of the keyed
             authentication types, this value is used in the
             computation of the key present in the BFD authentication
             packet."
        REFERENCE
            "RFC5880, Sections 4.2 - 4.4"
        ::= { raisecomBfdSessEntry 34 }

    raisecomBfdSessStorType OBJECT-TYPE
        SYNTAX     StorageType
        MAX-ACCESS read-create
        STATUS     current
        DESCRIPTION
            "This variable indicates the storage type for this
             object. Conceptual rows having the value
             'permanent' need not allow write-access to any
             columnar objects in the row."
        ::= { raisecomBfdSessEntry 35 }

    raisecomBfdSessRowStatus OBJECT-TYPE
        SYNTAX     RowStatus
        MAX-ACCESS read-create
        STATUS     current
        DESCRIPTION
            "This variable is used to create, modify, and/or
             delete a row in this table. When a row in this
             table has a row in the active(1) state, no
             objects in this row can be modified except the
             bfdSessRowStatus and bfdSessStorageType."
        ::= { raisecomBfdSessEntry 36 }

    raisecomBfdSessTemplateName OBJECT-TYPE
       SYNTAX     OCTET STRING (SIZE(1..32))
       MAX-ACCESS read-create
       STATUS     current
       DESCRIPTION
       "This object specifies the name of BFD template."
       ::= { raisecomBfdSessEntry 37 }

 -- BFD Session Performance Table

    raisecomBfdSessPerfTable OBJECT-TYPE
        SYNTAX     SEQUENCE OF RaisecomBfdSessPerfEntry
        MAX-ACCESS not-accessible
        STATUS     current
        DESCRIPTION
            "This table specifies BFD Session performance counters."
        ::= { raisecomBfdObjects 3 }

    raisecomBfdSessPerfEntry OBJECT-TYPE
        SYNTAX     RaisecomBfdSessPerfEntry
        MAX-ACCESS not-accessible
        STATUS     current
        DESCRIPTION
            "An entry in this table is created by a BFD-enabled node
             for every BFD Session. bfdSessPerfDiscTime is used to
             indicate potential discontinuity for all counter objects
             in this table."
        AUGMENTS    { raisecomBfdSessEntry }
        ::= { raisecomBfdSessPerfTable 1 }

    RaisecomBfdSessPerfEntry ::= SEQUENCE {
       raisecomBfdSessPerfCtrlPktIn           Counter32,
       raisecomBfdSessPerfCtrlPktOut          Counter32,
       raisecomBfdSessPerfCtrlPktDrop         Counter32,
       raisecomBfdSessPerfCtrlPktDropLastTime TimeStamp,
       raisecomBfdSessPerfEchoPktIn           Counter32,
       raisecomBfdSessPerfEchoPktOut          Counter32,
       raisecomBfdSessPerfEchoPktDrop         Counter32,
       raisecomBfdSessPerfEchoPktDropLastTime TimeStamp,
       raisecomBfdSessUpTime                  TimeStamp,
       raisecomBfdSessPerfLastSessDownTime    TimeStamp,
       raisecomBfdSessPerfLastCommLostDiag    BfdDiagTC,
       raisecomBfdSessPerfSessUpCount         Counter32,
       raisecomBfdSessPerfDiscTime            TimeStamp,

       -- High Capacity Counters
       raisecomBfdSessPerfCtrlPktInHC         Counter64,
       raisecomBfdSessPerfCtrlPktOutHC        Counter64,
       raisecomBfdSessPerfCtrlPktDropHC       Counter64,
       raisecomBfdSessPerfEchoPktInHC         Counter64,
       raisecomBfdSessPerfEchoPktOutHC        Counter64,
       raisecomBfdSessPerfEchoPktDropHC       Counter64
    }

 -- Ed Note: should we add per-diag code counts here,

    raisecomBfdSessPerfCtrlPktIn OBJECT-TYPE
        SYNTAX     Counter32
        MAX-ACCESS read-only
        STATUS     current
        DESCRIPTION
            "The total number of BFD control messages received for this
             BFD session. This value MUST be equal to the least
             significant 32 bits of bfdSessPerfCtrlPktInHC."
        ::= { raisecomBfdSessPerfEntry 1 }

    raisecomBfdSessPerfCtrlPktOut OBJECT-TYPE
        SYNTAX     Counter32
        MAX-ACCESS read-only
        STATUS     current
        DESCRIPTION
            "The total number of BFD control messages sent for this BFD
             session. This value MUST be equal to the least significant
             32 bits of bfdSessPerfCtrlPktOutHC."
        ::= { raisecomBfdSessPerfEntry 2 }

    raisecomBfdSessPerfCtrlPktDrop OBJECT-TYPE
        SYNTAX     Counter32
        MAX-ACCESS read-only
        STATUS     current
        DESCRIPTION
            "The total number of BFD control messages received for this
             session yet dropped for being invalid. This value MUST be
             equal to the least significant 32 bits of
             bfdSessPerfCtrlPktDropHC."
        ::= { raisecomBfdSessPerfEntry 3 }

    raisecomBfdSessPerfCtrlPktDropLastTime OBJECT-TYPE
        SYNTAX     TimeStamp
        MAX-ACCESS read-only
        STATUS     current
        DESCRIPTION
            "The value of sysUpTime on the most recent occasion at
             which received BFD control message for this session was
             dropped. If no such up event exists, this object contains
             a zero value."
        ::= { raisecomBfdSessPerfEntry 4 }

    raisecomBfdSessPerfEchoPktIn OBJECT-TYPE
        SYNTAX     Counter32
        MAX-ACCESS read-only
        STATUS     current
        DESCRIPTION
            "The total number of BFD echo messages received for this
             BFD session. This value MUST be equal to the least
             significant 32 bits of bfdSessPerfEchoPktInHC."
        ::= { raisecomBfdSessPerfEntry 5 }

    raisecomBfdSessPerfEchoPktOut OBJECT-TYPE
        SYNTAX     Counter32
        MAX-ACCESS read-only
        STATUS     current
        DESCRIPTION
            "The total number of BFD echo messages sent for this BFD
             session. This value MUST be equal to the least significant
             32 bits of bfdSessPerfEchoPktOutHC."
        ::= { raisecomBfdSessPerfEntry 6 }

    raisecomBfdSessPerfEchoPktDrop OBJECT-TYPE
        SYNTAX     Counter32
        MAX-ACCESS read-only
        STATUS     current
        DESCRIPTION
            "The total number of BFD echo messages received for this
             session yet dropped for being invalid. This value MUST be
             equal to the least significant 32 bits of
             bfdSessPerfEchoPktDropHC."
        ::= { raisecomBfdSessPerfEntry 7 }

    raisecomBfdSessPerfEchoPktDropLastTime OBJECT-TYPE
        SYNTAX     TimeStamp
        MAX-ACCESS read-only
        STATUS     current
        DESCRIPTION
            "The value of sysUpTime on the most recent occasion at
             which received BFD echo message for this session was
             dropped. If no such up event exists, this object contains
             a zero value."
        ::= { raisecomBfdSessPerfEntry 8 }

    raisecomBfdSessUpTime OBJECT-TYPE
        SYNTAX     TimeStamp
        MAX-ACCESS read-only
        STATUS     current
        DESCRIPTION
            "The value of sysUpTime on the most recent occasion at which
             the session came up. If no such up event exists this object
             contains a zero value."
        ::= { raisecomBfdSessPerfEntry 9 }

    raisecomBfdSessPerfLastSessDownTime OBJECT-TYPE
        SYNTAX     TimeStamp
        MAX-ACCESS read-only
        STATUS     current
        DESCRIPTION
            "The value of sysUpTime on the most recent occasion at
             which the last time communication was lost with the
             neighbor. If no such down event exist this object
             contains a zero value."
        ::= { raisecomBfdSessPerfEntry 10 }

    raisecomBfdSessPerfLastCommLostDiag OBJECT-TYPE
        SYNTAX     BfdDiagTC
        MAX-ACCESS read-only
        STATUS     current
        DESCRIPTION
            "The BFD diag code for the last time communication was lost
             with the neighbor. If no such down event exists this object
             contains a zero value."
        ::= { raisecomBfdSessPerfEntry 11 }

    raisecomBfdSessPerfSessUpCount OBJECT-TYPE
        SYNTAX     Counter32
        MAX-ACCESS read-only
        STATUS     current
        DESCRIPTION
            "The number of times this session has gone into the Up
             state since the system last rebooted."
        ::= { raisecomBfdSessPerfEntry 12 }

    raisecomBfdSessPerfDiscTime OBJECT-TYPE
        SYNTAX     TimeStamp
        MAX-ACCESS read-only
        STATUS     current
        DESCRIPTION
          "The value of sysUpTime on the most recent occasion at
           which any one or more of the session counters suffered
           a discontinuity.
           The relevant counters are the specific instances associated
           with this BFD session of any Counter32 object contained in
           the BfdSessPerfTable. If no such discontinuities have
           occurred since the last re-initialization of the local
           management subsystem, then this object contains a zero
           value."
        ::= { raisecomBfdSessPerfEntry 13 }

    raisecomBfdSessPerfCtrlPktInHC OBJECT-TYPE
        SYNTAX     Counter64
        MAX-ACCESS read-only
        STATUS     current
        DESCRIPTION
            "This value represents the total number of BFD control
             messages received for this BFD session."
        ::= { raisecomBfdSessPerfEntry 14 }

    raisecomBfdSessPerfCtrlPktOutHC OBJECT-TYPE
        SYNTAX     Counter64
        MAX-ACCESS read-only
        STATUS     current
        DESCRIPTION
            "This value represents the total number of BFD control
             messages transmitted for this BFD session."
        ::= { raisecomBfdSessPerfEntry 15 }

    raisecomBfdSessPerfCtrlPktDropHC OBJECT-TYPE
        SYNTAX     Counter64
        MAX-ACCESS read-only
        STATUS     current
        DESCRIPTION
            "This value represents the total number of BFD control
             messages received for this BFD session yet dropped for
             being invalid."
        ::= { raisecomBfdSessPerfEntry 16 }

    raisecomBfdSessPerfEchoPktInHC OBJECT-TYPE
        SYNTAX     Counter64
        MAX-ACCESS read-only
        STATUS     current
        DESCRIPTION
            "This value represents the total number of BFD echo
             messages received for this BFD session."
        ::= { raisecomBfdSessPerfEntry 17 }

    raisecomBfdSessPerfEchoPktOutHC OBJECT-TYPE
        SYNTAX     Counter64
        MAX-ACCESS read-only
        STATUS     current
        DESCRIPTION
            "This value represents the total number of BFD echo
             messages transmitted for this BFD session."
        ::= { raisecomBfdSessPerfEntry 18 }

    raisecomBfdSessPerfEchoPktDropHC OBJECT-TYPE
        SYNTAX     Counter64
        MAX-ACCESS read-only
        STATUS     current
        DESCRIPTION
            "This value represents the total number of BFD echo
             messages received for this BFD session yet dropped
             for being invalid."
        ::= { raisecomBfdSessPerfEntry 19 }

 -- BFD Session Discriminator Mapping Table

    raisecomBfdSessDiscMapTable OBJECT-TYPE
        SYNTAX     SEQUENCE OF RaisecomBfdSessDiscMapEntry
        MAX-ACCESS not-accessible
        STATUS     current
        DESCRIPTION
            "The BFD Session Discriminator Mapping Table maps a
             local discriminator value to associated BFD session's
             BfdSessIndexTC used in the bfdSessionTable."
        ::= { raisecomBfdObjects 4 }

    raisecomBfdSessDiscMapEntry OBJECT-TYPE
        SYNTAX     RaisecomBfdSessDiscMapEntry
        MAX-ACCESS not-accessible
        STATUS     current
        DESCRIPTION
            "The BFD Session Discriminator Map Entry describes
             BFD session that is mapped to this BfdSessIndexTC."
        INDEX { raisecomBfdSessDiscriminator }
        ::= { raisecomBfdSessDiscMapTable 1 }

    RaisecomBfdSessDiscMapEntry ::= SEQUENCE {
        raisecomBfdSessDiscMapIndex            BfdSessIndexTC
    }

    raisecomBfdSessDiscMapIndex OBJECT-TYPE
        SYNTAX     BfdSessIndexTC
        MAX-ACCESS read-only
        STATUS     current
        DESCRIPTION
            "This object specifies the BfdSessIndexTC referred to by
             the indices of this row. In essence, a mapping is
             provided between these indexes and the BfdSessTable."
        ::= { raisecomBfdSessDiscMapEntry 1 }

 -- BFD Session IP Mapping Table

    raisecomBfdSessIpMapTable OBJECT-TYPE
        SYNTAX     SEQUENCE OF RaisecomBfdSessIpMapEntry
        MAX-ACCESS not-accessible
        STATUS     current
        DESCRIPTION
            "The BFD Session IP Mapping Table maps given
             bfdSessInterface, bfdSessSrcAddrType, bfdSessSrcAddr,
             bfdSessDstAddrType and bfdSessDstAddr
             to an associated BFD session's BfdSessIndexTC used in
             the bfdSessionTable."
        ::= { raisecomBfdObjects 5 }

    raisecomBfdSessIpMapEntry OBJECT-TYPE
        SYNTAX     RaisecomBfdSessIpMapEntry
        MAX-ACCESS not-accessible
        STATUS     current
        DESCRIPTION
           "The BFD Session IP Map Entry describes
            BFD session that is mapped to this BfdSessIndexTC."
        INDEX {
            raisecomBfdSessInterface,
            raisecomBfdSessSrcAddrType,
            raisecomBfdSessSrcAddr,
            raisecomBfdSessDstAddrType,
            raisecomBfdSessDstAddr
        }
        ::= { raisecomBfdSessIpMapTable 1 }

    RaisecomBfdSessIpMapEntry ::= SEQUENCE {
        raisecomBfdSessIpMapIndex            BfdSessIndexTC
    }

    raisecomBfdSessIpMapIndex OBJECT-TYPE
        SYNTAX     BfdSessIndexTC
        MAX-ACCESS read-only
        STATUS     current
        DESCRIPTION
            "This object specifies the BfdSessIndexTC referred to by
             the indexes of this row. In essence, a mapping is
             provided between these indexes and the BfdSessTable."
        ::= { raisecomBfdSessIpMapEntry 1 }

 -- Notification Configuration

    raisecomBfdSessUp NOTIFICATION-TYPE
        OBJECTS {
            raisecomBfdSessDiag, -- low range value
            raisecomBfdSessDiag  -- high range value
        }
        STATUS     current
        DESCRIPTION
            "This notification is generated when the
             bfdSessState object for one or more contiguous
             entries in bfdSessTable are about to enter the up(4)
             state from some other state. The included values of
             bfdSessDiag MUST both be set equal to this
             new state (i.e: up(4)).  The two instances of
             bfdSessDiag in this notification indicate the range
             of indexes that are affected.  Note that all the indexes
             of the two ends of the range can be derived from the
             instance identifiers of these two objects.  For the
             cases where a contiguous range of sessions
             have transitioned into the up(4) state at roughly
             the same time, the device SHOULD issue a single
             notification for each range of contiguous indexes in
             an effort to minimize the emission of a large number
             of notifications.  If a notification has to be
             issued for just a single bfdSessEntry, then
             the instance identifier (and values) of the two
             bfdSessDiag objects MUST be the identical."
        ::= { raisecomBfdNotifications 1 }

    raisecomBfdSessDown NOTIFICATION-TYPE
        OBJECTS {
            raisecomBfdSessDiag, -- low range value
            raisecomBfdSessDiag  -- high range value
        }
        STATUS     current
        DESCRIPTION
            "This notification is generated when the
             bfdSessState object for one or more contiguous
             entries in bfdSessTable are about to enter the down(2)
             or adminDown(1) states from some other state. The included
             values of bfdSessDiag MUST both be set equal to this new
             state (i.e: down(2) or adminDown(1)).  The two instances
             of bfdSessDiag in this notification indicate the range
             of indexes that are affected.  Note that all the indexes
             of the two ends of the range can be derived from the
             instance identifiers of these two objects.  For
             cases where a contiguous range of sessions
             have transitioned into the down(2) or adminDown(1) states
             at roughly the same time, the device SHOULD issue a single
             notification for each range of contiguous indexes in
             an effort to minimize the emission of a large number
             of notifications.  If a notification has to be
             issued for just a single bfdSessEntry, then
             the instance identifier (and values) of the two
             bfdSessDiag objects MUST be the identical."
        ::= { raisecomBfdNotifications 2 }

 -- Ed Note: We need to add notification for changes
 -- when the two ends automatically negotiate to a new detection time
 -- value or when detection multiplier changes.
 -- Module compliance.

    raisecomBfdGroups
        OBJECT IDENTIFIER ::= { raisecomBfdConformance 1 }

    raisecomBfdCompliances
        OBJECT IDENTIFIER ::= { raisecomBfdConformance 2 }
     
-- bfd scalar object define end  
-- bfd interface var define  
raisecomBfdIfTable OBJECT-TYPE
   SYNTAX      SEQUENCE OF RaisecomBfdIfEntry
   MAX-ACCESS  not-accessible
   STATUS      current
   DESCRIPTION
       "This table contains session information of this interface."
   ::= { raisecomBfdObjects 6 }

raisecomBfdIfEntry OBJECT-TYPE
   SYNTAX      RaisecomBfdIfEntry
   MAX-ACCESS  not-accessible
   STATUS      current
   DESCRIPTION
       "Session information of this interface."
   INDEX       { raisecomBfdIfIndex  }
   ::= { raisecomBfdIfTable 1 }
   
   RaisecomBfdIfEntry ::= SEQUENCE {
   raisecomBfdIfIndex                   Unsigned32,
   raisecomBfdIfDesiredMinTxInterval    Unsigned32,  
   raisecomBfdIfReqMinRxInterval        Unsigned32,
   raisecomBfdIfDetectMult              Unsigned32,
   raisecomBfdIfReqMinEchoRxInterval    Unsigned32, 
   raisecomBfdIfAuthPresFlag            TruthValue,
   raisecomBfdIfAuthenticationType      BfdSessAuthenticationTypeTC,
   raisecomBfdIfAuthenticationKeyID     Integer32,
   raisecomBfdIfAuthenticationKey       BfdSessionAuthenticationKeyTC,
   raisecomBfdIfDemandModeDesiredFlag   TruthValue
   } 
   
raisecomBfdIfIndex OBJECT-TYPE
   SYNTAX     Unsigned32
   MAX-ACCESS not-accessible
   STATUS     current
   DESCRIPTION
       "This object contains an interface index used to indicate
             the interface which this BFD session is running on. "
   ::= { raisecomBfdIfEntry 1 }

raisecomBfdIfDesiredMinTxInterval OBJECT-TYPE
   SYNTAX     Unsigned32
   MAX-ACCESS read-write
   STATUS     current
   DESCRIPTION
       "This object specifies the minimum interval, in
             microseconds, that the local system would like to use
             when transmitting BFD Control packets in this interface. 
             The value of zero(0) is reserved, and should not be used." 
   DEFVAL { 500 }
   ::= { raisecomBfdIfEntry 2 }

raisecomBfdIfReqMinRxInterval OBJECT-TYPE
   SYNTAX     Unsigned32
   MAX-ACCESS read-write
   STATUS     current
   DESCRIPTION
       "This object specifies the minimum interval, in
             microseconds, between received  BFD Control packets the
             local system is capable of supporting. The value of
             zero(0) can be specified when the transmitting system
             does not want the remote system to send any periodic BFD
             control packets."
   DEFVAL { 500 }
   ::= { raisecomBfdIfEntry 3 }


raisecomBfdIfDetectMult OBJECT-TYPE
   SYNTAX     Unsigned32
   MAX-ACCESS read-write
   STATUS     current
   DESCRIPTION
       "This object specifies the Detect time multiplier."  
   DEFVAL { 3 }
   ::= { raisecomBfdIfEntry 4 }
 
raisecomBfdIfReqMinEchoRxInterval OBJECT-TYPE
   SYNTAX     Unsigned32
   MAX-ACCESS read-write
   STATUS     current
   DESCRIPTION
       "This object specifies the minimum interval, in
             microseconds, between received BFD Echo packets that this
             system is capable of supporting. Value must be zero(0) if
             not support echo function."
   DEFVAL { 500 }
   ::= { raisecomBfdIfEntry 5 } 
   
raisecomBfdIfAuthPresFlag OBJECT-TYPE
        SYNTAX     TruthValue
        MAX-ACCESS read-write
        STATUS     current
        DESCRIPTION
            "This object indicates that the local system's
             desire to use Authentication. Specifically, it is set
             to true(1) if the local system wishes the session
             to be authenticated or false(2) if not."
        REFERENCE
            "RFC5880, Sections 4.2 - 4.4"
        DEFVAL { false }
        ::= { raisecomBfdIfEntry 6 }

raisecomBfdIfAuthenticationType OBJECT-TYPE
        SYNTAX     BfdSessAuthenticationTypeTC
        MAX-ACCESS read-write
        STATUS     current
        DESCRIPTION
            "The Authentication Type used for this BFD session.
             This field is valid only when the Authentication
             Present bit is set. Max-access to this object as well as
             other authentication related objects are set to
             read-create in order to support management of a single
             key ID at a time, key rotation is not handled. Key update
             in practice must be done by atomic update using a set
             containing all affected objects in the same varBindList
             or otherwise risk the session dropping. Value -1
             indicates that no authentication is in use for this
             session."
        REFERENCE
            "RFC5880, Sections 4.2 - 4.4"
        DEFVAL { -1 }
        ::= { raisecomBfdIfEntry 7 }
raisecomBfdIfAuthenticationKeyID OBJECT-TYPE
        SYNTAX     Integer32 (-1 | 0..255)
        MAX-ACCESS read-write
        STATUS     current
        DESCRIPTION
            "The authentication key ID in use for this session.  This
             object permits multiple keys to be active simultaneously.
             When bfdSessAuthPresFlag is false(2), then the value
             of this object MUST be -1.  The value -1 indicates that
             no Authentication Key ID will be present in the optional
             BFD Authentication Section."
        REFERENCE
            "RFC5880, Sections 4.2 - 4.4"
        DEFVAL { -1 }
        ::= { raisecomBfdIfEntry 8 }

raisecomBfdIfAuthenticationKey OBJECT-TYPE
        SYNTAX     BfdSessionAuthenticationKeyTC
        MAX-ACCESS read-write
        STATUS     current
        DESCRIPTION
            "The authentication key.  When the
             bfdSessAuthenticationType is simplePassword(1), the value
             of this object is the password present in the BFD packets.

             When the bfdSessAuthentication type is one of the keyed
             authentication types, this value is used in the
             computation of the key present in the BFD authentication
             packet."
        REFERENCE
            "RFC5880, Sections 4.2 - 4.4"
        ::= { raisecomBfdIfEntry 9 }  
        
raisecomBfdIfDemandModeDesiredFlag OBJECT-TYPE
        SYNTAX     TruthValue
        MAX-ACCESS read-write
        STATUS     current
        DESCRIPTION
            "This object indicates that the local if's
             desire to use Demand mode. Specifically, it is set
             to true(1) if the local if wishes to use
             Demand mode or false(2) if not"
        DEFVAL { false }
        ::= { raisecomBfdIfEntry 10 }
                
-- bfd interface var define end 
-- bfd session template define   
raisecomBfdTemplateTable OBJECT-TYPE
   SYNTAX      SEQUENCE OF RaisecomBfdTemplateEntry
   MAX-ACCESS  not-accessible
   STATUS      current
   DESCRIPTION
       "This table contains session information of this BFD template."
   ::= { raisecomBfdObjects 7 } 

raisecomBfdTemplateEntry OBJECT-TYPE
   SYNTAX      RaisecomBfdTemplateEntry
   MAX-ACCESS  not-accessible
   STATUS      current
   DESCRIPTION
       "Session information of this BFD template."
   INDEX       { raisecomBfdTemplateName}
   ::= { raisecomBfdTemplateTable 1 }
   
   RaisecomBfdTemplateEntry ::= SEQUENCE {
   raisecomBfdTemplateName                    OCTET STRING ,  
   raisecomBfdTemplateType                    BfdSessTypeTC,
   raisecomBfdTemplateDesiredMinTxInterval    Unsigned32,  
   raisecomBfdTemplateReqMinRxInterval        Unsigned32,
   raisecomBfdTemplateDetectMult              Unsigned32,
   raisecomBfdTemplateAuthPresFlag            TruthValue,
   raisecomBfdTemplateAuthenticationType      BfdSessAuthenticationTypeTC,
   raisecomBfdTemplateAuthenticationKeyID     Integer32,
   raisecomBfdTemplateAuthenticationKey       BfdSessionAuthenticationKeyTC, 
   raisecomBfdTemplateDemandModeDesiredFlag   TruthValue,
   raisecomBfdTemplateRowStatus               RowStatus
   } 
   
raisecomBfdTemplateName OBJECT-TYPE
   SYNTAX     OCTET STRING (SIZE(1..32))
   MAX-ACCESS not-accessible
   STATUS     current
   DESCRIPTION
       "This object specifies the name of BFD template."
   ::= { raisecomBfdTemplateEntry 1 }  
   
raisecomBfdTemplateType OBJECT-TYPE
        SYNTAX     BfdSessTypeTC
        MAX-ACCESS read-create
        STATUS     current
        DESCRIPTION
            "This object specifies the type of this BFD session template."
        ::= { raisecomBfdTemplateEntry 2 }

raisecomBfdTemplateDesiredMinTxInterval OBJECT-TYPE
   SYNTAX     Unsigned32
   MAX-ACCESS read-create
   STATUS     current
   DESCRIPTION
       "This object specifies the minimum interval, in
             microseconds, that the local system would like to use
             when transmitting BFD Control packets in this template. 
             The value of zero(0) is reserved, and should not be used." 
   DEFVAL { 500 }
   ::= { raisecomBfdTemplateEntry 3 }

raisecomBfdTemplateReqMinRxInterval OBJECT-TYPE
   SYNTAX     Unsigned32
   MAX-ACCESS read-create
   STATUS     current
   DESCRIPTION
       "This object specifies the minimum interval, in
             microseconds, between received  BFD Control packets the
             local system is capable of supporting. The value of
             zero(0) can be specified when the transmitting system
             does not want the remote system to send any periodic BFD
             control packets." 
   DEFVAL { 500 }
   ::= { raisecomBfdTemplateEntry 4 }


raisecomBfdTemplateDetectMult OBJECT-TYPE
   SYNTAX     Unsigned32
   MAX-ACCESS read-create
   STATUS     current
   DESCRIPTION
       "This object specifies the Detect time multiplier." 
   DEFVAL { 3 }
   ::= { raisecomBfdTemplateEntry 5 }

raisecomBfdTemplateAuthPresFlag OBJECT-TYPE
        SYNTAX     TruthValue
        MAX-ACCESS read-write
        STATUS     current
        DESCRIPTION
            "This object indicates that the local system's
             desire to use Authentication. Specifically, it is set
             to true(1) if the local system wishes the session
             to be authenticated or false(2) if not."
        REFERENCE
            "RFC5880, Sections 4.2 - 4.4"
        DEFVAL { false }
        ::= { raisecomBfdTemplateEntry 6 }

raisecomBfdTemplateAuthenticationType OBJECT-TYPE
        SYNTAX     BfdSessAuthenticationTypeTC
        MAX-ACCESS read-write
        STATUS     current
        DESCRIPTION
            "The Authentication Type used for this BFD session.
             This field is valid only when the Authentication
             Present bit is set. Max-access to this object as well as
             other authentication related objects are set to
             read-create in order to support management of a single
             key ID at a time, key rotation is not handled. Key update
             in practice must be done by atomic update using a set
             containing all affected objects in the same varBindList
             or otherwise risk the session dropping. Value -1
             indicates that no authentication is in use for this
             session."
        REFERENCE
            "RFC5880, Sections 4.2 - 4.4"
        DEFVAL { -1 }
        ::= { raisecomBfdTemplateEntry 7 }
raisecomBfdTemplateAuthenticationKeyID OBJECT-TYPE
        SYNTAX     Integer32 (-1 | 0..255)
        MAX-ACCESS read-write
        STATUS     current
        DESCRIPTION
            "The authentication key ID in use for this session.  This
             object permits multiple keys to be active simultaneously.
             When bfdSessAuthPresFlag is false(2), then the value
             of this object MUST be -1.  The value -1 indicates that
             no Authentication Key ID will be present in the optional
             BFD Authentication Section."
        REFERENCE
            "RFC5880, Sections 4.2 - 4.4"
        DEFVAL { -1 }
        ::= { raisecomBfdTemplateEntry 8 }

raisecomBfdTemplateAuthenticationKey OBJECT-TYPE
        SYNTAX     BfdSessionAuthenticationKeyTC
        MAX-ACCESS read-write
        STATUS     current
        DESCRIPTION
            "The authentication key.  When the
             bfdSessAuthenticationType is simplePassword(1), the value
             of this object is the password present in the BFD packets.

             When the bfdSessAuthentication type is one of the keyed
             authentication types, this value is used in the
             computation of the key present in the BFD authentication
             packet."
        REFERENCE
            "RFC5880, Sections 4.2 - 4.4"
        ::= { raisecomBfdTemplateEntry 9 }

raisecomBfdTemplateDemandModeDesiredFlag OBJECT-TYPE
        SYNTAX     TruthValue
        MAX-ACCESS read-write
        STATUS     current
        DESCRIPTION
            "This object indicates that the local template's
             desire to use Demand mode. Specifically, it is set
             to true(1) if the local template wishes to use
             Demand mode or false(2) if not"
        DEFVAL { false }
        ::= { raisecomBfdTemplateEntry 10 }

raisecomBfdTemplateRowStatus OBJECT-TYPE
   SYNTAX     RowStatus
   MAX-ACCESS read-create
   STATUS     current
   DESCRIPTION
       "Row status of this template." 
   ::= { raisecomBfdTemplateEntry 11 } 
   
-- bfd session template define end
  END

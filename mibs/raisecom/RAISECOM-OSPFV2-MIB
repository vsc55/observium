-- *****************************************************************
-- RAISECOM-OSPFv2-MIB.mib
--
-- September 2011, wangmingzhou
--
-- Copyright(c) 2011-2013 by RAISECOM TECH, Ltd. 
-- All rights reserved.
-- 01,20111231,yangkewei,ROS00008218,advent mib编译检查
-- *****************************************************************

--MibName=raisecomOspf
RAISECOM-OSPFV2-MIB DEFINITIONS ::= BEGIN

IMPORTS
    MODULE-IDENTITY, OBJECT-TYPE, Counter32, Gauge32,
    Integer32, Unsigned32, IpAddress
                 FROM SNMPv2-SMI
    TEXTUAL-CONVENTION, TruthValue, RowStatus
                 FROM SNMPv2-TC 
    EnableVar	 FROM SWITCH-TC   
    InterfaceIndexOrZero
                 FROM IF-MIB                
    raisecomAgent	            	         
                 FROM RAISECOM-BASE-MIB;       

    raisecomOspf MODULE-IDENTITY
        LAST-UPDATED    "201109140000Z"  -- Sep 14, 2011
        ORGANIZATION    "Raisecom, Inc."
        CONTACT-INFO    
                "       Raise Systems        
                        Postal: Beijing, China
                        Tel: 86-010-82884499
                        E-mail: support@raisecom.com"

        DESCRIPTION     "This MIB module defines objects to Ospf."

        REVISION        "201109140000Z"  -- Sep 14, 2011
        DESCRIPTION     "Initial MIB creation."

        ::= { raisecomAgent 47} 

ProcessID ::= TEXTUAL-CONVENTION
       DISPLAY-HINT "d-0"
       STATUS       current
       DESCRIPTION
          "The OSPF process id."
       SYNTAX       Unsigned32 (1..'5'h)
         
        
AreaID ::= TEXTUAL-CONVENTION
       STATUS       current
       DESCRIPTION
          "An OSPF Area Identifier.
           Note that the Area ID, in OSPF, has the same format
           as an IP address, but has the function of defining
           a summarization point for link state advertisements."
       SYNTAX       IpAddress

RouterID ::= TEXTUAL-CONVENTION
       STATUS       current
       DESCRIPTION
          "A OSPF Router Identifier.
           Note that the Router ID, in OSPF, has the same format
           as an IP address, but identifies the router independent
           of its IP address."
       SYNTAX       IpAddress

Metric ::= TEXTUAL-CONVENTION
       DISPLAY-HINT "d-0"
       STATUS       current
       DESCRIPTION
          "The OSPF internal metric.
           Note that the OSPF metric is defined as an unsigned value
           in the range."
       SYNTAX       Integer32 (0..'FFFF'h)

BigMetric ::= TEXTUAL-CONVENTION
       DISPLAY-HINT "d-0"
       STATUS       current
       DESCRIPTION
          "The OSPF external metric."
       SYNTAX       Integer32 (0..'FFFFFF'h)

Status ::= TEXTUAL-CONVENTION
       STATUS       current
       DESCRIPTION
          "An indication of the operability of an OSPF
          function or feature.  For example, the status
          of an interface: 'enabled' indicates that
          it is willing to communicate with other OSPF routers,
          and 'disabled' indicates that it is not."
       SYNTAX       INTEGER { enabled (1), disabled (2) }

PositiveInteger ::= TEXTUAL-CONVENTION
       DISPLAY-HINT "d-0"
       STATUS       current
       DESCRIPTION
          "A positive integer.  Values in excess are precluded as
          unnecessary and prone to interoperability issues."
       SYNTAX       Integer32 (0..'7FFFFFFF'h)

HelloRange ::= TEXTUAL-CONVENTION
       DISPLAY-HINT "d-0"
       STATUS       current
       DESCRIPTION
          "The range of intervals in seconds on which Hello messages
          are exchanged."
       SYNTAX       Integer32 (1..'FFFF'h)

UpToMaxAge ::= TEXTUAL-CONVENTION
       DISPLAY-HINT "d-0"
       STATUS       current

       DESCRIPTION
          "The values in seconds that one might find or configure
          for variables bounded by the maximum age of an LSA."
       SYNTAX       Integer32 (0..3600)

DesignatedRouterPriority ::= TEXTUAL-CONVENTION
       DISPLAY-HINT "d-0"
       STATUS       current
       DESCRIPTION
          "The range of values defined for the priority of a system
          for becoming the designated router."
       SYNTAX       Integer32 (0..'FF'h)

OspfAuthenticationType ::= TEXTUAL-CONVENTION
       STATUS       current
       DESCRIPTION
          "The authentication type."
       SYNTAX       INTEGER {
                       none (0),
                       simplePassword (1),
                       md5 (2)
                       -- reserved for specification by IANA (> 2)
                    }

------------------------------------------------------------------------------
--  Define groups in RAISECOM-OSPFv2-MIB
------------------------------------------------------------------------------

    raisecomOspfNotifications        OBJECT IDENTIFIER ::= { raisecomOspf 1 } 
    raisecomOspfObjects              OBJECT IDENTIFIER ::= { raisecomOspf 2 } 
    raisecomOspfConformance          OBJECT IDENTIFIER ::= { raisecomOspf 3 } 
 
------------------------------------------------------------------------------
--
--   raisecomOspfNotifications 
--   
--   This group defines the traps related to Ospf.
------------------------------------------------------------------------------   

------------------------------------------------------------------------------
--  Define groups in raisecomOspfNotifications
------------------------------------------------------------------------------

--    raisecomOspfTrapControl    OBJECT IDENTIFIER ::= { raisecomOspfNotifications 1 }

   
------------------------------------------------------------------------------
--
--  raisecomOspfTrapControl 
--
--  This Table defines the control infomation of Ospf Traps.
--
------------------------------------------------------------------------------ 
   raisecomOspfTrapControlTable OBJECT-TYPE
       SYNTAX       SEQUENCE OF RaisecomOspfTrapControlEntry
       MAX-ACCESS   not-accessible
       STATUS       current
       DESCRIPTION
          "The table enable or disable ospf traps"
       ::= { raisecomOspfNotifications 1 }

  raisecomOspfTrapControlEntry OBJECT-TYPE
       SYNTAX   RaisecomOspfTrapControlEntry
       MAX-ACCESS   not-accessible
       STATUS   current
       DESCRIPTION
          "Define an entry in the raisecomOspfTrapControl.

          Information in this table is persistent and when this object
          is written the entity SHOULD save the change to non-volatile
          storage."
       INDEX { raisecomOspfProcessId }
       ::= { raisecomOspfTrapControlTable 1 }

  RaisecomOspfTrapControlEntry ::=
       SEQUENCE {
          raisecomOspfSetTrap
             EnableVar,
          raisecomOspfConfigErrorType
             INTEGER,
          raisecomOspfPacketType
             INTEGER,
          raisecomOspfPacketSrc
             IpAddress
             }
             
    raisecomOspfSetTrap OBJECT-TYPE
        SYNTAX   EnableVar
        MAX-ACCESS   read-write
        STATUS   current
        DESCRIPTION
           "Whether the Device shoule send traps."    
       DEFVAL {disable}
       ::= { raisecomOspfTrapControlEntry 1 }


    raisecomOspfConfigErrorType OBJECT-TYPE
        SYNTAX   INTEGER   {
                    badVersion (1),
                    areaMismatch (2),
                    unknownNbmaNbr (3), -- Router is Dr eligible
                    unknownVirtualNbr (4),
                    authTypeMismatch(5),
                    authFailure (6),
                    netMaskMismatch (7),
                    helloIntervalMismatch (8),
                    deadIntervalMismatch (9),
                    optionMismatch (10) }
        MAX-ACCESS   read-only
        STATUS   current
        DESCRIPTION
           "Potential types  of  configuration  conflicts.
           Used  by the ospfConfigError and ospfConfigVir-
           tError traps."
   ::= { raisecomOspfTrapControlEntry 2 }


    raisecomOspfPacketType OBJECT-TYPE
        SYNTAX   INTEGER   {
                    hello (1),
                    dbDescript (2),
                    lsReq (3),
                    lsUpdate (4),
                    lsAck (5) }
        MAX-ACCESS   read-only
        STATUS   current
        DESCRIPTION
           "OSPF packet types."
   ::= { raisecomOspfTrapControlEntry 3 }


    raisecomOspfPacketSrc OBJECT-TYPE
        SYNTAX   IpAddress
        MAX-ACCESS   read-only
        STATUS   current
        DESCRIPTION
           "The IP address of an inbound packet that  can-
           not be identified by a neighbor instance."
       ::= { raisecomOspfTrapControlEntry 4 }  

------------------------------------------------------------------------------
--
--  raisecomOspfTraps 
--
--  This Table defines the Ospf Traps.
--
------------------------------------------------------------------------------
------------------------------------------------------------------------------
--  Define groups in raisecomOspfNotifications
------------------------------------------------------------------------------
    raisecomOspfTraps          OBJECT IDENTIFIER ::= { raisecomOspfNotifications 2 }
   
------------------------------------------------------------------------------
    
   raisecomOspfIfStateChange NOTIFICATION-TYPE
        OBJECTS { 
                    raisecomOspfProcessId,
                    raisecomOspfRouterId, -- The originator of the trap
                    raisecomOspfIfIpAddress,
                    raisecomOspfAddressLessIf,
                    raisecomOspfIfState   -- The new state
                  }
        STATUS             current
        DESCRIPTION
           "An raisecomOspfIfStateChange trap signifies that there
           has been a change in the state of a non-virtual
           OSPF interface. This trap should  be  generated
           when  the interface state regresses (e.g., goes
           from Dr to Down) or progresses  to  a  terminal
           state  (i.e.,  Point-to-Point, DR Other, Dr, or
           Backup)."
   ::= { raisecomOspfTraps 1 }


    raisecomOspfVirtIfStateChange NOTIFICATION-TYPE
        OBJECTS {   
                    raisecomOspfProcessId,
                    raisecomOspfRouterId, -- The originator of the trap
                    raisecomOspfVirtIfAreaId,
                    raisecomOspfVirtIfNeighbor,
                    raisecomOspfVirtIfState  -- The new state
                  }
        STATUS             current
        DESCRIPTION
           "An raisecomOspfIfStateChange trap signifies that there
           has  been a change in the state of an OSPF vir-
           tual interface.
           This trap should be generated when  the  inter-
           face  state  regresses  (e.g., goes from Point-
           to-Point to Down) or progresses to  a  terminal
           state (i.e., Point-to-Point)."
   ::= { raisecomOspfTraps 2 }  
    
       raisecomOspfNbrStateChange NOTIFICATION-TYPE
        OBJECTS {   
                    raisecomOspfProcessId,
                    raisecomOspfRouterId, -- The originator of the trap
                    raisecomOspfNbrIpAddr,
                    raisecomOspfNbrAddressLessIndex,
                    raisecomOspfNbrRtrId,
                    raisecomOspfNbrState  -- The new state
                  }
        STATUS             current
        DESCRIPTION
           "An  raisecomOspfNbrStateChange  trap  signifies   that
           there  has been a change in the state of a non-
           virtual OSPF neighbor.   This  trap  should  be
           generated  when  the  neighbor  state regresses
           (e.g., goes from Attempt or Full  to  1-Way  or
           Down)  or progresses to a terminal state (e.g.,
           2-Way or Full).  When an  neighbor  transitions
           from  or  to Full on non-broadcast multi-access
           and broadcast networks, the trap should be gen-
           erated  by the designated router.  A designated
           router transitioning to Down will be  noted  by
           raisecomOspfIfStateChange."
   ::= { raisecomOspfTraps 3 }

    raisecomOspfVirtNbrStateChange NOTIFICATION-TYPE
        OBJECTS {   
                    raisecomOspfProcessId,
                    raisecomOspfRouterId, -- The originator of the trap
                    raisecomOspfVirtNbrArea,
                    raisecomOspfVirtNbrRtrId,
                    raisecomOspfVirtNbrState  -- The new state
                  }
        STATUS             current
        DESCRIPTION
           "An raisecomOspfIfStateChange trap signifies that there
           has  been a change in the state of an OSPF vir-
           tual neighbor.  This trap should  be  generated
           when  the  neighbor state regresses (e.g., goes
           from Attempt or  Full  to  1-Way  or  Down)  or
           progresses to a terminal state (e.g., Full)."
   ::= { raisecomOspfTraps 4 }

    raisecomOspfIfConfigError NOTIFICATION-TYPE
        OBJECTS {    
                    raisecomOspfProcessId,
                    raisecomOspfRouterId, -- The originator of the trap
                    raisecomOspfIfIpAddress,
                    raisecomOspfAddressLessIf,
                    raisecomOspfPacketSrc,  -- The source IP address
                    raisecomOspfConfigErrorType, -- Type of error
                    raisecomOspfPacketType
                  }
        STATUS             current
        DESCRIPTION
           "An raisecomOspfIfConfigError  trap  signifies  that  a
           packet  has  been received on a non-virtual in-
           terface  from  a  router  whose   configuration
           parameters  conflict  with this router's confi-
           guration parameters.  Note that the  event  op-
           tionMismatch  should  cause  a  trap only if it
           prevents an adjacency from forming."
   ::= { raisecomOspfTraps 5 }

    raisecomOspfVirtIfConfigError NOTIFICATION-TYPE
        OBJECTS {   
                    raisecomOspfProcessId,
                    raisecomOspfRouterId, -- The originator of the trap
                    raisecomOspfVirtIfAreaId,
                    raisecomOspfVirtIfNeighbor,
                    raisecomOspfConfigErrorType, -- Type of error
                    raisecomOspfPacketType
                  }
        STATUS             current
        DESCRIPTION
           "An ospfConfigError trap signifies that a pack-
           et  has  been  received  on a virtual interface
           from a router  whose  configuration  parameters
           conflict   with   this  router's  configuration
           parameters.  Note that the event optionMismatch
           should  cause a trap only if it prevents an ad-
           jacency from forming."
   ::= { raisecomOspfTraps 6 }


    raisecomOspfIfAuthFailure NOTIFICATION-TYPE
        OBJECTS {   
                    raisecomOspfProcessId,
                    raisecomOspfRouterId, -- The originator of the trap
                    raisecomOspfIfIpAddress,
                    raisecomOspfAddressLessIf,
                    raisecomOspfPacketSrc,  -- The source IP address
                    raisecomOspfConfigErrorType, -- authTypeMismatch or
                                         -- authFailure
                    raisecomOspfPacketType
                  }
        STATUS             current
        DESCRIPTION
           "An raisecomOspfIfAuthFailure  trap  signifies  that  a
           packet  has  been received on a non-virtual in-
           terface from a router whose authentication  key
           or  authentication  type  conflicts  with  this
           router's authentication key  or  authentication
           type."
   ::= { raisecomOspfTraps 7 }


    raisecomOspfVirtIfAuthFailure NOTIFICATION-TYPE
        OBJECTS {    
                    raisecomOspfProcessId,
                    raisecomOspfRouterId, -- The originator of the trap
                    raisecomOspfVirtIfAreaId,
                    raisecomOspfVirtIfNeighbor,
                    raisecomOspfConfigErrorType, -- authTypeMismatch or
                                         -- authFailure
                    raisecomOspfPacketType
                  }
        STATUS             current
        DESCRIPTION
           "An raisecomOspfVirtIfAuthFailure trap signifies that a
           packet has been received on a virtual interface
           from a router whose authentication key  or  au-
           thentication  type conflicts with this router's
           authentication key or authentication type."
   ::= { raisecomOspfTraps 8 }

    raisecomOspfIfRxBadPacket NOTIFICATION-TYPE
        OBJECTS {     
                    raisecomOspfProcessId,
                    raisecomOspfRouterId, -- The originator of the trap
                    raisecomOspfIfIpAddress,
                    raisecomOspfAddressLessIf,
                    raisecomOspfPacketSrc,  -- The source IP address
                    raisecomOspfPacketType
                  }
        STATUS             current
        DESCRIPTION
           "An raisecomOspfIfRxBadPacket trap  signifies  that  an
           OSPF  packet has been received on a non-virtual
           interface that cannot be parsed."
   ::= { raisecomOspfTraps 9 }

    raisecomOspfVirtIfRxBadPacket NOTIFICATION-TYPE
        OBJECTS {    
                    raisecomOspfProcessId,
                    raisecomOspfRouterId, -- The originator of the trap
                    raisecomOspfVirtIfAreaId,
                    raisecomOspfVirtIfNeighbor,
                    raisecomOspfPacketType
                  }
        STATUS             current
        DESCRIPTION
           "An ospfRxBadPacket trap signifies that an OSPF
           packet has been received on a virtual interface
           that cannot be parsed."
   ::= { raisecomOspfTraps 10 }


    raisecomOspfTxRetransmit NOTIFICATION-TYPE
        OBJECTS {    
                    raisecomOspfProcessId,
                    raisecomOspfRouterId, -- The originator of the trap
                    raisecomOspfIfIpAddress,
                    raisecomOspfAddressLessIf,
                    raisecomOspfNbrRtrId, -- Destination
                    raisecomOspfPacketType,
                    raisecomOspfLsdbType,
                    raisecomOspfLsdbLsId,
                    raisecomOspfLsdbRouterId
                  }
        STATUS             current
        DESCRIPTION
           "An ospfTxRetransmit  trap  signifies  than  an
           OSPF  packet  has  been retransmitted on a non-
           virtual interface.  All packets that may be re-
           transmitted  are associated with an LSDB entry.
           The LS type, LS ID, and Router ID are  used  to
           identify the LSDB entry."
   ::= { raisecomOspfTraps 11 }


    raisecomOspfVirtIfTxRetransmit NOTIFICATION-TYPE
        OBJECTS {      
                    raisecomOspfProcessId,
                    raisecomOspfRouterId, -- The originator of the trap
                    raisecomOspfVirtIfAreaId,
                    raisecomOspfVirtIfNeighbor,
                    raisecomOspfPacketType,
                    raisecomOspfLsdbType,
                    raisecomOspfLsdbLsId,
                    raisecomOspfLsdbRouterId
                  }
        STATUS             current
        DESCRIPTION
           "An ospfTxRetransmit  trap  signifies  than  an
           OSPF packet has been retransmitted on a virtual
           interface.  All packets that may be retransmit-
           ted  are  associated with an LSDB entry. The LS
           type, LS ID, and Router ID are used to identify
           the LSDB entry."
   ::= { raisecomOspfTraps 12 }

    raisecomOspfOriginateLsa NOTIFICATION-TYPE
        OBJECTS {   
                    raisecomOspfProcessId,
                    raisecomOspfRouterId, -- The originator of the trap
                    raisecomOspfLsdbAreaId,  -- 0.0.0.0 for AS Externals
                    raisecomOspfLsdbType,
                    raisecomOspfLsdbLsId,
                    raisecomOspfLsdbRouterId
                  }
        STATUS             current
        DESCRIPTION
           "An ospfOriginateLsa trap signifies that a  new
           LSA  has  been originated by this router.  This
           trap should not be invoked for simple refreshes
           of  LSAs  (which happesn every 30 minutes), but
           instead will only be invoked  when  an  LSA  is
           (re)originated due to a topology change.  Addi-
           tionally, this trap does not include LSAs  that
           are  being  flushed  because  they have reached
           MaxAge."
   ::= { raisecomOspfTraps 13 }

    raisecomOspfMaxAgeLsa NOTIFICATION-TYPE
        OBJECTS {    
                    raisecomOspfProcessId,
                    raisecomOspfRouterId, -- The originator of the trap
                    raisecomOspfLsdbAreaId,  -- 0.0.0.0 for AS Externals
                    raisecomOspfLsdbType,
                    raisecomOspfLsdbLsId,
                    raisecomOspfLsdbRouterId
                  }
        STATUS             current
        DESCRIPTION
           "An ospfMaxAgeLsa trap signifies  that  one  of
           the LSA in the router's link-state database has
           aged to MaxAge."
   ::= { raisecomOspfTraps 14 }

    raisecomOspfLsdbOverflow NOTIFICATION-TYPE
        OBJECTS {    
                    raisecomOspfProcessId,
                    raisecomOspfRouterId, -- The originator of the trap
                    raisecomOspfExtLsdbLimit
                  }
        STATUS             current
        DESCRIPTION
           "An raisecomOspfLsdbOverflow trap  signifies  that  the
           number of LSAs in the router's link-state data-
           base has exceeded raisecomOspfExtLsdbLimit."
   ::= { raisecomOspfTraps 15 }


    raisecomOspfLsdbApproachingOverflow NOTIFICATION-TYPE
        OBJECTS {    
                    raisecomOspfProcessId,
                    raisecomOspfRouterId, -- The originator of the trap
                    raisecomOspfExtLsdbLimit
                  }
        STATUS             current
        DESCRIPTION
           "An raisecomOspfLsdbApproachingOverflow trap  signifies
           that  the  number of LSAs in the router's link-
           state database has exceeded ninety  percent  of
           raisecomOspfExtLsdbLimit."
   ::= { raisecomOspfTraps 16 }     
   
    raisecomOspfIfKeyValid NOTIFICATION-TYPE
        OBJECTS {    
                    raisecomOspfProcessId,
                    raisecomOspfRouterId, -- The originator of the trap
                    raisecomOspfIfIpAddress,
                    raisecomOspfAddressLessIf,
                    raisecomOspfIfAuthKeyChain
                  }
        STATUS             current
        DESCRIPTION
           "This trap will notify the network manager that some key 
           associated with an interface recovers valid."
   ::= { raisecomOspfTraps 17 }


    raisecomOspfIfLastKeyExpiration NOTIFICATION-TYPE
        OBJECTS {    
                    raisecomOspfProcessId,
                    raisecomOspfRouterId, -- The originator of the trap
                    raisecomOspfIfIpAddress,
                    raisecomOspfAddressLessIf, 
                    raisecomOspfIfAuthKeyChain
                  }
        STATUS             current
        DESCRIPTION
           "This trap will notify the network manager that the last 
 	       key associated with an interface expires."
   ::= { raisecomOspfTraps 18 }      
   
    raisecomOspfVirtIfKeyValid NOTIFICATION-TYPE
        OBJECTS {    
                    raisecomOspfProcessId,
                    raisecomOspfRouterId, -- The originator of the trap
                    raisecomOspfVirtIfAreaId,
                    raisecomOspfVirtIfNeighbor, 
                    raisecomOspfVirtIfAuthKeyChain
                  }
        STATUS             current
        DESCRIPTION
           "This trap will notify the network manager that some key 
           associated with an virtual link recovers valid."
   ::= { raisecomOspfTraps 19 }


    raisecomOspfVirtIfLastKeyExpiration NOTIFICATION-TYPE
        OBJECTS {    
                    raisecomOspfProcessId,
                    raisecomOspfRouterId, -- The originator of the trap
                    raisecomOspfVirtIfAreaId,
                    raisecomOspfVirtIfNeighbor,
                    raisecomOspfVirtIfAuthKeyChain
                  }
        STATUS             current
        DESCRIPTION
           "This trap will notify the network manager that the last 
 	       key associated with an virtual link expires."
   ::= { raisecomOspfTraps 20 } 
   
     raisecomOspfRedistributeOverflow NOTIFICATION-TYPE
        OBJECTS {    
                   raisecomOspfProcessId,
                   raisecomOspfRedistributeProtocol, -- The originator of the trap
                   raisecomOspfRedistributeProcessId,
                   raisecomOspfRedistributeRouteLimit
                  }
        STATUS             current
        DESCRIPTION
           "This trap should  be  generated when  the number of 
            redistribute routes exceeds limit."
   ::= { raisecomOspfTraps 21 }
 
      raisecomOspfRedistributeNotOverflow NOTIFICATION-TYPE
        OBJECTS {    
                   raisecomOspfProcessId,
                   raisecomOspfRedistributeProtocol, -- The originator of the trap
                   raisecomOspfRedistributeProcessId,
                   raisecomOspfRedistributeRouteLimit
                  }
        STATUS             current
        DESCRIPTION
           "This trap should  be  generated when  the number of 
            redistribute routes  drop to limit."
   ::= { raisecomOspfTraps 22 }

------------------------------------------------------------------------------
--
--   raisecomOspfObjects 
--   
--   This group defines all the objects related to Ospf.
------------------------------------------------------------------------------

------------------------------------------------------------------------------
--  Define groups in raisecomOspfObjects
------------------------------------------------------------------------------
--    raisecomOspfGlobalTable             OBJECT IDENTIFIER ::= { raisecomOspfObjects 1 }
--    raisecomOspfAreaTable               OBJECT IDENTIFIER ::= { raisecomOspfObjects 2 } 
--    raisecomOspfNetWorkTable            OBJECT IDENTIFIER ::= { raisecomOspfObjects 3 }
--    raisecomOspfStubAreaTable           OBJECT IDENTIFIER ::= { raisecomOspfObjects 4 }
--    raisecomOspfNssaAreaTable           OBJECT IDENTIFIER ::= { raisecomOspfObjects 5 }         
--    raisecomOspfIfTable                 OBJECT IDENTIFIER ::= { raisecomOspfObjects 6 }
--    raisecomOspfVirtIfTable             OBJECT IDENTIFIER ::= { raisecomOspfObjects 7 }
--    raisecomOspfNbrTable                OBJECT IDENTIFIER ::= { raisecomOspfObjects 8 }
--    raisecomOspfNbmaCfgNbrTable         OBJECT IDENTIFIER ::= { raisecomOspfObjects 9 }
--    raisecomOspfVirtNbrTable            OBJECT IDENTIFIER ::= { raisecomOspfObjects 10}
--    raisecomOspfAreaAggregateTable      OBJECT IDENTIFIER ::= { raisecomOspfObjects 11}
--    raisecomOspfExternalAggregateTable  OBJECT IDENTIFIER ::= { raisecomOspfObjects 12}  
--    raisecomOspfLsdbTable               OBJECT IDENTIFIER ::= { raisecomOspfObjects 13}
--    raisecomOspfAsLsdbTable             OBJECT IDENTIFIER ::= { raisecomOspfObjects 14}
--    raisecomOspfAreaLsaCountTable       OBJECT IDENTIFIER ::= { raisecomOspfObjects 15}
--    raisecomOspfRedistributeTable       OBJECT IDENTIFIER ::= { raisecomOspfObjects 16}
--    raisecomOspfDefaultInfoTable        OBJECT IDENTIFIER ::= { raisecomOspfObjects 17} 
--    raisecomOspfPacketIoStatisTable     OBJECT IDENTIFIER ::= { raisecomOspfObjects 18}
--    raisecomOspfRouteTable              OBJECT IDENTIFIER ::= { raisecomOspfObjects 19}
--    raisecomOspfBdrRouteTable           OBJECT IDENTIFIER ::= { raisecomOspfObjects 20}    
--    raisecomOspfDistributeListGroup     OBJECT IDENTIFIER ::= { raisecomOspfObjects 21} 
------------------------------------------------------------------------------

------------------------------------------------------------------------------
--
--  raisecomOspfGlobalTable 
--
--  This Table defines the Global Vars.
--
------------------------------------------------------------------------------
 raisecomOspfGlobalTable OBJECT-TYPE
       SYNTAX       SEQUENCE OF RaisecomOspfGlobalEntry
       MAX-ACCESS   not-accessible
       STATUS       current
       DESCRIPTION
          "OSPF global Vars for every ospf process."
       ::= { raisecomOspfObjects 1 }

  raisecomOspfGlobalEntry OBJECT-TYPE
       SYNTAX       RaisecomOspfGlobalEntry
       MAX-ACCESS   not-accessible
       STATUS       current
       DESCRIPTION
          "OSPF global Vars for every ospf process."
       INDEX { raisecomOspfProcessId }
       ::= { raisecomOspfGlobalTable 1 }

  RaisecomOspfGlobalEntry ::=
        SEQUENCE {
           raisecomOspfProcessId
              ProcessID,
           raisecomOspfRouterId
              RouterID,
           raisecomOspfAdminStat
              EnableVar,
           raisecomOspfVersionNumber
              INTEGER,
           raisecomOspfAreaBdrRtrStatus
              TruthValue,
           raisecomOspfASBdrRtrStatus
              TruthValue,
           raisecomOspfExternLsaCount
              Gauge32,
           raisecomOspfExternLsaCksumSum
              Integer32,
           raisecomOspfOriginateNewLsas
              Counter32,
           raisecomOspfRxNewLsas
              Counter32,
           raisecomOspfExtLsdbLimit
              Integer32,
           raisecomOspfExitOverflowInterval
              PositiveInteger,
           raisecomOspfReferenceBandwidth
              Unsigned32,   
           raisecomOspfAsLsaCount  
              Gauge32,
           raisecomOspfAsLsaCksumSum   
              Unsigned32,
           raisecomOspfStubRouterSupport   
              TruthValue,
           raisecomOspfStubRouterAdvertisement   
              INTEGER,
           raisecomOspfAdminDistance 
              Integer32, 
           raisecomOspfSpfInterval   
              Integer32,   
           raisecomOspfReset   
              TruthValue,
           raisecomOspfExportMetric   
              Integer32,
           raisecomOspfExportTag   
              Integer32,
           raisecomOspfExportType   
              INTEGER,
           raisecomOspfNetCounts   
              Integer32,
           raisecomOspfAreaCounts   
              Integer32,
           raisecomOspfNssaAreaCounts
              Integer32,           
           raisecomOspfSpfCounts
              Integer32, 
           raisecomOspfGlobalStatus   
              RowStatus,
           raisecomOspfRedistributeRouteLimit 
              INTEGER
           }    

  raisecomOspfProcessId OBJECT-TYPE
       SYNTAX       ProcessID
       MAX-ACCESS   read-only
       STATUS       current
       DESCRIPTION
          "A 32-bit unsigned integer uniquely identifying the
          ospf process."
       ::= { raisecomOspfGlobalEntry 1 }
         
  
  raisecomOspfRouterId OBJECT-TYPE
       SYNTAX       RouterID
       MAX-ACCESS   read-create
       STATUS       current
       DESCRIPTION
          "A 32-bit integer uniquely identifying the
          router in the Autonomous System.
          By convention, to ensure uniqueness, this
          should default to the value of one of the
          router's IP interface addresses.

          This object is persistent and when written
          the entity SHOULD save the change to non-volatile storage."
       REFERENCE
          "OSPF Version 2, C.1 Global parameters"
       ::= { raisecomOspfGlobalEntry 2 }

  raisecomOspfAdminStat OBJECT-TYPE
       SYNTAX       EnableVar
       MAX-ACCESS   read-only
       STATUS       current
       DESCRIPTION
          "The administrative status of OSPF in the
          router.  The value 'enabled' denotes that the
          OSPF Process is active on at least one interface;
          'disabled' disables it on all interfaces.

          This object is persistent and when written
          the entity SHOULD save the change to non-volatile storage."  
       DEFVAL { disable }
       ::= { raisecomOspfGlobalEntry 3 }

  raisecomOspfVersionNumber OBJECT-TYPE
       SYNTAX       INTEGER { version2 (2) }
       MAX-ACCESS   read-only
       STATUS       current

       DESCRIPTION
          "The current version number of the OSPF protocol is 2."
       REFERENCE
          "OSPF Version 2, Title"
       ::= { raisecomOspfGlobalEntry 4 }

  raisecomOspfAreaBdrRtrStatus OBJECT-TYPE
       SYNTAX       TruthValue
       MAX-ACCESS   read-only
       STATUS       current
       DESCRIPTION
          "A flag to note whether this router is an Area
          Border Router."
       REFERENCE
          "OSPF Version 2, Section 3 Splitting the AS into
          Areas"
       ::= { raisecomOspfGlobalEntry 5 }

  raisecomOspfASBdrRtrStatus OBJECT-TYPE
       SYNTAX       TruthValue
       MAX-ACCESS   read-only
       STATUS       current
       DESCRIPTION
          "A flag to note whether this router is configured as
           an Autonomous System Border Router.

           This object is persistent and when written the
           entity SHOULD save the change to non-volatile storage."
       REFERENCE
          "OSPF Version 2, Section 3.3 Classification of
          routers"
       ::= { raisecomOspfGlobalEntry 6 }

  raisecomOspfExternLsaCount OBJECT-TYPE
        SYNTAX       Gauge32
        MAX-ACCESS   read-only
        STATUS       current
        DESCRIPTION
           "The number of external (LS type-5) link state
           advertisements in the link state database."
        REFERENCE
           "OSPF Version 2, Appendix A.4.5 AS external link
           advertisements"
        ::= { raisecomOspfGlobalEntry 7 }

  raisecomOspfExternLsaCksumSum OBJECT-TYPE
        SYNTAX       Integer32
        MAX-ACCESS   read-only

        STATUS       current
        DESCRIPTION
           "The 32-bit sum of the LS checksums of
           the external link state advertisements
           contained in the link state database.  This sum
           can be used to determine if there has been a
           change in a router's link state database and
           to compare the link state database of two
           routers.  The value should be treated as unsigned
           when comparing two sums of checksums."
        ::= { raisecomOspfGlobalEntry 8 }

   raisecomOspfOriginateNewLsas OBJECT-TYPE
       SYNTAX       Counter32
       MAX-ACCESS   read-only
       STATUS       current
       DESCRIPTION
          "The number of new link state advertisements
          that have been originated.  This number is
          incremented each time the router originates a new
          LSA.

          Discontinuities in the value of this counter can
          occur at re-initialization of the management system,
          and at other times as indicated by the value of
          ospfDiscontinuityTime."
        ::= { raisecomOspfGlobalEntry 9 }

  raisecomOspfRxNewLsas OBJECT-TYPE
       SYNTAX       Counter32
       MAX-ACCESS   read-only
       STATUS       current
       DESCRIPTION

          "The number of link state advertisements received
          that are determined to be new instantiations.
          This number does not include newer instantiations
          of self-originated link state advertisements.

          Discontinuities in the value of this counter can
          occur at re-initialization of the management system,
          and at other times as indicated by the value of
          ospfDiscontinuityTime."
       ::= { raisecomOspfGlobalEntry 10 }

  raisecomOspfExtLsdbLimit OBJECT-TYPE
       SYNTAX       Integer32 (-1..'7FFFFFFF'h)
       MAX-ACCESS   read-only
       STATUS       current
       DESCRIPTION
          "The maximum number of non-default
          AS-external LSAs entries that can be stored in the
          link state database.  If the value is -1, then
          there is no limit.

          When the number of non-default AS-external LSAs
          in a router's link state database reaches
          raisecomOspfExtLsdbLimit, the router enters
          overflow state.  The router never holds more than
          raisecomOspfExtLsdbLimit non-default AS-external LSAs
          in its database.  raisecomOspfExtLsdbLimit MUST be set
          identically in all routers attached to the OSPF
          backbone and/or any regular OSPF area (i.e.,
          OSPF stub areas and NSSAs are excluded).

          This object is persistent and when written
          the entity SHOULD save the change to non-volatile
          storage."
        DEFVAL { -1 }
        ::= { raisecomOspfGlobalEntry 11 }

  raisecomOspfExitOverflowInterval OBJECT-TYPE
       SYNTAX       PositiveInteger
       MAX-ACCESS   read-only
       STATUS       current
       DESCRIPTION
          "The number of seconds that, after entering
          OverflowState, a router will attempt to leave
          OverflowState.  This allows the router to again
          originate non-default AS-external LSAs.  When
          set to 0, the router will not leave
          overflow state until restarted.

          This object is persistent and when written
          the entity SHOULD save the change to non-volatile
          storage."
       DEFVAL { 0 }
       ::= { raisecomOspfGlobalEntry 12 }

  raisecomOspfReferenceBandwidth OBJECT-TYPE
       SYNTAX       Unsigned32(1..4296967)
       UNITS        "millionbits per second"
       MAX-ACCESS   read-create
       STATUS       current
       DESCRIPTION
          "Reference bandwidth in millionbits/second for
          calculating default interface metrics.  The
          default value is 100 MBPS.

          This object is persistent and when written
          the entity SHOULD save the change to non-volatile
          storage."
       ::= { raisecomOspfGlobalEntry 13 }

  raisecomOspfAsLsaCount OBJECT-TYPE
       SYNTAX       Gauge32
       MAX-ACCESS   read-only
       STATUS       current

       DESCRIPTION
           "The number of AS-scope link state
           advertisements in the AS-scope link state database."
       ::= { raisecomOspfGlobalEntry 14 }

  raisecomOspfAsLsaCksumSum OBJECT-TYPE
       SYNTAX       Unsigned32
       MAX-ACCESS   read-only
       STATUS       current
       DESCRIPTION
           "The 32-bit unsigned sum of the LS checksums of
           the AS link state advertisements contained in the AS-scope
           link state database.  This sum can be used to determine
           if there has been a change in a router's AS-scope link
           state database, and to compare the AS-scope link state
           database of two routers."
       ::= { raisecomOspfGlobalEntry 15 }

  raisecomOspfStubRouterSupport OBJECT-TYPE
       SYNTAX       TruthValue
       MAX-ACCESS   read-only
       STATUS       current
       DESCRIPTION
           "The router's support for stub router functionality."
       REFERENCE
           "OSPF Stub Router Advertisement"
       ::= { raisecomOspfGlobalEntry 16 }

  raisecomOspfStubRouterAdvertisement OBJECT-TYPE
       SYNTAX       INTEGER {
                          doNotAdvertise (1),
                          advertise(2)
                          }
       MAX-ACCESS   read-only
       STATUS       current
       DESCRIPTION
           "This object controls the advertisement of
           stub router LSAs by the router.  The value
           doNotAdvertise will result in the advertisement
           of a standard router LSA and is the default value.

           This object is persistent and when written
           the entity SHOULD save the change to non-volatile
           storage."
       ::= { raisecomOspfGlobalEntry 17 }   
       
  raisecomOspfAdminDistance OBJECT-TYPE
       SYNTAX       Integer32 (1..255)
       MAX-ACCESS   read-create
       STATUS       current
       DESCRIPTION
           "The administrative distance of ospf process."     
       DEFVAL { 110 }
       ::= { raisecomOspfGlobalEntry 18 }  
        
  raisecomOspfSpfInterval OBJECT-TYPE
       SYNTAX       Integer32 (1..60)
       MAX-ACCESS   read-create
       STATUS       current
       DESCRIPTION
           "The number of seconds between two SPF calculation."     
       DEFVAL { 5 }
       ::= { raisecomOspfGlobalEntry 19 }  
 
  raisecomOspfReset OBJECT-TYPE
       SYNTAX       TruthValue
       MAX-ACCESS   read-create
       STATUS       current
       DESCRIPTION
           "Reset ospf process by process ID."     
       DEFVAL { false }
       ::= { raisecomOspfGlobalEntry 20 }   

  raisecomOspfExportMetric OBJECT-TYPE
       SYNTAX       Integer32 (0.. 16777215)
       MAX-ACCESS   read-create
       STATUS       current
       DESCRIPTION
           "The default metric of imporing route into ospf process."     
       DEFVAL { 0 }
       ::= { raisecomOspfGlobalEntry 21 }

  raisecomOspfExportTag OBJECT-TYPE
       SYNTAX       Integer32
       MAX-ACCESS   read-create
       STATUS       current
       DESCRIPTION
           "The default tag of importing route into ospf process."     
       ::= { raisecomOspfGlobalEntry 22 }

  raisecomOspfExportType OBJECT-TYPE
       SYNTAX       INTEGER {
                      type1 (1),
                      type2 (2)
                      }                             
       MAX-ACCESS   read-create
       STATUS       current
       DESCRIPTION
           "The default type of importing route into ospf process."     
       DEFVAL { type1 }
       ::= { raisecomOspfGlobalEntry 23 }

  raisecomOspfNetCounts OBJECT-TYPE
       SYNTAX       Integer32
       MAX-ACCESS   read-only
       STATUS       current
       DESCRIPTION
           "It bas been used to describe the total number of networks in OSPF process."     
       ::= { raisecomOspfGlobalEntry 24 }

  raisecomOspfAreaCounts OBJECT-TYPE
       SYNTAX       Integer32
       MAX-ACCESS   read-only
       STATUS       current
       DESCRIPTION
           "It bas been used to describe the number of areas in OSPF process."     
       ::= { raisecomOspfGlobalEntry 25 }

  raisecomOspfNssaAreaCounts OBJECT-TYPE
       SYNTAX       Integer32
       MAX-ACCESS   read-only
       STATUS       current
       DESCRIPTION
           "It bas been used to describe the number of NSSA areas in OSPF process."     
       ::= { raisecomOspfGlobalEntry 26 }

  raisecomOspfSpfCounts OBJECT-TYPE
       SYNTAX       Integer32
       MAX-ACCESS   read-only
       STATUS       current
       DESCRIPTION
           "It bas been used to describe the total number of SPF calculation in OSPF process. "     
       ::= { raisecomOspfGlobalEntry 27 }

  raisecomOspfGlobalStatus OBJECT-TYPE
       SYNTAX       RowStatus
       MAX-ACCESS   read-create
       STATUS       current
       DESCRIPTION
          "This object permits management of the table by
          facilitating actions such as row creation,
          construction, and destruction.

          The value of this object has no effect on
          whether other objects in this conceptual row can be
          modified."
       ::= { raisecomOspfGlobalEntry 28 }   
       
  raisecomOspfRedistributeRouteLimit OBJECT-TYPE
       SYNTAX       INTEGER(1..65535) 
       MAX-ACCESS   read-create
       STATUS       current
       DESCRIPTION
          "import limit of route."
       ::= { raisecomOspfGlobalEntry 29 }      

---------------------------------------------------------------       
--  raisecomOspfAreaTable
--     The OSPF Area Table contains information
--     regarding the various areas.
---------------------------------------------------------------
  raisecomOspfAreaTable OBJECT-TYPE
       SYNTAX       SEQUENCE OF RaisecomOspfAreaEntry
       MAX-ACCESS   not-accessible
       STATUS       current
       DESCRIPTION
          "Information describing the configured parameters and
          cumulative statistics of the router's attached areas.
          The interfaces and virtual links are configured
          as part of these areas.  Area 0.0.0.0, by definition,
          is the backbone area."
       REFERENCE
          "OSPF Version 2, Section 6 The Area Data Structure"
       ::= { raisecomOspfObjects 2 }

  raisecomOspfAreaEntry OBJECT-TYPE
       SYNTAX       RaisecomOspfAreaEntry
       MAX-ACCESS   not-accessible
       STATUS       current
       DESCRIPTION
          "Information describing the configured parameters and
          cumulative statistics of one of the router's attached areas.
          The interfaces and virtual links are configured as part of
          these areas.  Area 0.0.0.0, by definition, is the backbone
          area.

          Information in this table is persistent and when this object
          is written the entity SHOULD save the change to non-volatile
          storage."
       INDEX { raisecomOspfProcessId,
               raisecomOspfAreaId }
       ::= { raisecomOspfAreaTable 1 }

  RaisecomOspfAreaEntry ::=
        SEQUENCE {
           raisecomOspfAreaId
              AreaID,
           raisecomOspfAuthType
              OspfAuthenticationType,
           raisecomOspfImportAsExtern
              INTEGER,
           raisecomOspfSpfRuns
              Counter32,
           raisecomOspfAreaBdrRtrCount
              Gauge32,
           raisecomOspfAsBdrRtrCount
              Gauge32,
           raisecomOspfAreaLsaCount
              Gauge32,
           raisecomOspfAreaLsaCksumSum
              Integer32,
           raisecomOspfAreaSummary
              INTEGER,
           raisecomOspfAreaNssaTranslatorRole
              INTEGER,
           raisecomOspfAreaNssaTranslatorState
              INTEGER,
           raisecomOspfAreaNssaTranslatorStabilityInterval
              PositiveInteger,
           raisecomOspfAreaNssaTranslatorEvents
              Counter32,     
           raisecomOspfAreaDefaultCost
              BigMetric,
           raisecomOspfAreaType
              INTEGER,
           raisecomOspfAreaAbrCount
              Integer32,
           raisecomOspfAreaAsbrCount
              Integer32,              
           raisecomOspfAreaStatus
              RowStatus,
           raisecomOspfAreaFilterInIpPrefixListName 
              OCTET STRING (SIZE(1..19)),  
           raisecomOspfAreaFilterOutIpPrefixListName
              OCTET STRING (SIZE(1..19))  
           }

  raisecomOspfAreaId OBJECT-TYPE
       SYNTAX       AreaID
       MAX-ACCESS   read-only -- read-only since originally
                              -- an SMIv1 index
       STATUS       current
       DESCRIPTION
          "A 32-bit integer uniquely identifying an area.
          Area ID 0.0.0.0 is used for the OSPF backbone."
       REFERENCE
          "OSPF Version 2, Appendix C.2 Area parameters"
       ::= { raisecomOspfAreaEntry 1 }

  raisecomOspfAuthType OBJECT-TYPE
       SYNTAX       OspfAuthenticationType
       MAX-ACCESS   read-create
       STATUS       current
       DESCRIPTION
          "The authentication type specified for an area."
       REFERENCE
          "OSPF Version 2, Appendix D Authentication"
       DEFVAL { none } -- no authentication, by default
       ::= { raisecomOspfAreaEntry 2 }

  raisecomOspfImportAsExtern OBJECT-TYPE
       SYNTAX       INTEGER {
                      importExternal (1),
                      importNoExternal (2),
                      importNssa (3)
                      }
       MAX-ACCESS   read-only
       STATUS       current
       DESCRIPTION
          "Indicates if an area is a stub area, NSSA, or standard
          area.  Type-5 AS-external LSAs and type-11 Opaque LSAs are
          not imported into stub areas or NSSAs.  NSSAs import
          AS-external data as type-7 LSAs"
       REFERENCE
          "OSPF Version 2, Appendix C.2 Area parameters"
       DEFVAL { importExternal }
       ::= { raisecomOspfAreaEntry 3 }

  raisecomOspfSpfRuns OBJECT-TYPE
       SYNTAX       Counter32
       MAX-ACCESS   read-only
       STATUS       current
       DESCRIPTION
          "The number of times that the intra-area route
          table has been calculated using this area's
          link state database.  This is typically done
          using Dijkstra's algorithm.

          Discontinuities in the value of this counter can occur
          at re-initialization of the management system, and at other
          times as indicated by the value of ospfDiscontinuityTime."
       ::= { raisecomOspfAreaEntry 4 }

  raisecomOspfAreaBdrRtrCount OBJECT-TYPE
       SYNTAX       Gauge32
       MAX-ACCESS   read-only
       STATUS       current
       DESCRIPTION
          "The total number of Area Border Routers reachable
          within this area.  This is initially zero and is
          calculated in each Shortest Path First (SPF) pass."

       ::= { raisecomOspfAreaEntry 5 }

  raisecomOspfAsBdrRtrCount OBJECT-TYPE
       SYNTAX       Gauge32
       MAX-ACCESS   read-only
       STATUS       current
       DESCRIPTION
          "The total number of Autonomous System Border
          Routers reachable within this area.  This is
          initially zero and is calculated in each SPF
          pass."
       ::= { raisecomOspfAreaEntry 6 }

  raisecomOspfAreaLsaCount OBJECT-TYPE
       SYNTAX       Gauge32
       MAX-ACCESS   read-only
       STATUS       current
       DESCRIPTION
          "The total number of link state advertisements
          in this area's link state database, excluding
          AS-external LSAs."
       ::= { raisecomOspfAreaEntry 7 }

  raisecomOspfAreaLsaCksumSum OBJECT-TYPE
       SYNTAX       Integer32
       MAX-ACCESS   read-only
       STATUS       current
       DESCRIPTION
          "The 32-bit sum of the link state
          advertisements' LS checksums contained in this
          area's link state database.  This sum excludes
          external (LS type-5) link state advertisements.
          The sum can be used to determine if there has
          been a change in a router's link state
          database, and to compare the link state database of
          two routers.  The value should be treated as unsigned
          when comparing two sums of checksums."
       DEFVAL { 0 }
       ::= { raisecomOspfAreaEntry 8 }

  raisecomOspfAreaSummary OBJECT-TYPE
       SYNTAX       INTEGER {
                       noAreaSummary (1),
                       sendAreaSummary (2)
                       }
       MAX-ACCESS   read-create
       STATUS       current
       DESCRIPTION

          "The variable ospfAreaSummary controls the
          import of summary LSAs into stub and NSSA areas.
          It has no effect on other areas.

          If it is noAreaSummary, the router will not
          originate summary LSAs into the stub or NSSA area.
          It will rely entirely on its default route.

          If it is sendAreaSummary, the router will both
          summarize and propagate summary LSAs."
       DEFVAL { noAreaSummary }
       ::= { raisecomOspfAreaEntry 9 }


  raisecomOspfAreaNssaTranslatorRole OBJECT-TYPE
       SYNTAX       INTEGER { always (1), candidate (2) }
       MAX-ACCESS   read-create
       STATUS       current
       DESCRIPTION
          "Indicates an NSSA border router's ability to
          perform NSSA translation of type-7 LSAs into
          type-5 LSAs."
       DEFVAL { candidate }
       ::= { raisecomOspfAreaEntry 10 }

  raisecomOspfAreaNssaTranslatorState OBJECT-TYPE
       SYNTAX       INTEGER { enabled (1),
                       elected (2),
                       disabled (3)
                       }
       MAX-ACCESS   read-only
       STATUS       current
       DESCRIPTION
          "Indicates if and how an NSSA border router is
          performing NSSA translation of type-7 LSAs into type-5

          LSAs.  When this object is set to enabled, the NSSA Border
          router's OspfAreaNssaExtTranslatorRole has been set to
          always.  When this object is set to elected, a candidate
          NSSA Border router is Translating type-7 LSAs into type-5.
          When this object is set to disabled, a candidate NSSA
          border router is NOT translating type-7 LSAs into type-5."
       ::= { raisecomOspfAreaEntry 11 }

  raisecomOspfAreaNssaTranslatorStabilityInterval OBJECT-TYPE
       SYNTAX       PositiveInteger
       UNITS        "seconds"
       MAX-ACCESS   read-create
       STATUS       current
       DESCRIPTION
          "The number of seconds after an elected translator
          determines its services are no longer required, that
          it should continue to perform its translation duties."
       DEFVAL { 40 }
       ::= { raisecomOspfAreaEntry 12 }

  raisecomOspfAreaNssaTranslatorEvents OBJECT-TYPE
       SYNTAX       Counter32
       MAX-ACCESS   read-only
       STATUS       current
       DESCRIPTION
          "Indicates the number of translator state changes
          that have occurred since the last boot-up.

          Discontinuities in the value of this counter can occur
          at re-initialization of the management system, and at other
          times as indicated by the value of ospfDiscontinuityTime."
       ::= { raisecomOspfAreaEntry 13 }   
       
  raisecomOspfAreaDefaultCost OBJECT-TYPE
       SYNTAX       BigMetric
       MAX-ACCESS   read-create
       STATUS       current
       DESCRIPTION
          "It indicates the cost of default route of NSSA area or 
          stub area."
       DEFVAL { 1 }
       ::= { raisecomOspfAreaEntry 14 }
 
  raisecomOspfAreaType OBJECT-TYPE
       SYNTAX       INTEGER {  
                      backbone (1),
                      normal (2),
                      stub (3),
                      nssa (4),
                      transmit (5)
                      }
       MAX-ACCESS   read-only
       STATUS       current
       DESCRIPTION
          "It has been used to describe the type of 
          area,area 0 indicates backbone, area that has virtual-links is 
          transmit area. When area is configured as stub,it's a stub area, and 
          same as nssa area.other areas are called normal areas."
       ::= { raisecomOspfAreaEntry 15 }
  
  raisecomOspfAreaAbrCount OBJECT-TYPE
       SYNTAX       Integer32
       MAX-ACCESS   read-only
       STATUS       current
       DESCRIPTION
          "It has been used to describe the number of ABR in this area."
       ::= { raisecomOspfAreaEntry 16 }
  
  raisecomOspfAreaAsbrCount OBJECT-TYPE
       SYNTAX       Integer32
       MAX-ACCESS   read-only
       STATUS       current
       DESCRIPTION
          "It has been used to describe the number of ASBR in this area."
       ::= { raisecomOspfAreaEntry 17 }
 
  raisecomOspfAreaStatus OBJECT-TYPE
       SYNTAX       RowStatus
       MAX-ACCESS   read-create
       STATUS       current
       DESCRIPTION
          "This object permits management of the table by
          facilitating actions such as row creation,
          construction, and destruction.

          The value of this object has no effect on
          whether other objects in this conceptual row can be
          modified."
       ::= { raisecomOspfAreaEntry 18 }   
  raisecomOspfAreaFilterInIpPrefixListName OBJECT-TYPE
       SYNTAX       OCTET STRING (SIZE(1..19))
       MAX-ACCESS   read-create
       STATUS       current
       DESCRIPTION
          "Filter incoming summary lsa,the value of this object 
           indicates the name of an ip-prefix-list."
       ::= { raisecomOspfAreaEntry 19 }   

  raisecomOspfAreaFilterOutIpPrefixListName OBJECT-TYPE
       SYNTAX       OCTET STRING (SIZE(1..19))
       MAX-ACCESS   read-create
       STATUS       current
       DESCRIPTION
          "Filter outgoing summary lsa,the value of this object 
           indicates the name of an ip-prefix-list."
       ::= { raisecomOspfAreaEntry 20 }  
        
---------------------------------------------------------------       
--  raisecomOspfNetWorkTable
--     The OSPF netwrok Table contains information
--     regarding the various areas.
---------------------------------------------------------------
raisecomOspfNetWorkTable OBJECT-TYPE
       SYNTAX       SEQUENCE OF RaisecomOspfNetWorkEntry
       MAX-ACCESS   not-accessible
       STATUS       current
       DESCRIPTION
          "The list of directly-connected networks which enable 
          the OSPF function."
       ::= { raisecomOspfObjects 3 }

  raisecomOspfNetWorkEntry OBJECT-TYPE
       SYNTAX       RaisecomOspfNetWorkEntry
       MAX-ACCESS   not-accessible
       STATUS       current
       DESCRIPTION
          "Defines an entry in the raisecomOspfNetWorkTable.

          Information in this table is persistent and when this object
          is written the entity SHOULD save the change to non-volatile
          storage."
       INDEX { raisecomOspfProcessId,
               raisecomOspfAreaId,
               raisecomOspfNet, 
               raisecomOspfMask }
       ::= { raisecomOspfNetWorkTable 1 }

  RaisecomOspfNetWorkEntry ::=
       SEQUENCE {
          raisecomOspfNet
             IpAddress,
          raisecomOspfMask
             IpAddress,
          raisecomOspfNetWorkStatus
             RowStatus
          }

  raisecomOspfNet OBJECT-TYPE
       SYNTAX       IpAddress
       MAX-ACCESS   read-only -- read-only since originally an
                              -- SMIv1 index   
       STATUS       current
       DESCRIPTION
          "The IP address of the net or subnet indicated
          by the range."
       REFERENCE
          "OSPF Version 2, Appendix C.2 Area parameters"
       ::= { raisecomOspfNetWorkEntry 1 }

  raisecomOspfMask OBJECT-TYPE
       SYNTAX       IpAddress
       MAX-ACCESS   read-only
       STATUS       current
       DESCRIPTION
          "The subnet mask that pertains to the net or
          subnet."
       REFERENCE
          "OSPF Version 2, Appendix C.2 Area parameters"
       ::= { raisecomOspfNetWorkEntry 2 }

  raisecomOspfNetWorkStatus OBJECT-TYPE
       SYNTAX       RowStatus
       MAX-ACCESS   read-create
       STATUS       current
       DESCRIPTION
          "This object permits management of the table by
          facilitating actions such as row creation,
          construction, and destruction.

          The value of this object has no effect on
          whether other objects in this conceptual row can be
          modified."
       ::= { raisecomOspfNetWorkEntry 3 }
       
------------------------------------------------------------------
--raisecomOspfStubAreaTable    
--
--The table define ospf stub area
------------------------------------------------------------------
  raisecomOspfStubAreaTable OBJECT-TYPE
       SYNTAX       SEQUENCE OF RaisecomOspfStubAreaEntry
       MAX-ACCESS   not-accessible
       STATUS       current
       DESCRIPTION
          "The set of metrics that will be advertised
          by a default Area Border Router into a stub area."
       REFERENCE
          "OSPF Version 2, Appendix C.2, Area Parameters"
       ::= { raisecomOspfObjects 4 }

  raisecomOspfStubAreaEntry OBJECT-TYPE
       SYNTAX       RaisecomOspfStubAreaEntry
       MAX-ACCESS   not-accessible
       STATUS      current
       DESCRIPTION
          "The metric for a given Type of Service that
          will be advertised by a default Area Border
          Router into a stub area.

          Information in this table is persistent and when this object
          is written the entity SHOULD save the change to non-volatile
          storage."
       REFERENCE
          "OSPF Version 2, Appendix C.2, Area Parameters"
       INDEX { raisecomOspfProcessId, 
               raisecomOspfStubAreaId }
       ::= { raisecomOspfStubAreaTable 1 }

  RaisecomOspfStubAreaEntry ::=
       SEQUENCE {
          raisecomOspfStubAreaId
             AreaID,
          raisecomOspfStubAreaOption
             TruthValue,
          raisecomOspfStubAreaStatus
             RowStatus
          }

  raisecomOspfStubAreaId OBJECT-TYPE
       SYNTAX       AreaID
       MAX-ACCESS   read-only -- read-only since originally an
                              -- SMIv1 index
       STATUS       current
       DESCRIPTION
          "The 32-bit identifier for the stub area.  On
          creation, this can be derived from the
          instance."
       ::= { raisecomOspfStubAreaEntry 1 }

  raisecomOspfStubAreaOption OBJECT-TYPE
       SYNTAX       TruthValue
       MAX-ACCESS   read-create
       STATUS       current
       DESCRIPTION
          "The option of STUB area.True means that ABR cann't send summary lsa to
          stub area."
       ::= { raisecomOspfStubAreaEntry 2 }

  raisecomOspfStubAreaStatus OBJECT-TYPE
       SYNTAX       RowStatus
       MAX-ACCESS   read-create
       STATUS       current
       DESCRIPTION
          "This object permits management of the table by
          facilitating actions such as row creation,
          construction, and destruction.

          The value of this object has no effect on
          whether other objects in this conceptual row can be
          modified."
       ::= { raisecomOspfStubAreaEntry 3 }
  
------------------------------------------------------------------
--raisecomOspfNssaAreaTable    
--
--The table define ospf nssa area
------------------------------------------------------------------
  raisecomOspfNssaAreaTable OBJECT-TYPE
       SYNTAX       SEQUENCE OF RaisecomOspfNssaAreaEntry
       MAX-ACCESS   not-accessible
       STATUS       current
       DESCRIPTION
          "The set of metrics that will be advertised
          by a default Area Border Router into a Nssa area."
       REFERENCE
          "Rfc 1587"
       ::= { raisecomOspfObjects 5 }

  raisecomOspfNssaAreaEntry OBJECT-TYPE
       SYNTAX       RaisecomOspfNssaAreaEntry
       MAX-ACCESS   not-accessible
       STATUS      current
       DESCRIPTION
          "The metric for a given Type of Service that
          will be advertised by a default Area Border
          Router into a Nssa area.

          Information in this table is persistent and when this object
          is written the entity SHOULD save the change to non-volatile
          storage."
       REFERENCE
          "Rfc 1587"
       INDEX { raisecomOspfProcessId, 
               raisecomOspfNssaAreaId }
       ::= { raisecomOspfNssaAreaTable 1 }

  RaisecomOspfNssaAreaEntry ::=
       SEQUENCE {
          raisecomOspfNssaAreaId
             AreaID,
          raisecomOspfNssaAreaOption
             Integer32,
          raisecomOspfNssaAreaStatus
             RowStatus
          }

  raisecomOspfNssaAreaId OBJECT-TYPE
       SYNTAX       AreaID
       MAX-ACCESS   read-only -- read-only since originally an
                              -- SMIv1 index
       STATUS       current
       DESCRIPTION
          "The 32-bit identifier for the nssa area.  On
          creation, this can be derived from the
          instance."
       ::= { raisecomOspfNssaAreaEntry 1 }

  raisecomOspfNssaAreaOption OBJECT-TYPE
       SYNTAX       Integer32(0..7)
       MAX-ACCESS   read-create
       STATUS       current
       DESCRIPTION
          "The option of Nssa area. If first bit is set, Router should generate
          default type-7 lsa; if second bit is set, nssa area cann't import ex-
          ternal route; if third bit is set, ABR cann't send summary lsas to the
          nssa area."
       ::= { raisecomOspfNssaAreaEntry 2 }

  raisecomOspfNssaAreaStatus OBJECT-TYPE
       SYNTAX       RowStatus
       MAX-ACCESS   read-create
       STATUS       current
       DESCRIPTION
          "This object permits management of the table by
          facilitating actions such as row creation,
          construction, and destruction.

          The value of this object has no effect on
          whether other objects in this conceptual row can be
          modified."
       ::= { raisecomOspfNssaAreaEntry 3 }       
       
---------------------------------------------------------------       
--  raisecomOspfIfTable
--  OSPF Interface Table
-- 
--------------------------------------------------------------- 
  raisecomOspfIfTable OBJECT-TYPE
       SYNTAX       SEQUENCE OF RaisecomOspfIfEntry
       MAX-ACCESS   not-accessible
       STATUS       current
       DESCRIPTION
          "The OSPF Interface Table describes the interfaces
          from the viewpoint of OSPF.
          It augments the ipAddrTable with OSPF specific information."
       REFERENCE
          "OSPF Version 2, Appendix C.3  Router interface
          parameters"
       ::= { raisecomOspfObjects 6 }

  raisecomOspfIfEntry OBJECT-TYPE
       SYNTAX       RaisecomOspfIfEntry
       MAX-ACCESS   not-accessible
       STATUS       current
       DESCRIPTION
          "The OSPF interface entry describes one interface
          from the viewpoint of OSPF.

          Information in this table is persistent and when this object
          is written the entity SHOULD save the change to non-volatile
          storage."
       INDEX { raisecomOspfProcessId,
               raisecomOspfAddressLessIf }
       ::= { raisecomOspfIfTable 1 }

  RaisecomOspfIfEntry ::=
       SEQUENCE {
          raisecomOspfIfIpAddress
             IpAddress,
          raisecomOspfAddressLessIf
             InterfaceIndexOrZero,
          raisecomOspfIfAreaId
             AreaID,
          raisecomOspfIfType
             INTEGER,
          raisecomOspfIfAdminStat
             Status,
          raisecomOspfIfRtrPriority
             DesignatedRouterPriority,
          raisecomOspfIfTransitDelay
             UpToMaxAge,
          raisecomOspfIfRetransInterval
             UpToMaxAge,
          raisecomOspfIfHelloInterval
             HelloRange,
          raisecomOspfIfRtrDeadInterval
             PositiveInteger,
          raisecomOspfIfPollInterval
             PositiveInteger,
          raisecomOspfIfState
             INTEGER,
          raisecomOspfIfDesignatedRouter
             IpAddress,
          raisecomOspfIfBackupDesignatedRouter
             IpAddress,
          raisecomOspfIfEvents
             Counter32,
          raisecomOspfIfAuthKeyId
             Integer32,  
          raisecomOspfIfAuthSimpleKeyType 
             INTEGER,
          raisecomOspfIfAuthMd5KeyType 
             INTEGER,
          raisecomOspfIfAuthSimpleKey  
             OCTET STRING (SIZE (0..68)),     
          raisecomOspfIfAuthMd5Key  
             OCTET STRING (SIZE (0..68)),     
          raisecomOspfIfAuthKeyChain
             OCTET STRING (SIZE (0..16)),
          raisecomOspfIfAuthType
             OspfAuthenticationType,
          raisecomOspfIfLsaCount
             Gauge32,
          raisecomOspfIfLsaCksumSum
             Unsigned32,
          raisecomOspfIfDesignatedRouterId
             RouterID,
          raisecomOspfIfBackupDesignatedRouterId
             RouterID, 
          raisecomOspfIfPassive   
             EnableVar,
          raisecomOspfIfMtu   
             EnableVar, 
          raisecomOspfIfMetric
             Metric
             }
  
  raisecomOspfAddressLessIf OBJECT-TYPE
       SYNTAX       InterfaceIndexOrZero
       MAX-ACCESS   read-only -- read-only since originally an
                              -- SMIv1 index
       STATUS       current
       DESCRIPTION
          "For the purpose of easing the instancing of
          addressed and addressless interfaces; this
          variable takes the value 0 on interfaces with
          IP addresses and the corresponding value of
          ifIndex for interfaces having no IP address."
       ::= { raisecomOspfIfEntry 1 }
  
  raisecomOspfIfIpAddress OBJECT-TYPE
       SYNTAX       IpAddress
       MAX-ACCESS   read-only 
       STATUS       current
       DESCRIPTION
          "The IP address of this OSPF interface."

       ::= { raisecomOspfIfEntry 2 }

  raisecomOspfIfAreaId OBJECT-TYPE
       SYNTAX       AreaID
       MAX-ACCESS   read-only
       STATUS       current
       DESCRIPTION
          "A 32-bit integer uniquely identifying the area
          to which the interface connects.  Area ID
          0.0.0.0 is used for the OSPF backbone."
       DEFVAL { '00000000'H }  -- 0.0.0.0
       ::= { raisecomOspfIfEntry 3 }

  raisecomOspfIfType OBJECT-TYPE
       SYNTAX       INTEGER {
                       broadcast (1),
                       nbma (2),
                       pointToPoint (3),
                       pointToMultipoint (5)
                       }
       MAX-ACCESS   read-create
       STATUS       current
       DESCRIPTION
          "The OSPF interface type.
          By way of a default, this field may be intuited
          from the corresponding value of ifType.
          Broadcast LANs, such as Ethernet and IEEE 802.5,
          take the value 'broadcast', X.25 and similar
          technologies take the value 'nbma', and links
          that are definitively point to point take the
          value 'pointToPoint'."  
       DEFVAL {broadcast}
        ::= { raisecomOspfIfEntry 4 }

  raisecomOspfIfAdminStat OBJECT-TYPE
       SYNTAX       Status

       MAX-ACCESS   read-only
       STATUS       current
       DESCRIPTION
          "The OSPF interface's administrative status.
          The value formed on the interface, and the interface
          will be advertised as an internal route to some area.
          The value 'disabled' denotes that the interface is
          external to OSPF."
       DEFVAL { enabled }
       ::= { raisecomOspfIfEntry 5 }

  raisecomOspfIfRtrPriority OBJECT-TYPE
       SYNTAX       DesignatedRouterPriority
       MAX-ACCESS   read-create
       STATUS       current
       DESCRIPTION
          "The priority of this interface.  Used in
          multi-access networks, this field is used in
          the designated router election algorithm.  The
          value 0 signifies that the router is not eligible
          to become the designated router on this particular
          network.  In the event of a tie in this value,
          routers will use their Router ID as a tie breaker."
        DEFVAL { 1 }
        ::= { raisecomOspfIfEntry 6 }

  raisecomOspfIfTransitDelay OBJECT-TYPE
        SYNTAX       UpToMaxAge
        UNITS        "seconds"
        MAX-ACCESS   read-create
        STATUS       current
        DESCRIPTION
           "The estimated number of seconds it takes to
           transmit a link state update packet over this
           interface.  Note that the minimal value SHOULD be
           1 second."
        DEFVAL { 1 }
        ::= { raisecomOspfIfEntry 7 }

  raisecomOspfIfRetransInterval OBJECT-TYPE
       SYNTAX       UpToMaxAge
       UNITS        "seconds"
       MAX-ACCESS   read-create
       STATUS       current
       DESCRIPTION
          "The number of seconds between link state advertisement
          retransmissions, for adjacencies belonging to this
          interface.  This value is also used when retransmitting

          database description and Link State request packets.
          Note that minimal value SHOULD be 1 second."
       DEFVAL { 5 }
       ::= { raisecomOspfIfEntry 8 }

  raisecomOspfIfHelloInterval OBJECT-TYPE
       SYNTAX       HelloRange
       UNITS        "seconds"
       MAX-ACCESS   read-create
       STATUS       current
       DESCRIPTION
          "The length of time, in seconds, between the Hello packets
          that the router sends on the interface.  This value must be
          the same for all routers attached to a common network."
       DEFVAL { 10 }
       ::= { raisecomOspfIfEntry 9 }

  raisecomOspfIfRtrDeadInterval OBJECT-TYPE
       SYNTAX       PositiveInteger
       UNITS        "seconds"
       MAX-ACCESS   read-create
       STATUS       current
       DESCRIPTION
          "The number of seconds that a router's Hello packets have
          not been seen before its neighbors declare the router down.
          This should be some multiple of the Hello interval.  This
          value must be the same for all routers attached to a common
          network."
        DEFVAL { 40 }
        ::= { raisecomOspfIfEntry 10 }

  raisecomOspfIfPollInterval OBJECT-TYPE
       SYNTAX       PositiveInteger
       UNITS        "seconds"
       MAX-ACCESS   read-create
       STATUS       current
       DESCRIPTION
          "The larger time interval, in seconds, between the Hello
          packets sent to an inactive non-broadcast multi-access
          neighbor."
       DEFVAL { 120 }
       ::= { raisecomOspfIfEntry 11 }

  raisecomOspfIfState OBJECT-TYPE
       SYNTAX       INTEGER {
                       down (1),
                       loopback (2),
                       waiting (3),
                       pointToPoint (4),
                       designatedRouter (5),
                       backupDesignatedRouter (6),
                       otherDesignatedRouter (7)
                       }
       MAX-ACCESS   read-only
       STATUS       current
       DESCRIPTION
          "The OSPF Interface State."
       DEFVAL { down }
       ::= { raisecomOspfIfEntry 12 }

  raisecomOspfIfDesignatedRouter OBJECT-TYPE
       SYNTAX       IpAddress
       MAX-ACCESS   read-only
       STATUS       current
       DESCRIPTION
          "The IP address of the designated router."
       DEFVAL { '00000000'H } -- 0.0.0.0
       ::= { raisecomOspfIfEntry 13 }

  raisecomOspfIfBackupDesignatedRouter OBJECT-TYPE
       SYNTAX       IpAddress
       MAX-ACCESS   read-only
       STATUS       current
       DESCRIPTION
          "The IP address of the backup designated
          router."
       DEFVAL { '00000000'H }  -- 0.0.0.0
       ::= { raisecomOspfIfEntry 14 }

  raisecomOspfIfEvents OBJECT-TYPE
       SYNTAX       Counter32
       MAX-ACCESS   read-only
       STATUS       current
       DESCRIPTION
          "The number of times this OSPF interface has
          changed its state or an error has occurred.

          Discontinuities in the value of this counter can occur
          at re-initialization of the management system, and at other
          times as indicated by the value of ospfDiscontinuityTime."
       ::= { raisecomOspfIfEntry 15 }
 
  raisecomOspfIfAuthKeyId OBJECT-TYPE
       SYNTAX       Integer32 (0..255)
       MAX-ACCESS   read-create
       STATUS       current
       DESCRIPTION  
          "The key id of md5 authentication."   
       DEFVAL { 0 }   
       ::= { raisecomOspfIfEntry 16 } 
         
  raisecomOspfIfAuthSimpleKeyType OBJECT-TYPE
       SYNTAX       INTEGER {plain(0), cipher(7)}
       MAX-ACCESS   read-create
       STATUS       current
       DESCRIPTION  
          "The type of password for simple authentication."   
       DEFVAL { 0 }   
       ::= { raisecomOspfIfEntry 17 }
  
  raisecomOspfIfAuthMd5KeyType OBJECT-TYPE
       SYNTAX       INTEGER {plain(0), cipher(7)}
       MAX-ACCESS   read-create
       STATUS       current
       DESCRIPTION  
          "The type of password for md5 authentication."   
       DEFVAL { 0 }
       ::= { raisecomOspfIfEntry 18 }

  raisecomOspfIfAuthSimpleKey OBJECT-TYPE
       SYNTAX       OCTET STRING (SIZE (0..68))
       MAX-ACCESS   read-create
       STATUS       current
       DESCRIPTION
          "The password used as an OSPF
          authentication key when simple password security
          is enabled."
       DEFVAL {''h}    
       ::= { raisecomOspfIfEntry 19 } 
       
  raisecomOspfIfAuthMd5Key OBJECT-TYPE
       SYNTAX       OCTET STRING (SIZE (0..68))
       MAX-ACCESS   read-create
       STATUS       current
       DESCRIPTION
          "The password used as an OSPF
          authentication key when md5 security
          is enabled."  
       DEFVAL {''h}   
       ::= { raisecomOspfIfEntry 20 }
  
  raisecomOspfIfAuthKeyChain OBJECT-TYPE
       SYNTAX       OCTET STRING (SIZE (0..16))
       MAX-ACCESS   read-create
       STATUS       current
       DESCRIPTION
          "The name of key chain."
       DEFVAL {''h}
       ::= { raisecomOspfIfEntry 21 }

  raisecomOspfIfAuthType OBJECT-TYPE
       SYNTAX       OspfAuthenticationType
       MAX-ACCESS   read-create
       STATUS       current
       DESCRIPTION
          "The authentication type specified for an interface.

          Note that this object can be used to engage
          in significant attacks against an OSPF router."
       REFERENCE
          "OSPF Version 2, Appendix D Authentication"
       DEFVAL { none } -- no authentication, by default
       ::= { raisecomOspfIfEntry 22 }

  raisecomOspfIfLsaCount OBJECT-TYPE
       SYNTAX       Gauge32
       MAX-ACCESS   read-only
       STATUS       current
       DESCRIPTION
          "The total number of link-local link state advertisements
          in this interface's link-local link state database."
       ::= { raisecomOspfIfEntry 23 }

  raisecomOspfIfLsaCksumSum OBJECT-TYPE
       SYNTAX       Unsigned32
       MAX-ACCESS   read-only
       STATUS       current
       DESCRIPTION
          "The 32-bit unsigned sum of the Link State
          Advertisements' LS checksums contained in this
          interface's link-local link state database.
          The sum can be used to determine if there has
          been a change in the interface's link state
          database and to compare the interface link state
          database of routers attached to the same subnet."
       ::= { raisecomOspfIfEntry 24 }

  raisecomOspfIfDesignatedRouterId OBJECT-TYPE
       SYNTAX       RouterID
       MAX-ACCESS   read-only
       STATUS       current
       DESCRIPTION
          "The Router ID of the designated router."
       ::= { raisecomOspfIfEntry 25 }

  raisecomOspfIfBackupDesignatedRouterId OBJECT-TYPE
       SYNTAX       RouterID
       MAX-ACCESS   read-only
       STATUS       current
       DESCRIPTION
          "The Router ID of the backup designated router."
       ::= { raisecomOspfIfEntry 26 } 
       
  raisecomOspfIfPassive OBJECT-TYPE
       SYNTAX       EnableVar
       MAX-ACCESS   read-create
       STATUS       current
       DESCRIPTION
          "Indicate the interface is a passive interface." 
       DEFVAL {disable}  
       ::= { raisecomOspfIfEntry 27 }
    
  raisecomOspfIfMtu OBJECT-TYPE
       SYNTAX       EnableVar
       MAX-ACCESS   read-create
       STATUS       current
       DESCRIPTION
          "Indicate ignore the interface's mtu." 
       DEFVAL {enable}  
       ::= { raisecomOspfIfEntry 28 }     

  raisecomOspfIfMetric OBJECT-TYPE
       SYNTAX       Metric
       MAX-ACCESS   read-create
       STATUS       current
       DESCRIPTION
          "The metric of using this Type of Service on
          this interface.  The default value of the TOS 0
          metric is 10^8 / ifSpeed."
       ::= { raisecomOspfIfEntry 29 }

------------------------------------------------------------------
--raisecomOspfVirtIfTable    
--
--OSPF Virtual Interface Table
------------------------------------------------------------------
  raisecomOspfVirtIfTable OBJECT-TYPE
       SYNTAX       SEQUENCE OF RaisecomOspfVirtIfEntry
       MAX-ACCESS   not-accessible
       STATUS       current
       DESCRIPTION
          "Information about this router's virtual interfaces
          that the OSPF Process is configured to carry on."
       REFERENCE
          "OSPF Version 2, Appendix C.4  Virtual link
          parameters"
       ::= { raisecomOspfObjects 7 }

  raisecomOspfVirtIfEntry OBJECT-TYPE
       SYNTAX       RaisecomOspfVirtIfEntry
       MAX-ACCESS   not-accessible
       STATUS       current
       DESCRIPTION
          "Information about a single virtual interface.

          Information in this table is persistent and when this object
          is written the entity SHOULD save the change to non-volatile
          storage."

       INDEX { raisecomOspfProcessId,
               raisecomOspfVirtIfAreaId, 
               raisecomOspfVirtIfNeighbor }
       ::= { raisecomOspfVirtIfTable 1 }

  RaisecomOspfVirtIfEntry ::=
       SEQUENCE {
          raisecomOspfVirtIfAreaId
             AreaID,
          raisecomOspfVirtIfNeighbor
             RouterID,
          raisecomOspfVirtIfTransitDelay
             UpToMaxAge,
          raisecomOspfVirtIfRetransInterval
             UpToMaxAge,
          raisecomOspfVirtIfHelloInterval
             HelloRange,
          raisecomOspfVirtIfRtrDeadInterval
             PositiveInteger,
          raisecomOspfVirtIfState
             INTEGER,
          raisecomOspfVirtIfEvents
             Counter32,    
          raisecomOspfVirtIfAuthKeyId
             Integer32,  
          raisecomOspfVirtIfAuthSimpleKeyType 
             INTEGER,
          raisecomOspfVirtIfAuthMd5KeyType 
             INTEGER,
          raisecomOspfVirtIfAuthSimpleKey  
             OCTET STRING (SIZE (0..68)),     
          raisecomOspfVirtIfAuthMd5Key  
             OCTET STRING (SIZE (0..68)),     
          raisecomOspfVirtIfAuthKeyChain
             OCTET STRING (SIZE (0..16)),
          raisecomOspfVirtIfAuthType
             OspfAuthenticationType,
          raisecomOspfVirtIfLsaCount
             Gauge32,
          raisecomOspfVirtIfLsaCksumSum
             Unsigned32,
          raisecomOspfVirtIfCost
             Integer32,
          raisecomOspfVirtIfStatus
             RowStatus
          }

  raisecomOspfVirtIfAreaId OBJECT-TYPE
       SYNTAX       AreaID
       MAX-ACCESS   read-only -- read-only since originally an
                              -- SMIv1 index
       STATUS       current
       DESCRIPTION
          "The transit area that the virtual link
          traverses.  By definition, this is not 0.0.0.0."
       ::= { raisecomOspfVirtIfEntry 1 }

  raisecomOspfVirtIfNeighbor OBJECT-TYPE
       SYNTAX       RouterID
       MAX-ACCESS   read-only -- read-only since originally an
                              -- SMIv1 index
       STATUS       current
       DESCRIPTION
          "The Router ID of the virtual neighbor."
       ::= { raisecomOspfVirtIfEntry 2 }

  raisecomOspfVirtIfTransitDelay OBJECT-TYPE
       SYNTAX       UpToMaxAge
       UNITS        "seconds"
       MAX-ACCESS   read-create
       STATUS       current
       DESCRIPTION
          "The estimated number of seconds it takes to
          transmit a Link State update packet over this
          interface.  Note that the minimal value SHOULD be
          1 second."
       DEFVAL { 1 }
       ::= { raisecomOspfVirtIfEntry 3 }

  raisecomOspfVirtIfRetransInterval OBJECT-TYPE
       SYNTAX       UpToMaxAge
       UNITS        "seconds"
       MAX-ACCESS   read-create
       STATUS       current
       DESCRIPTION
          "The number of seconds between link state
          avertisement retransmissions, for adjacencies
          belonging to this interface.  This value is
          also used when retransmitting database
          description and Link State request packets.  This
          value should be well over the expected
          round-trip time.  Note that the minimal value SHOULD be
          1 second."
       DEFVAL { 5 }
       ::= { raisecomOspfVirtIfEntry 4 }

  raisecomOspfVirtIfHelloInterval OBJECT-TYPE
       SYNTAX       HelloRange
       UNITS        "seconds"
       MAX-ACCESS   read-create
       STATUS       current
       DESCRIPTION
          "The length of time, in seconds, between the
          Hello packets that the router sends on the
          interface.  This value must be the same for the
          virtual neighbor."
       DEFVAL { 10 }
       ::= { raisecomOspfVirtIfEntry 5 }

  raisecomOspfVirtIfRtrDeadInterval OBJECT-TYPE

       SYNTAX       PositiveInteger
       UNITS        "seconds"
       MAX-ACCESS   read-create
       STATUS       current
       DESCRIPTION
          "The number of seconds that a router's Hello
          packets have not been seen before its
          neighbors declare the router down.  This should be
          some multiple of the Hello interval.  This
          value must be the same for the virtual neighbor."
       DEFVAL { 60 }
       ::= { raisecomOspfVirtIfEntry 6 }

  raisecomOspfVirtIfState OBJECT-TYPE
       SYNTAX       INTEGER {
                       down (1), -- these use the same encoding
                       pointToPoint (4) -- as the raisecomOspfIfTable
                       }
       MAX-ACCESS   read-only
       STATUS       current
       DESCRIPTION
          "OSPF virtual interface states."
       DEFVAL { down }
       ::= { raisecomOspfVirtIfEntry 7 }

  raisecomOspfVirtIfEvents OBJECT-TYPE
       SYNTAX       Counter32
       MAX-ACCESS   read-only
       STATUS       current
       DESCRIPTION
          "The number of state changes or error events on
          this virtual link.

          Discontinuities in the value of this counter can occur
          at re-initialization of the management system, and at other
          times as indicated by the value of ospfDiscontinuityTime."
       ::= { raisecomOspfVirtIfEntry 8 } 
       
   raisecomOspfVirtIfAuthKeyId OBJECT-TYPE
       SYNTAX       Integer32 (0..255)
       MAX-ACCESS   read-create
       STATUS       current
       DESCRIPTION  
          "The key id of md5 authentication."   
       DEFVAL { 0 }   
       ::= { raisecomOspfVirtIfEntry 9 } 
         
  raisecomOspfVirtIfAuthSimpleKeyType OBJECT-TYPE
       SYNTAX       INTEGER {plain(0), cipher(7)}
       MAX-ACCESS   read-create
       STATUS       current
       DESCRIPTION  
          "The type of password for simple authentication."   
       DEFVAL { 0 }   
       ::= { raisecomOspfVirtIfEntry 10 }
  
  raisecomOspfVirtIfAuthMd5KeyType OBJECT-TYPE
       SYNTAX       INTEGER {plain(0), cipher(7)}
       MAX-ACCESS   read-create
       STATUS       current
       DESCRIPTION  
          "The type of password for md5 authentication."   
       DEFVAL { 0 }
       ::= { raisecomOspfVirtIfEntry 11 }

  raisecomOspfVirtIfAuthSimpleKey OBJECT-TYPE
       SYNTAX       OCTET STRING (SIZE (0..68))
       MAX-ACCESS   read-create
       STATUS       current

       DESCRIPTION
          "The password used as an OSPF
          authentication key when simple password security
          is enabled."  
       DEFVAL {''h}   
       ::= { raisecomOspfVirtIfEntry 12 } 
       
  raisecomOspfVirtIfAuthMd5Key OBJECT-TYPE
       SYNTAX       OCTET STRING (SIZE (0..68))
       MAX-ACCESS   read-create
       STATUS       current
       DESCRIPTION
          "The password used as an OSPF
          authentication key when md5 security
          is enabled."
       DEFVAL {''h} 
       ::= { raisecomOspfVirtIfEntry 13 }
  
  raisecomOspfVirtIfAuthKeyChain OBJECT-TYPE
       SYNTAX       OCTET STRING (SIZE (0..16))
       MAX-ACCESS   read-create
       STATUS       current
       DESCRIPTION
          "The name of key chain."
       DEFVAL {''h}
       ::= { raisecomOspfVirtIfEntry 14 }

  raisecomOspfVirtIfAuthType OBJECT-TYPE
       SYNTAX       OspfAuthenticationType
       MAX-ACCESS   read-create
       STATUS       current
       DESCRIPTION
          "The authentication type specified for a virtual interface.

          Note that this object can be used to engage
          in significant attacks against an OSPF router."
       REFERENCE
          "OSPF Version 2, Appendix E Authentication"
       DEFVAL { none } -- no authentication, by default

       ::= { raisecomOspfVirtIfEntry 15 }

  raisecomOspfVirtIfLsaCount OBJECT-TYPE
       SYNTAX       Gauge32
       MAX-ACCESS   read-only
       STATUS       current
       DESCRIPTION
          "The total number of link-local link state advertisements
          in this virtual interface's link-local link state database."
       ::= { raisecomOspfVirtIfEntry 16 }

  raisecomOspfVirtIfLsaCksumSum OBJECT-TYPE
       SYNTAX       Unsigned32
       MAX-ACCESS   read-only
       STATUS       current
       DESCRIPTION
          "The 32-bit unsigned sum of the link state
          advertisements' LS checksums contained in this
          virtual interface's link-local link state database.
          The sum can be used to determine if there has
          been a change in the virtual interface's link state
          database, and to compare the virtual interface
          link state database of the virtual neighbors."
       ::= { raisecomOspfVirtIfEntry 17 }  

  raisecomOspfVirtIfCost OBJECT-TYPE
       SYNTAX       Integer32 (1.. 65535)
       MAX-ACCESS   read-only
       STATUS       current
       DESCRIPTION
          "It has been used to describe the cost of 
          virtual interface."
       DEFVAL { 1 }
       ::= { raisecomOspfVirtIfEntry 18 } 
       
  raisecomOspfVirtIfStatus OBJECT-TYPE
       SYNTAX       RowStatus
       MAX-ACCESS   read-create
       STATUS       current
       DESCRIPTION
          "This object permits management of the table by
          facilitating actions such as row creation,
          construction, and destruction.

          The value of this object has no effect on
          whether other objects in this conceptual row can be
          modified."
        ::= { raisecomOspfVirtIfEntry 19 }   
        
------------------------------------------------------------------
--raisecomOspfNbrTable    
--
--OSPF Neighbor Table
------------------------------------------------------------------
  raisecomOspfNbrTable OBJECT-TYPE
       SYNTAX       SEQUENCE OF RaisecomOspfNbrEntry
       MAX-ACCESS   not-accessible
       STATUS       current
       DESCRIPTION
          "A table describing all non-virtual neighbors
          in the locality of the OSPF router."
       REFERENCE
          "OSPF Version 2, Section 10 The Neighbor Data
          Structure"
       ::= { raisecomOspfObjects 8 }

  raisecomOspfNbrEntry OBJECT-TYPE
       SYNTAX       RaisecomOspfNbrEntry
       MAX-ACCESS   not-accessible
       STATUS       current
       DESCRIPTION
          "The information regarding a single neighbor.

          Information in this table is persistent and when this object
          is written the entity SHOULD save the change to non-volatile
          storage."
       REFERENCE
          "OSPF Version 2, Section 10 The Neighbor Data
          Structure"
       INDEX { raisecomOspfProcessId,
               raisecomOspfNbrIpAddr }
       ::= { raisecomOspfNbrTable 1 }

  RaisecomOspfNbrEntry ::=
       SEQUENCE {
          raisecomOspfNbrIpAddr
             IpAddress,
          raisecomOspfNbrAddressLessIndex
             InterfaceIndexOrZero,
          raisecomOspfNbrRtrId
             RouterID,
          raisecomOspfNbrOptions
             Integer32,
          raisecomOspfNbrPriority
             DesignatedRouterPriority,
          raisecomOspfNbrState
             INTEGER,
          raisecomOspfNbrEvents
             Counter32,
          raisecomOspfNbrLsRetransQLen
             Gauge32,
          raisecomOspfNbrMode
             INTEGER   
          }

  raisecomOspfNbrIpAddr OBJECT-TYPE
       SYNTAX       IpAddress
       MAX-ACCESS   read-only -- read-only since originally an
                              -- SMIv1 index
       STATUS       current
       DESCRIPTION
          "The IP address this neighbor is using in its
          IP source address.  Note that, on addressless
          links, this will not be 0.0.0.0 but the

          address of another of the neighbor's interfaces."
       ::= { raisecomOspfNbrEntry 1 }

   raisecomOspfNbrAddressLessIndex OBJECT-TYPE
       SYNTAX       InterfaceIndexOrZero
       MAX-ACCESS   read-only -- read-only since originally an
                              -- SMIv1 index
       STATUS       current
       DESCRIPTION
          "On an interface having an IP address, zero.
          On addressless interfaces, the corresponding
          value of ifIndex in the Internet Standard MIB.
          On row creation, this can be derived from the
          instance."
        ::= { raisecomOspfNbrEntry 2 }

  raisecomOspfNbrRtrId OBJECT-TYPE
       SYNTAX       RouterID
       MAX-ACCESS   read-only
       STATUS       current
       DESCRIPTION
          "A 32-bit integer (represented as a type
          IpAddress) uniquely identifying the neighboring
          router in the Autonomous System."
       DEFVAL { '00000000'H } -- 0.0.0.0
       ::= { raisecomOspfNbrEntry 3 }

  raisecomOspfNbrOptions OBJECT-TYPE
       SYNTAX       Integer32
       MAX-ACCESS   read-only
       STATUS       current
       DESCRIPTION
          "A bit mask corresponding to the neighbor's
          options field.

          Bit 0, if set, indicates that the system will
          operate on Type of Service metrics other than
          TOS 0.  If zero, the neighbor will ignore all
          metrics except the TOS 0 metric.

          Bit 1, if set, indicates that the associated
          area accepts and operates on external
          information; if zero, it is a stub area.

          Bit 2, if set, indicates that the system is
          capable of routing IP multicast datagrams, that is
          that it implements the multicast extensions to
          OSPF.

          Bit 3, if set, indicates that the associated
          area is an NSSA.  These areas are capable of
          carrying type-7 external advertisements, which
          are translated into type-5 external advertisements
          at NSSA borders."
       REFERENCE
           "OSPF Version 2, Section 12.1.2 Options"
       DEFVAL { 0 }
       ::= { raisecomOspfNbrEntry 4 }

   raisecomOspfNbrPriority OBJECT-TYPE
       SYNTAX       DesignatedRouterPriority
       MAX-ACCESS   read-only
       STATUS       current
       DESCRIPTION
          "The priority of this neighbor in the designated
          router election algorithm.  The value 0 signifies
          that the neighbor is not eligible to become
          the designated router on this particular network."
       DEFVAL { 1 }
       ::= { raisecomOspfNbrEntry 5 }

   raisecomOspfNbrState OBJECT-TYPE
        SYNTAX       INTEGER {
                         down (1),
                         attempt (2),
                         init (3),
                         twoWay (4),
                         exchangeStart (5),
                         exchange (6),
                         loading (7),
                         full (8)
                         }
         MAX-ACCESS   read-only
         STATUS       current
         DESCRIPTION
            "The state of the relationship with this neighbor."
         REFERENCE
            "OSPF Version 2, Section 10.1 Neighbor States"
         DEFVAL { down }
         ::= { raisecomOspfNbrEntry 6 }

  raisecomOspfNbrEvents OBJECT-TYPE
       SYNTAX       Counter32
       MAX-ACCESS   read-only
       STATUS       current
       DESCRIPTION
          "The number of times this neighbor relationship
          has changed state or an error has occurred.

          Discontinuities in the value of this counter can occur
          at re-initialization of the management system, and at other
          times as indicated by the value of ospfDiscontinuityTime."
       ::= { raisecomOspfNbrEntry 7 }

  raisecomOspfNbrLsRetransQLen OBJECT-TYPE
       SYNTAX       Gauge32
       MAX-ACCESS   read-only
       STATUS       current
       DESCRIPTION
          "The current length of the retransmission
          queue."
       ::= { raisecomOspfNbrEntry 8 } 
  
  raisecomOspfNbrMode OBJECT-TYPE
       SYNTAX       INTEGER {  
                      slave (1),
                      master (2)
                      }
       MAX-ACCESS   read-only
       STATUS       current
       DESCRIPTION
          "It has been used to describe the master-slave mode of 
          neighbor. "
       DEFVAL { slave }
       ::= { raisecomOspfNbrEntry 9 }           
       
------------------------------------------------------------------
--raisecomOspfNbmaCfgNbrTable    
--
--OSPF Nbma Network Configed Neighbor Table
------------------------------------------------------------------
  raisecomOspfNbmaCfgNbrTable   OBJECT-TYPE
       SYNTAX       SEQUENCE OF RaisecomOspfNbmaCfgNbrEntry
       MAX-ACCESS   not-accessible
       STATUS       current
       DESCRIPTION
          "A table describing all configured neigbors on nbma network."
       ::= { raisecomOspfObjects 9 }

  raisecomOspfNbmaCfgNbrEntry OBJECT-TYPE
       SYNTAX       RaisecomOspfNbmaCfgNbrEntry
       MAX-ACCESS   not-accessible
       STATUS       current
       DESCRIPTION
          "The information regarding a Configured neighbor.

          Information in this table is persistent and when this object
          is written the entity SHOULD save the change to non-volatile
          storage."
       REFERENCE
          "OSPF Version 2, Section 10 The Neighbor Data
          Structure"
       INDEX { raisecomOspfProcessId,
               raisecomOspfNbmaCfgNbrIpAddr }
       ::= { raisecomOspfNbmaCfgNbrTable 1 }

  RaisecomOspfNbmaCfgNbrEntry ::=
       SEQUENCE {
          raisecomOspfNbmaCfgNbrIpAddr
             IpAddress,
          raisecomOspfNbmaCfgNbrPriority 
             DesignatedRouterPriority, 
          raisecomOspfNbmaCfgNbrStatus
             RowStatus       
          }

  raisecomOspfNbmaCfgNbrIpAddr OBJECT-TYPE
       SYNTAX       IpAddress
       MAX-ACCESS   read-only -- read-only since originally an
                              -- SMIv1 index
       STATUS       current
       DESCRIPTION
          "The IP address this neighbor is using in its
          IP source address.  Note that, on addressless
          links, this will not be 0.0.0.0 but the
          address of another of the neighbor's interfaces."
       ::= { raisecomOspfNbmaCfgNbrEntry 1 }    
              
  raisecomOspfNbmaCfgNbrPriority OBJECT-TYPE
       SYNTAX       DesignatedRouterPriority
       MAX-ACCESS   read-create 
       STATUS       current
       DESCRIPTION
          "The priority of this neighbor in the designated
          router election algorithm.  The value 0 signifies
          that the neighbor is not eligible to become
          the designated router on this particular network." 
       DEFVAL { 1 }
       ::= { raisecomOspfNbmaCfgNbrEntry 2 }           

  raisecomOspfNbmaCfgNbrStatus OBJECT-TYPE
       SYNTAX       RowStatus
       MAX-ACCESS   read-create
       STATUS       current
       DESCRIPTION
          "This object permits management of the table by
          facilitating actions such as row creation,
          construction, and destruction.

          The value of this object has no effect on
          whether other objects in this conceptual row can be
          modified."
       ::= { raisecomOspfNbmaCfgNbrEntry 3 }
 
------------------------------------------------------------------
--raisecomOspfVirtNbrTable    
--
--OSPF Virtual Neighbor Table
------------------------------------------------------------------
  raisecomOspfVirtNbrTable OBJECT-TYPE
       SYNTAX       SEQUENCE OF RaisecomOspfVirtNbrEntry
       MAX-ACCESS   not-accessible
       STATUS       current
       DESCRIPTION
          "This table describes all virtual neighbors.
          Since virtual links are configured
          in the Virtual Interface Table, this table is read-only."
       REFERENCE
          "OSPF Version 2, Section 15 Virtual Links"
       ::= { raisecomOspfObjects 10 }

  raisecomOspfVirtNbrEntry OBJECT-TYPE
       SYNTAX       RaisecomOspfVirtNbrEntry
       MAX-ACCESS   not-accessible
       STATUS       current
       DESCRIPTION
          "Virtual neighbor information."
       INDEX { raisecomOspfProcessId,
               raisecomOspfVirtNbrArea, 
               raisecomOspfVirtNbrRtrId }
       ::= { raisecomOspfVirtNbrTable 1 }

  RaisecomOspfVirtNbrEntry ::=
       SEQUENCE {
          raisecomOspfVirtNbrArea
             AreaID,
          raisecomOspfVirtNbrRtrId
             RouterID,
          raisecomOspfVirtNbrIpAddr
             IpAddress,
          raisecomOspfVirtNbrOptions
             Integer32,
          raisecomOspfVirtNbrState
             INTEGER,
          raisecomOspfVirtNbrEvents
             Counter32,
          raisecomOspfVirtNbrLsRetransQLen
             Gauge32,
          raisecomOspfVirtNbrLessIf
             Integer32,
          raisecomOspfVirtNbrMode
             INTEGER
          }

  raisecomOspfVirtNbrArea OBJECT-TYPE

       SYNTAX       AreaID
       MAX-ACCESS   read-only -- read-only since originally an
                              -- SMIv1 index
       STATUS       current
       DESCRIPTION
          "The Transit Area Identifier."
       ::= { raisecomOspfVirtNbrEntry 1 }

  raisecomOspfVirtNbrRtrId OBJECT-TYPE
       SYNTAX       RouterID
       MAX-ACCESS   read-only -- read-only since originally an
                              -- SMIv1 index
       STATUS      current
       DESCRIPTION
          "A 32-bit integer uniquely identifying the
          neighboring router in the Autonomous System."
       ::= { raisecomOspfVirtNbrEntry 2 }

  raisecomOspfVirtNbrIpAddr OBJECT-TYPE
       SYNTAX       IpAddress
       MAX-ACCESS   read-only
       STATUS       current
       DESCRIPTION
          "The IP address this virtual neighbor is using."
       ::= { raisecomOspfVirtNbrEntry 3 }

  raisecomOspfVirtNbrOptions OBJECT-TYPE
       SYNTAX       Integer32
       MAX-ACCESS   read-only
       STATUS       current
       DESCRIPTION
          "A bit mask corresponding to the neighbor's
          options field.

          Bit 1, if set, indicates that the system will
          operate on Type of Service metrics other than
          TOS 0.  If zero, the neighbor will ignore all
          metrics except the TOS 0 metric.

          Bit 2, if set, indicates that the system is
          network multicast capable, i.e., that it
          implements OSPF multicast routing."
       ::= { raisecomOspfVirtNbrEntry 4 }

   raisecomOspfVirtNbrState OBJECT-TYPE
       SYNTAX       INTEGER {
                       down (1),
                       attempt (2),
                       init (3),
                       twoWay (4),
                       exchangeStart (5),
                       exchange (6),
                       loading (7),
                       full (8)
                       }
       MAX-ACCESS   read-only
       STATUS       current
       DESCRIPTION
          "The state of the virtual neighbor relationship."
       ::= { raisecomOspfVirtNbrEntry 5 }

  raisecomOspfVirtNbrEvents OBJECT-TYPE
       SYNTAX       Counter32
       MAX-ACCESS   read-only
       STATUS       current
       DESCRIPTION
          "The number of times this virtual link has
          changed its state or an error has occurred.

          Discontinuities in the value of this counter can occur
          at re-initialization of the management system, and at other
          times as indicated by the value of ospfDiscontinuityTime."
       ::= { raisecomOspfVirtNbrEntry 6 }

  raisecomOspfVirtNbrLsRetransQLen OBJECT-TYPE
       SYNTAX       Gauge32
       MAX-ACCESS   read-only
       STATUS       current
       DESCRIPTION
          "The current length of the retransmission
          queue."
       ::= { raisecomOspfVirtNbrEntry 7 }
       
  raisecomOspfVirtNbrLessIf OBJECT-TYPE
       SYNTAX       Integer32
       MAX-ACCESS   read-only
       STATUS       current
       DESCRIPTION
          "It has been used to describe the out interface index of 
          this virtual neighbor."
       ::= { raisecomOspfVirtNbrEntry 8 }

  raisecomOspfVirtNbrMode OBJECT-TYPE
       SYNTAX       INTEGER {  
                      slave (1),
                      master (2)
                      }
       MAX-ACCESS   read-only
       STATUS       current
       DESCRIPTION
          "It has been used to describe the master-slave mode of 
          virtual neighbor. "
       DEFVAL { slave }
       ::= { raisecomOspfVirtNbrEntry 9 }

----------------------------------------------------------------
--  The OSPF Area Aggregate Table
--
--     This table replaces the OSPF Area Summary Table, being an
--     extension of that for CIDR routers.
----------------------------------------------------------------
   raisecomOspfAreaAggregateTable OBJECT-TYPE
       SYNTAX       SEQUENCE OF RaisecomOspfAreaAggregateEntry
       MAX-ACCESS   not-accessible
       STATUS       current

       DESCRIPTION
          "The Area Aggregate Table acts as an adjunct
           to the Area Table.  It describes those address aggregates
           that are configured to be propagated from an area.
           Its purpose is to reduce the amount of information
           that is known beyond an Area's borders.

           It contains a set of IP address ranges
           specified by an IP address/IP network mask pair.
           For example, a class B address range of X.X.X.X
           with a network mask of 255.255.0.0 includes all IP
           addresses from X.X.0.0 to X.X.255.255.

           Note that if ranges are configured such that one range
           subsumes another range (e.g., 10.0.0.0 mask 255.0.0.0
           and 10.1.0.0 mask 255.255.0.0),
           the most specific match is the preferred one."
       REFERENCE
          "OSPF Version 2, Appendix C.2  Area parameters"
       ::= { raisecomOspfObjects 11 }

  raisecomOspfAreaAggregateEntry OBJECT-TYPE
       SYNTAX   RaisecomOspfAreaAggregateEntry
       MAX-ACCESS   not-accessible
       STATUS   current
       DESCRIPTION
          "A single area aggregate entry.

          Information in this table is persistent and when this object
          is written the entity SHOULD save the change to non-volatile
          storage."
       REFERENCE
          "OSPF Version 2, Appendix C.2  Area parameters"
       INDEX { raisecomOspfProcessId,
               raisecomOspfAreaAggregateAreaID, 
               raisecomOspfAreaAggregateLsdbType,
               raisecomOspfAreaAggregateNet, 
               raisecomOspfAreaAggregateMask }
       ::= { raisecomOspfAreaAggregateTable 1 }

  RaisecomOspfAreaAggregateEntry ::=
       SEQUENCE {
          raisecomOspfAreaAggregateAreaID
             AreaID,
          raisecomOspfAreaAggregateLsdbType
             INTEGER,
          raisecomOspfAreaAggregateNet
             IpAddress,
          raisecomOspfAreaAggregateMask
             IpAddress, 
          raisecomOspfAreaAggregateEffect
             INTEGER,
          raisecomOspfAreaAggregateStatus
             RowStatus
          }

  raisecomOspfAreaAggregateAreaID OBJECT-TYPE
       SYNTAX       AreaID
       MAX-ACCESS   read-only -- read-only since originally an
                              -- SMIv1 index
       STATUS       current
       DESCRIPTION
          "The area within which the address aggregate is to be
          found."
       REFERENCE
          "OSPF Version 2, Appendix C.2 Area parameters"
       ::= { raisecomOspfAreaAggregateEntry 1 }

  raisecomOspfAreaAggregateLsdbType OBJECT-TYPE
       SYNTAX       INTEGER {
                       summaryLink (3),
                       nssaExternalLink (7)
                       }
       MAX-ACCESS   read-only -- read-only since originally an
                              -- SMIv1 index
       STATUS       current
       DESCRIPTION
          "The type of the address aggregate.  This field
          specifies the Lsdb type that this address
          aggregate applies to."
       REFERENCE
          "OSPF Version 2, Appendix A.4.1 The Link State
          Advertisement header"
       ::= { raisecomOspfAreaAggregateEntry 2 }

  raisecomOspfAreaAggregateNet OBJECT-TYPE
       SYNTAX   IpAddress
       MAX-ACCESS   read-only -- read-only since originally an
                              -- SMIv1 index
       STATUS   current
       DESCRIPTION
          "The IP address of the net or subnet indicated
          by the range."
       REFERENCE
          "OSPF Version 2, Appendix C.2 Area parameters"
       ::= { raisecomOspfAreaAggregateEntry 3 }

  raisecomOspfAreaAggregateMask OBJECT-TYPE
       SYNTAX       IpAddress
       MAX-ACCESS   read-only -- read-only since originally an
                              -- SMIv1 index
       STATUS      current
       DESCRIPTION
          "The subnet mask that pertains to the net or
          subnet."
       REFERENCE
          "OSPF Version 2, Appendix C.2 Area parameters"
       ::= { raisecomOspfAreaAggregateEntry 4 } 
       
  raisecomOspfAreaAggregateEffect OBJECT-TYPE
       SYNTAX       INTEGER {
                       advertiseMatching (1),
                       doNotAdvertiseMatching (2)
                       }
       MAX-ACCESS   read-create
       STATUS       current
       DESCRIPTION
          "Subnets subsumed by ranges either trigger the
          advertisement of the indicated aggregate
         (advertiseMatching) or result in the subnet's not
          being advertised at all outside the area."
       DEFVAL { advertiseMatching }
       ::= { raisecomOspfAreaAggregateEntry 5 }

  raisecomOspfAreaAggregateStatus OBJECT-TYPE
       SYNTAX       RowStatus
       MAX-ACCESS   read-create
       STATUS       current
       DESCRIPTION
          "This object permits management of the table by
          facilitating actions such as row creation,
          construction, and destruction.

          The value of this object has no effect on
          whether other objects in this conceptual row can be
          modified."
       ::= { raisecomOspfAreaAggregateEntry 6 }    
       
----------------------------------------------------------------
--  The OSPF External Aggregate Table
--
----------------------------------------------------------------
   raisecomOspfExternalAggregateTable   OBJECT-TYPE
       SYNTAX       SEQUENCE OF RaisecomOspfExternalAggregateEntry
       MAX-ACCESS   not-accessible
       STATUS       current

       DESCRIPTION
          "It contains a set of IP address ranges
           specified by an IP address/IP network mask pair.
           For example, a class B address range of X.X.X.X
           with a network mask of 255.255.0.0 includes all IP
           addresses from X.X.0.0 to X.X.255.255.

           Note that if ranges are configured such that one range
           subsumes another range (e.g., 10.0.0.0 mask 255.0.0.0
           and 10.1.0.0 mask 255.255.0.0),
           the most specific match is the preferred one."
       ::= { raisecomOspfObjects 12 }

  raisecomOspfExternalAggregateEntry OBJECT-TYPE
       SYNTAX   RaisecomOspfExternalAggregateEntry
       MAX-ACCESS   not-accessible
       STATUS   current
       DESCRIPTION
          "A single external aggregate entry.

          Information in this table is persistent and when this object
          is written the entity SHOULD save the change to non-volatile
          storage."
       INDEX { raisecomOspfProcessId,
               raisecomOspfExternalAggregateNet, 
               raisecomOspfExternalAggregateMask }
       ::= { raisecomOspfExternalAggregateTable 1 }

  RaisecomOspfExternalAggregateEntry ::=
       SEQUENCE {
          raisecomOspfExternalAggregateNet
             IpAddress,   
          raisecomOspfExternalAggregateMask
             IpAddress, 
          raisecomOspfExternalAggregateEffect
             INTEGER,
          raisecomOspfExternalAggregateCost
             BigMetric,
          raisecomOspfExternalAggregateStatus
             RowStatus
          }

  raisecomOspfExternalAggregateNet OBJECT-TYPE
       SYNTAX       IpAddress
       MAX-ACCESS   read-only -- read-only since originally an
                              -- SMIv1 index
       STATUS       current
       DESCRIPTION
          "The IP address of the net or subnet indicated
          by the range."
       ::= { raisecomOspfExternalAggregateEntry 1 } 
       
  raisecomOspfExternalAggregateMask OBJECT-TYPE
       SYNTAX       IpAddress
       MAX-ACCESS   read-only -- read-only since originally an
                              -- SMIv1 index
       STATUS      current
       DESCRIPTION
          "The subnet mask that pertains to the net or
          subnet."
       ::= { raisecomOspfExternalAggregateEntry 2 } 

  raisecomOspfExternalAggregateEffect OBJECT-TYPE
       SYNTAX       INTEGER {
                             doNotAdvertise (1),
                             advertise(2)
                             }
       MAX-ACCESS   read-create       
       STATUS       current
       DESCRIPTION
          "This object controls the advertisement of external route summary."  
       DEFVAL { advertise }
       ::= { raisecomOspfExternalAggregateEntry 3 }

  raisecomOspfExternalAggregateCost OBJECT-TYPE
       SYNTAX   BigMetric
       MAX-ACCESS   read-create
       STATUS   current
       DESCRIPTION
          "It indicates the cost of d external route summary." 
       DEFVAL { 1 }
       ::= { raisecomOspfExternalAggregateEntry 4 }

  raisecomOspfExternalAggregateStatus OBJECT-TYPE
       SYNTAX       RowStatus
       MAX-ACCESS   read-create
       STATUS       current
       DESCRIPTION
          "This object permits management of the table by
          facilitating actions such as row creation,
          construction, and destruction.

          The value of this object has no effect on
          whether other objects in this conceptual row can be
          modified."
       ::= { raisecomOspfExternalAggregateEntry 5 } 

------------------------------------------------------------------
--raisecomOspfLsdbTable    
--
--The table define link state database
------------------------------------------------------------------ 
  raisecomOspfLsdbTable OBJECT-TYPE
       SYNTAX       SEQUENCE OF RaisecomOspfLsdbEntry
       MAX-ACCESS   not-accessible
       STATUS       current

       DESCRIPTION
          "The OSPF Process's link state database (LSDB).
           The LSDB contains the link state advertisements
           from throughout the areas that the device is attached to."
       REFERENCE
          "OSPF Version 2, Section 12 Link State Advertisements"
       ::= { raisecomOspfObjects 13 }

  raisecomOspfLsdbEntry OBJECT-TYPE
       SYNTAX   RaisecomOspfLsdbEntry
       MAX-ACCESS   not-accessible
       STATUS   current
       DESCRIPTION
          "A single link state advertisement."
       INDEX { raisecomOspfProcessId,
               raisecomOspfLsdbAreaId, 
               raisecomOspfLsdbType,
               raisecomOspfLsdbLsId, 
               raisecomOspfLsdbRouterId }
       ::= { raisecomOspfLsdbTable 1 }

  RaisecomOspfLsdbEntry ::=
       SEQUENCE {
          raisecomOspfLsdbAreaId
             AreaID,
          raisecomOspfLsdbType
             INTEGER,
          raisecomOspfLsdbLsId
             IpAddress,
          raisecomOspfLsdbRouterId
             RouterID,
          raisecomOspfLsdbSequence
             Integer32,
          raisecomOspfLsdbAge
             Integer32,
          raisecomOspfLsdbChecksum
             Integer32,
          raisecomOspfLsdbAdvertisement
             OCTET STRING
          }

  raisecomOspfLsdbAreaId OBJECT-TYPE
       SYNTAX       AreaID
       MAX-ACCESS   read-only -- read-only since originally an
                              -- SMIv1 index
       STATUS       current
       DESCRIPTION
          "The 32-bit identifier of the area from which
          the LSA was received."
       REFERENCE
          "OSPF Version 2, Appendix C.2 Area parameters"

       ::= { raisecomOspfLsdbEntry 1 }

  raisecomOspfLsdbType OBJECT-TYPE
       SYNTAX       INTEGER {
                       routerLink (1),
                       networkLink (2),
                       summaryLink (3),
                       asSummaryLink (4),
                       asExternalLink (5), -- but see raisecomOspfAsLsdbTable
                       multicastLink (6),
                       nssaExternalLink (7),
                       areaOpaqueLink (10)
                       }
       MAX-ACCESS   read-only -- read-only since originally an
                              -- SMIv1 index
       STATUS       current
       DESCRIPTION
          "The type of the link state advertisement.
          Each link state type has a separate advertisement
          format.

          Note: External link state advertisements are permitted
          for backward compatibility, but should be displayed
          in the raisecomOspfAsLsdbTable rather than here."
       REFERENCE
          "OSPF Version 2, Appendix A.4.1 The Link State
          Advertisement header"
       ::= { raisecomOspfLsdbEntry 2 }

  raisecomOspfLsdbLsId OBJECT-TYPE
       SYNTAX       IpAddress
       MAX-ACCESS   read-only -- read-only since originally an
                              -- SMIv1 index
       STATUS       current
       DESCRIPTION
          "The Link State ID is an LS Type Specific field
          containing either a Router ID or an IP address;
          it identifies the piece of the routing domain
          that is being described by the advertisement."
       REFERENCE
          "OSPF Version 2, Section 12.1.4 Link State ID"
       ::= { raisecomOspfLsdbEntry 3 }

  raisecomOspfLsdbRouterId OBJECT-TYPE
       SYNTAX       RouterID
       MAX-ACCESS   read-only -- read-only since originally an
                              -- SMIv1 index
       STATUS       current

       DESCRIPTION
          "The 32-bit number that uniquely identifies the
          originating router in the Autonomous System."
       REFERENCE
          "OSPF Version 2, Appendix C.1 Global parameters"
       ::= { raisecomOspfLsdbEntry 4 }

  raisecomOspfLsdbSequence OBJECT-TYPE
       SYNTAX       Integer32
       MAX-ACCESS   read-only
       STATUS       current
       DESCRIPTION
          "The sequence number field is a signed 32-bit
          integer.  It starts with the value '80000001'h,
          or -'7FFFFFFF'h, and increments until '7FFFFFFF'h.
          Thus, a typical sequence number will be very negative.
          It is used to detect old and duplicate Link State
          Advertisements.  The space of sequence numbers is linearly
          ordered.  The larger the sequence number, the more recent
          the advertisement."
       REFERENCE
          "OSPF Version 2, Section 12.1.6 LS sequence
          number"
       ::= { raisecomOspfLsdbEntry 5 }

  raisecomOspfLsdbAge OBJECT-TYPE
       SYNTAX       Integer32 -- Should be 0..MaxAge, except when
                              -- doNotAge bit is set
       UNITS        "seconds"
       MAX-ACCESS   read-only
       STATUS       current
       DESCRIPTION
          "This field is the age of the link state advertisement
          in seconds."
       REFERENCE
          "OSPF Version 2, Section 12.1.1 LS age"
       ::= { raisecomOspfLsdbEntry 6 }

  raisecomOspfLsdbChecksum OBJECT-TYPE
       SYNTAX       Integer32
       MAX-ACCESS   read-only
       STATUS       current
       DESCRIPTION
          "This field is the checksum of the complete contents of
          the advertisement, excepting the age field.  The age field
          is excepted so that an advertisement's age can be
          incremented without updating the checksum.  The checksum
          used is the same that is used for ISO connectionless

          datagrams; it is commonly referred to as the
          Fletcher checksum."
        REFERENCE
           "OSPF Version 2, Section 12.1.7 LS checksum"
        ::= { raisecomOspfLsdbEntry 7 }

  raisecomOspfLsdbAdvertisement OBJECT-TYPE
       SYNTAX       OCTET STRING (SIZE (1..65535))
       MAX-ACCESS   read-only
       STATUS       current
       DESCRIPTION
          "The entire link state advertisement, including
          its header.

          Note that for variable length LSAs, SNMP agents
          may not be able to return the largest string size."
       REFERENCE
          "OSPF Version 2, Section 12 Link State Advertisements"
       ::= { raisecomOspfLsdbEntry 8 } 
         
------------------------------------------------------------------
--raisecomOspfAsLsdbTable    
--
--OSPF Link State Database, External
------------------------------------------------------------------
  raisecomOspfAsLsdbTable OBJECT-TYPE
       SYNTAX       SEQUENCE OF RaisecomOspfAsLsdbEntry
       MAX-ACCESS   not-accessible
       STATUS       current
       DESCRIPTION
          "The OSPF Process's AS-scope LSA link state database.
           The database contains the AS-scope Link State
           Advertisements from throughout the areas that
           the device is attached to.

           This table is identical to the OSPF LSDB Table
           in format, but contains only AS-scope Link State
           Advertisements.  The purpose is to allow AS-scope
           LSAs to be displayed once for the router rather
           than once in each non-stub area."
       REFERENCE
          "OSPF Version 2, Section 12 Link State
          Advertisements"
       ::= { raisecomOspfObjects 14 }

  raisecomOspfAsLsdbEntry OBJECT-TYPE
       SYNTAX       RaisecomOspfAsLsdbEntry

       MAX-ACCESS   not-accessible
       STATUS       current
       DESCRIPTION
          "A single link state advertisement."
       INDEX { raisecomOspfProcessId,
               raisecomOspfAsLsdbType, 
               raisecomOspfAsLsdbLsId, 
               raisecomOspfAsLsdbRouterId }
       ::= { raisecomOspfAsLsdbTable 1 }

  RaisecomOspfAsLsdbEntry ::=
       SEQUENCE {
          raisecomOspfAsLsdbType
             INTEGER,
          raisecomOspfAsLsdbLsId
             IpAddress,
          raisecomOspfAsLsdbRouterId
             RouterID,
          raisecomOspfAsLsdbSequence
             Integer32,
          raisecomOspfAsLsdbAge
             Integer32,
          raisecomOspfAsLsdbChecksum
             Integer32,
          raisecomOspfAsLsdbAdvertisement
             OCTET STRING
          }

  raisecomOspfAsLsdbType OBJECT-TYPE
       SYNTAX      INTEGER { asExternalLink (5) }
       MAX-ACCESS   not-accessible
       STATUS       current
       DESCRIPTION
          "The type of the link state advertisement.
          Each link state type has a separate
          advertisement format."
       REFERENCE
          "OSPF Version 2, Appendix A.4.1 The Link State
          Advertisement header"
       ::= { raisecomOspfAsLsdbEntry 1 }

  raisecomOspfAsLsdbLsId OBJECT-TYPE
       SYNTAX       IpAddress
       MAX-ACCESS   not-accessible
       STATUS       current
       DESCRIPTION
          "The Link State ID is an LS Type Specific field
          containing either a Router ID or an IP address;

          it identifies the piece of the routing domain
          that is being described by the advertisement."
       REFERENCE
          "OSPF Version 2, Section 12.1.4 Link State ID"
       ::= { raisecomOspfAsLsdbEntry 2 }

  raisecomOspfAsLsdbRouterId OBJECT-TYPE
       SYNTAX       RouterID
       MAX-ACCESS   not-accessible
       STATUS       current
       DESCRIPTION
          "The 32-bit number that uniquely identifies the
          originating router in the Autonomous System."
       REFERENCE
          "OSPF Version 2, Appendix C.1 Global parameters"
       ::= { raisecomOspfAsLsdbEntry 3 }

  raisecomOspfAsLsdbSequence OBJECT-TYPE
       SYNTAX       Integer32
       MAX-ACCESS   read-only
       STATUS       current
       DESCRIPTION
          "The sequence number field is a signed 32-bit
          integer.  It starts with the value '80000001'h,
          or -'7FFFFFFF'h, and increments until '7FFFFFFF'h.
          Thus, a typical sequence number will be very negative.
          It is used to detect old and duplicate link state
          advertisements.  The space of sequence numbers is linearly
          ordered.  The larger the sequence number, the more recent
          the advertisement."
       REFERENCE
          "OSPF Version  2,  Section  12.1.6  LS  sequence
          number"
       ::= { raisecomOspfAsLsdbEntry 4 }

  raisecomOspfAsLsdbAge OBJECT-TYPE
       SYNTAX       Integer32 -- Should be 0..MaxAge, except when
                              -- doNotAge bit is set
       UNITS        "seconds"
       MAX-ACCESS   read-only
       STATUS       current
       DESCRIPTION
          "This field is the age of the link state
          advertisement in seconds."
       REFERENCE
          "OSPF Version 2, Section 12.1.1 LS age"
       ::= { raisecomOspfAsLsdbEntry 5 }

  raisecomOspfAsLsdbChecksum OBJECT-TYPE
       SYNTAX       Integer32
       MAX-ACCESS   read-only
       STATUS       current
       DESCRIPTION
          "This field is the checksum of the complete
          contents of the advertisement, excepting the
          age field.  The age field is excepted so that
          an advertisement's age can be incremented
          without updating the checksum.  The checksum
          used is the same that is used for ISO
          connectionless datagrams; it is commonly referred
          to as the Fletcher checksum."
       REFERENCE
          "OSPF Version 2, Section 12.1.7 LS checksum"
       ::= { raisecomOspfAsLsdbEntry 6 }

  raisecomOspfAsLsdbAdvertisement OBJECT-TYPE
       SYNTAX       OCTET STRING (SIZE (1..65535))
       MAX-ACCESS   read-only
       STATUS       current
       DESCRIPTION
          "The entire link state advertisement, including
          its header."
       REFERENCE
          "OSPF Version 2, Section 12 Link State
          Advertisements.

          Note that for variable length LSAs, SNMP agents
          may not be able to return the largest string size."
       ::= { raisecomOspfAsLsdbEntry 7 }   
       
------------------------------------------------------------------
--raisecomOspfAreaLsaCountTable    
--
--OSPF Area LSA Counter Table
------------------------------------------------------------------
  raisecomOspfAreaLsaCountTable OBJECT-TYPE
          SYNTAX       SEQUENCE OF RaisecomOspfAreaLsaCountEntry
          MAX-ACCESS   not-accessible
          STATUS       current
          DESCRIPTION
             "This table maintains per-area, per-LSA-type counters"
          ::= { raisecomOspfObjects 15 }

      raisecomOspfAreaLsaCountEntry OBJECT-TYPE
          SYNTAX       RaisecomOspfAreaLsaCountEntry
          MAX-ACCESS   not-accessible
          STATUS       current
          DESCRIPTION
             "An entry with a number of link advertisements
              of a given type for a given area."
          INDEX { raisecomOspfProcessId,
                  raisecomOspfAreaLsaCountAreaId, 
                  raisecomOspfAreaLsaCountLsaType }
          ::= { raisecomOspfAreaLsaCountTable 1 }

      RaisecomOspfAreaLsaCountEntry ::=
           SEQUENCE {
              raisecomOspfAreaLsaCountAreaId
                 AreaID,
              raisecomOspfAreaLsaCountLsaType
                 INTEGER,
              raisecomOspfAreaLsaCountNumber
                 Gauge32
           }

      raisecomOspfAreaLsaCountAreaId OBJECT-TYPE
          SYNTAX       AreaID
          MAX-ACCESS   read-only
          STATUS       current
          DESCRIPTION
             "This entry Area ID."
         ::= { raisecomOspfAreaLsaCountEntry 1 }

      raisecomOspfAreaLsaCountLsaType OBJECT-TYPE
          SYNTAX       INTEGER {
                          routerLink (1),
                          networkLink (2),
                          summaryLink (3),
                          asSummaryLink (4),
                          multicastLink (6),
                          nssaExternalLink (7),
                          areaOpaqueLink (10)
                       }
          MAX-ACCESS   read-only
          STATUS       current
          DESCRIPTION
             "This entry LSA type."
         ::= { raisecomOspfAreaLsaCountEntry 2 }

      raisecomOspfAreaLsaCountNumber OBJECT-TYPE
          SYNTAX       Gauge32
          MAX-ACCESS   read-only
          STATUS       current
          DESCRIPTION
             "Number of LSAs of a given type for a given area."
         ::= { raisecomOspfAreaLsaCountEntry 3 }
    
---------------------------------------------------------------
-- raisecomOspfRedistributeTable  
--
---------------------------------------------------------------
  raisecomOspfRedistributeTable OBJECT-TYPE
       SYNTAX       SEQUENCE OF RaisecomOspfRedistributeEntry
       MAX-ACCESS   not-accessible
       STATUS       current
       DESCRIPTION
          "Import external route to ospf protocol."
       ::= { raisecomOspfObjects 16 }

  raisecomOspfRedistributeEntry OBJECT-TYPE
       SYNTAX       RaisecomOspfRedistributeEntry
       MAX-ACCESS   not-accessible
       STATUS       current
       DESCRIPTION
          "Define an entry in the raisecomOspfRedistributeTable"
       INDEX { raisecomOspfProcessId,
               raisecomOspfRedistributeProtocol, 
               raisecomOspfRedistributeProcessId }
       ::= { raisecomOspfRedistributeTable 1 }

  RaisecomOspfRedistributeEntry ::=
       SEQUENCE {
          raisecomOspfRedistributeProtocol
             INTEGER,
          raisecomOspfRedistributeProcessId
             ProcessID,
          raisecomOspfRedistributeCost
             BigMetric,
          raisecomOspfRedistributeType
             INTEGER,
          raisecomOspfRedistributeStatus
             RowStatus,
          raisecomOspfRedistributeRouteMapName
             OCTET STRING (SIZE(1..19)),
          raisecomOspfRedistributeTag
             INTEGER
          }

  raisecomOspfRedistributeProtocol OBJECT-TYPE
       SYNTAX      INTEGER {      
                             local(2),      
                             netmgmt(3),    
                             rip(8),
                             ospf(13)
                           }

       MAX-ACCESS   read-only -- read-only since originally an
                              -- SMIv1 index
       STATUS       current
       DESCRIPTION
          "Route protocol to import, only support static, connect,
          rip and ospf now."
       ::= { raisecomOspfRedistributeEntry 1 }

  raisecomOspfRedistributeProcessId OBJECT-TYPE
       SYNTAX       ProcessID
       MAX-ACCESS   read-only -- read-only since originally an
                              -- SMIv1 index
       STATUS       current
       DESCRIPTION
          "Process id of import route protocol, only support ospf."
       ::= { raisecomOspfRedistributeEntry 2 }

  raisecomOspfRedistributeCost OBJECT-TYPE
       SYNTAX       BigMetric
       MAX-ACCESS   read-create 
       STATUS       current
       DESCRIPTION
          "The cost of import route."  
       DEFVAL { 1 }
       ::= { raisecomOspfRedistributeEntry 3 }

  raisecomOspfRedistributeType OBJECT-TYPE
       SYNTAX       INTEGER { e1(1),e2(2) }
       MAX-ACCESS   read-create
       STATUS       current
       DESCRIPTION
          "The type of external route."   
       DEFVAL { e2 }
       ::= { raisecomOspfRedistributeEntry 4 }

  raisecomOspfRedistributeStatus OBJECT-TYPE
       SYNTAX       RowStatus 
       MAX-ACCESS   read-create
       STATUS       current
       DESCRIPTION
          "This object permits management of the table by
          facilitating actions such as row creation,
          construction, and destruction.

          The value of this object has no effect on
          whether other objects in this conceptual row can be
          modified."
       ::= { raisecomOspfRedistributeEntry 5 }
   raisecomOspfRedistributeRouteMapName OBJECT-TYPE
       SYNTAX       OCTET STRING (SIZE(1..19)) 
       MAX-ACCESS   read-create
       STATUS       current
       DESCRIPTION
          "Specify a route-map."
       ::= { raisecomOspfRedistributeEntry 6 }

   raisecomOspfRedistributeTag OBJECT-TYPE
       SYNTAX       INTEGER(0..2147483647) 
       MAX-ACCESS   read-create
       STATUS       current
       DESCRIPTION
          "Set tag of route."
       ::= { raisecomOspfRedistributeEntry 7 }

------------------------------------------------------------------
--raisecomOspfDefaultInfoTable    
--
------------------------------------------------------------------
  raisecomOspfDefaultInfoTable OBJECT-TYPE
       SYNTAX       SEQUENCE OF RaisecomOspfDefaultInfoEntry
       MAX-ACCESS   not-accessible
       STATUS       current
       DESCRIPTION
          "The table generate or delete the default route."
       ::= { raisecomOspfObjects 17 }

  raisecomOspfDefaultInfoEntry OBJECT-TYPE
       SYNTAX       RaisecomOspfDefaultInfoEntry
       MAX-ACCESS   not-accessible
       STATUS       current
       DESCRIPTION
          "Define an entry in the raisecomOspfDefaultInfoTable"
       INDEX { raisecomOspfProcessId }
       ::= { raisecomOspfDefaultInfoTable 1 }

  RaisecomOspfDefaultInfoEntry ::=
       SEQUENCE {
          raisecomOspfDefaultInfoAlways
             TruthValue,
          raisecomOspfDefaultInfoCost
             BigMetric,
          raisecomOspfDefaultInfoType
             INTEGER,
          raisecomOspfDefaultInfoStatus
             RowStatus
                }

  raisecomOspfDefaultInfoAlways OBJECT-TYPE
       SYNTAX       TruthValue
       MAX-ACCESS   read-create
       STATUS       current
       DESCRIPTION
          "Whether always inform default route."    
       DEFVAL { false }
       ::= { raisecomOspfDefaultInfoEntry 1 }

  raisecomOspfDefaultInfoCost OBJECT-TYPE
       SYNTAX       BigMetric
       MAX-ACCESS   read-create
       STATUS       current
       DESCRIPTION
          "It indicates the cost of default route."     
       DEFVAL { 1 }
       ::= { raisecomOspfDefaultInfoEntry 2 }

  raisecomOspfDefaultInfoType OBJECT-TYPE
       SYNTAX       INTEGER  { e1(1),e2(2) }
       MAX-ACCESS   read-create
       STATUS       current
       DESCRIPTION
          "It indicates the type of default route."    
       DEFVAL { e2 }
       ::= { raisecomOspfDefaultInfoEntry 3 }

  raisecomOspfDefaultInfoStatus OBJECT-TYPE
       SYNTAX       RowStatus 
       MAX-ACCESS   read-create
       STATUS       current
       DESCRIPTION
          "This object permits management of the table by
          facilitating actions such as row creation,
          construction, and destruction.

          The value of this object has no effect on
          whether other objects in this conceptual row can be
          modified."
       ::= { raisecomOspfDefaultInfoEntry 4 }   

------------------------------------------------------------------
-- raisecomOspfPacketIoStatisTable  
--
------------------------------------------------------------------
  raisecomOspfPacketIoStatisTable OBJECT-TYPE
       SYNTAX       SEQUENCE OF RaisecomOspfPacketIoStatisEntry
       MAX-ACCESS   not-accessible
       STATUS       current
       DESCRIPTION
          "The table is used to storage all kinds of 
          input and output packet statistical information of 
          OSPF process."
       ::= { raisecomOspfObjects 18 }

  raisecomOspfPacketIoStatisEntry OBJECT-TYPE
       SYNTAX       RaisecomOspfPacketIoStatisEntry
       MAX-ACCESS   not-accessible
       STATUS       current
       DESCRIPTION
          "Define an entry in the raisecomOspfPacketIoStatisTable"
       INDEX { raisecomOspfProcessId,
               raisecomOspfPacketIoStatisIoType,
               raisecomOspfPacketIoStatisPktType }
       ::= { raisecomOspfPacketIoStatisTable 1 }                

  RaisecomOspfPacketIoStatisEntry ::=
       SEQUENCE {
          raisecomOspfPacketIoStatisIoType
             INTEGER,
          raisecomOspfPacketIoStatisPktType
             INTEGER,
          raisecomOspfPacketIoStatisNumber
             Integer32
                }

  raisecomOspfPacketIoStatisIoType OBJECT-TYPE
       SYNTAX       INTEGER {
                      input (1),
                      output (2)
                      }
       MAX-ACCESS   read-only
       STATUS       current
       DESCRIPTION
          "It has been used to describe the IO direction of 
          packet."    
       ::= { raisecomOspfPacketIoStatisEntry 1 }       

  raisecomOspfPacketIoStatisPktType OBJECT-TYPE
       SYNTAX       INTEGER {
                      hello (1),
                      dbDescript (2),
                      lsReq (3),
                      lsUpdate (4),
                      lsAck (5)
                      }
       MAX-ACCESS   read-only
       STATUS       current
       DESCRIPTION
          "It has been used to describe the type of 
          OSPF packet."    
       ::= { raisecomOspfPacketIoStatisEntry 2 } 
       
  raisecomOspfPacketIoStatisNumber OBJECT-TYPE
       SYNTAX       Integer32
       MAX-ACCESS   read-only
       STATUS       current
       DESCRIPTION
          "The number indicates the number of specified type of 
          packets on input or output direction."    
       ::= { raisecomOspfPacketIoStatisEntry 3 }        

------------------------------------------------------------------
-- raisecomOspfRouteTable  
--
------------------------------------------------------------------
  raisecomOspfRouteTable OBJECT-TYPE
       SYNTAX       SEQUENCE OF RaisecomOspfRouteEntry
       MAX-ACCESS   not-accessible
       STATUS       current
       DESCRIPTION
          "The table is used to storage OSPF calculation of routing table."
       ::= { raisecomOspfObjects 19 }

  raisecomOspfRouteEntry OBJECT-TYPE
       SYNTAX       RaisecomOspfRouteEntry
       MAX-ACCESS   not-accessible
       STATUS       current
       DESCRIPTION
          "Define an entry in the raisecomOspfRouteTable"
       INDEX { raisecomOspfProcessId,
               raisecomOspfRouteDest,
               raisecomOspfRouteMask,
               raisecomOspfRouteType }
       ::= { raisecomOspfRouteTable 1 }                

  RaisecomOspfRouteEntry ::=
       SEQUENCE {
          raisecomOspfRouteDest
             IpAddress,
          raisecomOspfRouteMask
             IpAddress,
          raisecomOspfRouteType
             INTEGER,
          raisecomOspfRouteLsType   
             INTEGER,
          raisecomOspfRouteMetric   
             Integer32,
          raisecomOspfRouteNextHop
             IpAddress, 
          raisecomOspfRouteAdvRtr
             IpAddress, 
          raisecomOspfRouteArea
             Integer32
                }

  raisecomOspfRouteDest OBJECT-TYPE
       SYNTAX       IpAddress
       MAX-ACCESS   read-only
       STATUS       current
       DESCRIPTION
          "It has been used to describe the destination address of 
          an ospf route."    
       ::= { raisecomOspfRouteEntry 1 }       

  raisecomOspfRouteMask OBJECT-TYPE
       SYNTAX       IpAddress
       MAX-ACCESS   read-only
       STATUS       current
       DESCRIPTION
          "It has been used to describe the mask of 
          an ospf route."    
       ::= { raisecomOspfRouteEntry 2 }
  
  raisecomOspfRouteType OBJECT-TYPE
       SYNTAX       INTEGER {  
                      network (1),
                      ase (2),
                      nssa (3)
                      }
       MAX-ACCESS   read-only
       STATUS       current
       DESCRIPTION
          "It has been used to describe the type of 
          an ospf route."    
       ::= { raisecomOspfRouteEntry 3 } 
  
  raisecomOspfRouteLsType OBJECT-TYPE
       SYNTAX       INTEGER {
                      stub (0),
                      routerLink (1),
                      networkLink (2),
                      summaryLink (3),
                      asSummaryLink (4),
                      asExternalLink (5), 
                      multicastLink (6),
                      nssaExternalLink (7),
                      areaOpaqueLink (10)
                      }
       MAX-ACCESS   read-only
       STATUS       current
       DESCRIPTION
          "It has been used to describe the LSA type of 
          a router."  
       ::= { raisecomOspfRouteEntry 4 } 

  raisecomOspfRouteMetric OBJECT-TYPE
       SYNTAX       Integer32
       MAX-ACCESS   read-only
       STATUS       current
       DESCRIPTION
          "It has been used to describe the metric of 
          an ospf route. "    
       ::= { raisecomOspfRouteEntry 5 } 
  
  raisecomOspfRouteNextHop OBJECT-TYPE
       SYNTAX       IpAddress
       MAX-ACCESS   read-only
       STATUS       current
       DESCRIPTION
          "It has been used to describe the nexthop address of 
          an ospf route."    
       ::= { raisecomOspfRouteEntry 6 } 
  
  raisecomOspfRouteAdvRtr OBJECT-TYPE
       SYNTAX       IpAddress
       MAX-ACCESS   read-only
       STATUS       current
       DESCRIPTION
          "It has been used to describe the advertising router of 
          an ospf route."    
       ::= { raisecomOspfRouteEntry 7 } 
  
  raisecomOspfRouteArea OBJECT-TYPE
       SYNTAX       Integer32
       MAX-ACCESS   read-only
       STATUS       current
       DESCRIPTION
          "It has been used to describe the ccmputing area of 
          an ospf route."    
       ::= { raisecomOspfRouteEntry 8 } 
                                                         
------------------------------------------------------------------
-- raisecomOspfBdrRouteTable 
--
------------------------------------------------------------------
  raisecomOspfBdrRouteTable OBJECT-TYPE
       SYNTAX       SEQUENCE OF RaisecomOspfBdrRouteEntry
       MAX-ACCESS   not-accessible
       STATUS       current
       DESCRIPTION
          "The table is used to storage the imformation of boder router."
       ::= { raisecomOspfObjects 20 }

  raisecomOspfBdrRouteEntry OBJECT-TYPE
       SYNTAX       RaisecomOspfBdrRouteEntry
       MAX-ACCESS   not-accessible
       STATUS       current
       DESCRIPTION
          "Define an entry in the raisecomOspfBdrRouteTable"
       INDEX { raisecomOspfProcessId,
               raisecomOspfBdrRouteRtrType,
               raisecomOspfBdrRouteArea,
               raisecomOspfBdrRouteDest,
               raisecomOspfBdrRouteNextHop }
       ::= { raisecomOspfBdrRouteTable 1 }                

  RaisecomOspfBdrRouteEntry ::=
       SEQUENCE {
          raisecomOspfBdrRouteRtrType
             INTEGER,
          raisecomOspfBdrRouteArea
             IpAddress,
          raisecomOspfBdrRouteDest
             IpAddress,
          raisecomOspfBdrRouteNextHop   
             IpAddress, 
          raisecomOspfBdrRouteLsType   
             INTEGER,
          raisecomOspfBdrRouteMetric
             Integer32
             }

  raisecomOspfBdrRouteRtrType OBJECT-TYPE
       SYNTAX       INTEGER {
                      asbr (1),
                      abr (2),
                      sumasbr (3)
                      }
       MAX-ACCESS   read-only
       STATUS       current
       DESCRIPTION
          "It has been used to describe the type of 
          a boder router."    
       ::= { raisecomOspfBdrRouteEntry 1 }       
     
  raisecomOspfBdrRouteArea OBJECT-TYPE
       SYNTAX       IpAddress
       MAX-ACCESS   read-only
       STATUS       current
       DESCRIPTION
          "It has been used to describe the area of 
          a boder router."    
       ::= { raisecomOspfBdrRouteEntry 2 }       
  
  raisecomOspfBdrRouteDest OBJECT-TYPE
       SYNTAX       IpAddress
       MAX-ACCESS   read-only
       STATUS       current
       DESCRIPTION
          "It has been used to describe the boder router by 
          it's router id."    
       ::= { raisecomOspfBdrRouteEntry 3 }       
  
  raisecomOspfBdrRouteNextHop OBJECT-TYPE
       SYNTAX       IpAddress
       MAX-ACCESS   read-only
       STATUS       current
       DESCRIPTION
          "IIt has been used to describe the nexthop router to 
          reach a boder router."    
       ::= { raisecomOspfBdrRouteEntry 4 }       
  
  raisecomOspfBdrRouteLsType OBJECT-TYPE
       SYNTAX       INTEGER {
                      routerLink (1),
                      networkLink (2),
                      summaryLink (3),
                      asSummaryLink (4),
                      asExternalLink (5), 
                      multicastLink (6),
                      nssaExternalLink (7),
                      areaOpaqueLink (10)
                      }
       MAX-ACCESS   read-only
       STATUS       current
       DESCRIPTION
          "It has been used to describe the LSA type of 
          a boder router."    
       ::= { raisecomOspfBdrRouteEntry 5 }       
  
  raisecomOspfBdrRouteMetric OBJECT-TYPE
       SYNTAX       Integer32
       MAX-ACCESS   read-only
       STATUS       current
       DESCRIPTION
          "It has been used to describe the metric to 
          a boder router."    
       ::= { raisecomOspfBdrRouteEntry 6 }       
       
  raisecomOspfDistributeListGroup     OBJECT IDENTIFIER ::= { raisecomOspfObjects 21}  
  
------------------------------------------------------------------
-- raisecomOspfDistributeListInTable 
--
------------------------------------------------------------------
  raisecomOspfDistributeListInTable OBJECT-TYPE
       SYNTAX       SEQUENCE OF RaisecomOspfDistributeListInEntry
       MAX-ACCESS   not-accessible
       STATUS       current
       DESCRIPTION
          "The table is used to config and check distribute-in policy."
       ::= { raisecomOspfDistributeListGroup 1 }

  raisecomOspfDistributeListInEntry OBJECT-TYPE
       SYNTAX       RaisecomOspfDistributeListInEntry
       MAX-ACCESS   not-accessible
       STATUS       current
       DESCRIPTION
          "Define an entry in the raisecomOspfDistributeListInTable"
       INDEX { raisecomOspfProcessId }
       ::= { raisecomOspfDistributeListInTable 1 }                

  RaisecomOspfDistributeListInEntry ::=
       SEQUENCE {
          raisecomOspfDistrInIpPrefixListName
             OCTET STRING (SIZE(1..19)),
          raisecomOspfDistrInAclNum
             INTEGER,
          raisecomOspfDistrInRowStatus
             RowStatus
             }

  raisecomOspfDistrInIpPrefixListName OBJECT-TYPE
       SYNTAX       OCTET STRING (SIZE(1..19))
       MAX-ACCESS   read-create
       STATUS       current
       DESCRIPTION
          "Filter incoming routing updates,the value of this 
           object indicates the name of an ip-prefix-list."    
       ::= { raisecomOspfDistributeListInEntry 1 }       
         
   raisecomOspfDistrInAclNum OBJECT-TYPE
       SYNTAX       INTEGER
       MAX-ACCESS   read-create
       STATUS       current
       DESCRIPTION
          "Filter incoming routing updates by the IP ACL number of OSPF distribute-in policy,
          -1 is a value to inditace no setting of acl."    
       ::= { raisecomOspfDistributeListInEntry 2 }  

   raisecomOspfDistrInRowStatus OBJECT-TYPE
       SYNTAX       RowStatus
       MAX-ACCESS   read-create
       STATUS       current
       DESCRIPTION
          "This object permits management of the table by
           facilitating actions such as row creation,construction, 
           and destruction.The value of this object has no effect
           on whether other objects in this conceptual row can be 
           modified."    
       ::= { raisecomOspfDistributeListInEntry 3 }  
       
------------------------------------------------------------------
-- raisecomOspfDistributeListOutTable  
--
------------------------------------------------------------------
  raisecomOspfDistributeListOutTable OBJECT-TYPE
       SYNTAX       SEQUENCE OF RaisecomOspfDistributeListOutEntry
       MAX-ACCESS   not-accessible
       STATUS       current
       DESCRIPTION
          "The table is used to config and check distribute-out policy."
       ::= { raisecomOspfDistributeListGroup 2 }

  raisecomOspfDistributeListOutEntry OBJECT-TYPE
       SYNTAX       RaisecomOspfDistributeListOutEntry
       MAX-ACCESS   not-accessible
       STATUS       current
       DESCRIPTION
          "Define an entry in the raisecomOspfDistributeListOutTable"
       INDEX { raisecomOspfProcessId }
       ::= { raisecomOspfDistributeListOutTable 1 }                

  RaisecomOspfDistributeListOutEntry ::=
       SEQUENCE {
          raisecomOspfDistrOutIpPrefixListName
             OCTET STRING (SIZE(1..19)),
          raisecomOspfDistrOutAclNum
             INTEGER,
          raisecomOspfDistrOutRowStatus
             RowStatus
             }

  raisecomOspfDistrOutIpPrefixListName OBJECT-TYPE
       SYNTAX       OCTET STRING (SIZE(1..19))
       MAX-ACCESS   read-create
       STATUS       current
       DESCRIPTION
          "Filter outgoing routing updates,the value of this object
           indicates the name of an ip-prefix-list."    
       ::= { raisecomOspfDistributeListOutEntry 1 }       
         
   raisecomOspfDistrOutAclNum OBJECT-TYPE
       SYNTAX       INTEGER
       MAX-ACCESS   read-create
       STATUS       current
       DESCRIPTION
          "Filter incoming outgoing updates by the IP ACL number of OSPF distribute-out policy,
          -1 is a value to inditace no setting of acl."    
       ::= { raisecomOspfDistributeListOutEntry 2 }  

   raisecomOspfDistrOutRowStatus OBJECT-TYPE
       SYNTAX       RowStatus
       MAX-ACCESS   read-create
       STATUS       current
       DESCRIPTION
          "This object permits management of the table by
           facilitating actions such as row creation,construction, 
           and destruction. The value of this object has no effect 
           on whether other objects in this conceptual row can be 
           modified."    
       ::= { raisecomOspfDistributeListOutEntry 3 }     

------------------------------------------------------------------
-- raisecomOspfDistributeListOutProtocolTable   
--
------------------------------------------------------------------
  raisecomOspfDistributeListOutProtocolTable OBJECT-TYPE
       SYNTAX       SEQUENCE OF RaisecomOspfDistributeListOutProtocolEntry
       MAX-ACCESS   not-accessible
       STATUS       current
       DESCRIPTION
          "The table is used to config and check distribute-out policy based on protocol."
       ::= { raisecomOspfDistributeListGroup 3 }

  raisecomOspfDistributeListOutProtocolEntry OBJECT-TYPE
       SYNTAX       RaisecomOspfDistributeListOutProtocolEntry
       MAX-ACCESS   not-accessible
       STATUS       current
       DESCRIPTION
          "Define an entry in the raisecomOspfDistributeListOutProtocolTable"
       INDEX { 
               raisecomOspfProcessId, 
               raisecomOspfDistrOutProtocol,
               raisecomOspfDistrOutProcessId
                }
       ::= { raisecomOspfDistributeListOutProtocolTable 1 }                

  RaisecomOspfDistributeListOutProtocolEntry ::=
       SEQUENCE {
          raisecomOspfDistrOutProtocol
             INTEGER,
          raisecomOspfDistrOutProcessId
             ProcessID,
          raisecomOspfDistrOutProIpPrefixListName
             OCTET STRING (SIZE(1..19)),
          raisecomOspfDistrOutProAclNum
             INTEGER,
          raisecomOspfDistrOutProRowStatus
             RowStatus    
             }

  raisecomOspfDistrOutProtocol OBJECT-TYPE
       SYNTAX       INTEGER 
                    {    
                       local(2),      
                       netmgmt(3),  
                       rip(8),
                       ospf(13) 
                    }
       MAX-ACCESS   read-only
       STATUS       current
       DESCRIPTION
          "Imported route protocol, only support static, connect, 
          rip and ospf now."    
       ::= { raisecomOspfDistributeListOutProtocolEntry 1 }       
         
   raisecomOspfDistrOutProcessId OBJECT-TYPE
       SYNTAX       ProcessID
       MAX-ACCESS   read-only
       STATUS       current
       DESCRIPTION
          "Process id of imported route protocol, only support ospf."    
       ::= { raisecomOspfDistributeListOutProtocolEntry 2 }  

   raisecomOspfDistrOutProIpPrefixListName OBJECT-TYPE
       SYNTAX       OCTET STRING (SIZE(1..19))
       MAX-ACCESS   read-create
       STATUS       current
       DESCRIPTION
          "Filtering outgoing updates based on imported protocol, the value 
           of this object indicates the name of an ip-prefix-list."    
       ::= { raisecomOspfDistributeListOutProtocolEntry 3 } 
       
    raisecomOspfDistrOutProAclNum OBJECT-TYPE
       SYNTAX       INTEGER
       MAX-ACCESS   read-create
       STATUS       current
       DESCRIPTION
          "Filtering outgoing updates based on imported protocol, the value of this object 
          indicates the IP ACL number, -1 is a value to inditace no setting of acl."    
       ::= { raisecomOspfDistributeListOutProtocolEntry 4 }  
       
     raisecomOspfDistrOutProRowStatus OBJECT-TYPE
       SYNTAX       RowStatus
       MAX-ACCESS   read-create
       STATUS       current
       DESCRIPTION
          "This object permits management of the table by
           facilitating actions such as row creation,construction, 
           and destruction.The value of this object has no effect 
           on whether other objects in this conceptual row can be 
           modified."    
       ::= { raisecomOspfDistributeListOutProtocolEntry 5 }                                             
END

-- File: RC002-REMOTEII-DEVICE-MIB.my
-- Changes:
-- author:SunSuli
-- remote card including RC952-EE1,RC952-FXE1,RC601,RC501,RC511


  RC002-REMOTEII-DEVICE-MIB   DEFINITIONS ::= BEGIN
     
   IMPORTS
		IpAddress,
		OBJECT-TYPE, MODULE-IDENTITY, NOTIFICATION-TYPE, Integer32,Counter32
        	FROM SNMPv2-SMI
		DisplayString,
		TimeStamp
			FROM SNMPv2-TC
    	rcftChassisIndex, rcftSlotIndex,rcftMibObjects 
       	FROM RAISECOM-RCFT-MIB;  
     
	 rcftRemoteIIDeviceMib MODULE-IDENTITY
	    LAST-UPDATED "1010221657Z"
	    ORGANIZATION "RaiseCom Technology CO.,LTD"
	    CONTACT-INFO
	        "
	       www.raisecom.com
	        "
	    DESCRIPTION
	        "MIB for RC002 RemoteII Device equipment."
	    REVISION      "0507060000Z"
	    DESCRIPTION
	        ""
        REVISION      "0902090000Z"
        DESCRIPTION
	        "	
	        	add node:	
	        	rcftRemoteIIDeviceModelID、
	        	rcftRemoteIIDeviceVenderCode、
	        	rcftRemoteIIDeviceStatus;        
	        	--by sunying
	        "
        REVISION      "0903061500Z"
        DESCRIPTION
	        "	
	        	add node:	
	        	rcftRemoteIIDeviceLoopBackStatus
	        	rcftRemoteIIDeviceLoopBackMode
	        	
	        	rcftRemoteIIEthFxPortAutoNegotiation
	        	rcftRemoteIIEthFxPortOptHeadType
						rcftRemoteIIEthFxSfpRXLOS
						rcftRemoteIIEthFxSfpTXDisable
						rcftRemoteIIEthFxSfpExist
						rcftRemoteIIEthFxSfpSpeedStatus
						rcftRemoteIIEthFxSfpTransportDistance
						rcftRemoteIIEthFxSfpWaveLength
						rcftRemoteIIEthFxSfpManufactory
						rcftRemoteIIEthFxSfpProductType
						rcftRemoteIIEthFxSfpVersion
						rcftRemoteIIEthFxSfpWaterMask
						
						add trap:
						rcftRemoteIIEthFxPortSfpRXLOSTrap
						rcftRemoteIIEthFxPortSfpExistTrap
	        	--by xujingru
	        "   
	        
	    REVISION      "0903230000Z"
        DESCRIPTION
	        "	
	        	add node:	
	        	rcftRemoteIIDeviceVLANType
	        	rcftRemoteIIQosEnable
	        	rcftRemoteIIBaseCOS
	        	rcftRemoteIIDeviceStatus  
	        	rcftRemoteIIQueuesPolicy  
	        	rcftRemoteIIDeviceQoSPolicy  
	        	
	        	rcftRemoteIIEthFxUntag   
	        	rcftRemoteIIEthFxPVID     
	        	
	        	rcftRemoteIIEthFePVID  
	        	rcftRemoteIIEthFeQoSPolicy
	        	
	            add entry
	            rcftRemoteIIVLANEntry
	            					
				--by kuanglili
	        "                       
	        REVISION      "0904150000Z"
        	DESCRIPTION
	        "		            					
				delete   rcftRemoteIIEthFxPVID、rcftRemoteIIEthFePVID、 rcftRemoteIIEthFeQoSPolicy
				中的枚举值
				--by kuanglili
	        "
	  REVISION      "0909021000Z"
     DESCRIPTION
              "
       add device type:    
               rcftTypeRC521H-FE-SS34-S-REV-A(30016),   		  --单纤台式                              
               rcftTypeRC521H-FE-SS34-C-REV-A(30017),        --单纤卡式  
				--by xujingru
              "
	  REVISION      "0909081430Z"
     DESCRIPTION
              "
       add device type:    
               rcftTypeRC521H-FE-S(30026),
				--by xujingru
              "       
      REVISION      "1004281734Z"
     DESCRIPTION
              "
       add device type:    
                   rcftRemoteIIDeviceMibUse
				--by kuanglili
              "    
              
	   REVISION      "1010221657Z"
      DESCRIPTION
              "	
              添加二级远端配置信息表rcftRemoteIIEthFePortConfTable,用于配置信息的显示和配置
              其中添加配置信息表入口rcftRemoteIIEthFePortConfEntry,同时定义两个节点：
              rcftRemoteIIEthFeConfSpeed
			  rcftRemoteIIEthFeConfDuplex
			  		
			  --by yangbintao
			   " 

	    ::= { rcftMibObjects 7 }    

     --对象定义
     	rcftRemoteIIDeviceSystemMIB  OBJECT IDENTIFIER ::= { rcftRemoteIIDeviceMib 1 }	 
    	rcftRemoteIIDeviceSysObjects OBJECT IDENTIFIER ::= { rcftRemoteIIDeviceSystemMIB 1 }   
    	rcftRemoteIIDeviceSysTraps	OBJECT IDENTIFIER	::={ rcftRemoteIIDeviceSystemMIB 2}
    	
      rcftRemoteIIDeviceEthMIB        OBJECT IDENTIFIER ::= { rcftRemoteIIDeviceMib 2 }    
      rcftRemoteIIDeviceEthFeMIB		OBJECT IDENTIFIER ::= {rcftRemoteIIDeviceEthMIB 1}   
      rcftRemoteIIDeviceEthFeObjects	OBJECT IDENTIFIER ::={rcftRemoteIIDeviceEthFeMIB 1} 
      rcftRemoteIIDeviceEthFeTraps	OBJECT IDENTIFIER ::={rcftRemoteIIDeviceEthFeMIB 2}    
      	
      rcftRemoteIIDeviceEthFxMIB		OBJECT IDENTIFIER ::= {rcftRemoteIIDeviceEthMIB 2}      
      rcftRemoteIIDeviceEthFxObjects	OBJECT IDENTIFIER ::={rcftRemoteIIDeviceEthFxMIB 1} 
      rcftRemoteIIDeviceEthFxTraps	OBJECT IDENTIFIER ::={rcftRemoteIIDeviceEthFxMIB 2}  
      
      rcftRemoteIIDeviceVLANMIB		OBJECT IDENTIFIER ::= { rcftRemoteIIDeviceMib 3 }
      rcftRemoteIIDeviceVLANObjects	OBJECT IDENTIFIER ::={rcftRemoteIIDeviceVLANMIB 1} 			
  
      	

      
 -- 系统配置表
 		rcftRemoteIIDeviceSysTable OBJECT-TYPE
              SYNTAX  SEQUENCE OF RcftRemoteIIDeviceSysEntry
              MAX-ACCESS  not-accessible
              STATUS  current
              DESCRIPTION
                 "
                 The RemoteII Device System table.
                 "
             ::= { rcftRemoteIIDeviceSysObjects 1 }

    	rcftRemoteIIDeviceSysEntry OBJECT-TYPE
              SYNTAX  RcftRemoteIIDeviceSysEntry
              MAX-ACCESS  not-accessible
              STATUS  current
              DESCRIPTION
                 "
                 An entry in the remote remote system table.
                
                 "
              INDEX   { rcftChassisIndex, rcftSlotIndex,rcftRemoteIIDeviceIndex }
             ::= { rcftRemoteIIDeviceSysTable 1 }

     	RcftRemoteIIDeviceSysEntry ::=
              SEQUENCE {
                   rcftRemoteIIDeviceIndex		 	Integer32,
                   rcftRemoteIIDeviceExist         	INTEGER,
                   rcftRemoteIIDeviceType    		INTEGER, 
                   rcftRemoteIIDeviceToRDeviceID	INTEGER,
                   rcftRemoteIIDeviceToRPortType	INTEGER,
                   rcftRemoteIIDeviceToRPortIndex	INTEGER,
                   rcftRemoteIIDeviceVersionInfo	OCTET STRING,  
                   rcftRemoteIISysTemperature      	INTEGER,
                   rcftRemoteIISysVoltageStatus    	INTEGER,
                   rcftRemoteIIDeviceFrameLen		INTEGER,
                   rcftRemoteIIDeviceOrder			INTEGER,
                   rcftRemoteIIDeviceConfigFlag		INTEGER,
                   rcftRemoteIIDeviceStatus			INTEGER,
                   rcftRemoteIIDeviceVenderCode		INTEGER,
                   rcftRemoteIIDeviceModelID		INTEGER,
                   rcftRemoteIIDeviceLoopBackStatus INTEGER,
                   rcftRemoteIIDeviceLoopBackMode INTEGER,
                   rcftRemoteIIDeviceVLANType	INTEGER,
                   rcftRemoteIIQosEnable	INTEGER,
                   rcftRemoteIIBaseCOS		INTEGER,
                   rcftRemoteIIDeviceStatus INTEGER,
                   rcftRemoteIIQueuesPolicy INTEGER,
                   rcftRemoteIIDeviceQoSPolicy	INTEGER,
                   rcftRemoteIIDeviceMibUse  INTEGER
                   }


        rcftRemoteIIDeviceIndex OBJECT-TYPE
           SYNTAX      Integer32
           MAX-ACCESS  read-only
           STATUS      current
           DESCRIPTION
           "
          	远端设备的索引
           "
        	::= { rcftRemoteIIDeviceSysEntry 1 }
 			
 		rcftRemoteIIDeviceExist OBJECT-TYPE
            SYNTAX      INTEGER 
            {
          	  exist(1),
          	  noexist(2) 
            }
           MAX-ACCESS  read-only
           STATUS      current
           DESCRIPTION
           "
          	远端设备是否在位
           "
           ::= { rcftRemoteIIDeviceSysEntry 2 }  
         
 
        rcftRemoteIIDeviceType   OBJECT-TYPE
           SYNTAX      INTEGER
           {
               rcftTypeRC501-FE-REV-C(30001),
               rcftTypeRC601-FE-REV-C(30002),
               rcftTypeRC511-FE-REV-A(30003),
               rcftTypeRC511-4FE-REV-A(30004),
               rcftTypeRC601-FE-REV-E(30005),
               rcftTypeRC511-FE-C-REV-A(30006), 
               rcftTypeRC513-FE-REV-A(30007),
               rcftTypeRC513-FE-C-REV-A(30008),
               rcftTypeRC532-FE-REV-A(30009),
               rcftTypeRC531-FE-REV-A(30010),
               rcftTypeRC532-2FE-REV-A(30011),    
               rcftTypeRC512-FE-DoubleFiber-S-REV-A(30012),   --双纤台式
               rcftTypeRC512-FE-SingleFiber-S-REV-A(30013),   --单纤台式                              
               rcftTypeRC512-FE-DoubleFiber-C-REV-A(30014),   --双纤卡式 
               rcftTypeRC512-FE-SingleFiber-C-REV-A(30015),   --单纤卡式
               rcftTypeRC512-FE-SS34-S-REV-A(30016),   		  --单纤台式                              
               rcftTypeRC512-FE-SS34-C-REV-A(30017),           --单纤卡式  
               
               rcftTypeRC512-FE-SLAVE(30018),     --512-FE-SLAVE（局端slave）
               rcftTypeRC512-FE-SS13-SLAVE(30019),  --对应于RC512-FE-SLAVE（局端slave）
               rcftTypeRC512-FE-SS23-SLAVE(30020),  --对应于RC512-FE-SLAVE（局端slave）
               rcftTypeRC512-FE-SS34-SLAVE(30021),   --对应于RC512-FE-SLAVE（局端slave)        
               rcftTypeRC552-FE-REV-A-SLAVE-NEW(30022), --增加了SFP状态的新协议  
               rcftTypeRC511-4FE-REV-B-SLAVE(30023),
               rcftTypeRC521H-FE-DoubleFiber-S(30024),   --双纤台式
               rcftTypeRC521H-FE-SingleFiber-S(30025),   --单纤台式                              
               rcftTypeRC521H-FE-S(30026),
               rcftTypeRC522E-FE-REMOTE(30027),
               rcftTypeRC521E-FE(30028),
               rcftTypeRC512-FE(30029),  --对于B版以前未处理的光头类型统一占用的类型号，虚拟的号
               rcftTypeRC512-FE-SLAVE(30030),  --对于B版以前未处理的光头类型统一占用的类型号，虚拟的号

               rcftTypeTS1000-UNCONFIG-PRODUCT(65025),      ---对应设备类型0xFE01
               rcftTypeRC521-FE-REV-C(65026),	---对应设备类型0xFE02 
               rcftTypeRC521-FE-REV-D(65027)	---对应设备类型0xFE03 
                                                                         
           } 
           MAX-ACCESS  read-only
           STATUS      current
           DESCRIPTION
           "
          	远端设备的类型
           "
           ::= { rcftRemoteIIDeviceSysEntry 3 } 
          
        rcftRemoteIIDeviceToRDeviceID	OBJECT-TYPE
        	SYNTAX			INTEGER
        	MAX-ACCESS		read-only
        	STATUS			current
        	DESCRIPTION
        		"
        			远端的远端设备所对应的远端设备的索引
        		"
            ::= { rcftRemoteIIDeviceSysEntry 4 }  
                      
            
       rcftRemoteIIDeviceToRPortType	OBJECT-TYPE
        	SYNTAX INTEGER{
               ethport(1),
               optical(2),
               e1port(3)
       		}
        MAX-ACCESS read-only
        STATUS current
        DESCRIPTION
          " 
          	远端设备所接局端设备的物理端口类型
          	接口类型（1:电口，2：光口，3：E1口)
          "
           ::= { rcftRemoteIIDeviceSysEntry 5 }
         
            
       rcftRemoteIIDeviceToRPortIndex OBJECT-TYPE
           SYNTAX      INTEGER 
           MAX-ACCESS  read-only
           STATUS      current
           DESCRIPTION
           "
          	远端设备所接局端设备的物理端口索引，哪一端口被占用相应的位被置1
		   	--------------------------------------------------------------
		    | Bit15 | Bit14 | Bit13 | Bit12 | Bit11 | Bit10 |Bit9 | Bit8 | 
		    --------------------------------------------------------------   
		    ---------------------------------------------------------
		    | Bit7 | Bit6 | Bit5 | Bit4 | Bit3 | Bit2 | Bit1 | Bit0 |
		    ---------------------------------------------------------           	 
          	 
           "
           ::= { rcftRemoteIIDeviceSysEntry 6 } 

       rcftRemoteIIDeviceVersionInfo  OBJECT-TYPE
          	SYNTAX OCTET 	STRING(SIZE (0..100))
          	MAX-ACCESS 		read-only
          	STATUS 			current
          	DESCRIPTION
          	"
          	    远端板卡的版本信息版本信息的格式是：A.x-X.x-Ex-Fx.y 
                其中：A.x为硬件版本号；X.x为软件版本号；Ex中的x为以太网交换芯片类型；
                Fx.y中的x为FPGA芯片代号，y为FPGA代码版本号。  
          	"    
            ::= { rcftRemoteIIDeviceSysEntry 7 } 


      rcftRemoteIISysTemperature  OBJECT-TYPE
           SYNTAX      INTEGER 
           MAX-ACCESS  read-only
           STATUS      current
           DESCRIPTION
           "
          	远端设备温度
           "      	
           ::= { rcftRemoteIIDeviceSysEntry 8 } 

        rcftRemoteIISysVoltageStatus OBJECT-TYPE
           SYNTAX     INTEGER 
           {
          		normal(1),
          		toohigh(2),
          		toolow(3)
           }
           MAX-ACCESS  read-only
           STATUS      current
           DESCRIPTION
           "
          	远端设备电压异常
           "
        ::= { rcftRemoteIIDeviceSysEntry 9 }
         
        
       rcftRemoteIIDeviceFrameLen	OBJECT-TYPE
	        SYNTAX INTEGER
	        {   
	           framelen1916B(1),
	    	   framelen1536B(2)
	        }
	        MAX-ACCESS read-write
	        STATUS current
	        DESCRIPTION
	          "
	          	第二层远端设备以太网帧的最大帧长：（1：1916B，2：1536B）.    
	          	The max frame length of the ethernet port in the remoteII module.
	          "
              ::= { rcftRemoteIIDeviceSysEntry 10 } 
                           
       rcftRemoteIIDeviceOrder	OBJECT-TYPE
       		SYNTAX		INTEGER
       		{
       			  reset(1),
       			  reqInfoStart(2),
       			  reqInfoStop(3),
       			  linePortInsideLoopEnable(4), 
 				  linePortOutsideLoopEnable(5), 
 				  linePortInsideLoopDisable(6),
 				  linePortOutsideLoopDisable(7) 
 	    
       			  
       		}             
       		MAX-ACCESS	read-write
       		STATUS		current
       		DESCRIPTION
       			"
       				远端设备命令字，每个设备都有自己固定的命令字  
       				1:复位 ，2：开始查询信息，3：结束查询信息
       							
       			"                           
            ::= { rcftRemoteIIDeviceSysEntry 11 }                      
                      
       rcftRemoteIIDeviceConfigFlag OBJECT-TYPE
       		SYNTAX		 INTEGER
       		{
       			set(1)
       		}
       		MAX-ACCESS	 read-write
       		STATUS		 current
       		DESCRIPTION
       			"
       				远端的远端设备的配置标志，绑定对象结束的标志	
       			"	           
       	::= { rcftRemoteIIDeviceSysEntry 12 }

       rcftRemoteIIDeviceStatus	OBJECT-TYPE   
       		SYNTAX	INTEGER
       		MAX-ACCESS	read-write
       		STATUS	current
       		DESCRIPTION
       		"
	      	   BIT0	  	0：单电口，1：多电口 
	      	   BIT1	  	故障转移。1：使能， 0：禁止 

       		"	           
       	::= { rcftRemoteIIDeviceSysEntry 13 }
	      	   	 
       	rcftRemoteIIDeviceVenderCode   OBJECT-TYPE
       		SYNTAX INTEGER
       		MAX-ACCESS	read-only
       		STATUS	current
       		DESCRIPTION   
       		"	    
       			vender code，厂家ID。
       			在移动标准信息中为1字节。
       			在TS1000标准信息中为3字节，我公司ID为：0x00-0x0E-0x5E。	
       		"         
       	::= {rcftRemoteIIDeviceSysEntry 14}
	   		
       	rcftRemoteIIDeviceModelID   OBJECT-TYPE
       		SYNTAX INTEGER
       		MAX-ACCESS	read-only
       		STATUS	current
       		DESCRIPTION   
       		"	    
       			Model ID ，表示各厂家私有设备类型。
       			在TS1000标准信息中为3字节：
       				RC521-FE-C的Model ID为 0x00fc24，
       				RC521-FE-D的Model ID为 0x00fc00。
       		"         
       	::= {rcftRemoteIIDeviceSysEntry 15}

        rcftRemoteIIDeviceLoopBackStatus    OBJECT-TYPE
       		SYNTAX INTEGER
       		MAX-ACCESS	read-only
       		STATUS	current
       		DESCRIPTION   
       		"	    
						环回测试状态信息  
						Bit7：远端是否正在进行环回：1：正在进行环回，0：没有进行环回；
						Bit6：远端光口环回的状态：1：表示光口外环，0：光口内环；
						Bit5：远端测试响应端交换 MAC 地址后是否环回给（MAC）电口：1：是，0：否；
						（当处于光口内环方式下，此位无意义）
						Bit4：远端测试响应端重新计算CRC后是否环回给（MAC）电口：1：是，0：否；
						Bit3：远端测试请求端是否将环回的数据从电口输出：1：是，0：否；
						Bit2：远端测试数据的来源：1：测试请求端输入，0：电口输入；
						Bit1：远端测试请求端产生测试数据的速率：1：速率为100％，0：速率为10％；
						Bit0：远端测试请求端产生测试数据的帧长度：1：1518字节，0：64字节
       			
       		"         
       	::= {rcftRemoteIIDeviceSysEntry 16}
        
        rcftRemoteIIDeviceLoopBackMode    OBJECT-TYPE
       		SYNTAX INTEGER
       		MAX-ACCESS	read-write
       		STATUS	current
       		DESCRIPTION   
       		"	    
						环回测试模式 
						Bit5：远端测试响应端交换 MAC 地址后是否环回给（MAC）电口：1：是，0：否；（当发送光口内环命令时，该选项没有意义）
						Bit4：远端测试响应端重新计算CRC后是否环回给（MAC）电口：1：是，0：否；
						Bit3：远端测试请求端是否将环回的数据从电口输出：1：是，0：否；（固定为1）
						Bit2：远端测试数据的来源：1：测试请求端输入，0：电口输入；（固定为0）
						Bit1：远端测试请求端产生测试数据的速率：1：速率为100％，0：速率为10％；（固定为0）
						Bit0：远端测试请求端产生测试数据的帧长度：1：1518字节，0：64字节；（固定为0）
       		"         
       	::= {rcftRemoteIIDeviceSysEntry 17}  
       	
       	rcftRemoteIIDeviceVLANType	OBJECT-TYPE   
       		SYNTAX	INTEGER
       		MAX-ACCESS	read-write
       		STATUS	current
       		DESCRIPTION
       		"
	      	   VLAN模式：
	      	   	1：no vlan
				2：port vlan
				3：tag vlan
       		"	           
       	::= { rcftRemoteIIDeviceSysEntry 18 }
       	
        rcftRemoteIIQosEnable	OBJECT-TYPE   
       		SYNTAX	INTEGER
       		MAX-ACCESS	read-write
       		STATUS	current
       		DESCRIPTION
       		"
	      	   1：使能，2：禁止
       		"	           
       	::= { rcftRemoteIIDeviceSysEntry 19 }
       	
        rcftRemoteIIBaseCOS		OBJECT-TYPE   
       		SYNTAX	INTEGER
       		MAX-ACCESS	read-write
       		STATUS	current
       		DESCRIPTION
       		"
	      	   范围是0~7，从以太口进入的带tag数据包如果它的tag中COS值大于等于此值，
	      	   则此数据包为高优先级，反之为低优先级。       		"	           
       	::= { rcftRemoteIIDeviceSysEntry 20 }
	      	          	       	
        rcftRemoteIIQueuesPolicy OBJECT-TYPE   
       		SYNTAX	INTEGER
       		MAX-ACCESS	read-write
       		STATUS	current
       		DESCRIPTION
       		"
	      	   队列调度策略：
	      	   	1:严格优先
				2：加权循环（高：低）10:1；
				3：加权循环（高：低）5:1；
				4：加权循环（高：低）2:1；
	      	"	           
       	::= { rcftRemoteIIDeviceSysEntry 21 }
       	
       	rcftRemoteIIDeviceQoSPolicy	  OBJECT-TYPE   
       		SYNTAX	INTEGER
       		MAX-ACCESS	read-write
       		STATUS	current
       		DESCRIPTION
       		"
	      	     QoS优先级划分策略：
	      	      	1：基于端口的
					2：基于COS的
       		"	           
       	::= { rcftRemoteIIDeviceSysEntry 22 }     
       	
       	rcftRemoteIIDeviceMibUse   OBJECT-TYPE   
       		SYNTAX INTEGER
       		{
	      		mib002(1),
	      		rccomlib(2)
	      	}

       		MAX-ACCESS read-only
       		STATUS current
       		DESCRIPTION
       		"
       			 设备支持的mib类型
       			1:使用002mib
				2:使用组件库mib

       		"   
       	::= { rcftRemoteIIDeviceSysEntry 23 }  
                   
      	
 	    rcftRemoteIIDeviceConfigFlagTable OBJECT-TYPE
              SYNTAX  SEQUENCE OF RcftRemoteIIDeviceConfigFlagEntry
              MAX-ACCESS  not-accessible
              STATUS  current
              DESCRIPTION
                 "
                 "
             ::= { rcftRemoteIIDeviceSysObjects 2 }

    	rcftRemoteIIDeviceConfigFlagEntry OBJECT-TYPE
              SYNTAX  RcftRemoteIIDeviceConfigFlagEntry
              MAX-ACCESS  not-accessible
              STATUS  current
              DESCRIPTION
                 "
                 "
              INDEX   { rcftChassisIndex, rcftSlotIndex,rcftRemoteIIDeviceIndex }
             ::= { rcftRemoteIIDeviceConfigFlagTable 1 }

     	RcftRemoteIIDeviceConfigFlagEntry ::=
              SEQUENCE {
                   rcftRemoteIIDeviceConfigFinishFlag	INTEGER
				}       
				
	  	rcftRemoteIIDeviceConfigFinishFlag	OBJECT-TYPE	 		      
	  		SYNTAX	INTEGER
	  		MAX-ACCESS 	read-write
	  		STATUS	current
	  		DESCRIPTION
	  		"          
	  			第二层远端设备配置结束标志。新设备中用该标志来表明远端配置当次SNMP操作结束。
	  			具体哪些设备用该标志，将在配置说明文档中详细说明。
	  		"                 
	  	   ::={rcftRemoteIIDeviceConfigFlagEntry 1}         	  
                   
                   
----------------------------------------------------------------------------
------------------RemoteII DEVICE FX TABLE
----------------------------------------------------------------------------        



        rcftRemoteIIEthFxPortTable OBJECT-TYPE
              SYNTAX  SEQUENCE OF RcftRemoteIIEthFxPortEntry
              MAX-ACCESS  not-accessible
              STATUS  current
              DESCRIPTION
                 "
                 The RemoteII Device FX Port table.
                 "
             ::= { rcftRemoteIIDeviceEthFxObjects 1 }

   		rcftRemoteIIEthFxPortEntry OBJECT-TYPE
              SYNTAX  RcftRemoteIIEthFxPortEntry
              MAX-ACCESS  not-accessible
              STATUS  current
              DESCRIPTION
                 "
                 An entry in the Fx Port config table.
                 
                 "
              INDEX   { rcftChassisIndex, rcftSlotIndex,rcftRemoteIIDeviceIndex, rcftRemoteIIEthFxIndex }
             ::= { rcftRemoteIIEthFxPortTable 1 }
             
          RcftRemoteIIEthFxPortEntry ::=
              SEQUENCE {
            rcftRemoteIIEthFxIndex                  	Integer32,
            rcftRemoteIIEthFxPortRLK                	INTEGER,
            rcftRemoteIIEthFxPortTLK                	INTEGER,
          	rcftRemoteIIEthFxPortSD           				INTEGER,
          	rcftRemoteIIEthFxPortTxPowerAbnormal			INTEGER,
			rcftRemoteIIEthFxPortRxSensitiveAbnormal  		INTEGER,
			rcftRemoteIIEthFxPortLaserAbnormal        		INTEGER,
			rcftRemoteIIEthFxPortModuleType					INTEGER,
			rcftRemoteIIEthFxPortFaultPass					INTEGER,
			rcftRemoteIIEthFxPortLink						INTEGER,
			rcftRemoteIIEthFxRxToTxFaultPass				INTEGER,   
			rcftRemoteIIEthFxTxDisabledByFR					INTEGER,
			rcftRemoteIIEthFxShutDown						INTEGER,
	        rcftRemoteIIEthFxPortAutoNegotiation			INTEGER,
	        rcftRemoteIIEthFxPortOptHeadType				INTEGER,
			rcftRemoteIIEthFxSfpRXLOS						INTEGER,
			rcftRemoteIIEthFxSfpTXDisable					INTEGER,
			rcftRemoteIIEthFxSfpExist						INTEGER,
			rcftRemoteIIEthFxSfpSpeedStatus					INTEGER,
			rcftRemoteIIEthFxSfpTransportDistance			INTEGER,
			rcftRemoteIIEthFxSfpWaveLength					Integer32,
			rcftRemoteIIEthFxSfpManufactory					OCTET STRING,
			rcftRemoteIIEthFxSfpProductType					OCTET STRING,
			rcftRemoteIIEthFxSfpVersion						OCTET STRING,
			rcftRemoteIIEthFxSfpWaterMask					OCTET STRING,
			rcftRemoteIIEthFxSfpMediaType					INTEGER,
			rcftRemoteIIEthFxSfpModuleType					INTEGER,
			rcftRemoteIIEthFxSfpOpticalInterface			INTEGER,
			rcftRemoteIIEthFxUntag			INTEGER,
			rcftRemoteIIEthFxPVID			INTEGER
	
																	
                   }
                   
          rcftRemoteIIEthFxIndex OBJECT-TYPE
          		SYNTAX  	Integer32
          		MAX-ACCESS  read-only
          		STATUS  	current
          		DESCRIPTION
                 "
                 远端设备光口的索引  
                 "
   		  		::= { rcftRemoteIIEthFxPortEntry 1 }
         
                   
         rcftRemoteIIEthFxPortRLK OBJECT-TYPE
	          SYNTAX  INTEGER 
	          		 {
	                    link(1),
	                    unlink(2)
	                 }
	          MAX-ACCESS  read-only
	          STATUS  current
	          DESCRIPTION
	           "
	              远端设备光口RLK  
	           "
          
		  	  ::= { rcftRemoteIIEthFxPortEntry 2 }

   		  rcftRemoteIIEthFxPortTLK OBJECT-TYPE
	          SYNTAX  INTEGER 
	          		 {
	                     link(1),
	                     unlink(2)
	                 }
	          MAX-ACCESS  read-only
	          STATUS  current
	          DESCRIPTION
	          "
	                远端设备光口TLK
	          "
	                
	          ::= { rcftRemoteIIEthFxPortEntry 3 }
          

        rcftRemoteIIEthFxPortSD OBJECT-TYPE
	          SYNTAX  INTEGER 
	           {
	              normal (1),
	              sd (2)
	           }
	          MAX-ACCESS  read-only
	          STATUS  current
	          DESCRIPTION
	          "
	             远端设备光口SD异常
	          "
	
			  ::= { rcftRemoteIIEthFxPortEntry 4 }

  
		rcftRemoteIIEthFxPortTxPowerAbnormal OBJECT-TYPE
		     SYNTAX  INTEGER 
		     {
		        normal (1),
		        abnormal (2)
		     }
		     MAX-ACCESS  read-only
		     STATUS  current
		     DESCRIPTION
		     "
		        远端设备发送功率异常
		     "
		       
		  ::= { rcftRemoteIIEthFxPortEntry 5 }
		  
		 rcftRemoteIIEthFxPortRxSensitiveAbnormal OBJECT-TYPE
          	SYNTAX  INTEGER  
          	{
               normal (1),
               abnormal (2)
            }
          	MAX-ACCESS  read-only
          	STATUS  current
          	DESCRIPTION
            "
                 远端设备接收灵敏度异常
            "
          
		  	::= { rcftRemoteIIEthFxPortEntry 6 }
		  
		  rcftRemoteIIEthFxPortLaserAbnormal OBJECT-TYPE
	          SYNTAX  INTEGER 
	          {
	             normal (1),
	             abnormal (2)
	          }
	          MAX-ACCESS  read-only
	          STATUS  current
	          DESCRIPTION
	          "
	              远端设备光激光管工作异常
	          "
			  ::= { rcftRemoteIIEthFxPortEntry 7 }  
			  
			  
       rcftRemoteIIEthFxPortModuleType  OBJECT-TYPE
	      	  SYNTAX INTEGER
	      	  {   
	      	     optical-M(1),
	      	     optical-S1(2),
	      	     optical-S2(3),
	      	     optical-S3(4),
	      	     optical-SS13(5), 
	      	     optical-SS15(6),
	      	     optical-SS23(7),
	      	     optical-SS25(8),
	      	     optical-SS34(9),     
	      	     optical-SS35(10),      	     
	      	     unknown-type(100)
	      	  }   
	      	  MAX-ACCESS read-only
	      	  STATUS current
	      	  DESCRIPTION
	      	  "
	      	    远端设备的光模块类型
	      	  "
         	::= { rcftRemoteIIEthFxPortEntry 8 }
         	
        rcftRemoteIIEthFxPortFaultPass	OBJECT-TYPE
        		SYNTAX	INTEGER
        		{
        			enable(1),
        			disable(2)
        		} 
        		MAX-ACCESS	read-write
        		STATUS	current
        		DESCRIPTION
        		"
        		远端设备的光口到电口故障转移功能(1:使能,2:禁止)	
        		"		  
		        ::= { rcftRemoteIIEthFxPortEntry 9 }  
		        
		 rcftRemoteIIEthFxPortLink	OBJECT-TYPE
	          SYNTAX  INTEGER 
	          		 {
	                     link(1),
	                     unlink(2)
	                 }
	          MAX-ACCESS  read-only
	          STATUS  current
	          DESCRIPTION
	          "
	                远端设备光口LINK
	          "
	                
	          ::= { rcftRemoteIIEthFxPortEntry 10 }     
	          
	          
		rcftRemoteIIEthFxRxToTxFaultPass	OBJECT-TYPE
			SYNTAX	INTEGER
			{
				enable(1),
				disable(2)
			}	    
		 	MAX-ACCESS read-write
		 	STATUS	current
		 	DESCRIPTION
		 	"
		 		远端设备以太网光口故障返回功能(1:使能,2:禁止)	
		 	"		       
			::= { rcftRemoteIIEthFxPortEntry 11 }
			
		rcftRemoteIIEthFxTxDisabledByFR	OBJECT-TYPE
			SYNTAX	INTEGER
			{
				open(1),
				close(2)
			}	    
		 	MAX-ACCESS read-only
		 	STATUS	current
		 	DESCRIPTION
		 	"
		 		远端设备以太网光口发送关闭的原因是由于光口接收故障向发送方向转移功能使能造成的。
			"		       
			::= { rcftRemoteIIEthFxPortEntry 12 }  
			
	 	rcftRemoteIIEthFxShutDown OBJECT-TYPE
			SYNTAX INTEGER
			{
				open(1),
				close(2),
				closeByFP(3),
				closeByALS(4),
				closeByLP(5)	
			}
			MAX-ACCESS read-write
			STATUS current
			DESCRIPTION
			"
				远端设备以太网光口的开关使能
			"
			::= { rcftRemoteIIEthFxPortEntry 13 }         

     rcftRemoteIIEthFxPortAutoNegotiation OBJECT-TYPE
	        SYNTAX INTEGER
	        {   
	            auto(1),
	            manul(2)
	        }
	        MAX-ACCESS read-write
	        STATUS current
	        DESCRIPTION
	          "
	          光口速率协商方式  
	          "					
      			::= { rcftRemoteIIEthFxPortEntry 14 }
 
     rcftRemoteIIEthFxPortOptHeadType OBJECT-TYPE
	        SYNTAX INTEGER
	        {   
	            sfpType(1),
	            normal(2)
	        }
	        MAX-ACCESS read-only
	        STATUS current
	        DESCRIPTION
	          "
	          光头类型  
	          "					
      			::= { rcftRemoteIIEthFxPortEntry 15 }
     
     rcftRemoteIIEthFxSfpRXLOS OBJECT-TYPE
						SYNTAX INTEGER
						{
							normal(1),
							alarm(2)
						}
						MAX-ACCESS  read-only
						STATUS  current
						DESCRIPTION
						"	
							光模块LOS状态
						"
						::= { rcftRemoteIIEthFxPortEntry 16 }

     
		 rcftRemoteIIEthFxSfpTXDisable OBJECT-TYPE
						SYNTAX INTEGER
						{
							enable(1), 
							disable(2)
						}
						MAX-ACCESS  read-write
						STATUS  current
						DESCRIPTION
						"
							光信号发送禁止.即关闭光口
						"
						::= { rcftRemoteIIEthFxPortEntry 17 }
					 
		 rcftRemoteIIEthFxSfpExist OBJECT-TYPE
						SYNTAX INTEGER
						{
							exist(1), 
							notExist(2) 
						}
						MAX-ACCESS  read-only
						STATUS  current
						DESCRIPTION
						"
							sfp模块在位通知
						"
					::= { rcftRemoteIIEthFxPortEntry 18 }
		 
     rcftRemoteIIEthFxSfpSpeedStatus OBJECT-TYPE
					SYNTAX INTEGER
					{ 
						unknown(1), 
						speed155M(2),
						speed622M(3),
						speed1250M(4),
						speed2500M(5)
					}
					MAX-ACCESS  read-only
					STATUS  current
					DESCRIPTION
					"
						 额定速率
					"
					::= { rcftRemoteIIEthFxPortEntry 19 }

     
     rcftRemoteIIEthFxSfpTransportDistance OBJECT-TYPE
					SYNTAX INTEGER
					MAX-ACCESS  read-only
					STATUS  current
					DESCRIPTION
					"
						传输距离.单位是公里
					"
					::= { rcftRemoteIIEthFxPortEntry 20 }	
     
     rcftRemoteIIEthFxSfpWaveLength OBJECT-TYPE
					SYNTAX Integer32
					MAX-ACCESS  read-only
					STATUS  current
					DESCRIPTION
					"
						波长
					"
					::= { rcftRemoteIIEthFxPortEntry 21 }

     rcftRemoteIIEthFxSfpManufactory OBJECT-TYPE
					SYNTAX OCTET STRING(SIZE (0..16))
					MAX-ACCESS  read-only
					STATUS  current
					DESCRIPTION
					"
						模块制造厂商
					"
					::= { rcftRemoteIIEthFxPortEntry 22 }
     
     rcftRemoteIIEthFxSfpProductType OBJECT-TYPE
				SYNTAX OCTET STRING(SIZE (0..16))
				MAX-ACCESS  read-only
				STATUS  current
				DESCRIPTION
				"
					产品型号
				"
				::= { rcftRemoteIIEthFxPortEntry 23 }
     
     rcftRemoteIIEthFxSfpVersion OBJECT-TYPE
					SYNTAX OCTET STRING(SIZE (0..4))
					MAX-ACCESS  read-only
					STATUS  current
					DESCRIPTION
					"
						模块版本号
					"
					::= { rcftRemoteIIEthFxPortEntry 24 }
     
     rcftRemoteIIEthFxSfpWaterMask OBJECT-TYPE
					SYNTAX OCTET STRING(SIZE (0..16))
					MAX-ACCESS  read-only
					STATUS  current
					DESCRIPTION
					"
						模块流水号
					"
					::= { rcftRemoteIIEthFxPortEntry 25 }

		rcftRemoteIIEthFxSfpMediaType OBJECT-TYPE
        SYNTAX  INTEGER   
        {
        	unknown(1),
        	fiber9u125u(2),
        	fiber50u125u(3),
        	fiber625u125u(4),
        	copper(5)
        	
        }     
        MAX-ACCESS read-only
        STATUS    current
        DESCRIPTION 
        "
            介质类型
        "  
        ::={ rcftRemoteIIEthFxPortEntry 26 } 	
		
		rcftRemoteIIEthFxSfpModuleType OBJECT-TYPE
			SYNTAX INTEGER
			{ 
				unknown(1),
				gbic(2), 
				sff(3), 
				sfp(4)
			}
			MAX-ACCESS  read-only
			STATUS  current
			DESCRIPTION
			"
				模块类型
			"
			::= { rcftRemoteIIEthFxPortEntry 27 }		
			
		rcftRemoteIIEthFxSfpOpticalInterface OBJECT-TYPE
			SYNTAX INTEGER
			{
				unknown(1),
				sc(2), 
				lc(3),
				rj45(4)
			}
			MAX-ACCESS  read-only
			STATUS  current
			DESCRIPTION
			"
				光连接头形式
			"
			::= { rcftRemoteIIEthFxPortEntry 28 }   
			
		rcftRemoteIIEthFxUntag    OBJECT-TYPE
			SYNTAX INTEGER
			{
				untag(1),
				tag(2)
			}
			MAX-ACCESS  read-write
			STATUS  current
			DESCRIPTION
			"
				tag 模式
			"
			::= { rcftRemoteIIEthFxPortEntry 29 }     
			
		rcftRemoteIIEthFxPVID    OBJECT-TYPE
			SYNTAX INTEGER
			MAX-ACCESS  read-write
			STATUS  current
			DESCRIPTION
			"
				PVID
			"
			::= { rcftRemoteIIEthFxPortEntry 30 }  

			
							
     rcftRemoteIIEthFxStatisticTable OBJECT-TYPE
	        SYNTAX SEQUENCE OF RcftRemoteIIEthFxStatisticEntry
	        MAX-ACCESS not-accessible
	        STATUS current
	        DESCRIPTION
	          "
	          远端设备Eth端口的统计表.
	          "
            ::= {rcftRemoteIIDeviceEthFxObjects 2}

	    rcftRemoteIIEthFxStatisticEntry OBJECT-TYPE
	        SYNTAX RcftRemoteIIEthFxStatisticEntry
	        MAX-ACCESS not-accessible
	        STATUS current
	        DESCRIPTION
	          "
	             以rcftRemoteIIEthFxIndex为索引
	          "
	        AUGMENTS { rcftRemoteIIEthFxPortEntry }
	        ::= {rcftRemoteIIEthFxStatisticTable 1}

	    RcftRemoteIIEthFxStatisticEntry ::= SEQUENCE {
	           
				rcftRemoteIIEthFxTxPackets         Counter32, 
				rcftRemoteIIEthFxTxBytes           Counter32,
				rcftRemoteIIEthFxRxPackets         Counter32,
				rcftRemoteIIEthFxRxBytes           Counter32,
				rcftRemoteIIEthFxRxLostPackets     Counter32,
				rcftRemoteIIEthFxFluxTimer		   Counter32, 
				rcftRemoteIIEthFxTxLostPackets     Counter32				
	         }
					

    	  rcftRemoteIIEthFxTxPackets OBJECT-TYPE
					SYNTAX Counter32
					MAX-ACCESS read-only
					STATUS current
					DESCRIPTION
						"
							以太网口发送以太网包数
						"
					::= { rcftRemoteIIEthFxStatisticEntry 1 }
					
		 rcftRemoteIIEthFxTxBytes OBJECT-TYPE
					SYNTAX Counter32
					MAX-ACCESS read-only
					STATUS current
					DESCRIPTION
						"
							以太网口发送以太网字节数
						"
					::= { rcftRemoteIIEthFxStatisticEntry 2 }
					
		 rcftRemoteIIEthFxRxPackets OBJECT-TYPE
					SYNTAX Counter32
					MAX-ACCESS read-only
					STATUS current
					DESCRIPTION
						"
							以太网口接收以太网包数
						"
					::= { rcftRemoteIIEthFxStatisticEntry 3 }
					
		 rcftRemoteIIEthFxRxBytes OBJECT-TYPE
					SYNTAX Counter32
					MAX-ACCESS read-only
					STATUS current
					DESCRIPTION
						"
							以太网口接收以太网字节数
						"
					::= { rcftRemoteIIEthFxStatisticEntry 4 }
					
	    rcftRemoteIIEthFxRxLostPackets OBJECT-TYPE
					SYNTAX Counter32
					MAX-ACCESS read-only
					STATUS current
					DESCRIPTION
						"
							以太网电口接收以太网丢包数
						"
					::= { rcftRemoteIIEthFxStatisticEntry 5 }

        rcftRemoteIIEthFxFluxTimer	OBJECT-TYPE
        			SYNTAX		Counter32
        			MAX-ACCESS 	read-only
        			STATUS		current
        			DESCRIPTION
        				"
        					流量统计的时间
        				"			
                    ::= { rcftRemoteIIEthFxStatisticEntry 6 } 
                
	    rcftRemoteIIEthFxTxLostPackets OBJECT-TYPE
					SYNTAX Counter32
					MAX-ACCESS read-only
					STATUS current
					DESCRIPTION
						"
							以太网电口发送以太网丢包数
						"
					::= { rcftRemoteIIEthFxStatisticEntry 7 }                	        


----------------------------------------------------------------------------
------------------REMOTE'S REMOTE DEVICE FE TABLE
----------------------------------------------------------------------------          
          
      --   Fe Current table
	     rcftRemoteIIEthFePortTable OBJECT-TYPE          
              SYNTAX  SEQUENCE OF RcftRemoteIIEthFePortEntry
              MAX-ACCESS  not-accessible
              STATUS  current
              DESCRIPTION
              "
                 The RemoteII Device Fe Port table.
              "
             ::= { rcftRemoteIIDeviceEthFeObjects 1 }

   			rcftRemoteIIEthFePortEntry OBJECT-TYPE
              SYNTAX  RcftRemoteIIEthFePortEntry
              MAX-ACCESS  not-accessible
              STATUS  current
              DESCRIPTION
              "
                 An entry in the Fe Port config table.
              "
              INDEX   { rcftChassisIndex, rcftSlotIndex,rcftRemoteIIDeviceIndex,  rcftRemoteIIEthFeIndex }
             ::= { rcftRemoteIIEthFePortTable 1 }       
             
          RcftRemoteIIEthFePortEntry ::=
              SEQUENCE {
              			rcftRemoteIIEthFeIndex                  Integer32,
                    	rcftRemoteIIEthFeLinkStatus             INTEGER,
          			    rcftRemoteIIEthFeShutDown               INTEGER,   
          			    rcftRemoteIIEthFeAutoNegotiation        INTEGER,
          			    rcftRemoteIIEthFeSpeed                	INTEGER,
						rcftRemoteIIEthFeDuplex                 INTEGER,
						rcftRemoteIIEthFeRestrictSpeed			INTEGER,
						rcftRemoteIIEthFeFaultPass				INTEGER,
						rcftRemoteIIEthFeDisabledByRemoteTP		INTEGER,
						rcftRemoteIIEthFeDisabledByFxToFeFP		INTEGER,
						rcftRemoteIIEthFeTxRestrictSpeed		INTEGER,
						rcftRemoteIIEthFeTag					INTEGER,
						rcftRemoteIIEthFePVID                   INTEGER,
						rcftRemoteIIEthFeQoSPolicy				INTEGER
						}

            rcftRemoteIIEthFeIndex OBJECT-TYPE
					SYNTAX Integer32
					MAX-ACCESS read-only
					STATUS current
					DESCRIPTION
					"
						远端设备以太网电口端口索引
					"
					::= { rcftRemoteIIEthFePortEntry 1 }
	   
	   		rcftRemoteIIEthFeLinkStatus OBJECT-TYPE
					SYNTAX INTEGER
					{
						linkup(1),
						linkdown(2)	
					}
					MAX-ACCESS read-only
					STATUS current
					DESCRIPTION
					"
						远端设备以太网电口的link状态
					"
					::= { rcftRemoteIIEthFePortEntry 2 }
					
	 		rcftRemoteIIEthFeShutDown OBJECT-TYPE
					SYNTAX INTEGER
					{
						open(1),
						close(2),	
						closebyLocalOtherPortFault(3),
						closebyOppositeFePortFault(4),
						closebyLoopBack(5)
					}
					MAX-ACCESS read-write
					STATUS current
					DESCRIPTION
					"
						远端设备以太网电口的开关使能
					"
					::= { rcftRemoteIIEthFePortEntry 3 }
					
		   rcftRemoteIIEthFeAutoNegotiation OBJECT-TYPE
			        SYNTAX INTEGER
			        {   
			            auto(1),
			            manul(2)
			        }
			        MAX-ACCESS read-write
			        STATUS current
			        DESCRIPTION
			          "
			          远端设备电口速率协商方式（1:自协商,2:手动）.   
			          This object indicating the negoation mode of the electronic port 
			          in the local module.When the value is 1 the eletronic port is 
			          set to auto negotiation,otherwise the eletronic port is set to manual negotiation.
			          "					
          			::= { rcftRemoteIIEthFePortEntry 4 }
					
		  rcftRemoteIIEthFeSpeed OBJECT-TYPE
		       SYNTAX INTEGER
		        {   
		            rcft10Mbps(1),
		            rcft100Mbps(2),
		            rcft1000Mbps(3),
		            rcft10Gbps(4),
		            other(16)
		        }
		        MAX-ACCESS read-write
		        STATUS current
		        DESCRIPTION
		          "
		            远端设备电口的速率.  
		            The speed of the electronic port. 
		            1、10Mbps
		            2、100Mbps
		            3、1000Mbps
		            4、10Gbps
		            5、other       
		          "					
		          ::= { rcftRemoteIIEthFePortEntry 5 }
					
					
		 rcftRemoteIIEthFeDuplex OBJECT-TYPE
		        SYNTAX INTEGER
		        {   
		            full-duplex(1),
		            half-duplex(2)
		        }
		        MAX-ACCESS read-write
		        STATUS current
		        DESCRIPTION
		          "
		          远端设备电口双工模式（1:全双工，2:半双工,3:自动）.   
		          The duplex mode of the electronic port.  
		          1:full duplex
		          2:half duplex      
		          "					
		         ::= { rcftRemoteIIEthFePortEntry 6 }
					
					
	  rcftRemoteIIEthFeRestrictSpeed	OBJECT-TYPE
				SYNTAX	INTEGER
				MAX-ACCESS	read-write
				STATUS	current
				DESCRIPTION
					"
						第二层远端设备以太网接口接收限定速率：(n * value；n = 0,1,2....2^12. value = 32kb/s).
					"
			 ::= { rcftRemoteIIEthFePortEntry 7 }
			 
	  rcftRemoteIIEthFeFaultPass	OBJECT-TYPE
	  			SYNTAX INTEGER  
	  			{
	  				enable(1),
	  				disable(2)
	  			}
	  			MAX-ACCESS	read-write
	  			STATUS		current
	  			DESCRIPTION
	  				"
	  					第二层远端设备以太网电口故障转移功能(1:使能,2:禁止)
	  				"	 
			  ::= { rcftRemoteIIEthFePortEntry 8 }   
			  
	  rcftRemoteIIEthFeDisabledByRemoteTP	OBJECT-TYPE
			SYNTAX INTEGER
			{
				open(1),
				close(2)
			}		 	
			MAX-ACCESS	read-only
			STATUS	current
			DESCRIPTION
			"
				远端设备以太网电口关闭的原因是由于对端电口linkdown		
			"
			::= { rcftRemoteIIEthFePortEntry 9 }		
			 	
		rcftRemoteIIEthFeDisabledByFxToFeFP	OBJECT-TYPE
			SYNTAX INTEGER
			{
				open(1),
				close(2)
			}		 	
			MAX-ACCESS	read-only
			STATUS	current
			DESCRIPTION
			"
				远端设备以太网电口关闭的原因是由于光到电故障转移功能使能		
			"
			::= { rcftRemoteIIEthFePortEntry 10 }		
			 	
		rcftRemoteIIEthFeTxRestrictSpeed		OBJECT-TYPE
			SYNTAX	INTEGER
			MAX-ACCESS	read-write
			STATUS	current
			DESCRIPTION
			"
				远端设备以太网电口接收限定速率。其最大值视板卡而不同。
			"
			::= { rcftRemoteIIEthFePortEntry 11 }	
				 	
			 
		rcftRemoteIIEthFeTag	OBJECT-TYPE
			SYNTAX INTEGER
			{
				tag(1),
				untag(2)
			}
			MAX-ACCESS read-write
			STATUS	current
			DESCRIPTION
			"
				远端设备以太网电口的标签
			"			                
		    ::= { rcftRemoteIIEthFePortEntry 12 }	
			                                         
		rcftRemoteIIEthFePVID   OBJECT-TYPE
			SYNTAX INTEGER
			MAX-ACCESS read-write
			STATUS	current
			DESCRIPTION
			"
				远端设备以太网电口的PVID
			"			                
		    ::= { rcftRemoteIIEthFePortEntry 13 }
			                                         
		rcftRemoteIIEthFeQoSPolicy	OBJECT-TYPE
			SYNTAX INTEGER
			MAX-ACCESS read-write
			STATUS	current
			DESCRIPTION
			"
				Bit0：端口优先级
     				1：高优先级，0：低优先级
			"			                
		    ::= { rcftRemoteIIEthFePortEntry 14 }	
		    
	  
		    	
					
      rcftRemoteIIEthFeStatisticTable OBJECT-TYPE
	        SYNTAX SEQUENCE OF RcftRemoteIIEthFeStatisticEntry
	        MAX-ACCESS not-accessible
	        STATUS current
	        DESCRIPTION
	          "
	          远端设备Eth端口的统计表.
	          "
            ::= {rcftRemoteIIDeviceEthFeObjects 2}

	    rcftRemoteIIEthFeStatisticEntry OBJECT-TYPE
	        SYNTAX RcftRemoteIIEthFeStatisticEntry
	        MAX-ACCESS not-accessible
	        STATUS current
	        DESCRIPTION
	          "
	             以rcftRemoteIIEthFeIndex为索引
	          "
	        AUGMENTS { rcftRemoteIIEthFePortEntry }
	        ::= {rcftRemoteIIEthFeStatisticTable 1}

	    RcftRemoteIIEthFeStatisticEntry ::= SEQUENCE {
	           
				rcftRemoteIIEthFeTxPackets         Counter32, 
				rcftRemoteIIEthFeTxBytes           Counter32,
				rcftRemoteIIEthFeRxPackets         Counter32,
				rcftRemoteIIEthFeRxBytes           Counter32,
				rcftRemoteIIEthFeRxLostPackets     Counter32,
				rcftRemoteIIEthFeFluxTimer		   Counter32,
				rcftRemoteIIEthFeTxLostPackets	   Counter32				
	         }
					

    	  rcftRemoteIIEthFeTxPackets OBJECT-TYPE
					SYNTAX Counter32
					MAX-ACCESS read-only
					STATUS current
					DESCRIPTION
						"
							以太网电口发送以太网包数
						"
					::= { rcftRemoteIIEthFeStatisticEntry 1 }
					
		 rcftRemoteIIEthFeTxBytes OBJECT-TYPE
					SYNTAX Counter32
					MAX-ACCESS read-only
					STATUS current
					DESCRIPTION
						"
							以太网电口发送以太网字节数
						"
					::= { rcftRemoteIIEthFeStatisticEntry 2 }
					
		 rcftRemoteIIEthFeRxPackets OBJECT-TYPE
					SYNTAX Counter32
					MAX-ACCESS read-only
					STATUS current
					DESCRIPTION
						"
							以太网电口接收以太网包数
						"
					::= { rcftRemoteIIEthFeStatisticEntry 3 }
					
		 rcftRemoteIIEthFeRxBytes OBJECT-TYPE
					SYNTAX Counter32
					MAX-ACCESS read-only
					STATUS current
					DESCRIPTION
						"
							以太网电口接收以太网字节数
						"
					::= { rcftRemoteIIEthFeStatisticEntry 4 }
					
	    rcftRemoteIIEthFeRxLostPackets OBJECT-TYPE
					SYNTAX Counter32
					MAX-ACCESS read-only
					STATUS current
					DESCRIPTION
						"
							以太网电口接收以太网丢包数
						"
					::= { rcftRemoteIIEthFeStatisticEntry 5 }

        rcftRemoteIIEthFeFluxTimer	OBJECT-TYPE
        			SYNTAX	Counter32
        			MAX-ACCESS 	read-only
        			STATUS		current
        			DESCRIPTION
        				"
        					流量统计的时间
        				"			
                    ::= { rcftRemoteIIEthFeStatisticEntry 6 }         
                    
       rcftRemoteIIEthFeTxLostPackets  OBJECT-TYPE
					SYNTAX Counter32
					MAX-ACCESS read-only
					STATUS current
					DESCRIPTION
						"
							以太网电口发送以太网丢包数
						"
					::= { rcftRemoteIIEthFeStatisticEntry 7 }
					
	     rcftRemoteIIEthFePortConfTable OBJECT-TYPE          
              SYNTAX  SEQUENCE OF RcftRemoteIIEthFePortConfEntry
              MAX-ACCESS  not-accessible
              STATUS  current
              DESCRIPTION
              "
                 The RemoteII Device Fe Port config table.
              "
             ::= { rcftRemoteIIDeviceEthFeObjects 3 }

   			rcftRemoteIIEthFePortConfEntry OBJECT-TYPE
              SYNTAX  RcftRemoteIIEthFePortConfEntry
              MAX-ACCESS  not-accessible
              STATUS  current
              DESCRIPTION
              "
                 An entry in the Fe Port config table.
              "
              INDEX   { rcftChassisIndex, rcftSlotIndex,rcftRemoteIIDeviceIndex,  rcftRemoteIIEthFeIndex }
             ::= { rcftRemoteIIEthFePortConfTable 1 }       
             
          RcftRemoteIIEthFePortConfEntry ::=
              SEQUENCE {
           			    rcftRemoteIIEthFeConfSpeed                	INTEGER,
						rcftRemoteIIEthFeConfDuplex                 INTEGER
					}
		  rcftRemoteIIEthFeConfSpeed OBJECT-TYPE
		       SYNTAX INTEGER
		        {   
		            rcft10Mbps(1),
		            rcft100Mbps(2),
		            rcft1000Mbps(3),
		            rcft10Gbps(4),
		            other(16)
		        }
		        MAX-ACCESS read-write
		        STATUS current
		        DESCRIPTION
		          "
		            远端设备电口的速率配置信息.  
		            The speed of the electronic port. 
		            1、10Mbps
		            2、100Mbps
		            3、1000Mbps
		            4、10Gbps
		            5、other       
		          "					
		          ::= { rcftRemoteIIEthFePortConfEntry 1 }
					
					
		 rcftRemoteIIEthFeConfDuplex OBJECT-TYPE
		        SYNTAX INTEGER
		        {   
		            full-duplex(1),
		            half-duplex(2)
		        }
		        MAX-ACCESS read-write
		        STATUS current
		        DESCRIPTION
		          "
		          远端设备电口双工模式配置信息（1:全双工，2:半双工,3:自动）.   
		          The duplex mode of the electronic port.  
		          1:full duplex
		          2:half duplex      
		          "					
		         ::= { rcftRemoteIIEthFePortConfEntry 2 }
           
       rcftRemoteIIDeviceVLANTable OBJECT-TYPE          
              SYNTAX  SEQUENCE OF RcftRemoteIIDeviceVLANEntry
              MAX-ACCESS  not-accessible
              STATUS  current
              DESCRIPTION
              "
                 The RemoteII Device VLAN table.
              "
             ::= { rcftRemoteIIDeviceVLANObjects 1 }

   			rcftRemoteIIDeviceVLANEntry OBJECT-TYPE
              SYNTAX  RcftRemoteIIDeviceVLANEntry
              MAX-ACCESS  not-accessible
              STATUS  current
              DESCRIPTION
              "
                 An entry in the VLAN config table.
              "
              INDEX   { rcftChassisIndex, rcftSlotIndex,rcftRemoteIIDeviceIndex,  rcftRemoteIIVLANIndex }
             ::= { rcftRemoteIIDeviceVLANTable 1 }       
             
          RcftRemoteIIDeviceVLANEntry ::=
              SEQUENCE {
              			rcftRemoteIIVLANIndex           Integer32,
                    	rcftRemoteIIVLANStatus          INTEGER,
          			    rcftRemoteIIVLANmember          INTEGER,   
          			    rcftRemoteIIVID        			INTEGER
   						}

            rcftRemoteIIVLANIndex 	OBJECT-TYPE
					SYNTAX Integer32
					MAX-ACCESS read-only
					STATUS current
					DESCRIPTION
					"
						远端设备VLAN索引
					"
					::= { rcftRemoteIIDeviceVLANEntry 1 }  
			
			rcftRemoteIIVLANStatus    OBJECT-TYPE
					SYNTAX INTEGER
					MAX-ACCESS read-write
					STATUS current
					DESCRIPTION
					"
						VLAN 表项的状态
						1:激活，2：挂起						
					"
					::= { rcftRemoteIIDeviceVLANEntry 2 }    
					
			rcftRemoteIIVLANmember    OBJECT-TYPE
					SYNTAX INTEGER
					MAX-ACCESS read-write
					STATUS current
					DESCRIPTION
					"
						 bit31~0对应第32路~第1路EthFe口，第n位为1表示第n+1端口为该该VLAN成员。
							目前RC511-4FEE1-REV-B设备只有4路EthFe。
							例如：bit3=1，bit0=1，表示端口4和端口1为该VLAN的成员。
					"
					::= { rcftRemoteIIDeviceVLANEntry 3 }  
			
			rcftRemoteIIVID     OBJECT-TYPE
					SYNTAX INTEGER
					MAX-ACCESS read-write
					STATUS current
					DESCRIPTION
					"
						 VLAN-ID：1~4094
					"
					::= { rcftRemoteIIDeviceVLANEntry 4 } 
       

	---以下是远端设备II系统的TRAP定义--
	
		rcftRemoteIIDevExistTrap	NOTIFICATION-TYPE
			OBJECTS{
				 rcftRemoteIIDeviceExist
			}
			STATUS 	 current
			DESCRIPTION
			"
			     远端设备II在位状态变化告警，当远端设备II由在位到丢失时发送告警，
			      远端设备II由丢失到恢复在位时发送告警恢复. 
 			"
		  	::={rcftRemoteIIDeviceSysTraps 1}
		  	
		rcftRemoteIIDevVoltTooHighTrap	NOTIFICATION-TYPE
			OBJECTS{   
			         rcftRemoteIISysVoltageStatus
			}
			STATUS	current
			DESCRIPTION
			"
				远端设备II电压超出阀值时发送该告警	
			"		  
            ::={rcftRemoteIIDeviceSysTraps 2}
     
		rcftRemoteIIDevVoltTooLowTrap	NOTIFICATION-TYPE
			OBJECTS{   
			      rcftRemoteIISysVoltageStatus   
			}
			STATUS	current
			DESCRIPTION
			"
				远端设备II电压超出阀值时发送该告警	
			"		  
            ::={rcftRemoteIIDeviceSysTraps 3}  
            
   		rcftRemoteIIDevTmptTrap NOTIFICATION-TYPE
	       OBJECTS {
	
	          rcftRemoteIISysTemperature
	       }
	       STATUS  current
	       DESCRIPTION
	       "
	           远端设备II所在机箱温度告警及恢复：当远端设备II所在机箱温度高于门限值时发送告警，
	           当恢复到门限值范围内时发送告警恢复。       
	       "
	       ::={ rcftRemoteIIDeviceSysTraps 4}     
	       
            
	---以下是远端设备II电口的TRAP定义--
            
            
	    rcftRemoteIIEthFeLinkTrap NOTIFICATION-TYPE
	        OBJECTS {
	      
	           rcftRemoteIIEthFeLinkStatus
	        }
	        STATUS             current
	        DESCRIPTION
	        "
	           远端设备II电口link状态变化告警及恢复.  
	           当电口link状态由up变down时发送告警，由down变up时发送告警恢复.  
	           The change of the link status of the eth port in the local module
	           will generate this trap.
	        "
	        ::= { rcftRemoteIIDeviceEthFeTraps 1 }  
	        
	---以下是远端设备II光口的TRAP定义--
	        
	     rcftRemoteIIEthFxPortRLKTrap  NOTIFICATION-TYPE
				OBJECTS{
				          rcftRemoteIIEthFxPortRLK
				}         
	        STATUS             current
	        DESCRIPTION  
	        "
	          远端设备II光口接收方向的link状态(1：linkup，2：linkdown).   
	    	  The object indicating the status of the optical port 
	    	  in the receiving direction.
	    	  When the value is 1 the optical port link up,otherwise link down.
	        "
	        ::= { rcftRemoteIIDeviceEthFxTraps 1 }  
	        
	    rcftRemoteIIEthFxPortTLKTrap  NOTIFICATION-TYPE
				OBJECTS{
				          rcftRemoteIIEthFxPortTLK
				}         
	        STATUS             current
	        DESCRIPTION  
	        "
	          远端设备II光口发送方向的link状态(1：linkup，2：linkdown).   
	    	  The object indicating the status of the optical port 
	    	  in the receiving direction.
	    	  When the value is 1 the optical port link up,otherwise link down.
	        "
	        ::= { rcftRemoteIIDeviceEthFxTraps 2 }  
	        
	    rcftRemoteIIEthFxPortTxPowerTrap NOTIFICATION-TYPE
	       OBJECTS {
	          rcftRemoteIIEthFxPortTxPowerAbnormal
	       }
	       STATUS     current
	       DESCRIPTION
	       "
	       	远端设备II发送光功率变化告警.
	       "
	       ::={ rcftRemoteIIDeviceEthFxTraps 3 }
	
	   rcftRemoteIIEthFxPortRxSensitiveTrap NOTIFICATION-TYPE
	       OBJECTS {
	
	          rcftRemoteIIEthFxPortRxSensitiveAbnormal
	       }
	       STATUS     current
	       DESCRIPTION
	       "
	         远端设备II接收灵敏度变化告警.
	       "
	       ::={ rcftRemoteIIDeviceEthFxTraps 4 }
	
	
	   rcftRemoteIIEthFxPortLaserTrap NOTIFICATION-TYPE
	       OBJECTS {
	
	          rcftRemoteIIEthFxPortLaserAbnormal
	       }
	       STATUS     current
	       DESCRIPTION
	       "
	         远端设备II激光管工作状态变化告警.
	       "
	       ::={ rcftRemoteIIDeviceEthFxTraps 5 }
	
	
	   rcftRemoteIIEthFxPortSDTrap NOTIFICATION-TYPE
	       OBJECTS {
	          rcftRemoteIIEthFxPortSD
	       }
	       STATUS     current
	       DESCRIPTION
	       "
	         远端设备II光模块SD输出信号异常告警和恢复. 当rcftSlotOSD的状态值发生变化时
	         发送该trap. 是告警还是恢复由绑定的对象rcftSlotOSD的状态值决定：
	         1: 恢复，  2：告警
	       "
	       ::={ rcftRemoteIIDeviceEthFxTraps 6 }
                    
	
	   rcftRemoteIIEthFxPortLinkTrap NOTIFICATION-TYPE
	       OBJECTS {
	          rcftRemoteIIEthFxPortLink
	       }
	       STATUS     current
	       DESCRIPTION
	       "
	          远端设备II光口的link状态(1：linkup，2：linkdown).   
	    	  The object indicating the status of the optical port.
	    	  When the value is 1 the optical port link up,otherwise link down.
	       "
	       ::={ rcftRemoteIIDeviceEthFxTraps 7 }
                      
	   rcftRemoteIIEthFxPortSfpRXLOSTrap NOTIFICATION-TYPE
	       OBJECTS {
	          rcftRemoteIIEthFxSfpRXLOS
	       }
	       STATUS     current
	       DESCRIPTION
	       "
	          远端设备输入信号LOS告警及恢复. 远端设备输入信号LOS由正常变丢失时发送告警，由丢失变正常时发送告警恢复.
	       "
	       ::={ rcftRemoteIIDeviceEthFxTraps 8 }
                      
	   rcftRemoteIIEthFxPortSfpExistTrap NOTIFICATION-TYPE
	       OBJECTS {
	          rcftRemoteIIEthFxSfpExist
	       }
	       STATUS     current
	       DESCRIPTION
	       "
	          远端设备sfp模块不在位告警及恢复. 远端设备sfp模块由在位变不在位时发送告警，由不在位变在位时发送告警恢复.
	       "
	       ::={ rcftRemoteIIDeviceEthFxTraps 9 }
                      
                      
                      
END

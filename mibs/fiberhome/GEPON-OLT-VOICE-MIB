--
-- GEPON-OLT-VOICE-MIB.my
-- MIB generated by MG-SOFT Visual MIB Builder Version 5.0  Build 250
-- Monday, July 04, 2016 at 16:28:54
--

--  GEPON-OLT-VOICE-MIB.mib
-- MIB generated by MG-SOFT Visual MIB Builder Version 5.0  Build 250
-- Thursday, July 09, 2015 at 15:57:55
-- 
--  GEPON-OLT-VOICE-MIB.my
-- MIB generated by MG-SOFT Visual MIB Builder Version 5.0  Build 250
-- Tuesday, June 07, 2011 at 16:47:51
-- 
--  File Name : GEPON-OLT-VOICE-MIB.mib
-- Date      : Mon Jan 24 13:55:36 CST 2011
-- Author    : AdventNet Agent Toolkit C Edition - MibEditor 6

	GEPON-OLT-VOICE-MIB DEFINITIONS ::= BEGIN
 
		IMPORTS
			standard, slotIndex, onuIndex			
				FROM GEPON-OLT-COMMON-MIB			
			ifIndex			
				FROM IF-MIB			
			OBJECT-GROUP, MODULE-COMPLIANCE			
				FROM SNMPv2-CONF			
			IpAddress, Integer32, OBJECT-TYPE, MODULE-IDENTITY			
				FROM SNMPv2-SMI			
			TruthValue, TEXTUAL-CONVENTION			
				FROM SNMPv2-TC;
	
	
		-- 1.3.6.1.4.1.5875.800.20.1002.3
		fhOltVoiceModule MODULE-IDENTITY 
			LAST-UPDATED "201507091545Z"		-- July 09, 2015 at 15:45 GMT
			ORGANIZATION 
				"Organization:fiberhome"
			CONTACT-INFO 
				"Contact-info：Please contact to fiberhome support"
			DESCRIPTION 
				"Description.support fiberhome voice function"
			REVISION "201507091545Z"		-- July 09, 2015 at 15:45 GMT
			DESCRIPTION 
				"Support fiberhome voice module"
			::= { fhOltVoiceGroup 3 }

		
	
--
-- Textual conventions
--
	
--  1.3.6.1.4.1.5875.800.20.1002.3
-- July 09, 2015 at 15:45 GMT
-- July 09, 2015 at 15:45 GMT
-- 
-- Textual conventions
-- 
--  Textual conventions
-- 
-- TEXTUAL-CONVENTIONS --
		MyTC ::= TEXTUAL-CONVENTION
			STATUS current
			DESCRIPTION 
				"TC Description"
			SYNTAX Integer32

	
--
-- Node definitions
--
	
--  Node definitions
-- 
-- Node definitions
-- 
-- 1.3.6.1.4.1.5875.800.20
-- 1.3.6.1.4.1.5875.800.20
		-- 1.3.6.1.4.1.5875.800.20
		oltVoice OBJECT IDENTIFIER ::= { standard 20 }

		
--   1.3.6.1.4.1.5875.800.20.1
-- 1.3.6.1.4.1.5875.800.20.1
		-- 1.3.6.1.4.1.5875.800.20.1
		signalProfile OBJECT IDENTIFIER ::= { oltVoice 1 }

		
--   1.3.6.1.4.1.5875.800.20.1.1
-- 1.3.6.1.4.1.5875.800.20.1.1
		-- 1.3.6.1.4.1.5875.800.20.1.1
		signalProfileTable OBJECT-TYPE
			SYNTAX SEQUENCE OF SignalProfileEntry
			MAX-ACCESS not-accessible
			STATUS current
			DESCRIPTION
				"Description"
			::= { signalProfile 1 }

		
--   1.3.6.1.4.1.5875.800.20.1.1.1
-- 1.3.6.1.4.1.5875.800.20.1.1.1
		-- 1.3.6.1.4.1.5875.800.20.1.1.1
		signalProfileEntry OBJECT-TYPE
			SYNTAX SignalProfileEntry
			MAX-ACCESS not-accessible
			STATUS current
			DESCRIPTION
				"Row Description"
			INDEX { signalProfileId }
			::= { signalProfileTable 1 }

		
		SignalProfileEntry ::=
			SEQUENCE { 
				signalProfileId
					Integer32,
				signalName
					OCTET STRING,
				mgcProtocolType
					Integer32,
				mgc1Address
					OCTET STRING,
				mgc1Port
					Integer32,
				mgc2Address
					OCTET STRING,
				mgc2Port
					Integer32,
				mgc3Address
					OCTET STRING,
				mgc3Port
					Integer32,
				primaryDNS
					IpAddress,
				secondaryDNS
					IpAddress,
				sipRegistrationAddress
					OCTET STRING,
				sipRegistrationPort
					Integer32,
				sipServerAddress
					OCTET STRING,
				sipServerPort
					Integer32,
				sipTimeOut
					Integer32,
				keepAlive
					TruthValue,
				aliveInterval
					Integer32,
				aliveTime
					Integer32,
				signalProfileAction
					INTEGER
			 }

--   1.3.6.1.4.1.5875.800.20.1.1.1.1
-- 1.3.6.1.4.1.5875.800.20.1.1.1.1
		-- 1.3.6.1.4.1.5875.800.20.1.1.1.1
		signalProfileId OBJECT-TYPE
			SYNTAX Integer32 (0..65535)
			MAX-ACCESS read-only
			STATUS current
			DESCRIPTION
				"Softswitch Platform Parameter Configuration Profile ID"
			::= { signalProfileEntry 1 }

		
--   1.3.6.1.4.1.5875.800.20.1.1.1.2
-- 1.3.6.1.4.1.5875.800.20.1.1.1.2
		-- 1.3.6.1.4.1.5875.800.20.1.1.1.2
		signalName OBJECT-TYPE
			SYNTAX OCTET STRING
			MAX-ACCESS read-create
			STATUS current
			DESCRIPTION
				"Signaling Service Name (Profile Name)"
			::= { signalProfileEntry 2 }

		
--   1.3.6.1.4.1.5875.800.20.1.1.1.3
-- 1.3.6.1.4.1.5875.800.20.1.1.1.3
		-- 1.3.6.1.4.1.5875.800.20.1.1.1.3
		mgcProtocolType OBJECT-TYPE
			SYNTAX Integer32
			MAX-ACCESS read-create
			STATUS current
			DESCRIPTION
				"0: MGCP
				1: H248
				2: SIP
				"
			::= { signalProfileEntry 3 }

		
--   1.3.6.1.4.1.5875.800.20.1.1.1.4
-- 1.3.6.1.4.1.5875.800.20.1.1.1.4
		-- 1.3.6.1.4.1.5875.800.20.1.1.1.4
		mgc1Address OBJECT-TYPE
			SYNTAX OCTET STRING
			MAX-ACCESS read-create
			STATUS current
			DESCRIPTION
				"MGC1 IP or Domain Name Address / Standby Registrar Address "
			::= { signalProfileEntry 4 }

		
--   1.3.6.1.4.1.5875.800.20.1.1.1.5
-- 1.3.6.1.4.1.5875.800.20.1.1.1.5
		-- 1.3.6.1.4.1.5875.800.20.1.1.1.5
		mgc1Port OBJECT-TYPE
			SYNTAX Integer32
			MAX-ACCESS read-create
			STATUS current
			DESCRIPTION
				"1024 to 65535"
			::= { signalProfileEntry 5 }

		
--   1.3.6.1.4.1.5875.800.20.1.1.1.6
-- 1.3.6.1.4.1.5875.800.20.1.1.1.6
		-- 1.3.6.1.4.1.5875.800.20.1.1.1.6
		mgc2Address OBJECT-TYPE
			SYNTAX OCTET STRING
			MAX-ACCESS read-create
			STATUS current
			DESCRIPTION
				"MGC2 IP or Domain Name Address / Standby Proxy Server Address"
			::= { signalProfileEntry 6 }

		
--   1.3.6.1.4.1.5875.800.20.1.1.1.7
-- 1.3.6.1.4.1.5875.800.20.1.1.1.7
		-- 1.3.6.1.4.1.5875.800.20.1.1.1.7
		mgc2Port OBJECT-TYPE
			SYNTAX Integer32
			MAX-ACCESS read-create
			STATUS current
			DESCRIPTION
				"65535"
			::= { signalProfileEntry 7 }

		
--   1.3.6.1.4.1.5875.800.20.1.1.1.8
-- 1.3.6.1.4.1.5875.800.20.1.1.1.8
		-- 1.3.6.1.4.1.5875.800.20.1.1.1.8
		mgc3Address OBJECT-TYPE
			SYNTAX OCTET STRING
			MAX-ACCESS read-create
			STATUS current
			DESCRIPTION
				"MGC3 IP or Domain Name Address"
			::= { signalProfileEntry 8 }

		
--   1.3.6.1.4.1.5875.800.20.1.1.1.9
-- 1.3.6.1.4.1.5875.800.20.1.1.1.9
		-- 1.3.6.1.4.1.5875.800.20.1.1.1.9
		mgc3Port OBJECT-TYPE
			SYNTAX Integer32
			MAX-ACCESS read-create
			STATUS current
			DESCRIPTION
				"1024 to 65535"
			::= { signalProfileEntry 9 }

		
--   1.3.6.1.4.1.5875.800.20.1.1.1.10
-- 1.3.6.1.4.1.5875.800.20.1.1.1.10
		-- 1.3.6.1.4.1.5875.800.20.1.1.1.10
		primaryDNS OBJECT-TYPE
			SYNTAX IpAddress
			MAX-ACCESS read-create
			STATUS current
			DESCRIPTION
				"Master DNS server"
			::= { signalProfileEntry 10 }

		
--   1.3.6.1.4.1.5875.800.20.1.1.1.11
-- 1.3.6.1.4.1.5875.800.20.1.1.1.11
		-- 1.3.6.1.4.1.5875.800.20.1.1.1.11
		secondaryDNS OBJECT-TYPE
			SYNTAX IpAddress
			MAX-ACCESS read-create
			STATUS current
			DESCRIPTION
				"Slave DNS server"
			::= { signalProfileEntry 11 }

		
--   1.3.6.1.4.1.5875.800.20.1.1.1.12
-- 1.3.6.1.4.1.5875.800.20.1.1.1.12
		-- 1.3.6.1.4.1.5875.800.20.1.1.1.12
		sipRegistrationAddress OBJECT-TYPE
			SYNTAX OCTET STRING
			MAX-ACCESS read-create
			STATUS current
			DESCRIPTION
				"MGC2 IP or Domain Name Address / Standby Proxy Server Address"
			::= { signalProfileEntry 12 }

		
--   1.3.6.1.4.1.5875.800.20.1.1.1.13
-- 1.3.6.1.4.1.5875.800.20.1.1.1.13
		-- 1.3.6.1.4.1.5875.800.20.1.1.1.13
		sipRegistrationPort OBJECT-TYPE
			SYNTAX Integer32
			MAX-ACCESS read-create
			STATUS current
			DESCRIPTION
				"1024 to 65535"
			::= { signalProfileEntry 13 }

		
--   1.3.6.1.4.1.5875.800.20.1.1.1.14
-- 1.3.6.1.4.1.5875.800.20.1.1.1.14
		-- 1.3.6.1.4.1.5875.800.20.1.1.1.14
		sipServerAddress OBJECT-TYPE
			SYNTAX OCTET STRING
			MAX-ACCESS read-create
			STATUS current
			DESCRIPTION
				"MGC3 IP or Domain Name Address"
			::= { signalProfileEntry 14 }

		
--   1.3.6.1.4.1.5875.800.20.1.1.1.15
-- 1.3.6.1.4.1.5875.800.20.1.1.1.15
		-- 1.3.6.1.4.1.5875.800.20.1.1.1.15
		sipServerPort OBJECT-TYPE
			SYNTAX Integer32
			MAX-ACCESS read-create
			STATUS current
			DESCRIPTION
				"1024 to 65535"
			::= { signalProfileEntry 15 }

		
--   1.3.6.1.4.1.5875.800.20.1.1.1.16
-- 1.3.6.1.4.1.5875.800.20.1.1.1.16
		-- 1.3.6.1.4.1.5875.800.20.1.1.1.16
		sipTimeOut OBJECT-TYPE
			SYNTAX Integer32
			MAX-ACCESS read-create
			STATUS current
			DESCRIPTION
				"120 to 86400"
			::= { signalProfileEntry 16 }

		
--   1.3.6.1.4.1.5875.800.20.1.1.1.17
-- 1.3.6.1.4.1.5875.800.20.1.1.1.17
		-- 1.3.6.1.4.1.5875.800.20.1.1.1.17
		keepAlive OBJECT-TYPE
			SYNTAX TruthValue
			MAX-ACCESS read-create
			STATUS current
			DESCRIPTION
				"0-Disable; 
				1-Enable initiative;
				2-Enable passive;
				"
			::= { signalProfileEntry 17 }

		
--   1.3.6.1.4.1.5875.800.20.1.1.1.18
-- 1.3.6.1.4.1.5875.800.20.1.1.1.18
		-- 1.3.6.1.4.1.5875.800.20.1.1.1.18
		aliveInterval OBJECT-TYPE
			SYNTAX Integer32 (-2147483648..2147483647)
			MAX-ACCESS read-create
			STATUS current
			DESCRIPTION
				"1 to 43200"
			::= { signalProfileEntry 18 }

		
--   1.3.6.1.4.1.5875.800.20.1.1.1.19
-- 1.3.6.1.4.1.5875.800.20.1.1.1.19
		-- 1.3.6.1.4.1.5875.800.20.1.1.1.19
		aliveTime OBJECT-TYPE
			SYNTAX Integer32 (-2147483648..2147483647)
			MAX-ACCESS read-create
			STATUS current
			DESCRIPTION
				"1 to 120"
			::= { signalProfileEntry 19 }

		
--   1.3.6.1.4.1.5875.800.20.1.1.1.25
-- 1.3.6.1.4.1.5875.800.20.1.1.1.25
		-- 1.3.6.1.4.1.5875.800.20.1.1.1.25
		signalProfileAction OBJECT-TYPE
			SYNTAX INTEGER
				{
				create(4),
				destory(6),
				modify(7)
				}
			MAX-ACCESS read-create
			STATUS current
			DESCRIPTION
				"4:create
				6:delete
				7:modify
				"
			::= { signalProfileEntry 25 }

		
--   1.3.6.1.4.1.5875.800.20.1.2
-- 1.3.6.1.4.1.5875.800.20.1.2
		-- 1.3.6.1.4.1.5875.800.20.1.2
		nextSignalProfileId OBJECT-TYPE
			SYNTAX Integer32
			MAX-ACCESS read-only
			STATUS current
			DESCRIPTION
				"Leaf node"
			::= { signalProfile 2 }

		
--   1.3.6.1.4.1.5875.800.20.2
-- 1.3.6.1.4.1.5875.800.20.2
		-- 1.3.6.1.4.1.5875.800.20.2
		potsUserCfg OBJECT IDENTIFIER ::= { oltVoice 2 }

		
--   1.3.6.1.4.1.5875.800.20.2.1
-- 1.3.6.1.4.1.5875.800.20.2.1
		-- 1.3.6.1.4.1.5875.800.20.2.1
		potsUserCfgTable OBJECT-TYPE
			SYNTAX SEQUENCE OF PotsUserCfgEntry
			MAX-ACCESS not-accessible
			STATUS current
			DESCRIPTION
				"Description"
			::= { potsUserCfg 1 }

		
--   1.3.6.1.4.1.5875.800.20.2.1.1
-- 1.3.6.1.4.1.5875.800.20.2.1.1
		-- 1.3.6.1.4.1.5875.800.20.2.1.1
		potsUserCfgEntry OBJECT-TYPE
			SYNTAX PotsUserCfgEntry
			MAX-ACCESS not-accessible
			STATUS current
			DESCRIPTION
				"Row Description"
			INDEX { ifIndex }
			::= { potsUserCfgTable 1 }

		
		PotsUserCfgEntry ::=
			SEQUENCE { 
				potsEnable
					INTEGER,
				telNum
					OCTET STRING,
				bindingSignalName
					OCTET STRING,
				signalVlan
					Integer32,
				svlanEnable
					TruthValue,
				svlanId
					Integer32,
				svlanCosFor5516
					Integer32,
				cvalnCosFor5516
					Integer32,
				voiceDomain
					OCTET STRING,
				protocolPort
					Integer32,
				userNameSipTelNum
					OCTET STRING,
				sipUserName
					OCTET STRING,
				sipPassword
					OCTET STRING,
				bindingPotsCfgProfileName
					OCTET STRING,
				potsUserCfgAction
					INTEGER
			 }

--   1.3.6.1.4.1.5875.800.20.2.1.1.2
-- 1.3.6.1.4.1.5875.800.20.2.1.1.2
		-- 1.3.6.1.4.1.5875.800.20.2.1.1.2
		potsEnable OBJECT-TYPE
			SYNTAX INTEGER
				{
				true(1),
				false(0)
				}
			MAX-ACCESS read-write
			STATUS current
			DESCRIPTION
				"The 5516: 
				1: enable
				0: disable
				The 5116: 
				1: enable
				0: disable
				"
			::= { potsUserCfgEntry 2 }

		
--   1.3.6.1.4.1.5875.800.20.2.1.1.3
-- 1.3.6.1.4.1.5875.800.20.2.1.1.3
		-- 1.3.6.1.4.1.5875.800.20.2.1.1.3
		telNum OBJECT-TYPE
			SYNTAX OCTET STRING
			MAX-ACCESS read-write
			STATUS current
			DESCRIPTION
				"No more than 8 bytes"
			::= { potsUserCfgEntry 3 }

		
--   1.3.6.1.4.1.5875.800.20.2.1.1.4
-- 1.3.6.1.4.1.5875.800.20.2.1.1.4
		-- 1.3.6.1.4.1.5875.800.20.2.1.1.4
		bindingSignalName OBJECT-TYPE
			SYNTAX OCTET STRING
			MAX-ACCESS read-write
			STATUS current
			DESCRIPTION
				"Softswitch platform parameter profile"
			::= { potsUserCfgEntry 4 }

		
--   1.3.6.1.4.1.5875.800.20.2.1.1.5
-- 1.3.6.1.4.1.5875.800.20.2.1.1.5
		-- 1.3.6.1.4.1.5875.800.20.2.1.1.5
		signalVlan OBJECT-TYPE
			SYNTAX Integer32
			MAX-ACCESS read-write
			STATUS current
			DESCRIPTION
				"NGPON: 
				Range: 1 to 4085
				"
			::= { potsUserCfgEntry 5 }

		
--   1.3.6.1.4.1.5875.800.20.2.1.1.6
-- 1.3.6.1.4.1.5875.800.20.2.1.1.6
		-- 1.3.6.1.4.1.5875.800.20.2.1.1.6
		svlanEnable OBJECT-TYPE
			SYNTAX TruthValue
			MAX-ACCESS read-write
			STATUS current
			DESCRIPTION
				"5516,NGPON:
				1: enable;
				2: disable
				"
			::= { potsUserCfgEntry 6 }

		
--   1.3.6.1.4.1.5875.800.20.2.1.1.7
-- 1.3.6.1.4.1.5875.800.20.2.1.1.7
		-- 1.3.6.1.4.1.5875.800.20.2.1.1.7
		svlanId OBJECT-TYPE
			SYNTAX Integer32
			MAX-ACCESS read-write
			STATUS current
			DESCRIPTION
				"NGPON:
				0 to 4085, 0xffff
				"
			::= { potsUserCfgEntry 7 }

		
--   1.3.6.1.4.1.5875.800.20.2.1.1.8
-- 1.3.6.1.4.1.5875.800.20.2.1.1.8
		-- 1.3.6.1.4.1.5875.800.20.2.1.1.8
		svlanCosFor5516 OBJECT-TYPE
			SYNTAX Integer32 (-2147483648..2147483647)
			MAX-ACCESS read-write
			STATUS current
			DESCRIPTION
				"Not available for the 5116
				NGPON/gpon:
				0 to 7, 0xff
				"
			::= { potsUserCfgEntry 8 }

		
--   1.3.6.1.4.1.5875.800.20.2.1.1.9
-- 1.3.6.1.4.1.5875.800.20.2.1.1.9
		-- 1.3.6.1.4.1.5875.800.20.2.1.1.9
		cvalnCosFor5516 OBJECT-TYPE
			SYNTAX Integer32 (-2147483648..2147483647)
			MAX-ACCESS read-write
			STATUS current
			DESCRIPTION
				"Not available for the 5116
				NGPON/gpon:
				0 to 7, 0xff
				"
			::= { potsUserCfgEntry 9 }

		
--   1.3.6.1.4.1.5875.800.20.2.1.1.11
-- 1.3.6.1.4.1.5875.800.20.2.1.1.11
		-- 1.3.6.1.4.1.5875.800.20.2.1.1.11
		voiceDomain OBJECT-TYPE
			SYNTAX OCTET STRING
			MAX-ACCESS read-write
			STATUS current
			DESCRIPTION
				"End Point Name"
			::= { potsUserCfgEntry 11 }

		
--   1.3.6.1.4.1.5875.800.20.2.1.1.12
-- 1.3.6.1.4.1.5875.800.20.2.1.1.12
		-- 1.3.6.1.4.1.5875.800.20.2.1.1.12
		protocolPort OBJECT-TYPE
			SYNTAX Integer32
			MAX-ACCESS read-write
			STATUS current
			DESCRIPTION
				"1 to 65535"
			::= { potsUserCfgEntry 12 }

		
--   1.3.6.1.4.1.5875.800.20.2.1.1.13
-- 1.3.6.1.4.1.5875.800.20.2.1.1.13
		-- 1.3.6.1.4.1.5875.800.20.2.1.1.13
		userNameSipTelNum OBJECT-TYPE
			SYNTAX OCTET STRING
			MAX-ACCESS read-write
			STATUS current
			DESCRIPTION
				"End Point Username / Sip Telephone Number"
			::= { potsUserCfgEntry 13 }

		
--   1.3.6.1.4.1.5875.800.20.2.1.1.14
-- 1.3.6.1.4.1.5875.800.20.2.1.1.14
		-- 1.3.6.1.4.1.5875.800.20.2.1.1.14
		sipUserName OBJECT-TYPE
			SYNTAX OCTET STRING
			MAX-ACCESS read-write
			STATUS current
			DESCRIPTION
				"Sip Protocol Authentication Username"
			::= { potsUserCfgEntry 14 }

		
--   1.3.6.1.4.1.5875.800.20.2.1.1.15
-- 1.3.6.1.4.1.5875.800.20.2.1.1.15
		-- 1.3.6.1.4.1.5875.800.20.2.1.1.15
		sipPassword OBJECT-TYPE
			SYNTAX OCTET STRING
			MAX-ACCESS read-write
			STATUS current
			DESCRIPTION
				"Sip Protocol Authentication Password"
			::= { potsUserCfgEntry 15 }

		
--   1.3.6.1.4.1.5875.800.20.2.1.1.16
-- 1.3.6.1.4.1.5875.800.20.2.1.1.16
		-- 1.3.6.1.4.1.5875.800.20.2.1.1.16
		bindingPotsCfgProfileName OBJECT-TYPE
			SYNTAX OCTET STRING
			MAX-ACCESS read-write
			STATUS current
			DESCRIPTION
				"One profile name can only correspond to one profile ID above"
			::= { potsUserCfgEntry 16 }

		
--   1.3.6.1.4.1.5875.800.20.2.1.1.20
-- 1.3.6.1.4.1.5875.800.20.2.1.1.20
		-- 1.3.6.1.4.1.5875.800.20.2.1.1.20
		potsUserCfgAction OBJECT-TYPE
			SYNTAX INTEGER { modify(7) }
			MAX-ACCESS read-write
			STATUS current
			DESCRIPTION
				"7: configure"
			::= { potsUserCfgEntry 20 }

		
--   1.3.6.1.4.1.5875.800.20.3
-- 1.3.6.1.4.1.5875.800.20.3
		-- 1.3.6.1.4.1.5875.800.20.3
		onuVoiceCfg OBJECT IDENTIFIER ::= { oltVoice 3 }

		
--   1.3.6.1.4.1.5875.800.20.3.1
-- 1.3.6.1.4.1.5875.800.20.3.1
		-- 1.3.6.1.4.1.5875.800.20.3.1
		onuVoiceCfgTable OBJECT-TYPE
			SYNTAX SEQUENCE OF OnuVoiceCfgEntry
			MAX-ACCESS not-accessible
			STATUS current
			DESCRIPTION
				"Description"
			::= { onuVoiceCfg 1 }

		
--   1.3.6.1.4.1.5875.800.20.3.1.1
-- 1.3.6.1.4.1.5875.800.20.3.1.1
		-- 1.3.6.1.4.1.5875.800.20.3.1.1
		onuVoiceCfgEntry OBJECT-TYPE
			SYNTAX OnuVoiceCfgEntry
			MAX-ACCESS not-accessible
			STATUS current
			DESCRIPTION
				"Row Description"
			INDEX { onuIndex }
			::= { onuVoiceCfgTable 1 }

		
		OnuVoiceCfgEntry ::=
			SEQUENCE { 
				ipCfgType
					Integer32,
				staticIPAddress
					IpAddress,
				staticIPMask
					IpAddress,
				staticIPGateway
					IpAddress,
				pppoeUserName
					OCTET STRING,
				pppoePassword
					OCTET STRING,
				dhcpOption60Enable
					TruthValue,
				dhcpOption60Suffix
					OCTET STRING,
				bindingVoicePlatformProfileName
					OCTET STRING,
				voiceCfgAction
					INTEGER
			 }

--   1.3.6.1.4.1.5875.800.20.3.1.1.3
-- 1.3.6.1.4.1.5875.800.20.3.1.1.3
		-- 1.3.6.1.4.1.5875.800.20.3.1.1.3
		ipCfgType OBJECT-TYPE
			SYNTAX Integer32 (-2147483648..2147483647)
			MAX-ACCESS read-write
			STATUS current
			DESCRIPTION
				"0:static
				1:pppoe
				2:dhcp
				"
			::= { onuVoiceCfgEntry 3 }

		
--   1.3.6.1.4.1.5875.800.20.3.1.1.4
-- 1.3.6.1.4.1.5875.800.20.3.1.1.4
		-- 1.3.6.1.4.1.5875.800.20.3.1.1.4
		staticIPAddress OBJECT-TYPE
			SYNTAX IpAddress
			MAX-ACCESS read-write
			STATUS current
			DESCRIPTION
				"ONU Static Public Network IP"
			::= { onuVoiceCfgEntry 4 }

		
--   1.3.6.1.4.1.5875.800.20.3.1.1.5
-- 1.3.6.1.4.1.5875.800.20.3.1.1.5
		-- 1.3.6.1.4.1.5875.800.20.3.1.1.5
		staticIPMask OBJECT-TYPE
			SYNTAX IpAddress
			MAX-ACCESS read-write
			STATUS current
			DESCRIPTION
				"ONU Static Public Network IP Mask"
			::= { onuVoiceCfgEntry 5 }

		
--   1.3.6.1.4.1.5875.800.20.3.1.1.6
-- 1.3.6.1.4.1.5875.800.20.3.1.1.6
		-- 1.3.6.1.4.1.5875.800.20.3.1.1.6
		staticIPGateway OBJECT-TYPE
			SYNTAX IpAddress
			MAX-ACCESS read-write
			STATUS current
			DESCRIPTION
				"ONU Static Public Network IP Gateway"
			::= { onuVoiceCfgEntry 6 }

		
--   1.3.6.1.4.1.5875.800.20.3.1.1.7
-- 1.3.6.1.4.1.5875.800.20.3.1.1.7
		-- 1.3.6.1.4.1.5875.800.20.3.1.1.7
		pppoeUserName OBJECT-TYPE
			SYNTAX OCTET STRING
			MAX-ACCESS read-write
			STATUS current
			DESCRIPTION
				"PPPoE Username"
			::= { onuVoiceCfgEntry 7 }

		
--   1.3.6.1.4.1.5875.800.20.3.1.1.8
-- 1.3.6.1.4.1.5875.800.20.3.1.1.8
		-- 1.3.6.1.4.1.5875.800.20.3.1.1.8
		pppoePassword OBJECT-TYPE
			SYNTAX OCTET STRING
			MAX-ACCESS read-write
			STATUS current
			DESCRIPTION
				"PPPoE Password"
			::= { onuVoiceCfgEntry 8 }

		
--   1.3.6.1.4.1.5875.800.20.3.1.1.9
-- 1.3.6.1.4.1.5875.800.20.3.1.1.9
		-- 1.3.6.1.4.1.5875.800.20.3.1.1.9
		dhcpOption60Enable OBJECT-TYPE
			SYNTAX TruthValue
			MAX-ACCESS read-write
			STATUS current
			DESCRIPTION
				"1- Enable; 
				0- Disable;
				"
			::= { onuVoiceCfgEntry 9 }

		
--   1.3.6.1.4.1.5875.800.20.3.1.1.10
-- 1.3.6.1.4.1.5875.800.20.3.1.1.10
		-- 1.3.6.1.4.1.5875.800.20.3.1.1.10
		dhcpOption60Suffix OBJECT-TYPE
			SYNTAX OCTET STRING
			MAX-ACCESS read-write
			STATUS current
			DESCRIPTION
				"DHCP Option60 Identifier Suffix"
			::= { onuVoiceCfgEntry 10 }

		
--   1.3.6.1.4.1.5875.800.20.3.1.1.11
-- 1.3.6.1.4.1.5875.800.20.3.1.1.11
		-- 1.3.6.1.4.1.5875.800.20.3.1.1.11
		bindingVoicePlatformProfileName OBJECT-TYPE
			SYNTAX OCTET STRING
			MAX-ACCESS read-write
			STATUS current
			DESCRIPTION
				"This node is used to configure profile for each version of all devices except the 5116 version 1.41"
			::= { onuVoiceCfgEntry 11 }

		
--   1.3.6.1.4.1.5875.800.20.3.1.1.20
-- 1.3.6.1.4.1.5875.800.20.3.1.1.20
		-- 1.3.6.1.4.1.5875.800.20.3.1.1.20
		voiceCfgAction OBJECT-TYPE
			SYNTAX INTEGER { modify(7) }
			MAX-ACCESS read-write
			STATUS current
			DESCRIPTION
				"7: configure"
			::= { onuVoiceCfgEntry 20 }

		
--   1.3.6.1.4.1.5875.800.20.6
-- 1.3.6.1.4.1.5875.800.20.6
		-- 1.3.6.1.4.1.5875.800.20.6
		voicePlatformProfile OBJECT IDENTIFIER ::= { oltVoice 6 }

		
--   1.3.6.1.4.1.5875.800.20.6.1
-- 1.3.6.1.4.1.5875.800.20.6.1
		-- 1.3.6.1.4.1.5875.800.20.6.1
		voicePlatformProfileTable OBJECT-TYPE
			SYNTAX SEQUENCE OF VoicePlatformProfileEntry
			MAX-ACCESS not-accessible
			STATUS current
			DESCRIPTION
				"Description"
			::= { voicePlatformProfile 1 }

		
--   1.3.6.1.4.1.5875.800.20.6.1.1
-- 1.3.6.1.4.1.5875.800.20.6.1.1
		-- 1.3.6.1.4.1.5875.800.20.6.1.1
		voicePlatformProfileEntry OBJECT-TYPE
			SYNTAX VoicePlatformProfileEntry
			MAX-ACCESS not-accessible
			STATUS current
			DESCRIPTION
				"Row Description"
			INDEX { voicePlatformProfileId }
			::= { voicePlatformProfileTable 1 }

		
		VoicePlatformProfileEntry ::=
			SEQUENCE { 
				voicePlatformProfileId
					Integer32,
				voicePlatformProfileName
					OCTET STRING,
				rtpNameFiexedPart
					OCTET STRING,
				rtpBeginValue
					Integer32,
				rtpEndValue
					Integer32,
				rtpStepValue
					Integer32,
				rtpNameFill
					Integer32,
				digitmapStartTimer
					Integer32,
				digitmapShortTimer
					Integer32,
				digitmapLongTimer
					Integer32,
				dialMapNotifyImmediately
					Integer32,
				vbdEnable
					Integer32,
				packetIntervalOut
					Integer32,
				packetIntervalIn
					Integer32,
				codeType
					Integer32,
				platformProfileAction
					INTEGER
			 }

--   1.3.6.1.4.1.5875.800.20.6.1.1.1
-- 1.3.6.1.4.1.5875.800.20.6.1.1.1
		-- 1.3.6.1.4.1.5875.800.20.6.1.1.1
		voicePlatformProfileId OBJECT-TYPE
			SYNTAX Integer32 (0..65535)
			MAX-ACCESS read-only
			STATUS current
			DESCRIPTION
				"Profile ID"
			::= { voicePlatformProfileEntry 1 }

		
--   1.3.6.1.4.1.5875.800.20.6.1.1.2
-- 1.3.6.1.4.1.5875.800.20.6.1.1.2
		-- 1.3.6.1.4.1.5875.800.20.6.1.1.2
		voicePlatformProfileName OBJECT-TYPE
			SYNTAX OCTET STRING
			MAX-ACCESS read-create
			STATUS current
			DESCRIPTION
				"Profile Name"
			::= { voicePlatformProfileEntry 2 }

		
--   1.3.6.1.4.1.5875.800.20.6.1.1.3
-- 1.3.6.1.4.1.5875.800.20.6.1.1.3
		-- 1.3.6.1.4.1.5875.800.20.6.1.1.3
		rtpNameFiexedPart OBJECT-TYPE
			SYNTAX OCTET STRING
			MAX-ACCESS read-create
			STATUS current
			DESCRIPTION
				"Fixed Part of RTP Source Name"
			::= { voicePlatformProfileEntry 3 }

		
--   1.3.6.1.4.1.5875.800.20.6.1.1.4
-- 1.3.6.1.4.1.5875.800.20.6.1.1.4
		-- 1.3.6.1.4.1.5875.800.20.6.1.1.4
		rtpBeginValue OBJECT-TYPE
			SYNTAX Integer32
			MAX-ACCESS read-create
			STATUS current
			DESCRIPTION
				"0 to 65534 (default:4000)"
			::= { voicePlatformProfileEntry 4 }

		
--   1.3.6.1.4.1.5875.800.20.6.1.1.5
-- 1.3.6.1.4.1.5875.800.20.6.1.1.5
		-- 1.3.6.1.4.1.5875.800.20.6.1.1.5
		rtpEndValue OBJECT-TYPE
			SYNTAX Integer32
			MAX-ACCESS read-create
			STATUS current
			DESCRIPTION
				"0 to 65534 (default:9000)"
			::= { voicePlatformProfileEntry 5 }

		
--   1.3.6.1.4.1.5875.800.20.6.1.1.6
-- 1.3.6.1.4.1.5875.800.20.6.1.1.6
		-- 1.3.6.1.4.1.5875.800.20.6.1.1.6
		rtpStepValue OBJECT-TYPE
			SYNTAX Integer32
			MAX-ACCESS read-create
			STATUS current
			DESCRIPTION
				"1 to 65534 (default:1)"
			::= { voicePlatformProfileEntry 6 }

		
--   1.3.6.1.4.1.5875.800.20.6.1.1.7
-- 1.3.6.1.4.1.5875.800.20.6.1.1.7
		-- 1.3.6.1.4.1.5875.800.20.6.1.1.7
		rtpNameFill OBJECT-TYPE
			SYNTAX Integer32 (-2147483648..2147483647)
			MAX-ACCESS read-create
			STATUS current
			DESCRIPTION
				"0- Unfixed
				1- (fixed) 
				"
			::= { voicePlatformProfileEntry 7 }

		
--   1.3.6.1.4.1.5875.800.20.6.1.1.8
-- 1.3.6.1.4.1.5875.800.20.6.1.1.8
		-- 1.3.6.1.4.1.5875.800.20.6.1.1.8
		digitmapStartTimer OBJECT-TYPE
			SYNTAX Integer32
			MAX-ACCESS read-create
			STATUS current
			DESCRIPTION
				"1 to 254"
			::= { voicePlatformProfileEntry 8 }

		
--   1.3.6.1.4.1.5875.800.20.6.1.1.9
-- 1.3.6.1.4.1.5875.800.20.6.1.1.9
		-- 1.3.6.1.4.1.5875.800.20.6.1.1.9
		digitmapShortTimer OBJECT-TYPE
			SYNTAX Integer32
			MAX-ACCESS read-create
			STATUS current
			DESCRIPTION
				"1 to 254"
			::= { voicePlatformProfileEntry 9 }

		
--   1.3.6.1.4.1.5875.800.20.6.1.1.10
-- 1.3.6.1.4.1.5875.800.20.6.1.1.10
		-- 1.3.6.1.4.1.5875.800.20.6.1.1.10
		digitmapLongTimer OBJECT-TYPE
			SYNTAX Integer32
			MAX-ACCESS read-create
			STATUS current
			DESCRIPTION
				"1 to 254"
			::= { voicePlatformProfileEntry 10 }

		
--   1.3.6.1.4.1.5875.800.20.6.1.1.11
-- 1.3.6.1.4.1.5875.800.20.6.1.1.11
		-- 1.3.6.1.4.1.5875.800.20.6.1.1.11
		dialMapNotifyImmediately OBJECT-TYPE
			SYNTAX Integer32
			MAX-ACCESS read-create
			STATUS current
			DESCRIPTION
				"2- report immediately
				0- report only if match
				"
			::= { voicePlatformProfileEntry 11 }

		
--   1.3.6.1.4.1.5875.800.20.6.1.1.12
-- 1.3.6.1.4.1.5875.800.20.6.1.1.12
		-- 1.3.6.1.4.1.5875.800.20.6.1.1.12
		vbdEnable OBJECT-TYPE
			SYNTAX Integer32
			MAX-ACCESS read-create
			STATUS current
			DESCRIPTION
				"1-enable
				0- disable
				"
			::= { voicePlatformProfileEntry 12 }

		
--   1.3.6.1.4.1.5875.800.20.6.1.1.13
-- 1.3.6.1.4.1.5875.800.20.6.1.1.13
		-- 1.3.6.1.4.1.5875.800.20.6.1.1.13
		packetIntervalOut OBJECT-TYPE
			SYNTAX Integer32
			MAX-ACCESS read-create
			STATUS current
			DESCRIPTION
				"10，20，30，40，50，60"
			::= { voicePlatformProfileEntry 13 }

		
--   1.3.6.1.4.1.5875.800.20.6.1.1.14
-- 1.3.6.1.4.1.5875.800.20.6.1.1.14
		-- 1.3.6.1.4.1.5875.800.20.6.1.1.14
		packetIntervalIn OBJECT-TYPE
			SYNTAX Integer32
			MAX-ACCESS read-create
			STATUS current
			DESCRIPTION
				"10，20，30，40，50，60"
			::= { voicePlatformProfileEntry 14 }

		
--   1.3.6.1.4.1.5875.800.20.6.1.1.15
-- 1.3.6.1.4.1.5875.800.20.6.1.1.15
		-- 1.3.6.1.4.1.5875.800.20.6.1.1.15
		codeType OBJECT-TYPE
			SYNTAX Integer32
			MAX-ACCESS read-create
			STATUS current
			DESCRIPTION
				"0-G.711U,
				8-G.711A,，
				-1 no change
				"
			::= { voicePlatformProfileEntry 15 }

		
--   1.3.6.1.4.1.5875.800.20.6.1.1.16
-- 1.3.6.1.4.1.5875.800.20.6.1.1.16
		-- 1.3.6.1.4.1.5875.800.20.6.1.1.16
		platformProfileAction OBJECT-TYPE
			SYNTAX INTEGER
				{
				create(4),
				destory(6),
				modify(7)
				}
			MAX-ACCESS read-create
			STATUS current
			DESCRIPTION
				"Operation"
			::= { voicePlatformProfileEntry 16 }

		
--   1.3.6.1.4.1.5875.800.20.6.2
-- 1.3.6.1.4.1.5875.800.20.6.2
		-- 1.3.6.1.4.1.5875.800.20.6.2
		nextVoicePlatformProfileId OBJECT-TYPE
			SYNTAX Integer32
			MAX-ACCESS read-only
			STATUS current
			DESCRIPTION
				"Get Free Profile ID"
			::= { voicePlatformProfile 2 }

		
--   1.3.6.1.4.1.5875.800.20.7
-- 1.3.6.1.4.1.5875.800.20.7
		-- 1.3.6.1.4.1.5875.800.20.7
		potsCfgProfile OBJECT IDENTIFIER ::= { oltVoice 7 }

		
--   1.3.6.1.4.1.5875.800.20.7.1
-- 1.3.6.1.4.1.5875.800.20.7.1
		-- 1.3.6.1.4.1.5875.800.20.7.1
		potsCfgProfileTable OBJECT-TYPE
			SYNTAX SEQUENCE OF PotsCfgProfileEntry
			MAX-ACCESS not-accessible
			STATUS current
			DESCRIPTION
				"Description"
			::= { potsCfgProfile 1 }

		
--   1.3.6.1.4.1.5875.800.20.7.1.1
-- 1.3.6.1.4.1.5875.800.20.7.1.1
		-- 1.3.6.1.4.1.5875.800.20.7.1.1
		potsCfgProfileEntry OBJECT-TYPE
			SYNTAX PotsCfgProfileEntry
			MAX-ACCESS not-accessible
			STATUS current
			DESCRIPTION
				"Row Description"
			INDEX { potsCfgProfileId }
			::= { potsCfgProfileTable 1 }

		
		PotsCfgProfileEntry ::=
			SEQUENCE { 
				potsCfgProfileId
					Integer32,
				potsCfgProfileName
					OCTET STRING,
				voiceCoder
					Integer32,
				faxMode
					Integer32,
				slienceSwitch
					TruthValue,
				echoCancel
					TruthValue,
				inputGain
					Integer32,
				outputGain
					Integer32,
				dtmfMode
					Integer32,
				faxCtrlMode
					Integer32,
				potsProfileAction
					INTEGER
			 }

--   1.3.6.1.4.1.5875.800.20.7.1.1.1
-- 1.3.6.1.4.1.5875.800.20.7.1.1.1
		-- 1.3.6.1.4.1.5875.800.20.7.1.1.1
		potsCfgProfileId OBJECT-TYPE
			SYNTAX Integer32 (0..65535)
			MAX-ACCESS read-only
			STATUS current
			DESCRIPTION
				"Profile ID"
			::= { potsCfgProfileEntry 1 }

		
--   1.3.6.1.4.1.5875.800.20.7.1.1.2
-- 1.3.6.1.4.1.5875.800.20.7.1.1.2
		-- 1.3.6.1.4.1.5875.800.20.7.1.1.2
		potsCfgProfileName OBJECT-TYPE
			SYNTAX OCTET STRING
			MAX-ACCESS read-create
			STATUS current
			DESCRIPTION
				"Profile Name"
			::= { potsCfgProfileEntry 2 }

		
--   1.3.6.1.4.1.5875.800.20.7.1.1.3
-- 1.3.6.1.4.1.5875.800.20.7.1.1.3
		-- 1.3.6.1.4.1.5875.800.20.7.1.1.3
		voiceCoder OBJECT-TYPE
			SYNTAX Integer32
			MAX-ACCESS read-create
			STATUS current
			DESCRIPTION
				"0: G.711U 
				1: G.711A
				2: G.723 
				3: G.729
				"
			::= { potsCfgProfileEntry 3 }

		
--   1.3.6.1.4.1.5875.800.20.7.1.1.4
-- 1.3.6.1.4.1.5875.800.20.7.1.1.4
		-- 1.3.6.1.4.1.5875.800.20.7.1.1.4
		faxMode OBJECT-TYPE
			SYNTAX Integer32
			MAX-ACCESS read-create
			STATUS current
			DESCRIPTION
				"0:transparent
				1: T．38
				"
			::= { potsCfgProfileEntry 4 }

		
--   1.3.6.1.4.1.5875.800.20.7.1.1.5
-- 1.3.6.1.4.1.5875.800.20.7.1.1.5
		-- 1.3.6.1.4.1.5875.800.20.7.1.1.5
		slienceSwitch OBJECT-TYPE
			SYNTAX TruthValue
			MAX-ACCESS read-create
			STATUS current
			DESCRIPTION
				"5116,NGPON
				1: enable
				2: disable
				"
			::= { potsCfgProfileEntry 5 }

		
--   1.3.6.1.4.1.5875.800.20.7.1.1.6
-- 1.3.6.1.4.1.5875.800.20.7.1.1.6
		-- 1.3.6.1.4.1.5875.800.20.7.1.1.6
		echoCancel OBJECT-TYPE
			SYNTAX TruthValue
			MAX-ACCESS read-create
			STATUS current
			DESCRIPTION
				"1: enable
				2: disable
				"
			::= { potsCfgProfileEntry 6 }

		
--   1.3.6.1.4.1.5875.800.20.7.1.1.7
-- 1.3.6.1.4.1.5875.800.20.7.1.1.7
		-- 1.3.6.1.4.1.5875.800.20.7.1.1.7
		inputGain OBJECT-TYPE
			SYNTAX Integer32 (-2147483648..2147483647)
			MAX-ACCESS read-create
			STATUS current
			DESCRIPTION
				"-32 to 32"
			::= { potsCfgProfileEntry 7 }

		
--   1.3.6.1.4.1.5875.800.20.7.1.1.8
-- 1.3.6.1.4.1.5875.800.20.7.1.1.8
		-- 1.3.6.1.4.1.5875.800.20.7.1.1.8
		outputGain OBJECT-TYPE
			SYNTAX Integer32 (-2147483648..2147483647)
			MAX-ACCESS read-create
			STATUS current
			DESCRIPTION
				"-32 to 32"
			::= { potsCfgProfileEntry 8 }

		
--   1.3.6.1.4.1.5875.800.20.7.1.1.9
-- 1.3.6.1.4.1.5875.800.20.7.1.1.9
		-- 1.3.6.1.4.1.5875.800.20.7.1.1.9
		dtmfMode OBJECT-TYPE
			SYNTAX Integer32 (-2147483648..2147483647)
			MAX-ACCESS read-create
			STATUS current
			DESCRIPTION
				"0: transparent
				1:RFC2833
				"
			::= { potsCfgProfileEntry 9 }

		
--   1.3.6.1.4.1.5875.800.20.7.1.1.10
-- 1.3.6.1.4.1.5875.800.20.7.1.1.10
		-- 1.3.6.1.4.1.5875.800.20.7.1.1.10
		faxCtrlMode OBJECT-TYPE
			SYNTAX Integer32
			MAX-ACCESS read-create
			STATUS current
			DESCRIPTION
				"Not available
				0: voice channel
				1: software fully control
				2: auto negotiate
				"
			::= { potsCfgProfileEntry 10 }

		
--   1.3.6.1.4.1.5875.800.20.7.1.1.15
-- 1.3.6.1.4.1.5875.800.20.7.1.1.15
		-- 1.3.6.1.4.1.5875.800.20.7.1.1.15
		potsProfileAction OBJECT-TYPE
			SYNTAX INTEGER
				{
				create(4),
				destory(6),
				modify(7)
				}
			MAX-ACCESS read-create
			STATUS current
			DESCRIPTION
				"4:create
				6:delete
				7:modify
				"
			::= { potsCfgProfileEntry 15 }

		
--   1.3.6.1.4.1.5875.800.20.7.2
-- 1.3.6.1.4.1.5875.800.20.7.2
		-- 1.3.6.1.4.1.5875.800.20.7.2
		nextPotsCfgProfileId OBJECT-TYPE
			SYNTAX Integer32
			MAX-ACCESS read-only
			STATUS current
			DESCRIPTION
				"Echo Suppression"
			::= { potsCfgProfile 2 }

		
--   1.3.6.1.4.1.5875.800.20.8
-- 1.3.6.1.4.1.5875.800.20.8
		-- 1.3.6.1.4.1.5875.800.20.8
		sipDigitmap OBJECT IDENTIFIER ::= { oltVoice 8 }

		
--   1.3.6.1.4.1.5875.800.20.8.1
-- 1.3.6.1.4.1.5875.800.20.8.1
		-- 1.3.6.1.4.1.5875.800.20.8.1
		digitmap OBJECT-TYPE
			SYNTAX OCTET STRING
			MAX-ACCESS read-write
			STATUS current
			DESCRIPTION
				"Numbering  scheme character strings"
			::= { sipDigitmap 1 }

		
--  1.3.6.1.4.1.5875.800.20.1002
		-- 1.3.6.1.4.1.5875.800.20.1002
		fhOltVoiceGroup OBJECT IDENTIFIER ::= { oltVoice 1002 }

		
--  1.3.6.1.4.1.5875.800.20.1002.1
		-- 1.3.6.1.4.1.5875.800.20.1002.1
		fhOltVoiceIndexGroup OBJECT-GROUP
			OBJECTS { signalProfileId, signalName, mgcProtocolType, mgc1Address, mgc1Port, 
				mgc2Address, mgc2Port, mgc3Address, mgc3Port, primaryDNS, 
				secondaryDNS, sipRegistrationAddress, sipRegistrationPort, sipServerAddress, sipServerPort, 
				sipTimeOut, keepAlive, aliveInterval, aliveTime, signalProfileAction, 
				nextSignalProfileId, potsEnable, telNum, bindingSignalName, signalVlan, 
				svlanEnable, svlanId, svlanCosFor5516, cvalnCosFor5516, voiceDomain, 
				protocolPort, userNameSipTelNum, sipUserName, sipPassword, bindingPotsCfgProfileName, 
				potsUserCfgAction, ipCfgType, staticIPAddress, staticIPMask, staticIPGateway, 
				pppoeUserName, pppoePassword, dhcpOption60Enable, dhcpOption60Suffix, bindingVoicePlatformProfileName, 
				voiceCfgAction, voicePlatformProfileId, voicePlatformProfileName, rtpNameFiexedPart, rtpBeginValue, 
				rtpEndValue, rtpStepValue, rtpNameFill, digitmapStartTimer, digitmapShortTimer, 
				digitmapLongTimer, dialMapNotifyImmediately, vbdEnable, packetIntervalOut, packetIntervalIn, 
				codeType, platformProfileAction, nextVoicePlatformProfileId, potsCfgProfileId, potsCfgProfileName, 
				voiceCoder, faxMode, slienceSwitch, echoCancel, inputGain, 
				outputGain, dtmfMode, faxCtrlMode, potsProfileAction, nextPotsCfgProfileId, 
				digitmap }
			STATUS current
			DESCRIPTION 
				"Description."
			::= { fhOltVoiceGroup 1 }

		
--  1.3.6.1.4.1.5875.800.20.1002.2
-- this module
		-- 1.3.6.1.4.1.5875.800.20.1002.2
		fhOltVoiceCompliance MODULE-COMPLIANCE
			STATUS current
			DESCRIPTION 
				"Description."
			MODULE -- this module
				MANDATORY-GROUPS { fhOltVoiceIndexGroup }
			::= { fhOltVoiceGroup 2 }

		
	
	END

--
-- GEPON-OLT-VOICE-MIB.my
--

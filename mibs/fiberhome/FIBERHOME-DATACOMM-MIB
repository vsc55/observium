--
-- FIBERHOME-DATACOMM-MIB.my
-- MIB generated by MG-SOFT Visual MIB Builder Version 6.0  Build 88
-- Wednesday, February 28, 2018 at 18:42:24
--


	FIBERHOME-DATACOMM-MIB DEFINITIONS ::= BEGIN
 
		IMPORTS
			entPhysicalIndex, PhysicalIndex			
				FROM ENTITY-MIB			
			ifIndex, InterfaceIndex			
				FROM IF-MIB			
			InetAddressType, InetAddress			
				FROM INET-ADDRESS-MIB			
			Ipv6Address			
				FROM IPV6-TC			
			OBJECT-GROUP, MODULE-COMPLIANCE, NOTIFICATION-GROUP			
				FROM SNMPv2-CONF			
			enterprises, TimeTicks, IpAddress, Integer32, Unsigned32, 
			Gauge32, Counter64, OBJECT-TYPE, MODULE-IDENTITY, NOTIFICATION-TYPE			
				FROM SNMPv2-SMI			
			DisplayString, PhysAddress, TEXTUAL-CONVENTION			
				FROM SNMPv2-TC;
	
	
		-- 1.3.6.1.4.1.11408.11.1
		fhDatacomm MODULE-IDENTITY 
			LAST-UPDATED "201802281842Z"		-- February 28, 2018 at 18:42:24 GMT
			ORGANIZATION 
				"fiberhome"
			CONTACT-INFO 
				"Fiberhome Telecommunication Technologies Co.,LTD.
				No.6,  Gaoxin 4th. Road , Wuhan, Hubei, P.R. China
				Zip:430073 
				Http://www.fiberhome.com                                       
				E-mail:support@fiberhome.com "
			DESCRIPTION 
				"The private mib file includes the general extent 
				information of the device."
			::= { fhMgmt 1 }

		
	
--
-- Textual conventions
--
	
--  1.3.6.1.4.1.11408.11.1
-- 
-- 
-- Textual conventions
-- 
--  1.3.6.1.4.1.11408.11.1
-- 
-- 
-- Textual conventions
-- 
		tcIpRanNeId ::= TEXTUAL-CONVENTION
			DISPLAY-HINT 
				"1d.1d.1d.1d"
			STATUS current
			DESCRIPTION 
				"Uniquely identify the network entity ID.
				The total valid length is 24 bit, 
				the high 8 bit is subnet number;
				the low 16 bit is base id;
				keep value range: subnet number should within 0x1-0xFE
				                  base id should within 0xBFF1-0xFFFE,
				valid value range: subnet number should within 0x1-0xFE,
				                   base id should within 0x1-0xBFEF,
				keep range will only use as factory value,
				in the running network must use the valid value.
				the IpRanNeId will be showed as 0.x.x.x."
			SYNTAX IpAddress

		MacAddress ::= TEXTUAL-CONVENTION
			DISPLAY-HINT 
				"1x:"
			STATUS current
			DESCRIPTION 
				"Represents an 802 MAC address represented in the
				`canonical' order defined by IEEE 802.1a, i.e., as if it
				were transmitted least significant bit first, even though
				802.5 (in contrast to other 802.x protocols) requires MAC
				addresses to be transmitted most significant bit first."
			SYNTAX OCTET STRING (SIZE (6))

	
--
-- Node definitions
--
	
--  Node definitions
-- 
-- Node definitions
-- 
-- 1.3.6.1.4.1.11408
-- 1.3.6.1.4.1.11408
		-- 1.3.6.1.4.1.11408
		fh OBJECT IDENTIFIER ::= { enterprises 11408 }

		
--   1.3.6.1.4.1.11408.11
-- 1.3.6.1.4.1.11408.11
		-- 1.3.6.1.4.1.11408.11
		fhMgmt OBJECT IDENTIFIER ::= { fh 11 }

		
--   1.3.6.1.4.1.11408.11.1.1
-- 1.3.6.1.4.1.11408.11.1.1
		-- 1.3.6.1.4.1.11408.11.1.1
		fhEntityExtentMIB OBJECT IDENTIFIER ::= { fhDatacomm 1 }

		
--   1.3.6.1.4.1.11408.11.1.1.1
-- 1.3.6.1.4.1.11408.11.1.1.1
		-- 1.3.6.1.4.1.11408.11.1.1.1
		fhEntityState OBJECT IDENTIFIER ::= { fhEntityExtentMIB 1 }

		
--   1.3.6.1.4.1.11408.11.1.1.1.1
-- 1.3.6.1.4.1.11408.11.1.1.1.1
		-- 1.3.6.1.4.1.11408.11.1.1.1.1
		fhEntityCpuUsage OBJECT-TYPE
			SYNTAX INTEGER (0..100)
			MAX-ACCESS read-only
			STATUS current
			DESCRIPTION
				"Description."
			::= { fhEntityState 1 }

		
--   1.3.6.1.4.1.11408.11.1.1.1.2
-- 1.3.6.1.4.1.11408.11.1.1.1.2
		-- 1.3.6.1.4.1.11408.11.1.1.1.2
		fhEntityMemUsage OBJECT-TYPE
			SYNTAX INTEGER (0..100)
			MAX-ACCESS read-only
			STATUS current
			DESCRIPTION
				"Description."
			::= { fhEntityState 2 }

		
--   1.3.6.1.4.1.11408.11.1.1.1.3
-- 1.3.6.1.4.1.11408.11.1.1.1.3
		-- 1.3.6.1.4.1.11408.11.1.1.1.3
		fhEntityBoardPfmTable OBJECT-TYPE
			SYNTAX SEQUENCE OF fhEntityBoardPfmEntry
			MAX-ACCESS not-accessible
			STATUS current
			DESCRIPTION
				"Description."
			::= { fhEntityState 3 }

		
--   1.3.6.1.4.1.11408.11.1.1.1.3.1
-- 1.3.6.1.4.1.11408.11.1.1.1.3.1
		-- 1.3.6.1.4.1.11408.11.1.1.1.3.1
		fhEntityBoardPfmEntry OBJECT-TYPE
			SYNTAX fhEntityBoardPfmEntry
			MAX-ACCESS not-accessible
			STATUS current
			DESCRIPTION
				"Description."
			INDEX { INTEGER }
			::= { fhEntityBoardPfmTable 1 }

		
		fhEntityBoardPfmEntry ::=
			SEQUENCE { 
				fhBoardIndex
					INTEGER,
				fhBoardNo
					INTEGER,
				fhBoardTemperature
					OCTET STRING,
				fhBoardVoltage
					OCTET STRING,
				fhEntityBoardIntfCount
					INTEGER
			 }

--   1.3.6.1.4.1.11408.11.1.1.1.3.1.1
-- 1.3.6.1.4.1.11408.11.1.1.1.3.1.1
		-- 1.3.6.1.4.1.11408.11.1.1.1.3.1.1
		fhBoardIndex OBJECT-TYPE
			SYNTAX INTEGER
			MAX-ACCESS read-only
			STATUS current
			DESCRIPTION
				"Description."
			::= { fhEntityBoardPfmEntry 1 }

		
--   1.3.6.1.4.1.11408.11.1.1.1.3.1.2
-- 1.3.6.1.4.1.11408.11.1.1.1.3.1.2
		-- 1.3.6.1.4.1.11408.11.1.1.1.3.1.2
		fhBoardNo OBJECT-TYPE
			SYNTAX INTEGER
			MAX-ACCESS read-only
			STATUS current
			DESCRIPTION
				"Description."
			::= { fhEntityBoardPfmEntry 2 }

		
--   1.3.6.1.4.1.11408.11.1.1.1.3.1.3
-- 1.3.6.1.4.1.11408.11.1.1.1.3.1.3
		-- 1.3.6.1.4.1.11408.11.1.1.1.3.1.3
		fhBoardTemperature OBJECT-TYPE
			SYNTAX OCTET STRING
			MAX-ACCESS read-only
			STATUS current
			DESCRIPTION
				"Description."
			::= { fhEntityBoardPfmEntry 3 }

		
--   1.3.6.1.4.1.11408.11.1.1.1.3.1.4
-- 1.3.6.1.4.1.11408.11.1.1.1.3.1.4
		-- 1.3.6.1.4.1.11408.11.1.1.1.3.1.4
		fhBoardVoltage OBJECT-TYPE
			SYNTAX OCTET STRING
			MAX-ACCESS read-only
			STATUS current
			DESCRIPTION
				"Description."
			::= { fhEntityBoardPfmEntry 4 }

		
--   1.3.6.1.4.1.11408.11.1.1.1.3.1.5
-- 1.3.6.1.4.1.11408.11.1.1.1.3.1.5
		-- 1.3.6.1.4.1.11408.11.1.1.1.3.1.5
		fhEntityBoardIntfCount OBJECT-TYPE
			SYNTAX INTEGER
			MAX-ACCESS read-only
			STATUS current
			DESCRIPTION
				"Description."
			::= { fhEntityBoardPfmEntry 5 }

		
--   1.3.6.1.4.1.11408.11.1.1.1.4
-- 1.3.6.1.4.1.11408.11.1.1.1.4
		-- 1.3.6.1.4.1.11408.11.1.1.1.4
		fhEntityIfPfmTable OBJECT-TYPE
			SYNTAX SEQUENCE OF fhEntityIfPfmEntry
			MAX-ACCESS not-accessible
			STATUS current
			DESCRIPTION
				"Description."
			::= { fhEntityState 4 }

		
--   1.3.6.1.4.1.11408.11.1.1.1.4.1
-- 1.3.6.1.4.1.11408.11.1.1.1.4.1
		-- 1.3.6.1.4.1.11408.11.1.1.1.4.1
		fhEntityIfPfmEntry OBJECT-TYPE
			SYNTAX fhEntityIfPfmEntry
			MAX-ACCESS not-accessible
			STATUS current
			DESCRIPTION
				"Description."
			INDEX { INTEGER }
			::= { fhEntityIfPfmTable 1 }

		
		fhEntityIfPfmEntry ::=
			SEQUENCE { 
				fhIfIndex
					INTEGER,
				fhIfSnr
					OCTET STRING,
				fhIfMacAccount
					OCTET STRING
			 }

--   1.3.6.1.4.1.11408.11.1.1.1.4.1.1
-- 1.3.6.1.4.1.11408.11.1.1.1.4.1.1
		-- 1.3.6.1.4.1.11408.11.1.1.1.4.1.1
		fhIfIndex OBJECT-TYPE
			SYNTAX INTEGER
			MAX-ACCESS read-only
			STATUS current
			DESCRIPTION
				"Description."
			::= { fhEntityIfPfmEntry 1 }

		
--   1.3.6.1.4.1.11408.11.1.1.1.4.1.2
-- 1.3.6.1.4.1.11408.11.1.1.1.4.1.2
		-- 1.3.6.1.4.1.11408.11.1.1.1.4.1.2
		fhIfSnr OBJECT-TYPE
			SYNTAX OCTET STRING
			MAX-ACCESS read-only
			STATUS current
			DESCRIPTION
				"Description."
			::= { fhEntityIfPfmEntry 2 }

		
--   1.3.6.1.4.1.11408.11.1.1.1.4.1.3
-- 1.3.6.1.4.1.11408.11.1.1.1.4.1.3
		-- 1.3.6.1.4.1.11408.11.1.1.1.4.1.3
		fhIfMacAccount OBJECT-TYPE
			SYNTAX OCTET STRING
			MAX-ACCESS read-only
			STATUS current
			DESCRIPTION
				"Description."
			::= { fhEntityIfPfmEntry 3 }

		
--   1.3.6.1.4.1.11408.11.1.1.1.5
-- 1.3.6.1.4.1.11408.11.1.1.1.5
		-- 1.3.6.1.4.1.11408.11.1.1.1.5
		fhEntityIfinfoTable OBJECT-TYPE
			SYNTAX SEQUENCE OF fhEntityIfinfoEntry
			MAX-ACCESS not-accessible
			STATUS current
			DESCRIPTION
				"Description."
			::= { fhEntityState 5 }

		
--   1.3.6.1.4.1.11408.11.1.1.1.5.1
-- 1.3.6.1.4.1.11408.11.1.1.1.5.1
		-- 1.3.6.1.4.1.11408.11.1.1.1.5.1
		fhEntityIfinfoEntry OBJECT-TYPE
			SYNTAX fhEntityIfinfoEntry
			MAX-ACCESS not-accessible
			STATUS current
			DESCRIPTION
				"Description."
			INDEX { INTEGER }
			::= { fhEntityIfinfoTable 1 }

		
		fhEntityIfinfoEntry ::=
			SEQUENCE { 
				fhSlotNo
					INTEGER,
				fhSubSlotNO
					INTEGER,
				fhBoardName
					OCTET STRING,
				fhIfName
					OCTET STRING,
				fhBoardType
					INTEGER,
				fhBoardStatus
					INTEGER,
				fhStatus
					INTEGER,
				fhPortNo
					INTEGER
			 }

--   1.3.6.1.4.1.11408.11.1.1.1.5.1.1
-- 1.3.6.1.4.1.11408.11.1.1.1.5.1.1
		-- 1.3.6.1.4.1.11408.11.1.1.1.5.1.1
		fhSlotNo OBJECT-TYPE
			SYNTAX INTEGER
			MAX-ACCESS read-only
			STATUS current
			DESCRIPTION
				"Description."
			::= { fhEntityIfinfoEntry 1 }

		
--   1.3.6.1.4.1.11408.11.1.1.1.5.1.2
-- 1.3.6.1.4.1.11408.11.1.1.1.5.1.2
		-- 1.3.6.1.4.1.11408.11.1.1.1.5.1.2
		fhSubSlotNO OBJECT-TYPE
			SYNTAX INTEGER
			MAX-ACCESS read-only
			STATUS current
			DESCRIPTION
				"Description."
			::= { fhEntityIfinfoEntry 2 }

		
--   1.3.6.1.4.1.11408.11.1.1.1.5.1.3
-- 1.3.6.1.4.1.11408.11.1.1.1.5.1.3
		-- 1.3.6.1.4.1.11408.11.1.1.1.5.1.3
		fhBoardName OBJECT-TYPE
			SYNTAX OCTET STRING
			MAX-ACCESS read-only
			STATUS current
			DESCRIPTION
				"Description."
			::= { fhEntityIfinfoEntry 3 }

		
--   1.3.6.1.4.1.11408.11.1.1.1.5.1.4
-- 1.3.6.1.4.1.11408.11.1.1.1.5.1.4
		-- 1.3.6.1.4.1.11408.11.1.1.1.5.1.4
		fhIfName OBJECT-TYPE
			SYNTAX OCTET STRING
			MAX-ACCESS read-only
			STATUS current
			DESCRIPTION
				"Description."
			::= { fhEntityIfinfoEntry 4 }

		
--   1.3.6.1.4.1.11408.11.1.1.1.5.1.5
-- 1.3.6.1.4.1.11408.11.1.1.1.5.1.5
		-- 1.3.6.1.4.1.11408.11.1.1.1.5.1.5
		fhBoardType OBJECT-TYPE
			SYNTAX INTEGER
			MAX-ACCESS read-only
			STATUS current
			DESCRIPTION
				"Description."
			::= { fhEntityIfinfoEntry 5 }

		
--   1.3.6.1.4.1.11408.11.1.1.1.5.1.6
-- 1.3.6.1.4.1.11408.11.1.1.1.5.1.6
		-- 1.3.6.1.4.1.11408.11.1.1.1.5.1.6
		fhBoardStatus OBJECT-TYPE
			SYNTAX INTEGER
			MAX-ACCESS read-only
			STATUS current
			DESCRIPTION
				"Description."
			::= { fhEntityIfinfoEntry 6 }

		
--   1.3.6.1.4.1.11408.11.1.1.1.5.1.7
-- 1.3.6.1.4.1.11408.11.1.1.1.5.1.7
		-- 1.3.6.1.4.1.11408.11.1.1.1.5.1.7
		fhStatus OBJECT-TYPE
			SYNTAX INTEGER
			MAX-ACCESS read-only
			STATUS current
			DESCRIPTION
				"Description."
			::= { fhEntityIfinfoEntry 7 }

		
--   1.3.6.1.4.1.11408.11.1.1.1.5.1.8
-- 1.3.6.1.4.1.11408.11.1.1.1.5.1.8
		-- 1.3.6.1.4.1.11408.11.1.1.1.5.1.8
		fhPortNo OBJECT-TYPE
			SYNTAX INTEGER
			MAX-ACCESS read-only
			STATUS current
			DESCRIPTION
				"Description."
			::= { fhEntityIfinfoEntry 8 }

		
--   1.3.6.1.4.1.11408.11.1.1.1.6
-- 1.3.6.1.4.1.11408.11.1.1.1.6
		-- 1.3.6.1.4.1.11408.11.1.1.1.6
		fhEntityPowerStatus OBJECT-TYPE
			SYNTAX OCTET STRING
			MAX-ACCESS read-only
			STATUS current
			DESCRIPTION
				"Description."
			::= { fhEntityState 6 }

		
--   1.3.6.1.4.1.11408.11.1.1.1.7
-- 1.3.6.1.4.1.11408.11.1.1.1.7
		-- 1.3.6.1.4.1.11408.11.1.1.1.7
		fhEntityPowerVoltage OBJECT-TYPE
			SYNTAX OCTET STRING
			MAX-ACCESS read-only
			STATUS current
			DESCRIPTION
				"Description."
			::= { fhEntityState 7 }

		
--   1.3.6.1.4.1.11408.11.1.1.1.8
-- 1.3.6.1.4.1.11408.11.1.1.1.8
		-- 1.3.6.1.4.1.11408.11.1.1.1.8
		fhEntityCurrent OBJECT-TYPE
			SYNTAX OCTET STRING
			MAX-ACCESS read-only
			STATUS current
			DESCRIPTION
				"Description."
			::= { fhEntityState 8 }

		
--   1.3.6.1.4.1.11408.11.1.1.1.9
-- 1.3.6.1.4.1.11408.11.1.1.1.9
		-- 1.3.6.1.4.1.11408.11.1.1.1.9
		fhEntityPower OBJECT-TYPE
			SYNTAX OCTET STRING
			MAX-ACCESS read-only
			STATUS current
			DESCRIPTION
				"Description."
			::= { fhEntityState 9 }

		
--   1.3.6.1.4.1.11408.11.1.1.1.10
-- 1.3.6.1.4.1.11408.11.1.1.1.10
		-- 1.3.6.1.4.1.11408.11.1.1.1.10
		fhEntityFanStatus OBJECT-TYPE
			SYNTAX OCTET STRING
			MAX-ACCESS read-only
			STATUS current
			DESCRIPTION
				"Description."
			::= { fhEntityState 10 }

		
		-- 1.3.6.1.4.1.11408.11.1.1.1.11
		fhEntityDiskUsage OBJECT-TYPE
			SYNTAX OCTET STRING
			MAX-ACCESS read-only
			STATUS current
			DESCRIPTION
				"Description."
			::= { fhEntityState 11 }

		
		-- 1.3.6.1.4.1.11408.11.1.1.1.12
		fhEntityFanSpeed OBJECT-TYPE
			SYNTAX OCTET STRING
			MAX-ACCESS read-only
			STATUS current
			DESCRIPTION
				"Description."
			::= { fhEntityState 12 }

		
		-- 1.3.6.1.4.1.11408.11.1.1.1.13
		fhEntityTemp OBJECT-TYPE
			SYNTAX OCTET STRING
			MAX-ACCESS read-only
			STATUS current
			DESCRIPTION
				"Description."
			::= { fhEntityState 13 }

		
		-- 1.3.6.1.4.1.11408.11.1.1.1.14
		fhEntityMemorySize OBJECT-TYPE
			SYNTAX OCTET STRING
			MAX-ACCESS read-only
			STATUS current
			DESCRIPTION
				"Description."
			::= { fhEntityState 14 }

		
		-- 1.3.6.1.4.1.11408.11.1.1.1.15
		fhEntityDiskSize OBJECT-TYPE
			SYNTAX OCTET STRING
			MAX-ACCESS read-only
			STATUS current
			DESCRIPTION
				"Description."
			::= { fhEntityState 15 }

		
		-- 1.3.6.1.4.1.11408.11.1.1.1.16
		fhEntitySn OBJECT-TYPE
			SYNTAX OCTET STRING
			MAX-ACCESS read-only
			STATUS current
			DESCRIPTION
				"Description."
			::= { fhEntityState 16 }

		
		-- 1.3.6.1.4.1.11408.11.1.1.1.17
		fhEntityOsVersion OBJECT-TYPE
			SYNTAX OCTET STRING
			MAX-ACCESS read-only
			STATUS current
			DESCRIPTION
				"Description."
			::= { fhEntityState 17 }

		
		-- 1.3.6.1.4.1.11408.11.1.1.1.18
		fhEntityCpuFrequency OBJECT-TYPE
			SYNTAX OCTET STRING
			MAX-ACCESS read-only
			STATUS current
			DESCRIPTION
				"Description."
			::= { fhEntityState 18 }

		
--   1.3.6.1.4.1.11408.11.1.1.2
-- 1.3.6.1.4.1.11408.11.1.1.2
		-- 1.3.6.1.4.1.11408.11.1.1.2
		fhEntityOpticalModuleInfoTable OBJECT-TYPE
			SYNTAX SEQUENCE OF FhEntityOpticalModuleInfoEntry
			MAX-ACCESS not-accessible
			STATUS current
			DESCRIPTION
				"Description."
			::= { fhEntityExtentMIB 2 }

		
--   1.3.6.1.4.1.11408.11.1.1.2.1
-- 1.3.6.1.4.1.11408.11.1.1.2.1
		-- 1.3.6.1.4.1.11408.11.1.1.2.1
		fhEntityOpticalModuleInfoEntry OBJECT-TYPE
			SYNTAX FhEntityOpticalModuleInfoEntry
			MAX-ACCESS not-accessible
			STATUS current
			DESCRIPTION
				"Description."
			INDEX { entPhysicalIndex }
			::= { fhEntityOpticalModuleInfoTable 1 }

		
		FhEntityOpticalModuleInfoEntry ::=
			SEQUENCE { 
				fhEntityOpticalIndex
					INTEGER,
				fhEntityOpticalMode
					INTEGER,
				fhEntityOpticalWavelength
					INTEGER,
				fhEntityOpticalTransDistance
					INTEGER,
				fhEntityOpticalMediaType
					INTEGER,
				fhEntityRxOpticalPower
					INTEGER,
				fhEntityTxOpticalPower
					INTEGER,
				fhEntityOpticalRxLowThreshold
					INTEGER,
				fhEntityOpticalRxHighThreshold
					INTEGER,
				fhEntityOpticalTxLowThreshold
					INTEGER,
				fhEntityOpticalTxHighThreshold
					INTEGER,
				fhEntityOpticalSpeed
					OCTET STRING,
				fhEntityOpticalHardwareType
					Integer32,
				fhEntityOpticalVendorName
					OCTET STRING,
				fhEntityOpticalSerialNumber
					OCTET STRING,
				fhEntityOpticalFiberDiameterType
					Integer32,
				fhEntityOpticalTemperature
					Integer32,
				fhEntityOpticalVoltage
					Integer32,
				fhEntityOpticalBiasCurrent
					Integer32
			 }

--   1.3.6.1.4.1.11408.11.1.1.2.1.1
-- 1.3.6.1.4.1.11408.11.1.1.2.1.1
		-- 1.3.6.1.4.1.11408.11.1.1.2.1.1
		fhEntityOpticalIndex OBJECT-TYPE
			SYNTAX INTEGER
			MAX-ACCESS read-only
			STATUS current
			DESCRIPTION
				"Description."
			::= { fhEntityOpticalModuleInfoEntry 1 }

		
--   1.3.6.1.4.1.11408.11.1.1.2.1.2
-- 1.3.6.1.4.1.11408.11.1.1.2.1.2
		-- 1.3.6.1.4.1.11408.11.1.1.2.1.2
		fhEntityOpticalMode OBJECT-TYPE
			SYNTAX INTEGER
			MAX-ACCESS read-only
			STATUS current
			DESCRIPTION
				"Description."
			::= { fhEntityOpticalModuleInfoEntry 2 }

		
--   1.3.6.1.4.1.11408.11.1.1.2.1.3
-- 1.3.6.1.4.1.11408.11.1.1.2.1.3
		-- 1.3.6.1.4.1.11408.11.1.1.2.1.3
		fhEntityOpticalWavelength OBJECT-TYPE
			SYNTAX INTEGER
			MAX-ACCESS read-only
			STATUS current
			DESCRIPTION
				"Description."
			::= { fhEntityOpticalModuleInfoEntry 3 }

		
--   1.3.6.1.4.1.11408.11.1.1.2.1.4
-- 1.3.6.1.4.1.11408.11.1.1.2.1.4
		-- 1.3.6.1.4.1.11408.11.1.1.2.1.4
		fhEntityOpticalTransDistance OBJECT-TYPE
			SYNTAX INTEGER
			MAX-ACCESS read-only
			STATUS current
			DESCRIPTION
				"Description."
			::= { fhEntityOpticalModuleInfoEntry 4 }

		
--   1.3.6.1.4.1.11408.11.1.1.2.1.5
-- 1.3.6.1.4.1.11408.11.1.1.2.1.5
		-- 1.3.6.1.4.1.11408.11.1.1.2.1.5
		fhEntityOpticalMediaType OBJECT-TYPE
			SYNTAX INTEGER
			MAX-ACCESS read-only
			STATUS current
			DESCRIPTION
				"Description."
			::= { fhEntityOpticalModuleInfoEntry 5 }

		
--   1.3.6.1.4.1.11408.11.1.1.2.1.6
-- 1.3.6.1.4.1.11408.11.1.1.2.1.6
		-- 1.3.6.1.4.1.11408.11.1.1.2.1.6
		fhEntityRxOpticalPower OBJECT-TYPE
			SYNTAX INTEGER
			MAX-ACCESS read-only
			STATUS current
			DESCRIPTION
				"Description."
			::= { fhEntityOpticalModuleInfoEntry 6 }

		
--   1.3.6.1.4.1.11408.11.1.1.2.1.7
-- 1.3.6.1.4.1.11408.11.1.1.2.1.7
		-- 1.3.6.1.4.1.11408.11.1.1.2.1.7
		fhEntityTxOpticalPower OBJECT-TYPE
			SYNTAX INTEGER
			MAX-ACCESS read-only
			STATUS current
			DESCRIPTION
				"Description."
			::= { fhEntityOpticalModuleInfoEntry 7 }

		
--   1.3.6.1.4.1.11408.11.1.1.2.1.8
-- 1.3.6.1.4.1.11408.11.1.1.2.1.8
		-- 1.3.6.1.4.1.11408.11.1.1.2.1.8
		fhEntityOpticalRxLowThreshold OBJECT-TYPE
			SYNTAX INTEGER
			MAX-ACCESS read-write
			STATUS current
			DESCRIPTION
				"Description."
			::= { fhEntityOpticalModuleInfoEntry 8 }

		
--   1.3.6.1.4.1.11408.11.1.1.2.1.9
-- 1.3.6.1.4.1.11408.11.1.1.2.1.9
		-- 1.3.6.1.4.1.11408.11.1.1.2.1.9
		fhEntityOpticalRxHighThreshold OBJECT-TYPE
			SYNTAX INTEGER
			MAX-ACCESS read-write
			STATUS current
			DESCRIPTION
				"Description."
			::= { fhEntityOpticalModuleInfoEntry 9 }

		
--   1.3.6.1.4.1.11408.11.1.1.2.1.10
-- 1.3.6.1.4.1.11408.11.1.1.2.1.10
		-- 1.3.6.1.4.1.11408.11.1.1.2.1.10
		fhEntityOpticalTxLowThreshold OBJECT-TYPE
			SYNTAX INTEGER
			MAX-ACCESS read-write
			STATUS current
			DESCRIPTION
				"Description."
			::= { fhEntityOpticalModuleInfoEntry 10 }

		
--   1.3.6.1.4.1.11408.11.1.1.2.1.11
-- 1.3.6.1.4.1.11408.11.1.1.2.1.11
		-- 1.3.6.1.4.1.11408.11.1.1.2.1.11
		fhEntityOpticalTxHighThreshold OBJECT-TYPE
			SYNTAX INTEGER
			MAX-ACCESS read-write
			STATUS current
			DESCRIPTION
				"Description."
			::= { fhEntityOpticalModuleInfoEntry 11 }

		
--   1.3.6.1.4.1.11408.11.1.1.2.1.12
-- 1.3.6.1.4.1.11408.11.1.1.2.1.12
		-- 1.3.6.1.4.1.11408.11.1.1.2.1.12
		fhEntityOpticalSpeed OBJECT-TYPE
			SYNTAX OCTET STRING
			MAX-ACCESS read-write
			STATUS current
			DESCRIPTION
				"Description."
			::= { fhEntityOpticalModuleInfoEntry 12 }

		
--   1.3.6.1.4.1.11408.11.1.1.2.1.13
-- 1.3.6.1.4.1.11408.11.1.1.2.1.13
		-- 1.3.6.1.4.1.11408.11.1.1.2.1.13
		fhEntityOpticalHardwareType OBJECT-TYPE
			SYNTAX Integer32
			MAX-ACCESS read-write
			STATUS current
			DESCRIPTION
				"Description."
			::= { fhEntityOpticalModuleInfoEntry 13 }

		
--   1.3.6.1.4.1.11408.11.1.1.2.1.14
-- 1.3.6.1.4.1.11408.11.1.1.2.1.14
		-- 1.3.6.1.4.1.11408.11.1.1.2.1.14
		fhEntityOpticalVendorName OBJECT-TYPE
			SYNTAX OCTET STRING
			MAX-ACCESS read-write
			STATUS current
			DESCRIPTION
				"Description."
			::= { fhEntityOpticalModuleInfoEntry 14 }

		
--   1.3.6.1.4.1.11408.11.1.1.2.1.15
-- 1.3.6.1.4.1.11408.11.1.1.2.1.15
		-- 1.3.6.1.4.1.11408.11.1.1.2.1.15
		fhEntityOpticalSerialNumber OBJECT-TYPE
			SYNTAX OCTET STRING
			MAX-ACCESS read-write
			STATUS current
			DESCRIPTION
				"Description."
			::= { fhEntityOpticalModuleInfoEntry 15 }

		
--   1.3.6.1.4.1.11408.11.1.1.2.1.16
-- 1.3.6.1.4.1.11408.11.1.1.2.1.16
		-- 1.3.6.1.4.1.11408.11.1.1.2.1.16
		fhEntityOpticalFiberDiameterType OBJECT-TYPE
			SYNTAX Integer32
			MAX-ACCESS read-write
			STATUS current
			DESCRIPTION
				"Description."
			::= { fhEntityOpticalModuleInfoEntry 16 }

		
--   1.3.6.1.4.1.11408.11.1.1.2.1.17
-- 1.3.6.1.4.1.11408.11.1.1.2.1.17
		-- 1.3.6.1.4.1.11408.11.1.1.2.1.17
		fhEntityOpticalTemperature OBJECT-TYPE
			SYNTAX Integer32
			MAX-ACCESS read-write
			STATUS current
			DESCRIPTION
				"Description."
			::= { fhEntityOpticalModuleInfoEntry 17 }

		
--   1.3.6.1.4.1.11408.11.1.1.2.1.18
-- 1.3.6.1.4.1.11408.11.1.1.2.1.18
		-- 1.3.6.1.4.1.11408.11.1.1.2.1.18
		fhEntityOpticalVoltage OBJECT-TYPE
			SYNTAX Integer32
			MAX-ACCESS read-write
			STATUS current
			DESCRIPTION
				"Description."
			::= { fhEntityOpticalModuleInfoEntry 18 }

		
--   1.3.6.1.4.1.11408.11.1.1.2.1.19
-- 1.3.6.1.4.1.11408.11.1.1.2.1.19
		-- 1.3.6.1.4.1.11408.11.1.1.2.1.19
		fhEntityOpticalBiasCurrent OBJECT-TYPE
			SYNTAX Integer32
			MAX-ACCESS read-write
			STATUS current
			DESCRIPTION
				"Description."
			::= { fhEntityOpticalModuleInfoEntry 19 }

		
--   1.3.6.1.4.1.11408.11.1.1.3
-- 1.3.6.1.4.1.11408.11.1.1.3
		-- 1.3.6.1.4.1.11408.11.1.1.3
		fhEntitySlotInfoTable OBJECT-TYPE
			SYNTAX SEQUENCE OF FhEntitySlotInfoEntry
			MAX-ACCESS not-accessible
			STATUS current
			DESCRIPTION
				"Description."
			::= { fhEntityExtentMIB 3 }

		
--   1.3.6.1.4.1.11408.11.1.1.3.1
-- 1.3.6.1.4.1.11408.11.1.1.3.1
		-- 1.3.6.1.4.1.11408.11.1.1.3.1
		fhEntitySlotInfoEntry OBJECT-TYPE
			SYNTAX FhEntitySlotInfoEntry
			MAX-ACCESS not-accessible
			STATUS current
			DESCRIPTION
				"Description."
			INDEX { fhSlotEntityIndex }
			::= { fhEntitySlotInfoTable 1 }

		
		FhEntitySlotInfoEntry ::=
			SEQUENCE { 
				fhSlotEntityIndex
					PhysicalIndex,
				fhSlotEntityNo
					INTEGER,
				fhSlotType
					OCTET STRING,
				fhSlotName
					OCTET STRING,
				fhSlotOccupyStatus
					OCTET STRING,
				fhSlotFabricNumber
					OCTET STRING
			 }

--   1.3.6.1.4.1.11408.11.1.1.3.1.1
-- 1.3.6.1.4.1.11408.11.1.1.3.1.1
		-- 1.3.6.1.4.1.11408.11.1.1.3.1.1
		fhSlotEntityIndex OBJECT-TYPE
			SYNTAX PhysicalIndex
			MAX-ACCESS not-accessible
			STATUS current
			DESCRIPTION
				"Description."
			::= { fhEntitySlotInfoEntry 1 }

		
--   1.3.6.1.4.1.11408.11.1.1.3.1.2
-- 1.3.6.1.4.1.11408.11.1.1.3.1.2
		-- 1.3.6.1.4.1.11408.11.1.1.3.1.2
		fhSlotEntityNo OBJECT-TYPE
			SYNTAX INTEGER
			MAX-ACCESS not-accessible
			STATUS current
			DESCRIPTION
				"Description."
			::= { fhEntitySlotInfoEntry 2 }

		
--   1.3.6.1.4.1.11408.11.1.1.3.1.3
-- 1.3.6.1.4.1.11408.11.1.1.3.1.3
		-- 1.3.6.1.4.1.11408.11.1.1.3.1.3
		fhSlotType OBJECT-TYPE
			SYNTAX OCTET STRING
			MAX-ACCESS read-only
			STATUS current
			DESCRIPTION
				"Description."
			::= { fhEntitySlotInfoEntry 3 }

		
--   1.3.6.1.4.1.11408.11.1.1.3.1.4
-- 1.3.6.1.4.1.11408.11.1.1.3.1.4
		-- 1.3.6.1.4.1.11408.11.1.1.3.1.4
		fhSlotName OBJECT-TYPE
			SYNTAX OCTET STRING
			MAX-ACCESS read-only
			STATUS current
			DESCRIPTION
				"Description."
			::= { fhEntitySlotInfoEntry 4 }

		
--   1.3.6.1.4.1.11408.11.1.1.3.1.5
-- 1.3.6.1.4.1.11408.11.1.1.3.1.5
		-- 1.3.6.1.4.1.11408.11.1.1.3.1.5
		fhSlotOccupyStatus OBJECT-TYPE
			SYNTAX OCTET STRING
			MAX-ACCESS read-only
			STATUS current
			DESCRIPTION
				"Description."
			::= { fhEntitySlotInfoEntry 5 }

		
--   1.3.6.1.4.1.11408.11.1.1.3.1.6
-- 1.3.6.1.4.1.11408.11.1.1.3.1.6
		-- 1.3.6.1.4.1.11408.11.1.1.3.1.6
		fhSlotFabricNumber OBJECT-TYPE
			SYNTAX OCTET STRING
			MAX-ACCESS read-only
			STATUS current
			DESCRIPTION
				"Description."
			::= { fhEntitySlotInfoEntry 6 }

		
--   1.3.6.1.4.1.11408.11.1.1.4
-- 1.3.6.1.4.1.11408.11.1.1.4
		-- 1.3.6.1.4.1.11408.11.1.1.4
		fhEntityBoardInfoTable OBJECT-TYPE
			SYNTAX SEQUENCE OF FhEntityBoardInfoEntry
			MAX-ACCESS not-accessible
			STATUS current
			DESCRIPTION
				"Description."
			::= { fhEntityExtentMIB 4 }

		
--   1.3.6.1.4.1.11408.11.1.1.4.1
-- 1.3.6.1.4.1.11408.11.1.1.4.1
		-- 1.3.6.1.4.1.11408.11.1.1.4.1
		fhEntityBoardInfoEntry OBJECT-TYPE
			SYNTAX FhEntityBoardInfoEntry
			MAX-ACCESS not-accessible
			STATUS current
			DESCRIPTION
				"Description."
			INDEX { fhBoardEntityIndex }
			::= { fhEntityBoardInfoTable 1 }

		
		FhEntityBoardInfoEntry ::=
			SEQUENCE { 
				fhBoardEntityIndex
					PhysicalIndex,
				fhBoardEntityNo
					PhysicalIndex,
				fhBoardHWIndex
					OCTET STRING,
				fhBoardSequence
					OCTET STRING,
				fhBoardType
					OCTET STRING,
				fhBoardDescr
					OCTET STRING,
				fhBoardParentType
					OCTET STRING,
				fhBoardHardwareRev
					OCTET STRING,
				fhBoardSlotSeq
					INTEGER,
				fhBoardSlotNum
					INTEGER,
				fhBoardOperStatus
					OCTET STRING,
				fhBoardWarrantyExpireDate
					OCTET STRING,
				fhBoardWarrantyObligor
					OCTET STRING,
				fhBoardFabricNumber
					OCTET STRING,
				fhComponentNumber
					OCTET STRING,
				fhHardwareModel
					OCTET STRING,
				fhHardwareClass
					OCTET STRING,
				fhHardwareIdentifier
					OCTET STRING,
				fhHardwareType
					OCTET STRING,
				fhBoardNumber
					OCTET STRING,
				fhPropertyLabel
					OCTET STRING,
				fhBoardIdleStatus
					INTEGER
			 }

--   1.3.6.1.4.1.11408.11.1.1.4.1.1
-- 1.3.6.1.4.1.11408.11.1.1.4.1.1
		-- 1.3.6.1.4.1.11408.11.1.1.4.1.1
		fhBoardEntityIndex OBJECT-TYPE
			SYNTAX PhysicalIndex
			MAX-ACCESS read-write
			STATUS current
			DESCRIPTION
				"Description."
			::= { fhEntityBoardInfoEntry 1 }

		
--   1.3.6.1.4.1.11408.11.1.1.4.1.2
-- 1.3.6.1.4.1.11408.11.1.1.4.1.2
		-- 1.3.6.1.4.1.11408.11.1.1.4.1.2
		fhBoardEntityNo OBJECT-TYPE
			SYNTAX PhysicalIndex
			MAX-ACCESS read-write
			STATUS current
			DESCRIPTION
				"Description."
			::= { fhEntityBoardInfoEntry 2 }

		
--   1.3.6.1.4.1.11408.11.1.1.4.1.3
-- 1.3.6.1.4.1.11408.11.1.1.4.1.3
		-- 1.3.6.1.4.1.11408.11.1.1.4.1.3
		fhBoardHWIndex OBJECT-TYPE
			SYNTAX OCTET STRING
			MAX-ACCESS read-write
			STATUS current
			DESCRIPTION
				"Description."
			::= { fhEntityBoardInfoEntry 3 }

		
--   1.3.6.1.4.1.11408.11.1.1.4.1.4
-- 1.3.6.1.4.1.11408.11.1.1.4.1.4
		-- 1.3.6.1.4.1.11408.11.1.1.4.1.4
		fhBoardSequence OBJECT-TYPE
			SYNTAX OCTET STRING
			MAX-ACCESS read-only
			STATUS current
			DESCRIPTION
				"Description."
			::= { fhEntityBoardInfoEntry 4 }

		
--   1.3.6.1.4.1.11408.11.1.1.4.1.5
-- 1.3.6.1.4.1.11408.11.1.1.4.1.5
		-- 1.3.6.1.4.1.11408.11.1.1.4.1.5
		fhBoardType OBJECT-TYPE
			SYNTAX OCTET STRING
			MAX-ACCESS read-only
			STATUS current
			DESCRIPTION
				"Description."
			::= { fhEntityBoardInfoEntry 5 }

		
--   1.3.6.1.4.1.11408.11.1.1.4.1.6
-- 1.3.6.1.4.1.11408.11.1.1.4.1.6
		-- 1.3.6.1.4.1.11408.11.1.1.4.1.6
		fhBoardDescr OBJECT-TYPE
			SYNTAX OCTET STRING
			MAX-ACCESS read-only
			STATUS current
			DESCRIPTION
				"Description."
			::= { fhEntityBoardInfoEntry 6 }

		
--   1.3.6.1.4.1.11408.11.1.1.4.1.7
-- 1.3.6.1.4.1.11408.11.1.1.4.1.7
		-- 1.3.6.1.4.1.11408.11.1.1.4.1.7
		fhBoardParentType OBJECT-TYPE
			SYNTAX OCTET STRING
			MAX-ACCESS read-only
			STATUS current
			DESCRIPTION
				"Description."
			::= { fhEntityBoardInfoEntry 7 }

		
--   1.3.6.1.4.1.11408.11.1.1.4.1.8
-- 1.3.6.1.4.1.11408.11.1.1.4.1.8
		-- 1.3.6.1.4.1.11408.11.1.1.4.1.8
		fhBoardHardwareRev OBJECT-TYPE
			SYNTAX OCTET STRING
			MAX-ACCESS read-only
			STATUS current
			DESCRIPTION
				"Description."
			::= { fhEntityBoardInfoEntry 8 }

		
--   1.3.6.1.4.1.11408.11.1.1.4.1.9
-- 1.3.6.1.4.1.11408.11.1.1.4.1.9
		-- 1.3.6.1.4.1.11408.11.1.1.4.1.9
		fhBoardSlotSeq OBJECT-TYPE
			SYNTAX INTEGER
			MAX-ACCESS read-only
			STATUS current
			DESCRIPTION
				"Description."
			::= { fhEntityBoardInfoEntry 9 }

		
--   1.3.6.1.4.1.11408.11.1.1.4.1.10
-- 1.3.6.1.4.1.11408.11.1.1.4.1.10
		-- 1.3.6.1.4.1.11408.11.1.1.4.1.10
		fhBoardSlotNum OBJECT-TYPE
			SYNTAX INTEGER
			MAX-ACCESS read-only
			STATUS current
			DESCRIPTION
				"Description."
			::= { fhEntityBoardInfoEntry 10 }

		
--   1.3.6.1.4.1.11408.11.1.1.4.1.11
-- 1.3.6.1.4.1.11408.11.1.1.4.1.11
		-- 1.3.6.1.4.1.11408.11.1.1.4.1.11
		fhBoardOperStatus OBJECT-TYPE
			SYNTAX OCTET STRING
			MAX-ACCESS read-only
			STATUS current
			DESCRIPTION
				"Description."
			::= { fhEntityBoardInfoEntry 11 }

		
--   1.3.6.1.4.1.11408.11.1.1.4.1.12
-- 1.3.6.1.4.1.11408.11.1.1.4.1.12
		-- 1.3.6.1.4.1.11408.11.1.1.4.1.12
		fhBoardWarrantyExpireDate OBJECT-TYPE
			SYNTAX OCTET STRING
			MAX-ACCESS read-only
			STATUS current
			DESCRIPTION
				"Description."
			::= { fhEntityBoardInfoEntry 12 }

		
--   1.3.6.1.4.1.11408.11.1.1.4.1.13
-- 1.3.6.1.4.1.11408.11.1.1.4.1.13
		-- 1.3.6.1.4.1.11408.11.1.1.4.1.13
		fhBoardWarrantyObligor OBJECT-TYPE
			SYNTAX OCTET STRING
			MAX-ACCESS read-only
			STATUS current
			DESCRIPTION
				"Description."
			::= { fhEntityBoardInfoEntry 13 }

		
--   1.3.6.1.4.1.11408.11.1.1.4.1.14
-- 1.3.6.1.4.1.11408.11.1.1.4.1.14
		-- 1.3.6.1.4.1.11408.11.1.1.4.1.14
		fhBoardFabricNumber OBJECT-TYPE
			SYNTAX OCTET STRING
			MAX-ACCESS read-only
			STATUS current
			DESCRIPTION
				"Description."
			::= { fhEntityBoardInfoEntry 14 }

		
--   1.3.6.1.4.1.11408.11.1.1.4.1.15
-- 1.3.6.1.4.1.11408.11.1.1.4.1.15
		-- 1.3.6.1.4.1.11408.11.1.1.4.1.15
		fhComponentNumber OBJECT-TYPE
			SYNTAX OCTET STRING
			MAX-ACCESS read-only
			STATUS current
			DESCRIPTION
				"Description."
			::= { fhEntityBoardInfoEntry 15 }

		
--   1.3.6.1.4.1.11408.11.1.1.4.1.16
-- 1.3.6.1.4.1.11408.11.1.1.4.1.16
		-- 1.3.6.1.4.1.11408.11.1.1.4.1.16
		fhHardwareModel OBJECT-TYPE
			SYNTAX OCTET STRING
			MAX-ACCESS read-only
			STATUS current
			DESCRIPTION
				"Description."
			::= { fhEntityBoardInfoEntry 16 }

		
--   1.3.6.1.4.1.11408.11.1.1.4.1.17
-- 1.3.6.1.4.1.11408.11.1.1.4.1.17
		-- 1.3.6.1.4.1.11408.11.1.1.4.1.17
		fhHardwareClass OBJECT-TYPE
			SYNTAX OCTET STRING
			MAX-ACCESS read-only
			STATUS current
			DESCRIPTION
				"Description."
			::= { fhEntityBoardInfoEntry 17 }

		
--   1.3.6.1.4.1.11408.11.1.1.4.1.18
-- 1.3.6.1.4.1.11408.11.1.1.4.1.18
		-- 1.3.6.1.4.1.11408.11.1.1.4.1.18
		fhHardwareIdentifier OBJECT-TYPE
			SYNTAX OCTET STRING
			MAX-ACCESS read-only
			STATUS current
			DESCRIPTION
				"Description."
			::= { fhEntityBoardInfoEntry 18 }

		
--   1.3.6.1.4.1.11408.11.1.1.4.1.19
-- 1.3.6.1.4.1.11408.11.1.1.4.1.19
		-- 1.3.6.1.4.1.11408.11.1.1.4.1.19
		fhHardwareType OBJECT-TYPE
			SYNTAX OCTET STRING
			MAX-ACCESS read-only
			STATUS current
			DESCRIPTION
				"Description."
			::= { fhEntityBoardInfoEntry 19 }

		
--   1.3.6.1.4.1.11408.11.1.1.4.1.20
-- 1.3.6.1.4.1.11408.11.1.1.4.1.20
		-- 1.3.6.1.4.1.11408.11.1.1.4.1.20
		fhBoardNumber OBJECT-TYPE
			SYNTAX OCTET STRING
			MAX-ACCESS read-only
			STATUS current
			DESCRIPTION
				"Description."
			::= { fhEntityBoardInfoEntry 20 }

		
--   1.3.6.1.4.1.11408.11.1.1.4.1.21
-- 1.3.6.1.4.1.11408.11.1.1.4.1.21
		-- 1.3.6.1.4.1.11408.11.1.1.4.1.21
		fhPropertyLabel OBJECT-TYPE
			SYNTAX OCTET STRING
			MAX-ACCESS read-write
			STATUS current
			DESCRIPTION
				"Description."
			::= { fhEntityBoardInfoEntry 21 }

		
--   1.3.6.1.4.1.11408.11.1.1.4.1.22
-- 1.3.6.1.4.1.11408.11.1.1.4.1.22
		-- 1.3.6.1.4.1.11408.11.1.1.4.1.22
		fhBoardIdleStatus OBJECT-TYPE
			SYNTAX INTEGER
			MAX-ACCESS read-only
			STATUS current
			DESCRIPTION
				"Description."
			::= { fhEntityBoardInfoEntry 22 }

		
--   1.3.6.1.4.1.11408.11.1.1.5
-- 1.3.6.1.4.1.11408.11.1.1.5
		-- 1.3.6.1.4.1.11408.11.1.1.5
		fhHardwareTraps OBJECT IDENTIFIER ::= { fhEntityExtentMIB 5 }

		
--   1.3.6.1.4.1.11408.11.1.1.5.1
-- 1.3.6.1.4.1.11408.11.1.1.5.1
		-- 1.3.6.1.4.1.11408.11.1.1.5.1
		fhBoardExistTraps OBJECT IDENTIFIER ::= { fhHardwareTraps 1 }

		
--   1.3.6.1.4.1.11408.11.1.1.5.1.1
-- 1.3.6.1.4.1.11408.11.1.1.5.1.1
		-- 1.3.6.1.4.1.11408.11.1.1.5.1.1
		fhBoardNotExist NOTIFICATION-TYPE
			OBJECTS { fhSlotNo, fhBoardType, fhBoardStatus, fhBoardName }
			STATUS current
			DESCRIPTION 
				"The board pull out action will send this trap."
			::= { fhBoardExistTraps 1 }

		
--   1.3.6.1.4.1.11408.11.1.1.5.1.2
-- 1.3.6.1.4.1.11408.11.1.1.5.1.2
		-- 1.3.6.1.4.1.11408.11.1.1.5.1.2
		fhBoardExist NOTIFICATION-TYPE
			OBJECTS { fhSlotNo, fhBoardType, fhBoardStatus, fhBoardName }
			STATUS current
			DESCRIPTION 
				"The board push in action will send this trap."
			::= { fhBoardExistTraps 2 }

		
--   1.3.6.1.4.1.11408.11.1.1.5.2
-- 1.3.6.1.4.1.11408.11.1.1.5.2
		-- 1.3.6.1.4.1.11408.11.1.1.5.2
		fhBoardStatusTraps OBJECT IDENTIFIER ::= { fhHardwareTraps 2 }

		
--   1.3.6.1.4.1.11408.11.1.1.5.2.1
-- 1.3.6.1.4.1.11408.11.1.1.5.2.1
		-- 1.3.6.1.4.1.11408.11.1.1.5.2.1
		fhBoardFault NOTIFICATION-TYPE
			OBJECTS { fhSlotNo, fhBoardType, fhBoardStatus, fhBoardName }
			STATUS current
			DESCRIPTION 
				"The board fault action will send this trap."
			::= { fhBoardStatusTraps 1 }

		
--   1.3.6.1.4.1.11408.11.1.1.5.2.2
-- 1.3.6.1.4.1.11408.11.1.1.5.2.2
		-- 1.3.6.1.4.1.11408.11.1.1.5.2.2
		fhBoardNormal NOTIFICATION-TYPE
			OBJECTS { fhSlotNo, fhBoardType, fhBoardStatus, fhBoardName }
			STATUS current
			DESCRIPTION 
				"The board normal action will send this trap."
			::= { fhBoardStatusTraps 2 }

		
--   1.3.6.1.4.1.11408.11.1.1.5.3
-- 1.3.6.1.4.1.11408.11.1.1.5.3
		-- 1.3.6.1.4.1.11408.11.1.1.5.3
		fhIntfPktLossTraps OBJECT IDENTIFIER ::= { fhHardwareTraps 3 }

		
--   1.3.6.1.4.1.11408.11.1.1.5.3.1
-- 1.3.6.1.4.1.11408.11.1.1.5.3.1
		-- 1.3.6.1.4.1.11408.11.1.1.5.3.1
		fhIntfPktLossExceed NOTIFICATION-TYPE
			OBJECTS { fhSlotNo, fhSubSlotNO, fhBoardName, fhIfName, fhPortNo
				 }
			STATUS current
			DESCRIPTION 
				"The board IntfPktLossExceed will send this trap."
			::= { fhIntfPktLossTraps 1 }

		
--   1.3.6.1.4.1.11408.11.1.1.5.3.2
-- 1.3.6.1.4.1.11408.11.1.1.5.3.2
		-- 1.3.6.1.4.1.11408.11.1.1.5.3.2
		fhIntfPktLossNormal NOTIFICATION-TYPE
			OBJECTS { fhSlotNo, fhSubSlotNO, fhBoardName, fhIfName, fhPortNo
				 }
			STATUS current
			DESCRIPTION 
				"The board IntfPktLossNormal will send this trap."
			::= { fhIntfPktLossTraps 2 }

		
--   1.3.6.1.4.1.11408.11.1.1.5.4
-- 1.3.6.1.4.1.11408.11.1.1.5.4
		-- 1.3.6.1.4.1.11408.11.1.1.5.4
		fhBoardTempTraps OBJECT IDENTIFIER ::= { fhHardwareTraps 4 }

		
--   1.3.6.1.4.1.11408.11.1.1.5.4.1
-- 1.3.6.1.4.1.11408.11.1.1.5.4.1
		-- 1.3.6.1.4.1.11408.11.1.1.5.4.1
		fhBoardTempExceed NOTIFICATION-TYPE
			OBJECTS { fhSlotNo, fhBoardType, fhBoardStatus, fhBoardName }
			STATUS current
			DESCRIPTION 
				"The board BoardTempExceed will send this trap."
			::= { fhBoardTempTraps 1 }

		
--   1.3.6.1.4.1.11408.11.1.1.5.4.2
-- 1.3.6.1.4.1.11408.11.1.1.5.4.2
		-- 1.3.6.1.4.1.11408.11.1.1.5.4.2
		fhBoardTempNormal NOTIFICATION-TYPE
			OBJECTS { fhSlotNo, fhBoardType, fhBoardStatus, fhBoardName }
			STATUS current
			DESCRIPTION 
				"The board BoardTempNormal will send this trap."
			::= { fhBoardTempTraps 2 }

		
--   1.3.6.1.4.1.11408.11.1.1.5.5
-- 1.3.6.1.4.1.11408.11.1.1.5.5
		-- 1.3.6.1.4.1.11408.11.1.1.5.5
		fhMemoryUsageTraps OBJECT IDENTIFIER ::= { fhHardwareTraps 5 }

		
--   1.3.6.1.4.1.11408.11.1.1.5.5.1
-- 1.3.6.1.4.1.11408.11.1.1.5.5.1
		-- 1.3.6.1.4.1.11408.11.1.1.5.5.1
		fhMemoryUsageExceed NOTIFICATION-TYPE
			OBJECTS { fhSlotNo, fhBoardType, fhBoardStatus, fhBoardName }
			STATUS current
			DESCRIPTION 
				"The board MemoryUsageExceed will send this trap."
			::= { fhMemoryUsageTraps 1 }

		
--   1.3.6.1.4.1.11408.11.1.1.5.5.2
-- 1.3.6.1.4.1.11408.11.1.1.5.5.2
		-- 1.3.6.1.4.1.11408.11.1.1.5.5.2
		fhMemoryUsageNormal NOTIFICATION-TYPE
			OBJECTS { fhSlotNo, fhBoardType, fhBoardStatus, fhBoardName }
			STATUS current
			DESCRIPTION 
				"The board MemoryUsageNormal will send this trap."
			::= { fhMemoryUsageTraps 2 }

		
--   1.3.6.1.4.1.11408.11.1.1.5.6
-- 1.3.6.1.4.1.11408.11.1.1.5.6
		-- 1.3.6.1.4.1.11408.11.1.1.5.6
		fhFlashUsageTraps OBJECT IDENTIFIER ::= { fhHardwareTraps 6 }

		
--   1.3.6.1.4.1.11408.11.1.1.5.6.1
-- 1.3.6.1.4.1.11408.11.1.1.5.6.1
		-- 1.3.6.1.4.1.11408.11.1.1.5.6.1
		fhFlashUsageExceed NOTIFICATION-TYPE
			OBJECTS { fhSlotNo, fhBoardType, fhBoardStatus, fhBoardName }
			STATUS current
			DESCRIPTION 
				"The board FlashUsageExceed will send this trap."
			::= { fhFlashUsageTraps 1 }

		
--   1.3.6.1.4.1.11408.11.1.1.5.6.2
-- 1.3.6.1.4.1.11408.11.1.1.5.6.2
		-- 1.3.6.1.4.1.11408.11.1.1.5.6.2
		fhFlashUsageNormal NOTIFICATION-TYPE
			OBJECTS { fhSlotNo, fhBoardType, fhBoardStatus, fhBoardName }
			STATUS current
			DESCRIPTION 
				"The board FlashUsageNormal will send this trap."
			::= { fhFlashUsageTraps 2 }

		
--   1.3.6.1.4.1.11408.11.1.1.5.7
-- 1.3.6.1.4.1.11408.11.1.1.5.7
		-- 1.3.6.1.4.1.11408.11.1.1.5.7
		fhCPUUsageTraps OBJECT IDENTIFIER ::= { fhHardwareTraps 7 }

		
--   1.3.6.1.4.1.11408.11.1.1.5.7.1
-- 1.3.6.1.4.1.11408.11.1.1.5.7.1
		-- 1.3.6.1.4.1.11408.11.1.1.5.7.1
		fhCPUUsageExceed NOTIFICATION-TYPE
			OBJECTS { fhSlotNo, fhBoardType, fhBoardStatus, fhBoardName }
			STATUS current
			DESCRIPTION 
				"The board CPUUsageExceed will send this trap."
			::= { fhCPUUsageTraps 1 }

		
--   1.3.6.1.4.1.11408.11.1.1.5.7.2
-- 1.3.6.1.4.1.11408.11.1.1.5.7.2
		-- 1.3.6.1.4.1.11408.11.1.1.5.7.2
		fhCPUUsageNormal NOTIFICATION-TYPE
			OBJECTS { fhSlotNo, fhBoardType, fhBoardStatus, fhBoardName }
			STATUS current
			DESCRIPTION 
				"The board CPUUsageNormal will send this trap."
			::= { fhCPUUsageTraps 2 }

		
--   1.3.6.1.4.1.11408.11.1.1.5.8
-- 1.3.6.1.4.1.11408.11.1.1.5.8
		-- 1.3.6.1.4.1.11408.11.1.1.5.8
		fhPowerTraps OBJECT IDENTIFIER ::= { fhHardwareTraps 8 }

		
--   1.3.6.1.4.1.11408.11.1.1.5.8.1
-- 1.3.6.1.4.1.11408.11.1.1.5.8.1
		-- 1.3.6.1.4.1.11408.11.1.1.5.8.1
		fhPowerRisk NOTIFICATION-TYPE
			OBJECTS { fhSlotNo, fhBoardType, fhBoardStatus, fhBoardName }
			STATUS current
			DESCRIPTION 
				"The board PowerRisk will send this trap."
			::= { fhPowerTraps 1 }

		
--   1.3.6.1.4.1.11408.11.1.1.5.8.2
-- 1.3.6.1.4.1.11408.11.1.1.5.8.2
		-- 1.3.6.1.4.1.11408.11.1.1.5.8.2
		fhPowerNormal NOTIFICATION-TYPE
			OBJECTS { fhSlotNo, fhBoardType, fhBoardStatus, fhBoardName }
			STATUS current
			DESCRIPTION 
				"The board PowerNormal will send this trap."
			::= { fhPowerTraps 2 }

		
--   1.3.6.1.4.1.11408.11.1.1.5.9
-- 1.3.6.1.4.1.11408.11.1.1.5.9
		-- 1.3.6.1.4.1.11408.11.1.1.5.9
		fhFanTraps OBJECT IDENTIFIER ::= { fhHardwareTraps 9 }

		
--   1.3.6.1.4.1.11408.11.1.1.5.9.1
-- 1.3.6.1.4.1.11408.11.1.1.5.9.1
		-- 1.3.6.1.4.1.11408.11.1.1.5.9.1
		fhFanFault NOTIFICATION-TYPE
			OBJECTS { fhSlotNo, fhBoardType, fhBoardStatus, fhBoardName }
			STATUS current
			DESCRIPTION 
				"The board FanFault will send this trap."
			::= { fhFanTraps 1 }

		
--   1.3.6.1.4.1.11408.11.1.1.5.9.2
-- 1.3.6.1.4.1.11408.11.1.1.5.9.2
		-- 1.3.6.1.4.1.11408.11.1.1.5.9.2
		fhFanNormal NOTIFICATION-TYPE
			OBJECTS { fhSlotNo, fhBoardType, fhBoardStatus, fhBoardName }
			STATUS current
			DESCRIPTION 
				"The board FanFault will send this trap."
			::= { fhFanTraps 2 }

		
--   1.3.6.1.4.1.11408.11.1.1.5.10
-- 1.3.6.1.4.1.11408.11.1.1.5.10
		-- 1.3.6.1.4.1.11408.11.1.1.5.10
		fhPowerSupplyTraps OBJECT IDENTIFIER ::= { fhHardwareTraps 10 }

		
--   1.3.6.1.4.1.11408.11.1.1.5.10.1
-- 1.3.6.1.4.1.11408.11.1.1.5.10.1
		-- 1.3.6.1.4.1.11408.11.1.1.5.10.1
		fhPowerSupplyShortage NOTIFICATION-TYPE
			OBJECTS { fhSlotNo, fhBoardType, fhBoardStatus, fhBoardName }
			STATUS current
			DESCRIPTION 
				"The board PowerSupplyShortage will send this trap."
			::= { fhPowerSupplyTraps 1 }

		
--   1.3.6.1.4.1.11408.11.1.1.5.10.2
-- 1.3.6.1.4.1.11408.11.1.1.5.10.2
		-- 1.3.6.1.4.1.11408.11.1.1.5.10.2
		fhPowerSupplyNormal NOTIFICATION-TYPE
			OBJECTS { fhSlotNo, fhBoardType, fhBoardStatus, fhBoardName }
			STATUS current
			DESCRIPTION 
				"The board PowerSupplyNormal will send this trap."
			::= { fhPowerSupplyTraps 2 }

		
--   1.3.6.1.4.1.11408.11.1.1.5.11
-- 1.3.6.1.4.1.11408.11.1.1.5.11
		-- 1.3.6.1.4.1.11408.11.1.1.5.11
		fhTempTraps OBJECT IDENTIFIER ::= { fhHardwareTraps 11 }

		
--   1.3.6.1.4.1.11408.11.1.1.5.11.1
-- 1.3.6.1.4.1.11408.11.1.1.5.11.1
		-- 1.3.6.1.4.1.11408.11.1.1.5.11.1
		fhTempHighAlarm NOTIFICATION-TYPE
			OBJECTS { fhSlotNo, fhBoardType, fhBoardStatus, fhBoardName }
			STATUS current
			DESCRIPTION 
				"The board TempHighAlarm will send this trap."
			::= { fhTempTraps 1 }

		
--   1.3.6.1.4.1.11408.11.1.1.5.11.2
-- 1.3.6.1.4.1.11408.11.1.1.5.11.2
		-- 1.3.6.1.4.1.11408.11.1.1.5.11.2
		fhTempResume NOTIFICATION-TYPE
			OBJECTS { fhSlotNo, fhBoardType, fhBoardStatus, fhBoardName }
			STATUS current
			DESCRIPTION 
				"The board TempResume will send this trap."
			::= { fhTempTraps 2 }

		
--   1.3.6.1.4.1.11408.11.1.1.5.12
-- 1.3.6.1.4.1.11408.11.1.1.5.12
		-- 1.3.6.1.4.1.11408.11.1.1.5.12
		fhInputVoltageTraps OBJECT IDENTIFIER ::= { fhHardwareTraps 12 }

		
--   1.3.6.1.4.1.11408.11.1.1.5.12.1
-- 1.3.6.1.4.1.11408.11.1.1.5.12.1
		-- 1.3.6.1.4.1.11408.11.1.1.5.12.1
		fhInputVoltageExceed NOTIFICATION-TYPE
			OBJECTS { fhSlotNo, fhBoardType, fhBoardStatus, fhBoardName }
			STATUS current
			DESCRIPTION 
				"The board InputVoltageExceed will send this trap."
			::= { fhInputVoltageTraps 1 }

		
--   1.3.6.1.4.1.11408.11.1.1.5.12.2
-- 1.3.6.1.4.1.11408.11.1.1.5.12.2
		-- 1.3.6.1.4.1.11408.11.1.1.5.12.2
		fhInputVoltageNormal NOTIFICATION-TYPE
			OBJECTS { fhSlotNo, fhBoardType, fhBoardStatus, fhBoardName }
			STATUS current
			DESCRIPTION 
				"The board InputVoltageNormal will send this trap."
			::= { fhInputVoltageTraps 2 }

		
--   1.3.6.1.4.1.11408.11.1.1.5.13
-- 1.3.6.1.4.1.11408.11.1.1.5.13
		-- 1.3.6.1.4.1.11408.11.1.1.5.13
		fhOpticalInTraps OBJECT IDENTIFIER ::= { fhHardwareTraps 13 }

		
--   1.3.6.1.4.1.11408.11.1.1.5.13.1
-- 1.3.6.1.4.1.11408.11.1.1.5.13.1
		-- 1.3.6.1.4.1.11408.11.1.1.5.13.1
		fhOpticalInLoss NOTIFICATION-TYPE
			OBJECTS { fhSlotNo, fhSubSlotNO, fhBoardName, fhIfName, fhPortNo
				 }
			STATUS current
			DESCRIPTION 
				"The board OpticalInLoss will send this trap."
			::= { fhOpticalInTraps 1 }

		
--   1.3.6.1.4.1.11408.11.1.1.5.13.2
-- 1.3.6.1.4.1.11408.11.1.1.5.13.2
		-- 1.3.6.1.4.1.11408.11.1.1.5.13.2
		fhOpticalInNormal NOTIFICATION-TYPE
			OBJECTS { fhSlotNo, fhSubSlotNO, fhBoardName, fhIfName, fhPortNo
				 }
			STATUS current
			DESCRIPTION 
				"The board OpticalInNormal will send this trap."
			::= { fhOpticalInTraps 2 }

		
--   1.3.6.1.4.1.11408.11.1.1.5.14
-- 1.3.6.1.4.1.11408.11.1.1.5.14
		-- 1.3.6.1.4.1.11408.11.1.1.5.14
		fhLaserSendTraps OBJECT IDENTIFIER ::= { fhHardwareTraps 14 }

		
--   1.3.6.1.4.1.11408.11.1.1.5.14.1
-- 1.3.6.1.4.1.11408.11.1.1.5.14.1
		-- 1.3.6.1.4.1.11408.11.1.1.5.14.1
		fhLaserSendFault NOTIFICATION-TYPE
			OBJECTS { fhSlotNo, fhSubSlotNO, fhBoardName, fhIfName, fhPortNo
				 }
			STATUS current
			DESCRIPTION 
				"The board LaserSendFault will send this trap."
			::= { fhLaserSendTraps 1 }

		
--   1.3.6.1.4.1.11408.11.1.1.5.14.2
-- 1.3.6.1.4.1.11408.11.1.1.5.14.2
		-- 1.3.6.1.4.1.11408.11.1.1.5.14.2
		fhLaserSendNormal NOTIFICATION-TYPE
			OBJECTS { fhSlotNo, fhSubSlotNO, fhBoardName, fhIfName, fhPortNo
				 }
			STATUS current
			DESCRIPTION 
				"The board LaserSendNormal will send this trap."
			::= { fhLaserSendTraps 2 }

		
--   1.3.6.1.4.1.11408.11.1.1.5.15
-- 1.3.6.1.4.1.11408.11.1.1.5.15
		-- 1.3.6.1.4.1.11408.11.1.1.5.15
		fhLaserTempTraps OBJECT IDENTIFIER ::= { fhHardwareTraps 15 }

		
--   1.3.6.1.4.1.11408.11.1.1.5.15.1
-- 1.3.6.1.4.1.11408.11.1.1.5.15.1
		-- 1.3.6.1.4.1.11408.11.1.1.5.15.1
		fhLaserTempExceed NOTIFICATION-TYPE
			OBJECTS { fhSlotNo, fhSubSlotNO, fhBoardName, fhIfName, fhPortNo
				 }
			STATUS current
			DESCRIPTION 
				"The board LaserTempExceed will send this trap."
			::= { fhLaserTempTraps 1 }

		
--   1.3.6.1.4.1.11408.11.1.1.5.15.2
-- 1.3.6.1.4.1.11408.11.1.1.5.15.2
		-- 1.3.6.1.4.1.11408.11.1.1.5.15.2
		fhLaserTempNormal NOTIFICATION-TYPE
			OBJECTS { fhSlotNo, fhSubSlotNO, fhBoardName, fhIfName, fhPortNo
				 }
			STATUS current
			DESCRIPTION 
				"The board LaserTempNormal will send this trap."
			::= { fhLaserTempTraps 2 }

		
--   1.3.6.1.4.1.11408.11.1.1.5.16
-- 1.3.6.1.4.1.11408.11.1.1.5.16
		-- 1.3.6.1.4.1.11408.11.1.1.5.16
		fhPowerOutShortageTraps OBJECT IDENTIFIER ::= { fhHardwareTraps 16 }

		
--   1.3.6.1.4.1.11408.11.1.1.5.16.1
-- 1.3.6.1.4.1.11408.11.1.1.5.16.1
		-- 1.3.6.1.4.1.11408.11.1.1.5.16.1
		fhPowerOutShortage NOTIFICATION-TYPE
			OBJECTS { fhSlotNo, fhSubSlotNO, fhBoardName, fhIfName, fhPortNo
				 }
			STATUS current
			DESCRIPTION 
				"The board PowerOutShortage will send this trap."
			::= { fhPowerOutShortageTraps 1 }

		
--   1.3.6.1.4.1.11408.11.1.1.5.16.2
-- 1.3.6.1.4.1.11408.11.1.1.5.16.2
		-- 1.3.6.1.4.1.11408.11.1.1.5.16.2
		fhPowerOutShortageNormal NOTIFICATION-TYPE
			OBJECTS { fhSlotNo, fhSubSlotNO, fhBoardName, fhIfName, fhPortNo
				 }
			STATUS current
			DESCRIPTION 
				"The board PowerOutShortageNormal will send this trap."
			::= { fhPowerOutShortageTraps 2 }

		
--   1.3.6.1.4.1.11408.11.1.1.5.17
-- 1.3.6.1.4.1.11408.11.1.1.5.17
		-- 1.3.6.1.4.1.11408.11.1.1.5.17
		fhPowerOutExceedTraps OBJECT IDENTIFIER ::= { fhHardwareTraps 17 }

		
--   1.3.6.1.4.1.11408.11.1.1.5.17.1
-- 1.3.6.1.4.1.11408.11.1.1.5.17.1
		-- 1.3.6.1.4.1.11408.11.1.1.5.17.1
		fhPowerOutExceed NOTIFICATION-TYPE
			OBJECTS { fhSlotNo, fhSubSlotNO, fhBoardName, fhIfName, fhPortNo
				 }
			STATUS current
			DESCRIPTION 
				"The board PowerOutExceed will send this trap."
			::= { fhPowerOutExceedTraps 1 }

		
--   1.3.6.1.4.1.11408.11.1.1.5.17.2
-- 1.3.6.1.4.1.11408.11.1.1.5.17.2
		-- 1.3.6.1.4.1.11408.11.1.1.5.17.2
		fhPowerOutExceedNormal NOTIFICATION-TYPE
			OBJECTS { fhSlotNo, fhSubSlotNO, fhBoardName, fhIfName, fhPortNo
				 }
			STATUS current
			DESCRIPTION 
				"The board PowerOutExceedNormal will send this trap."
			::= { fhPowerOutExceedTraps 2 }

		
--   1.3.6.1.4.1.11408.11.1.1.5.18
-- 1.3.6.1.4.1.11408.11.1.1.5.18
		-- 1.3.6.1.4.1.11408.11.1.1.5.18
		fhPowerInShortageTraps OBJECT IDENTIFIER ::= { fhHardwareTraps 18 }

		
--   1.3.6.1.4.1.11408.11.1.1.5.18.1
-- 1.3.6.1.4.1.11408.11.1.1.5.18.1
		-- 1.3.6.1.4.1.11408.11.1.1.5.18.1
		fhPowerInShortage NOTIFICATION-TYPE
			OBJECTS { fhSlotNo, fhSubSlotNO, fhBoardName, fhIfName, fhPortNo
				 }
			STATUS current
			DESCRIPTION 
				"The board PowerInShortage will send this trap."
			::= { fhPowerInShortageTraps 1 }

		
--   1.3.6.1.4.1.11408.11.1.1.5.18.2
-- 1.3.6.1.4.1.11408.11.1.1.5.18.2
		-- 1.3.6.1.4.1.11408.11.1.1.5.18.2
		fhPowerInShortageNormal NOTIFICATION-TYPE
			OBJECTS { fhSlotNo, fhSubSlotNO, fhBoardName, fhIfName, fhPortNo
				 }
			STATUS current
			DESCRIPTION 
				"The board PowerInShortageNormal will send this trap."
			::= { fhPowerInShortageTraps 2 }

		
--   1.3.6.1.4.1.11408.11.1.1.5.19
-- 1.3.6.1.4.1.11408.11.1.1.5.19
		-- 1.3.6.1.4.1.11408.11.1.1.5.19
		fhPowerInExceedTraps OBJECT IDENTIFIER ::= { fhHardwareTraps 19 }

		
--   1.3.6.1.4.1.11408.11.1.1.5.19.1
-- 1.3.6.1.4.1.11408.11.1.1.5.19.1
		-- 1.3.6.1.4.1.11408.11.1.1.5.19.1
		fhPowerInExceed NOTIFICATION-TYPE
			OBJECTS { fhSlotNo, fhSubSlotNO, fhBoardName, fhIfName, fhPortNo
				 }
			STATUS current
			DESCRIPTION 
				"The board PowerInExceed will send this trap."
			::= { fhPowerInExceedTraps 1 }

		
--   1.3.6.1.4.1.11408.11.1.1.5.19.2
-- 1.3.6.1.4.1.11408.11.1.1.5.19.2
		-- 1.3.6.1.4.1.11408.11.1.1.5.19.2
		fhPowerInExceedNormal NOTIFICATION-TYPE
			OBJECTS { fhSlotNo, fhSubSlotNO, fhBoardName, fhIfName, fhPortNo
				 }
			STATUS current
			DESCRIPTION 
				"The board PowerInExceedNormal will send this trap."
			::= { fhPowerInExceedTraps 2 }

		
--   1.3.6.1.4.1.11408.11.1.1.5.20
-- 1.3.6.1.4.1.11408.11.1.1.5.20
		-- 1.3.6.1.4.1.11408.11.1.1.5.20
		fhLinkTrap OBJECT IDENTIFIER ::= { fhHardwareTraps 20 }

		
--   1.3.6.1.4.1.11408.11.1.1.5.20.1
-- 1.3.6.1.4.1.11408.11.1.1.5.20.1
		-- 1.3.6.1.4.1.11408.11.1.1.5.20.1
		fhLinkLoss NOTIFICATION-TYPE
			STATUS current
			DESCRIPTION 
				"Description."
			::= { fhLinkTrap 1 }

		
--   1.3.6.1.4.1.11408.11.1.1.5.20.2
-- 1.3.6.1.4.1.11408.11.1.1.5.20.2
		-- 1.3.6.1.4.1.11408.11.1.1.5.20.2
		fhLinkNormal NOTIFICATION-TYPE
			STATUS current
			DESCRIPTION 
				"Description."
			::= { fhLinkTrap 2 }

		
--   1.3.6.1.4.1.11408.11.1.1.5.21
-- 1.3.6.1.4.1.11408.11.1.1.5.21
		-- 1.3.6.1.4.1.11408.11.1.1.5.21
		fhIfOscillationTrap OBJECT IDENTIFIER ::= { fhHardwareTraps 21 }

		
--   1.3.6.1.4.1.11408.11.1.1.5.21.1
-- 1.3.6.1.4.1.11408.11.1.1.5.21.1
		-- 1.3.6.1.4.1.11408.11.1.1.5.21.1
		fhIfOscillationNormal NOTIFICATION-TYPE
			STATUS current
			DESCRIPTION 
				"Description."
			::= { fhIfOscillationTrap 1 }

		
--   1.3.6.1.4.1.11408.11.1.1.5.21.2
-- 1.3.6.1.4.1.11408.11.1.1.5.21.2
		-- 1.3.6.1.4.1.11408.11.1.1.5.21.2
		fhIfOscillation NOTIFICATION-TYPE
			STATUS current
			DESCRIPTION 
				"Description."
			::= { fhIfOscillationTrap 2 }

		
--   1.3.6.1.4.1.11408.11.1.2
-- 1.3.6.1.4.1.11408.11.1.2
		-- 1.3.6.1.4.1.11408.11.1.2
		fhIfExtMIB OBJECT IDENTIFIER ::= { fhDatacomm 2 }

		
--   1.3.6.1.4.1.11408.11.1.2.1
-- 1.3.6.1.4.1.11408.11.1.2.1
		-- 1.3.6.1.4.1.11408.11.1.2.1
		fhIfStateTable OBJECT-TYPE
			SYNTAX SEQUENCE OF FhIfStateEntry
			MAX-ACCESS not-accessible
			STATUS current
			DESCRIPTION
				"Description."
			::= { fhIfExtMIB 1 }

		
--   1.3.6.1.4.1.11408.11.1.2.1.1
-- 1.3.6.1.4.1.11408.11.1.2.1.1
		-- 1.3.6.1.4.1.11408.11.1.2.1.1
		fhIfStateEntry OBJECT-TYPE
			SYNTAX FhIfStateEntry
			MAX-ACCESS not-accessible
			STATUS current
			DESCRIPTION
				"Description."
			INDEX { fhIfIndex }
			::= { fhIfStateTable 1 }

		
		FhIfStateEntry ::=
			SEQUENCE { 
				fhIfIndex
					InterfaceIndex,
				fhIfDescr
					OCTET STRING,
				fhIfMode
					INTEGER,
				fhOeMode
					Integer32
			 }

--   1.3.6.1.4.1.11408.11.1.2.1.1.1
-- 1.3.6.1.4.1.11408.11.1.2.1.1.1
		-- 1.3.6.1.4.1.11408.11.1.2.1.1.1
		fhIfIndex OBJECT-TYPE
			SYNTAX InterfaceIndex
			MAX-ACCESS not-accessible
			STATUS current
			DESCRIPTION
				"Description."
			::= { fhIfStateEntry 1 }

		
--   1.3.6.1.4.1.11408.11.1.2.1.1.2
-- 1.3.6.1.4.1.11408.11.1.2.1.1.2
		-- 1.3.6.1.4.1.11408.11.1.2.1.1.2
		fhIfDescr OBJECT-TYPE
			SYNTAX OCTET STRING
			MAX-ACCESS read-only
			STATUS current
			DESCRIPTION
				"Description."
			::= { fhIfStateEntry 2 }

		
--   1.3.6.1.4.1.11408.11.1.2.1.1.3
-- 1.3.6.1.4.1.11408.11.1.2.1.1.3
		-- 1.3.6.1.4.1.11408.11.1.2.1.1.3
		fhIfMode OBJECT-TYPE
			SYNTAX INTEGER
			MAX-ACCESS read-write
			STATUS current
			DESCRIPTION
				"Description."
			::= { fhIfStateEntry 3 }

		
--   1.3.6.1.4.1.11408.11.1.2.1.1.4
-- 1.3.6.1.4.1.11408.11.1.2.1.1.4
		-- 1.3.6.1.4.1.11408.11.1.2.1.1.4
		fhOeMode OBJECT-TYPE
			SYNTAX Integer32
			MAX-ACCESS read-write
			STATUS current
			DESCRIPTION
				"Description."
			::= { fhIfStateEntry 4 }

		
--   1.3.6.1.4.1.11408.11.1.2.2
-- 1.3.6.1.4.1.11408.11.1.2.2
		-- 1.3.6.1.4.1.11408.11.1.2.2
		fhIfPac OBJECT IDENTIFIER ::= { fhIfExtMIB 2 }

		
--   1.3.6.1.4.1.11408.11.1.2.2.0
-- 1.3.6.1.4.1.11408.11.1.2.2.0
		-- 1.3.6.1.4.1.11408.11.1.2.2.0
		fhIfPacketTable OBJECT-TYPE
			SYNTAX SEQUENCE OF fhIfPacketEntry
			MAX-ACCESS not-accessible
			STATUS current
			DESCRIPTION
				"Description."
			::= { fhIfPac 0 }

		
--   1.3.6.1.4.1.11408.11.1.2.2.0.0
-- 1.3.6.1.4.1.11408.11.1.2.2.0.0
		-- 1.3.6.1.4.1.11408.11.1.2.2.0.0
		fhIfPacketEntry OBJECT-TYPE
			SYNTAX fhIfPacketEntry
			MAX-ACCESS not-accessible
			STATUS current
			DESCRIPTION
				"Description."
			INDEX { INTEGER }
			::= { fhIfPacketTable 0 }

		
		fhIfPacketEntry ::=
			SEQUENCE { 
				ifName
					OCTET STRING,
				ifIndex
					INTEGER,
				ifDateTime
					OCTET STRING,
				ifTrapStatus
					INTEGER,
				ifInputPackets
					Counter64,
				ifOutputPackets
					Counter64,
				ifSeconds
					INTEGER,
				ifInputRate
					OCTET STRING,
				ifOutputRate
					OCTET STRING,
				ifInputError
					Counter64,
				ifOutputError
					Counter64
			 }

--   1.3.6.1.4.1.11408.11.1.2.2.0.0.1
-- 1.3.6.1.4.1.11408.11.1.2.2.0.0.1
		-- 1.3.6.1.4.1.11408.11.1.2.2.0.0.1
		ifName OBJECT-TYPE
			SYNTAX OCTET STRING
			MAX-ACCESS not-accessible
			STATUS current
			DESCRIPTION
				"Description."
			::= { fhIfPacketEntry 1 }

		
--   1.3.6.1.4.1.11408.11.1.2.2.0.0.2
-- 1.3.6.1.4.1.11408.11.1.2.2.0.0.2
		-- 1.3.6.1.4.1.11408.11.1.2.2.0.0.2
		ifIndex OBJECT-TYPE
			SYNTAX INTEGER
			MAX-ACCESS read-only
			STATUS current
			DESCRIPTION
				"Description."
			::= { fhIfPacketEntry 2 }

		
--   1.3.6.1.4.1.11408.11.1.2.2.0.0.3
-- 1.3.6.1.4.1.11408.11.1.2.2.0.0.3
		-- 1.3.6.1.4.1.11408.11.1.2.2.0.0.3
		ifDateTime OBJECT-TYPE
			SYNTAX OCTET STRING
			MAX-ACCESS read-write
			STATUS current
			DESCRIPTION
				"Description."
			::= { fhIfPacketEntry 3 }

		
--   1.3.6.1.4.1.11408.11.1.2.2.0.0.4
-- 1.3.6.1.4.1.11408.11.1.2.2.0.0.4
		-- 1.3.6.1.4.1.11408.11.1.2.2.0.0.4
		ifTrapStatus OBJECT-TYPE
			SYNTAX INTEGER
			MAX-ACCESS not-accessible
			STATUS current
			DESCRIPTION
				"Description."
			::= { fhIfPacketEntry 4 }

		
--   1.3.6.1.4.1.11408.11.1.2.2.0.0.5
-- 1.3.6.1.4.1.11408.11.1.2.2.0.0.5
		-- 1.3.6.1.4.1.11408.11.1.2.2.0.0.5
		ifInputPackets OBJECT-TYPE
			SYNTAX Counter64
			MAX-ACCESS read-only
			STATUS current
			DESCRIPTION
				"Description."
			::= { fhIfPacketEntry 5 }

		
--   1.3.6.1.4.1.11408.11.1.2.2.0.0.6
-- 1.3.6.1.4.1.11408.11.1.2.2.0.0.6
		-- 1.3.6.1.4.1.11408.11.1.2.2.0.0.6
		ifOutputPackets OBJECT-TYPE
			SYNTAX Counter64
			MAX-ACCESS read-write
			STATUS current
			DESCRIPTION
				"Description."
			::= { fhIfPacketEntry 6 }

		
--   1.3.6.1.4.1.11408.11.1.2.2.0.0.7
-- 1.3.6.1.4.1.11408.11.1.2.2.0.0.7
		-- 1.3.6.1.4.1.11408.11.1.2.2.0.0.7
		ifSeconds OBJECT-TYPE
			SYNTAX INTEGER
			MAX-ACCESS not-accessible
			STATUS current
			DESCRIPTION
				"Description."
			::= { fhIfPacketEntry 7 }

		
--   1.3.6.1.4.1.11408.11.1.2.2.0.0.8
-- 1.3.6.1.4.1.11408.11.1.2.2.0.0.8
		-- 1.3.6.1.4.1.11408.11.1.2.2.0.0.8
		ifInputRate OBJECT-TYPE
			SYNTAX OCTET STRING
			MAX-ACCESS read-only
			STATUS current
			DESCRIPTION
				"Description."
			::= { fhIfPacketEntry 8 }

		
--   1.3.6.1.4.1.11408.11.1.2.2.0.0.9
-- 1.3.6.1.4.1.11408.11.1.2.2.0.0.9
		-- 1.3.6.1.4.1.11408.11.1.2.2.0.0.9
		ifOutputRate OBJECT-TYPE
			SYNTAX OCTET STRING
			MAX-ACCESS read-write
			STATUS current
			DESCRIPTION
				"Description."
			::= { fhIfPacketEntry 9 }

		
--   1.3.6.1.4.1.11408.11.1.2.2.0.0.10
-- 1.3.6.1.4.1.11408.11.1.2.2.0.0.10
		-- 1.3.6.1.4.1.11408.11.1.2.2.0.0.10
		ifInputError OBJECT-TYPE
			SYNTAX Counter64
			MAX-ACCESS not-accessible
			STATUS current
			DESCRIPTION
				"Description."
			::= { fhIfPacketEntry 10 }

		
--   1.3.6.1.4.1.11408.11.1.2.2.0.0.11
-- 1.3.6.1.4.1.11408.11.1.2.2.0.0.11
		-- 1.3.6.1.4.1.11408.11.1.2.2.0.0.11
		ifOutputError OBJECT-TYPE
			SYNTAX Counter64
			MAX-ACCESS read-only
			STATUS current
			DESCRIPTION
				"Description."
			::= { fhIfPacketEntry 11 }

		
--   1.3.6.1.4.1.11408.11.1.2.3
-- 1.3.6.1.4.1.11408.11.1.2.3
		-- 1.3.6.1.4.1.11408.11.1.2.3
		fhIntfTraps OBJECT IDENTIFIER ::= { fhIfExtMIB 3 }

		
--   1.3.6.1.4.1.11408.11.1.2.3.1
-- 1.3.6.1.4.1.11408.11.1.2.3.1
		-- 1.3.6.1.4.1.11408.11.1.2.3.1
		fhIntfTrafficTraps OBJECT IDENTIFIER ::= { fhIntfTraps 1 }

		
--   1.3.6.1.4.1.11408.11.1.2.3.1.1
-- 1.3.6.1.4.1.11408.11.1.2.3.1.1
		-- 1.3.6.1.4.1.11408.11.1.2.3.1.1
		fhIntfTrafficExceed NOTIFICATION-TYPE
			OBJECTS { ifName, ifIndex, ifInputRate, ifOutputRate }
			STATUS current
			DESCRIPTION 
				"The board IntfTrafficExceed will send this trap."
			::= { fhIntfTrafficTraps 1 }

		
--   1.3.6.1.4.1.11408.11.1.2.3.1.2
-- 1.3.6.1.4.1.11408.11.1.2.3.1.2
		-- 1.3.6.1.4.1.11408.11.1.2.3.1.2
		fhIntfTrafficNormal NOTIFICATION-TYPE
			OBJECTS { ifName, ifIndex, ifInputRate, ifOutputRate }
			STATUS current
			DESCRIPTION 
				"The board IntfTrafficNormal will send this trap."
			::= { fhIntfTrafficTraps 2 }

		
--   1.3.6.1.4.1.11408.11.1.2.3.2
-- 1.3.6.1.4.1.11408.11.1.2.3.2
		-- 1.3.6.1.4.1.11408.11.1.2.3.2
		fhIntfRxBadPktTraps OBJECT IDENTIFIER ::= { fhIntfTraps 2 }

		
--   1.3.6.1.4.1.11408.11.1.2.3.2.1
-- 1.3.6.1.4.1.11408.11.1.2.3.2.1
		-- 1.3.6.1.4.1.11408.11.1.2.3.2.1
		fhIntfRxBadPktExceed NOTIFICATION-TYPE
			OBJECTS { ifName, ifIndex, ifInputError, ifOutputError }
			STATUS current
			DESCRIPTION 
				"The board IntfRxBadPktExceed will send this trap."
			::= { fhIntfRxBadPktTraps 1 }

		
--   1.3.6.1.4.1.11408.11.1.2.3.2.2
-- 1.3.6.1.4.1.11408.11.1.2.3.2.2
		-- 1.3.6.1.4.1.11408.11.1.2.3.2.2
		fhIntfRxBadPktNormal NOTIFICATION-TYPE
			OBJECTS { ifName, ifIndex, ifInputError, ifOutputError }
			STATUS current
			DESCRIPTION 
				"The board IntfRxBadPktNormal will send this trap."
			::= { fhIntfRxBadPktTraps 2 }

		
--   1.3.6.1.4.1.11408.11.1.2.3.3
-- 1.3.6.1.4.1.11408.11.1.2.3.3
		-- 1.3.6.1.4.1.11408.11.1.2.3.3
		fhPhysicalInterface OBJECT IDENTIFIER ::= { fhIntfTraps 3 }

		
--   1.3.6.1.4.1.11408.11.1.2.3.3.1
-- 1.3.6.1.4.1.11408.11.1.2.3.3.1
		-- 1.3.6.1.4.1.11408.11.1.2.3.3.1
		fhPhysicalInterfaceDown NOTIFICATION-TYPE
			STATUS current
			DESCRIPTION 
				"Description."
			::= { fhPhysicalInterface 1 }

		
--   1.3.6.1.4.1.11408.11.1.2.3.3.2
-- 1.3.6.1.4.1.11408.11.1.2.3.3.2
		-- 1.3.6.1.4.1.11408.11.1.2.3.3.2
		fhPhysicalInterfaceUp NOTIFICATION-TYPE
			STATUS current
			DESCRIPTION 
				"Description."
			::= { fhPhysicalInterface 2 }

		
--   1.3.6.1.4.1.11408.11.1.2.4
-- 1.3.6.1.4.1.11408.11.1.2.4
		-- 1.3.6.1.4.1.11408.11.1.2.4
		fhIfL3ExtTable OBJECT-TYPE
			SYNTAX SEQUENCE OF FhIfL3ExtEntry
			MAX-ACCESS not-accessible
			STATUS current
			DESCRIPTION
				"Description."
			::= { fhIfExtMIB 4 }

		
--   1.3.6.1.4.1.11408.11.1.2.4.1
-- 1.3.6.1.4.1.11408.11.1.2.4.1
		-- 1.3.6.1.4.1.11408.11.1.2.4.1
		fhIfL3ExtEntry OBJECT-TYPE
			SYNTAX FhIfL3ExtEntry
			MAX-ACCESS not-accessible
			STATUS current
			DESCRIPTION
				"Description."
			INDEX { fhIfL3ExtIndex }
			::= { fhIfL3ExtTable 1 }

		
		FhIfL3ExtEntry ::=
			SEQUENCE { 
				fhIfL3ExtIndex
					Integer32,
				fhIfL3ExtVrfId
					Integer32,
				fhIfL3ExtName
					OCTET STRING,
				fhIfL3ExtVrfName
					OCTET STRING
			 }

--   1.3.6.1.4.1.11408.11.1.2.4.1.1
-- 1.3.6.1.4.1.11408.11.1.2.4.1.1
		-- 1.3.6.1.4.1.11408.11.1.2.4.1.1
		fhIfL3ExtIndex OBJECT-TYPE
			SYNTAX Integer32
			MAX-ACCESS read-only
			STATUS current
			DESCRIPTION
				"Description."
			::= { fhIfL3ExtEntry 1 }

		
--   1.3.6.1.4.1.11408.11.1.2.4.1.2
-- 1.3.6.1.4.1.11408.11.1.2.4.1.2
		-- 1.3.6.1.4.1.11408.11.1.2.4.1.2
		fhIfL3ExtVrfId OBJECT-TYPE
			SYNTAX Integer32
			MAX-ACCESS read-only
			STATUS current
			DESCRIPTION
				"Description."
			::= { fhIfL3ExtEntry 2 }

		
--   1.3.6.1.4.1.11408.11.1.2.4.1.3
-- 1.3.6.1.4.1.11408.11.1.2.4.1.3
		-- 1.3.6.1.4.1.11408.11.1.2.4.1.3
		fhIfL3ExtName OBJECT-TYPE
			SYNTAX OCTET STRING
			MAX-ACCESS read-only
			STATUS current
			DESCRIPTION
				"Description."
			::= { fhIfL3ExtEntry 3 }

		
--   1.3.6.1.4.1.11408.11.1.2.4.1.4
-- 1.3.6.1.4.1.11408.11.1.2.4.1.4
		-- 1.3.6.1.4.1.11408.11.1.2.4.1.4
		fhIfL3ExtVrfName OBJECT-TYPE
			SYNTAX OCTET STRING
			MAX-ACCESS read-only
			STATUS current
			DESCRIPTION
				"Description."
			::= { fhIfL3ExtEntry 4 }

		
--   1.3.6.1.4.1.11408.11.1.2.5
-- 1.3.6.1.4.1.11408.11.1.2.5
		-- 1.3.6.1.4.1.11408.11.1.2.5
		fhIfTunnelTable OBJECT-TYPE
			SYNTAX SEQUENCE OF FhIfTunnelEntry
			MAX-ACCESS not-accessible
			STATUS current
			DESCRIPTION
				"Description."
			::= { fhIfExtMIB 5 }

		
--   1.3.6.1.4.1.11408.11.1.2.5.1
-- 1.3.6.1.4.1.11408.11.1.2.5.1
		-- 1.3.6.1.4.1.11408.11.1.2.5.1
		fhIfTunnelEntry OBJECT-TYPE
			SYNTAX FhIfTunnelEntry
			MAX-ACCESS not-accessible
			STATUS current
			DESCRIPTION
				"Description."
			INDEX { fhIfTunnelId }
			::= { fhIfTunnelTable 1 }

		
		FhIfTunnelEntry ::=
			SEQUENCE { 
				fhIfTunnelId
					Integer32,
				fhIfTunnelEncapMode
					Integer32,
				fhIfTunnelSrcIP
					IpAddress,
				fhIfTunnelDestIp
					IpAddress,
				fhIfTunnelLocalIp
					IpAddress,
				fhIfTunnelState
					Integer32
			 }

--   1.3.6.1.4.1.11408.11.1.2.5.1.1
-- 1.3.6.1.4.1.11408.11.1.2.5.1.1
		-- 1.3.6.1.4.1.11408.11.1.2.5.1.1
		fhIfTunnelId OBJECT-TYPE
			SYNTAX Integer32
			MAX-ACCESS read-only
			STATUS current
			DESCRIPTION
				"Description."
			::= { fhIfTunnelEntry 1 }

		
--   1.3.6.1.4.1.11408.11.1.2.5.1.2
-- 1.3.6.1.4.1.11408.11.1.2.5.1.2
		-- 1.3.6.1.4.1.11408.11.1.2.5.1.2
		fhIfTunnelEncapMode OBJECT-TYPE
			SYNTAX Integer32
			MAX-ACCESS read-only
			STATUS current
			DESCRIPTION
				"Description."
			::= { fhIfTunnelEntry 2 }

		
--   1.3.6.1.4.1.11408.11.1.2.5.1.3
-- 1.3.6.1.4.1.11408.11.1.2.5.1.3
		-- 1.3.6.1.4.1.11408.11.1.2.5.1.3
		fhIfTunnelSrcIP OBJECT-TYPE
			SYNTAX IpAddress
			MAX-ACCESS read-only
			STATUS current
			DESCRIPTION
				"Description."
			::= { fhIfTunnelEntry 3 }

		
--   1.3.6.1.4.1.11408.11.1.2.5.1.4
-- 1.3.6.1.4.1.11408.11.1.2.5.1.4
		-- 1.3.6.1.4.1.11408.11.1.2.5.1.4
		fhIfTunnelDestIp OBJECT-TYPE
			SYNTAX IpAddress
			MAX-ACCESS read-only
			STATUS current
			DESCRIPTION
				"Description."
			::= { fhIfTunnelEntry 4 }

		
--   1.3.6.1.4.1.11408.11.1.2.5.1.5
-- 1.3.6.1.4.1.11408.11.1.2.5.1.5
		-- 1.3.6.1.4.1.11408.11.1.2.5.1.5
		fhIfTunnelLocalIp OBJECT-TYPE
			SYNTAX IpAddress
			MAX-ACCESS read-only
			STATUS current
			DESCRIPTION
				"Description."
			::= { fhIfTunnelEntry 5 }

		
--   1.3.6.1.4.1.11408.11.1.2.5.1.6
-- 1.3.6.1.4.1.11408.11.1.2.5.1.6
		-- 1.3.6.1.4.1.11408.11.1.2.5.1.6
		fhIfTunnelState OBJECT-TYPE
			SYNTAX Integer32
			MAX-ACCESS read-only
			STATUS current
			DESCRIPTION
				"Description."
			::= { fhIfTunnelEntry 6 }

		
--   1.3.6.1.4.1.11408.11.1.3
-- 1.3.6.1.4.1.11408.11.1.3
		-- 1.3.6.1.4.1.11408.11.1.3
		fhSysExtMIB OBJECT IDENTIFIER ::= { fhDatacomm 3 }

		
--   1.3.6.1.4.1.11408.11.1.3.1
-- 1.3.6.1.4.1.11408.11.1.3.1
		-- 1.3.6.1.4.1.11408.11.1.3.1
		devType OBJECT-TYPE
			SYNTAX OCTET STRING
			MAX-ACCESS read-only
			STATUS current
			DESCRIPTION
				"Description."
			::= { fhSysExtMIB 1 }

		
--   1.3.6.1.4.1.11408.11.1.3.2
-- 1.3.6.1.4.1.11408.11.1.3.2
		-- 1.3.6.1.4.1.11408.11.1.3.2
		loopback OBJECT-TYPE
			SYNTAX IpAddress
			MAX-ACCESS read-only
			STATUS current
			DESCRIPTION
				"Description."
			::= { fhSysExtMIB 2 }

		
--   1.3.6.1.4.1.11408.11.1.3.3
-- 1.3.6.1.4.1.11408.11.1.3.3
		-- 1.3.6.1.4.1.11408.11.1.3.3
		enable OBJECT-TYPE
			SYNTAX Integer32
			MAX-ACCESS read-only
			STATUS current
			DESCRIPTION
				"Description."
			::= { fhSysExtMIB 3 }

		
--   1.3.6.1.4.1.11408.11.1.3.4
-- 1.3.6.1.4.1.11408.11.1.3.4
		-- 1.3.6.1.4.1.11408.11.1.3.4
		snmpVer OBJECT-TYPE
			SYNTAX OCTET STRING
			MAX-ACCESS read-only
			STATUS current
			DESCRIPTION
				"Description."
			::= { fhSysExtMIB 4 }

		
--   1.3.6.1.4.1.11408.11.1.3.5
-- 1.3.6.1.4.1.11408.11.1.3.5
		-- 1.3.6.1.4.1.11408.11.1.3.5
		snmpCommunityNameTable OBJECT-TYPE
			SYNTAX SEQUENCE OF snmpCommunityNameEntry
			MAX-ACCESS not-accessible
			STATUS current
			DESCRIPTION
				"Description."
			::= { fhSysExtMIB 5 }

		
--   1.3.6.1.4.1.11408.11.1.3.5.1
-- 1.3.6.1.4.1.11408.11.1.3.5.1
		-- 1.3.6.1.4.1.11408.11.1.3.5.1
		snmpCommunityNameEntry OBJECT-TYPE
			SYNTAX snmpCommunityNameEntry
			MAX-ACCESS not-accessible
			STATUS current
			DESCRIPTION
				"Description."
			INDEX { Index }
			::= { snmpCommunityNameTable 1 }

		
		snmpCommunityNameEntry ::=
			SEQUENCE { 
				Index
					InterfaceIndex,
				snmpCommunityName
					OCTET STRING
			 }

--   1.3.6.1.4.1.11408.11.1.3.5.1.1
-- 1.3.6.1.4.1.11408.11.1.3.5.1.1
		-- 1.3.6.1.4.1.11408.11.1.3.5.1.1
		Index OBJECT-TYPE
			SYNTAX InterfaceIndex
			MAX-ACCESS read-only
			STATUS current
			DESCRIPTION
				"Description."
			::= { snmpCommunityNameEntry 1 }

		
--   1.3.6.1.4.1.11408.11.1.3.5.1.2
-- 1.3.6.1.4.1.11408.11.1.3.5.1.2
		-- 1.3.6.1.4.1.11408.11.1.3.5.1.2
		snmpCommunityName OBJECT-TYPE
			SYNTAX OCTET STRING
			MAX-ACCESS read-only
			STATUS current
			DESCRIPTION
				"Description."
			::= { snmpCommunityNameEntry 2 }

		
--   1.3.6.1.4.1.11408.11.1.3.6
-- 1.3.6.1.4.1.11408.11.1.3.6
		-- 1.3.6.1.4.1.11408.11.1.3.6
		hostName OBJECT-TYPE
			SYNTAX OCTET STRING
			MAX-ACCESS read-only
			STATUS current
			DESCRIPTION
				"Description."
			::= { fhSysExtMIB 6 }

		
--   1.3.6.1.4.1.11408.11.1.3.7
-- 1.3.6.1.4.1.11408.11.1.3.7
		-- 1.3.6.1.4.1.11408.11.1.3.7
		passWord OBJECT-TYPE
			SYNTAX OCTET STRING
			MAX-ACCESS read-only
			STATUS current
			DESCRIPTION
				"Description."
			::= { fhSysExtMIB 7 }

		
--   1.3.6.1.4.1.11408.11.1.3.8
-- 1.3.6.1.4.1.11408.11.1.3.8
		-- 1.3.6.1.4.1.11408.11.1.3.8
		rcuVersion OBJECT-TYPE
			SYNTAX OCTET STRING
			MAX-ACCESS read-only
			STATUS current
			DESCRIPTION
				"Description."
			::= { fhSysExtMIB 8 }

		
--   1.3.6.1.4.1.11408.11.1.3.10
-- 1.3.6.1.4.1.11408.11.1.3.10
		-- 1.3.6.1.4.1.11408.11.1.3.10
		snmpInfo OBJECT IDENTIFIER ::= { fhSysExtMIB 10 }

		
--   1.3.6.1.4.1.11408.11.1.3.10.1
-- 1.3.6.1.4.1.11408.11.1.3.10.1
		-- 1.3.6.1.4.1.11408.11.1.3.10.1
		snmpGlobal OBJECT IDENTIFIER ::= { snmpInfo 1 }

		
--   1.3.6.1.4.1.11408.11.1.3.10.1.1
-- 1.3.6.1.4.1.11408.11.1.3.10.1.1
		-- 1.3.6.1.4.1.11408.11.1.3.10.1.1
		agentEnable OBJECT-TYPE
			SYNTAX Integer32
			MAX-ACCESS read-only
			STATUS current
			DESCRIPTION
				"Description."
			::= { snmpGlobal 1 }

		
--   1.3.6.1.4.1.11408.11.1.3.10.1.2
-- 1.3.6.1.4.1.11408.11.1.3.10.1.2
		-- 1.3.6.1.4.1.11408.11.1.3.10.1.2
		aclId OBJECT-TYPE
			SYNTAX Integer32
			MAX-ACCESS read-only
			STATUS current
			DESCRIPTION
				"Description."
			::= { snmpGlobal 2 }

		
--   1.3.6.1.4.1.11408.11.1.3.10.2
-- 1.3.6.1.4.1.11408.11.1.3.10.2
		-- 1.3.6.1.4.1.11408.11.1.3.10.2
		snmpNameTable OBJECT-TYPE
			SYNTAX SEQUENCE OF SnmpNameEntry
			MAX-ACCESS not-accessible
			STATUS current
			DESCRIPTION
				"Description."
			::= { snmpInfo 2 }

		
--   1.3.6.1.4.1.11408.11.1.3.10.2.1
-- 1.3.6.1.4.1.11408.11.1.3.10.2.1
		-- 1.3.6.1.4.1.11408.11.1.3.10.2.1
		snmpNameEntry OBJECT-TYPE
			SYNTAX SnmpNameEntry
			MAX-ACCESS not-accessible
			STATUS current
			DESCRIPTION
				"Description."
			INDEX { snmpVersion, snmpNameId }
			::= { snmpNameTable 1 }

		
		SnmpNameEntry ::=
			SEQUENCE { 
				snmpVersion
					Integer32,
				snmpNameId
					Integer32,
				snmpName
					OCTET STRING
			 }

--   1.3.6.1.4.1.11408.11.1.3.10.2.1.1
-- 1.3.6.1.4.1.11408.11.1.3.10.2.1.1
		-- 1.3.6.1.4.1.11408.11.1.3.10.2.1.1
		snmpVersion OBJECT-TYPE
			SYNTAX Integer32
			MAX-ACCESS read-only
			STATUS current
			DESCRIPTION
				"Description."
			::= { snmpNameEntry 1 }

		
--   1.3.6.1.4.1.11408.11.1.3.10.2.1.2
-- 1.3.6.1.4.1.11408.11.1.3.10.2.1.2
		-- 1.3.6.1.4.1.11408.11.1.3.10.2.1.2
		snmpNameId OBJECT-TYPE
			SYNTAX Integer32
			MAX-ACCESS read-only
			STATUS current
			DESCRIPTION
				"Description."
			::= { snmpNameEntry 2 }

		
--   1.3.6.1.4.1.11408.11.1.3.10.2.1.3
-- 1.3.6.1.4.1.11408.11.1.3.10.2.1.3
		-- 1.3.6.1.4.1.11408.11.1.3.10.2.1.3
		snmpName OBJECT-TYPE
			SYNTAX OCTET STRING
			MAX-ACCESS read-only
			STATUS current
			DESCRIPTION
				"Description."
			::= { snmpNameEntry 3 }

		
--   1.3.6.1.4.1.11408.11.1.3.10.3
-- 1.3.6.1.4.1.11408.11.1.3.10.3
		-- 1.3.6.1.4.1.11408.11.1.3.10.3
		snmpTrapTable OBJECT-TYPE
			SYNTAX SEQUENCE OF SnmpTrapEntry
			MAX-ACCESS not-accessible
			STATUS current
			DESCRIPTION
				"Description."
			::= { snmpInfo 3 }

		
--   1.3.6.1.4.1.11408.11.1.3.10.3.1
-- 1.3.6.1.4.1.11408.11.1.3.10.3.1
		-- 1.3.6.1.4.1.11408.11.1.3.10.3.1
		snmpTrapEntry OBJECT-TYPE
			SYNTAX SnmpTrapEntry
			MAX-ACCESS not-accessible
			STATUS current
			DESCRIPTION
				"Description."
			INDEX { snmpTrapIp }
			::= { snmpTrapTable 1 }

		
		SnmpTrapEntry ::=
			SEQUENCE { 
				snmpTrapIp
					IpAddress
			 }

--   1.3.6.1.4.1.11408.11.1.3.10.3.1.1
-- 1.3.6.1.4.1.11408.11.1.3.10.3.1.1
		-- 1.3.6.1.4.1.11408.11.1.3.10.3.1.1
		snmpTrapIp OBJECT-TYPE
			SYNTAX IpAddress
			MAX-ACCESS read-only
			STATUS current
			DESCRIPTION
				"Description."
			::= { snmpTrapEntry 1 }

		
--   1.3.6.1.4.1.11408.11.1.4
-- 1.3.6.1.4.1.11408.11.1.4
		-- 1.3.6.1.4.1.11408.11.1.4
		tcIpRanDcnMib OBJECT IDENTIFIER ::= { fhDatacomm 4 }

		
--   1.3.6.1.4.1.11408.11.1.4.1
-- 1.3.6.1.4.1.11408.11.1.4.1
		-- 1.3.6.1.4.1.11408.11.1.4.1
		tcIpRanDcnObjects OBJECT IDENTIFIER ::= { tcIpRanDcnMib 1 }

		
--   1.3.6.1.4.1.11408.11.1.4.1.1
-- 1.3.6.1.4.1.11408.11.1.4.1.1
		-- 1.3.6.1.4.1.11408.11.1.4.1.1
		tcIpRanDcnInfoObject OBJECT IDENTIFIER ::= { tcIpRanDcnObjects 1 }

		
--   1.3.6.1.4.1.11408.11.1.4.1.1.1
-- 1.3.6.1.4.1.11408.11.1.4.1.1.1
		-- 1.3.6.1.4.1.11408.11.1.4.1.1.1
		tcIpRanDcnNeId OBJECT-TYPE
			SYNTAX tcIpRanNeId
			MAX-ACCESS read-only
			STATUS current
			DESCRIPTION
				"
				This object indicates the ID of the node.
				"
			::= { tcIpRanDcnInfoObject 1 }

		
--   1.3.6.1.4.1.11408.11.1.4.1.1.2
-- 1.3.6.1.4.1.11408.11.1.4.1.1.2
		-- 1.3.6.1.4.1.11408.11.1.4.1.1.2
		tcIpRanDcnNeIpType OBJECT-TYPE
			SYNTAX InetAddressType
			MAX-ACCESS read-only
			STATUS current
			DESCRIPTION
				" 
				This object indicates the type of the node IP.
				"
			::= { tcIpRanDcnInfoObject 2 }

		
--   1.3.6.1.4.1.11408.11.1.4.1.1.3
-- 1.3.6.1.4.1.11408.11.1.4.1.1.3
		-- 1.3.6.1.4.1.11408.11.1.4.1.1.3
		tcIpRanDcnNeIp OBJECT-TYPE
			SYNTAX InetAddress
			MAX-ACCESS read-only
			STATUS current
			DESCRIPTION
				" 
				This object indicates the IP of the node.
				"
			::= { tcIpRanDcnInfoObject 3 }

		
--   1.3.6.1.4.1.11408.11.1.4.1.1.4
-- 1.3.6.1.4.1.11408.11.1.4.1.1.4
		-- 1.3.6.1.4.1.11408.11.1.4.1.1.4
		tcIpRanDcnMask OBJECT-TYPE
			SYNTAX InetAddress
			MAX-ACCESS read-only
			STATUS current
			DESCRIPTION
				" 
				This object indicates the IP address mask.
				"
			::= { tcIpRanDcnInfoObject 4 }

		
--   1.3.6.1.4.1.11408.11.1.4.1.1.5
-- 1.3.6.1.4.1.11408.11.1.4.1.1.5
		-- 1.3.6.1.4.1.11408.11.1.4.1.1.5
		tcIpRanDcnPort OBJECT-TYPE
			SYNTAX Unsigned32
			MAX-ACCESS read-only
			STATUS current
			DESCRIPTION
				"
				This object indicates the port of TCP.
				"
			::= { tcIpRanDcnInfoObject 5 }

		
--   1.3.6.1.4.1.11408.11.1.4.1.1.6
-- 1.3.6.1.4.1.11408.11.1.4.1.1.6
		-- 1.3.6.1.4.1.11408.11.1.4.1.1.6
		tcIpRanDcnConnectMode OBJECT-TYPE
			SYNTAX INTEGER
				{
				normal(1),
				ssl(2),
				both(3)
				}
			MAX-ACCESS read-only
			STATUS current
			DESCRIPTION
				"
				This object indicates the mode of connect.
				"
			::= { tcIpRanDcnInfoObject 6 }

		
--   1.3.6.1.4.1.11408.11.1.4.1.1.7
-- 1.3.6.1.4.1.11408.11.1.4.1.1.7
		-- 1.3.6.1.4.1.11408.11.1.4.1.1.7
		tcIpRanDcnSSLPort OBJECT-TYPE
			SYNTAX Unsigned32
			MAX-ACCESS read-only
			STATUS current
			DESCRIPTION
				"
				This object indicates the ssl port of TCP.
				"
			::= { tcIpRanDcnInfoObject 7 }

		
--   1.3.6.1.4.1.11408.11.1.4.1.2
-- 1.3.6.1.4.1.11408.11.1.4.1.2
		-- 1.3.6.1.4.1.11408.11.1.4.1.2
		tcIpRanDcnNeInfoTable OBJECT-TYPE
			SYNTAX SEQUENCE OF tcIpRanDcnNeInfoEntry
			MAX-ACCESS not-accessible
			STATUS current
			DESCRIPTION
				"A table of network element information."
			::= { tcIpRanDcnObjects 2 }

		
--   1.3.6.1.4.1.11408.11.1.4.1.2.1
-- 1.3.6.1.4.1.11408.11.1.4.1.2.1
		-- 1.3.6.1.4.1.11408.11.1.4.1.2.1
		tcIpRanDcnNeInfoEntry OBJECT-TYPE
			SYNTAX tcIpRanDcnNeInfoEntry
			MAX-ACCESS not-accessible
			STATUS current
			DESCRIPTION
				"A single network element information entry."
			INDEX { tcIpRanDcnNeInfoNeId }
			::= { tcIpRanDcnNeInfoTable 1 }

		
		tcIpRanDcnNeInfoEntry ::=
			SEQUENCE { 
				tcIpRanDcnNeInfoNeId
					tcIpRanNeId,
				tcIpRanDcnNeInfoNeIpType
					InetAddressType,
				tcIpRanDcnNeInfoNeIp
					InetAddress,
				tcIpRanDcnNeInfoDistance
					Integer32,
				tcIpRanDcnNeInfoLifeCycle
					Integer32,
				tcIpRanDcnNeInfoHostName
					DisplayString,
				tcIpRanDcnNeInfoNeIpMask
					InetAddress
			 }

--   1.3.6.1.4.1.11408.11.1.4.1.2.1.1
-- 1.3.6.1.4.1.11408.11.1.4.1.2.1.1
		-- 1.3.6.1.4.1.11408.11.1.4.1.2.1.1
		tcIpRanDcnNeInfoNeId OBJECT-TYPE
			SYNTAX tcIpRanNeId
			MAX-ACCESS accessible-for-notify
			STATUS current
			DESCRIPTION
				"The network element id, uniquely identifying 
				one network element in the routing domain."
			::= { tcIpRanDcnNeInfoEntry 1 }

		
--   1.3.6.1.4.1.11408.11.1.4.1.2.1.2
-- 1.3.6.1.4.1.11408.11.1.4.1.2.1.2
		-- 1.3.6.1.4.1.11408.11.1.4.1.2.1.2
		tcIpRanDcnNeInfoNeIpType OBJECT-TYPE
			SYNTAX InetAddressType
			MAX-ACCESS read-only
			STATUS current
			DESCRIPTION
				"The IP type of the network element node."
			::= { tcIpRanDcnNeInfoEntry 2 }

		
--   1.3.6.1.4.1.11408.11.1.4.1.2.1.3
-- 1.3.6.1.4.1.11408.11.1.4.1.2.1.3
		-- 1.3.6.1.4.1.11408.11.1.4.1.2.1.3
		tcIpRanDcnNeInfoNeIp OBJECT-TYPE
			SYNTAX InetAddress
			MAX-ACCESS read-only
			STATUS current
			DESCRIPTION
				"The IP address of the network element node."
			::= { tcIpRanDcnNeInfoEntry 3 }

		
--   1.3.6.1.4.1.11408.11.1.4.1.2.1.4
-- 1.3.6.1.4.1.11408.11.1.4.1.2.1.4
		-- 1.3.6.1.4.1.11408.11.1.4.1.2.1.4
		tcIpRanDcnNeInfoDistance OBJECT-TYPE
			SYNTAX Integer32
			MAX-ACCESS read-only
			STATUS current
			DESCRIPTION
				"The distance from current network element to the remote network element node."
			::= { tcIpRanDcnNeInfoEntry 4 }

		
--   1.3.6.1.4.1.11408.11.1.4.1.2.1.5
-- 1.3.6.1.4.1.11408.11.1.4.1.2.1.5
		-- 1.3.6.1.4.1.11408.11.1.4.1.2.1.5
		tcIpRanDcnNeInfoLifeCycle OBJECT-TYPE
			SYNTAX Integer32
			MAX-ACCESS read-only
			STATUS current
			DESCRIPTION
				"The left time period for the network element node exist, 
				The value will set to the initial period value when current 
				network element receive new advertisement packet for the 
				node, it will reduce one each period time and delete the 
				entry when Tm decrease to zero (The initial period value and
				one period time value may be different for different device version, 
				user no need care it's value)."
			::= { tcIpRanDcnNeInfoEntry 5 }

		
--   1.3.6.1.4.1.11408.11.1.4.1.2.1.6
-- 1.3.6.1.4.1.11408.11.1.4.1.2.1.6
		-- 1.3.6.1.4.1.11408.11.1.4.1.2.1.6
		tcIpRanDcnNeInfoHostName OBJECT-TYPE
			SYNTAX DisplayString (SIZE (0..255))
			MAX-ACCESS read-only
			STATUS current
			DESCRIPTION
				"The hostname of the network element."
			::= { tcIpRanDcnNeInfoEntry 6 }

		
--   1.3.6.1.4.1.11408.11.1.4.1.2.1.7
-- 1.3.6.1.4.1.11408.11.1.4.1.2.1.7
		-- 1.3.6.1.4.1.11408.11.1.4.1.2.1.7
		tcIpRanDcnNeInfoNeIpMask OBJECT-TYPE
			SYNTAX InetAddress
			MAX-ACCESS read-only
			STATUS current
			DESCRIPTION
				"The ip mask of the network element."
			::= { tcIpRanDcnNeInfoEntry 7 }

		
--   1.3.6.1.4.1.11408.11.1.4.2
-- 1.3.6.1.4.1.11408.11.1.4.2
		-- 1.3.6.1.4.1.11408.11.1.4.2
		tcIpRanDcnTrapObjects OBJECT IDENTIFIER ::= { tcIpRanDcnMib 2 }

		
--   1.3.6.1.4.1.11408.11.1.4.2.1
-- 1.3.6.1.4.1.11408.11.1.4.2.1
		-- 1.3.6.1.4.1.11408.11.1.4.2.1
		tcIpRanDcnNeNumber OBJECT-TYPE
			SYNTAX Integer32
			MAX-ACCESS accessible-for-notify
			STATUS current
			DESCRIPTION
				"The NE number."
			::= { tcIpRanDcnTrapObjects 1 }

		
--   1.3.6.1.4.1.11408.11.1.4.2.2
-- 1.3.6.1.4.1.11408.11.1.4.2.2
		-- 1.3.6.1.4.1.11408.11.1.4.2.2
		tcIpRanDcnNeChangeMode OBJECT-TYPE
			SYNTAX INTEGER
				{
				online(1),
				offline(2)
				}
			MAX-ACCESS accessible-for-notify
			STATUS current
			DESCRIPTION
				"
				This object is used to indicate the mode of NE added.
				"
			::= { tcIpRanDcnTrapObjects 2 }

		
--   1.3.6.1.4.1.11408.11.1.4.2.3
-- 1.3.6.1.4.1.11408.11.1.4.2.3
		-- 1.3.6.1.4.1.11408.11.1.4.2.3
		tcIpRanDcnCompanyName OBJECT-TYPE
			SYNTAX DisplayString (SIZE (0..255))
			MAX-ACCESS accessible-for-notify
			STATUS current
			DESCRIPTION
				"The name of company."
			::= { tcIpRanDcnTrapObjects 3 }

		
--   1.3.6.1.4.1.11408.11.1.4.2.4
-- 1.3.6.1.4.1.11408.11.1.4.2.4
		-- 1.3.6.1.4.1.11408.11.1.4.2.4
		tcIpRanDcnDeviceType OBJECT-TYPE
			SYNTAX DisplayString (SIZE (0..255))
			MAX-ACCESS accessible-for-notify
			STATUS current
			DESCRIPTION
				"The type of device."
			::= { tcIpRanDcnTrapObjects 4 }

		
--   1.3.6.1.4.1.11408.11.1.4.2.5
-- 1.3.6.1.4.1.11408.11.1.4.2.5
		-- 1.3.6.1.4.1.11408.11.1.4.2.5
		tcIpRanDcnDeviceMac OBJECT-TYPE
			SYNTAX PhysAddress
			MAX-ACCESS accessible-for-notify
			STATUS current
			DESCRIPTION
				"The MAC address of the interface."
			::= { tcIpRanDcnTrapObjects 5 }

		
--   1.3.6.1.4.1.11408.11.1.4.2.6
-- 1.3.6.1.4.1.11408.11.1.4.2.6
		-- 1.3.6.1.4.1.11408.11.1.4.2.6
		tcIpRanDcnIpv6 OBJECT-TYPE
			SYNTAX Ipv6Address
			MAX-ACCESS accessible-for-notify
			STATUS current
			DESCRIPTION
				"The address of IPV6."
			::= { tcIpRanDcnTrapObjects 6 }

		
--   1.3.6.1.4.1.11408.11.1.4.3
-- 1.3.6.1.4.1.11408.11.1.4.3
		-- 1.3.6.1.4.1.11408.11.1.4.3
		tcIpRanDcnTraps OBJECT IDENTIFIER ::= { tcIpRanDcnMib 3 }

		
--   1.3.6.1.4.1.11408.11.1.4.3.1
-- 1.3.6.1.4.1.11408.11.1.4.3.1
		-- 1.3.6.1.4.1.11408.11.1.4.3.1
		tcIpRanDcnNeNumberOverLoad NOTIFICATION-TYPE
			OBJECTS { tcIpRanDcnNeNumber }
			STATUS current
			DESCRIPTION 
				"This object is used to indicate NE number overload."
			::= { tcIpRanDcnTraps 1 }

		
--   1.3.6.1.4.1.11408.11.1.4.3.2
-- 1.3.6.1.4.1.11408.11.1.4.3.2
		-- 1.3.6.1.4.1.11408.11.1.4.3.2
		tcIpRanDcnNeNumberOverLoadRecovery NOTIFICATION-TYPE
			OBJECTS { tcIpRanDcnNeNumber }
			STATUS current
			DESCRIPTION 
				"This object is used to indicate NE number overload recovery."
			::= { tcIpRanDcnTraps 2 }

		
--   1.3.6.1.4.1.11408.11.1.4.3.3
-- 1.3.6.1.4.1.11408.11.1.4.3.3
		-- 1.3.6.1.4.1.11408.11.1.4.3.3
		tcIpRanDcnNeOnline NOTIFICATION-TYPE
			OBJECTS { tcIpRanDcnNeChangeMode, tcIpRanDcnNeInfoNeId, tcIpRanDcnNeInfoNeIpType, tcIpRanDcnNeInfoNeIp, tcIpRanDcnNeInfoNeIpMask, 
				tcIpRanDcnNeNumber, tcIpRanDcnCompanyName, tcIpRanDcnDeviceType, tcIpRanDcnDeviceMac, tcIpRanDcnIpv6
				 }
			STATUS current
			DESCRIPTION 
				"This object is used to indicate NE on-line."
			::= { tcIpRanDcnTraps 3 }

		
--   1.3.6.1.4.1.11408.11.1.4.3.4
-- 1.3.6.1.4.1.11408.11.1.4.3.4
		-- 1.3.6.1.4.1.11408.11.1.4.3.4
		tcIpRanDcnNeOffline NOTIFICATION-TYPE
			OBJECTS { tcIpRanDcnNeInfoNeId, tcIpRanDcnNeInfoNeIpType, tcIpRanDcnNeInfoNeIp }
			STATUS current
			DESCRIPTION 
				"This object is used to indicate NE off-line."
			::= { tcIpRanDcnTraps 4 }

		
--   1.3.6.1.4.1.11408.11.1.4.4
-- 1.3.6.1.4.1.11408.11.1.4.4
		-- 1.3.6.1.4.1.11408.11.1.4.4
		tcIpRanDcnConformance OBJECT IDENTIFIER ::= { tcIpRanDcnMib 4 }

		
--   1.3.6.1.4.1.11408.11.1.4.4.1
-- 1.3.6.1.4.1.11408.11.1.4.4.1
		-- 1.3.6.1.4.1.11408.11.1.4.4.1
		tcIpRanDcnCompliances OBJECT IDENTIFIER ::= { tcIpRanDcnConformance 1 }

		
--   1.3.6.1.4.1.11408.11.1.4.4.1.1
-- this module
-- 1.3.6.1.4.1.11408.11.1.4.4.1.1
-- this module
		-- 1.3.6.1.4.1.11408.11.1.4.4.1.1
		tcIpRanDcnFullCompliance MODULE-COMPLIANCE
			STATUS current
			DESCRIPTION 
				"The compliance statement for the TELCOM-IPRAN-DCN-MIB."
			MODULE -- this module
				MANDATORY-GROUPS { tcIpRanDcnInfoGroup }
			::= { tcIpRanDcnCompliances 1 }

		
--   1.3.6.1.4.1.11408.11.1.4.4.2
-- 1.3.6.1.4.1.11408.11.1.4.4.2
		-- 1.3.6.1.4.1.11408.11.1.4.4.2
		tcIpRanDcnGroups OBJECT IDENTIFIER ::= { tcIpRanDcnConformance 2 }

		
--   1.3.6.1.4.1.11408.11.1.4.4.2.1
-- 1.3.6.1.4.1.11408.11.1.4.4.2.1
		-- 1.3.6.1.4.1.11408.11.1.4.4.2.1
		tcIpRanDcnInfoGroup OBJECT-GROUP
			OBJECTS { tcIpRanDcnNeId, tcIpRanDcnNeIpType, tcIpRanDcnNeIp, tcIpRanDcnMask, tcIpRanDcnPort, 
				tcIpRanDcnConnectMode, tcIpRanDcnSSLPort }
			STATUS current
			DESCRIPTION 
				"The group for ipran dcn."
			::= { tcIpRanDcnGroups 1 }

		
--   1.3.6.1.4.1.11408.11.1.4.4.2.2
-- 1.3.6.1.4.1.11408.11.1.4.4.2.2
		-- 1.3.6.1.4.1.11408.11.1.4.4.2.2
		tcIpRanDcnTrapEventGroup NOTIFICATION-GROUP
			NOTIFICATIONS { tcIpRanDcnNeNumberOverLoad, tcIpRanDcnNeNumberOverLoadRecovery, tcIpRanDcnNeOnline, tcIpRanDcnNeOffline }
			STATUS current
			DESCRIPTION 
				"These objects are used to indicate the NE number state."
			::= { tcIpRanDcnGroups 2 }

		
--   1.3.6.1.4.1.11408.11.1.4.4.2.3
-- 1.3.6.1.4.1.11408.11.1.4.4.2.3
		-- 1.3.6.1.4.1.11408.11.1.4.4.2.3
		tcIpRanDcnTrapObjectsGroup OBJECT-GROUP
			OBJECTS { tcIpRanDcnNeNumber, tcIpRanDcnNeInfoNeId, tcIpRanDcnNeInfoNeIpType, tcIpRanDcnNeInfoNeIp, tcIpRanDcnNeInfoNeIpMask, 
				tcIpRanDcnNeChangeMode, tcIpRanDcnCompanyName, tcIpRanDcnDeviceType, tcIpRanDcnDeviceMac, tcIpRanDcnIpv6
				 }
			STATUS current
			DESCRIPTION 
				"The objects are used to indicate the NE number."
			::= { tcIpRanDcnGroups 3 }

		
--   1.3.6.1.4.1.11408.11.1.4.4.2.4
-- 1.3.6.1.4.1.11408.11.1.4.4.2.4
		-- 1.3.6.1.4.1.11408.11.1.4.4.2.4
		tcIpRanDcnNeInfoGroup OBJECT-GROUP
			OBJECTS { tcIpRanDcnNeInfoNeIpType, tcIpRanDcnNeInfoNeIp, tcIpRanDcnNeInfoDistance, tcIpRanDcnNeInfoLifeCycle, tcIpRanDcnNeInfoHostName, 
				tcIpRanDcnNeInfoNeIpMask }
			STATUS current
			DESCRIPTION 
				"These objects are required for display ne-info table."
			::= { tcIpRanDcnGroups 4 }

		
--   1.3.6.1.4.1.11408.11.1.5
-- 1.3.6.1.4.1.11408.11.1.5
		-- 1.3.6.1.4.1.11408.11.1.5
		fhBfd OBJECT IDENTIFIER ::= { fhDatacomm 5 }

		
--   1.3.6.1.4.1.11408.11.1.5.2
-- 1.3.6.1.4.1.11408.11.1.5.2
		-- 1.3.6.1.4.1.11408.11.1.5.2
		fhBfdTrap OBJECT IDENTIFIER ::= { fhBfd 2 }

		
--   1.3.6.1.4.1.11408.11.1.5.2.1
-- 1.3.6.1.4.1.11408.11.1.5.2.1
		-- 1.3.6.1.4.1.11408.11.1.5.2.1
		fhBfdSessPeer OBJECT IDENTIFIER ::= { fhBfdTrap 1 }

		
--   1.3.6.1.4.1.11408.11.1.5.2.1.1
-- 1.3.6.1.4.1.11408.11.1.5.2.1.1
		-- 1.3.6.1.4.1.11408.11.1.5.2.1.1
		fhBfdSessPeerDown NOTIFICATION-TYPE
			STATUS current
			DESCRIPTION 
				"Description."
			::= { fhBfdSessPeer 1 }

		
--   1.3.6.1.4.1.11408.11.1.5.2.1.2
-- 1.3.6.1.4.1.11408.11.1.5.2.1.2
		-- 1.3.6.1.4.1.11408.11.1.5.2.1.2
		fhBfdSessPeerUp NOTIFICATION-TYPE
			STATUS current
			DESCRIPTION 
				"Description."
			::= { fhBfdSessPeer 2 }

		
--   1.3.6.1.4.1.11408.11.1.5.2.2
-- 1.3.6.1.4.1.11408.11.1.5.2.2
		-- 1.3.6.1.4.1.11408.11.1.5.2.2
		fhBfdSessSingleHop OBJECT IDENTIFIER ::= { fhBfdTrap 2 }

		
--   1.3.6.1.4.1.11408.11.1.5.2.2.1
-- 1.3.6.1.4.1.11408.11.1.5.2.2.1
		-- 1.3.6.1.4.1.11408.11.1.5.2.2.1
		fhBfdSessSingleHopDown NOTIFICATION-TYPE
			STATUS current
			DESCRIPTION 
				"Description."
			::= { fhBfdSessSingleHop 1 }

		
--   1.3.6.1.4.1.11408.11.1.5.2.2.2
-- 1.3.6.1.4.1.11408.11.1.5.2.2.2
		-- 1.3.6.1.4.1.11408.11.1.5.2.2.2
		fhBfdSessSingleHopUp NOTIFICATION-TYPE
			STATUS current
			DESCRIPTION 
				"Description."
			::= { fhBfdSessSingleHop 2 }

		
--   1.3.6.1.4.1.11408.11.1.5.2.3
-- 1.3.6.1.4.1.11408.11.1.5.2.3
		-- 1.3.6.1.4.1.11408.11.1.5.2.3
		fhBfdSessRsvpLsp OBJECT IDENTIFIER ::= { fhBfdTrap 3 }

		
--   1.3.6.1.4.1.11408.11.1.5.2.3.1
-- 1.3.6.1.4.1.11408.11.1.5.2.3.1
		-- 1.3.6.1.4.1.11408.11.1.5.2.3.1
		fhBfdSessRsvpLspDown NOTIFICATION-TYPE
			STATUS current
			DESCRIPTION 
				"Description."
			::= { fhBfdSessRsvpLsp 1 }

		
--   1.3.6.1.4.1.11408.11.1.5.2.3.2
-- 1.3.6.1.4.1.11408.11.1.5.2.3.2
		-- 1.3.6.1.4.1.11408.11.1.5.2.3.2
		fhBfdSessRsvpLspUp NOTIFICATION-TYPE
			STATUS current
			DESCRIPTION 
				"Description."
			::= { fhBfdSessRsvpLsp 2 }

		
--   1.3.6.1.4.1.11408.11.1.5.2.4
-- 1.3.6.1.4.1.11408.11.1.5.2.4
		-- 1.3.6.1.4.1.11408.11.1.5.2.4
		fhBfdSessLdpLsp OBJECT IDENTIFIER ::= { fhBfdTrap 4 }

		
--   1.3.6.1.4.1.11408.11.1.5.2.4.1
-- 1.3.6.1.4.1.11408.11.1.5.2.4.1
		-- 1.3.6.1.4.1.11408.11.1.5.2.4.1
		fhBfdSessLdpLspDown NOTIFICATION-TYPE
			STATUS current
			DESCRIPTION 
				"Description."
			::= { fhBfdSessLdpLsp 1 }

		
--   1.3.6.1.4.1.11408.11.1.5.2.4.2
-- 1.3.6.1.4.1.11408.11.1.5.2.4.2
		-- 1.3.6.1.4.1.11408.11.1.5.2.4.2
		fhBfdSessLdpLspUp NOTIFICATION-TYPE
			STATUS current
			DESCRIPTION 
				"Description."
			::= { fhBfdSessLdpLsp 2 }

		
--   1.3.6.1.4.1.11408.11.1.5.2.5
-- 1.3.6.1.4.1.11408.11.1.5.2.5
		-- 1.3.6.1.4.1.11408.11.1.5.2.5
		fhBfdSessPw OBJECT IDENTIFIER ::= { fhBfdTrap 5 }

		
--   1.3.6.1.4.1.11408.11.1.5.2.5.1
-- 1.3.6.1.4.1.11408.11.1.5.2.5.1
		-- 1.3.6.1.4.1.11408.11.1.5.2.5.1
		fhBfdSessPwDown NOTIFICATION-TYPE
			STATUS current
			DESCRIPTION 
				"Description."
			::= { fhBfdSessPw 1 }

		
--   1.3.6.1.4.1.11408.11.1.5.2.5.2
-- 1.3.6.1.4.1.11408.11.1.5.2.5.2
		-- 1.3.6.1.4.1.11408.11.1.5.2.5.2
		fhBfdSessPwUp NOTIFICATION-TYPE
			STATUS current
			DESCRIPTION 
				"Description."
			::= { fhBfdSessPw 2 }

		
--   1.3.6.1.4.1.11408.11.1.5.2.6
-- 1.3.6.1.4.1.11408.11.1.5.2.6
		-- 1.3.6.1.4.1.11408.11.1.5.2.6
		fhBfdSessLimit OBJECT IDENTIFIER ::= { fhBfdTrap 6 }

		
--   1.3.6.1.4.1.11408.11.1.5.2.6.1
-- 1.3.6.1.4.1.11408.11.1.5.2.6.1
		-- 1.3.6.1.4.1.11408.11.1.5.2.6.1
		fhBfdSessReachLimit NOTIFICATION-TYPE
			STATUS current
			DESCRIPTION 
				"Description."
			::= { fhBfdSessLimit 1 }

		
--   1.3.6.1.4.1.11408.11.1.6
-- 1.3.6.1.4.1.11408.11.1.6
		-- 1.3.6.1.4.1.11408.11.1.6
		fhVC OBJECT IDENTIFIER ::= { fhDatacomm 6 }

		
--   1.3.6.1.4.1.11408.11.1.6.1
-- 1.3.6.1.4.1.11408.11.1.6.1
		-- 1.3.6.1.4.1.11408.11.1.6.1
		fhVCType OBJECT IDENTIFIER ::= { fhVC 1 }

		
--   1.3.6.1.4.1.11408.11.1.6.1.1
-- 1.3.6.1.4.1.11408.11.1.6.1.1
		-- 1.3.6.1.4.1.11408.11.1.6.1.1
		fhVCTable OBJECT-TYPE
			SYNTAX SEQUENCE OF fhVCEntry
			MAX-ACCESS not-accessible
			STATUS current
			DESCRIPTION
				"Description."
			::= { fhVCType 1 }

		
--   1.3.6.1.4.1.11408.11.1.6.1.1.1
-- 1.3.6.1.4.1.11408.11.1.6.1.1.1
		-- 1.3.6.1.4.1.11408.11.1.6.1.1.1
		fhVCEntry OBJECT-TYPE
			SYNTAX fhVCEntry
			MAX-ACCESS not-accessible
			STATUS current
			DESCRIPTION
				"Description."
			INDEX { INTEGER }
			::= { fhVCTable 1 }

		
		fhVCEntry ::=
			SEQUENCE { 
				fhVCName
					OCTET STRING,
				fhVCTypes
					INTEGER,
				fhVCnode0
					Integer32,
				fhVCnode1
					Integer32,
				fhVCCtrlWord
					INTEGER,
				fhVCSecondaryPwId
					INTEGER,
				fhVCnode2
					Integer32,
				fhVCPrimaryPwId
					IpAddress,
				fhVCPeerIP
					IpAddress,
				fhVCLocalIP
					IpAddress,
				fhVCEncapType
					INTEGER,
				fhVCId
					Integer32,
				fhVCPeerVcID
					Integer32,
				fhVCAcIfName
					OCTET STRING,
				fhVCRemoteAcIfName
					OCTET STRING,
				fhVCActiveStatus
					Integer32,
				fhVCOperStatus
					Integer32,
				fhVCOutboundLabel
					Integer32,
				fhVCInboundLabel
					Integer32,
				fhVCTunnelIfIndex
					Integer32,
				fhVCTunnelID
					Integer32,
				fhVCTunnelTyep
					Integer32
			 }

--   1.3.6.1.4.1.11408.11.1.6.1.1.1.1
-- 1.3.6.1.4.1.11408.11.1.6.1.1.1.1
		-- 1.3.6.1.4.1.11408.11.1.6.1.1.1.1
		fhVCName OBJECT-TYPE
			SYNTAX OCTET STRING
			MAX-ACCESS read-only
			STATUS current
			DESCRIPTION
				"Description."
			::= { fhVCEntry 1 }

		
--   1.3.6.1.4.1.11408.11.1.6.1.1.1.2
-- 1.3.6.1.4.1.11408.11.1.6.1.1.1.2
		-- 1.3.6.1.4.1.11408.11.1.6.1.1.1.2
		fhVCTypes OBJECT-TYPE
			SYNTAX INTEGER
			MAX-ACCESS read-only
			STATUS current
			DESCRIPTION
				"Description."
			::= { fhVCEntry 2 }

		
--   1.3.6.1.4.1.11408.11.1.6.1.1.1.3
-- 1.3.6.1.4.1.11408.11.1.6.1.1.1.3
		-- 1.3.6.1.4.1.11408.11.1.6.1.1.1.3
		fhVCnode0 OBJECT-TYPE
			SYNTAX Integer32
			MAX-ACCESS read-write
			STATUS current
			DESCRIPTION
				"Description."
			::= { fhVCEntry 3 }

		
--   1.3.6.1.4.1.11408.11.1.6.1.1.1.4
-- 1.3.6.1.4.1.11408.11.1.6.1.1.1.4
		-- 1.3.6.1.4.1.11408.11.1.6.1.1.1.4
		fhVCnode1 OBJECT-TYPE
			SYNTAX Integer32
			MAX-ACCESS read-write
			STATUS current
			DESCRIPTION
				"Description."
			::= { fhVCEntry 4 }

		
--   1.3.6.1.4.1.11408.11.1.6.1.1.1.5
-- 1.3.6.1.4.1.11408.11.1.6.1.1.1.5
		-- 1.3.6.1.4.1.11408.11.1.6.1.1.1.5
		fhVCCtrlWord OBJECT-TYPE
			SYNTAX INTEGER
			MAX-ACCESS read-only
			STATUS current
			DESCRIPTION
				"Description."
			::= { fhVCEntry 5 }

		
--   1.3.6.1.4.1.11408.11.1.6.1.1.1.6
-- 1.3.6.1.4.1.11408.11.1.6.1.1.1.6
		-- 1.3.6.1.4.1.11408.11.1.6.1.1.1.6
		fhVCSecondaryPwId OBJECT-TYPE
			SYNTAX INTEGER
			MAX-ACCESS read-only
			STATUS current
			DESCRIPTION
				"Description."
			::= { fhVCEntry 6 }

		
--   1.3.6.1.4.1.11408.11.1.6.1.1.1.7
-- 1.3.6.1.4.1.11408.11.1.6.1.1.1.7
		-- 1.3.6.1.4.1.11408.11.1.6.1.1.1.7
		fhVCnode2 OBJECT-TYPE
			SYNTAX Integer32
			MAX-ACCESS read-write
			STATUS current
			DESCRIPTION
				"Description."
			::= { fhVCEntry 7 }

		
--   1.3.6.1.4.1.11408.11.1.6.1.1.1.8
-- 1.3.6.1.4.1.11408.11.1.6.1.1.1.8
		-- 1.3.6.1.4.1.11408.11.1.6.1.1.1.8
		fhVCPrimaryPwId OBJECT-TYPE
			SYNTAX IpAddress
			MAX-ACCESS read-only
			STATUS current
			DESCRIPTION
				"Description."
			::= { fhVCEntry 8 }

		
--   1.3.6.1.4.1.11408.11.1.6.1.1.1.9
-- 1.3.6.1.4.1.11408.11.1.6.1.1.1.9
		-- 1.3.6.1.4.1.11408.11.1.6.1.1.1.9
		fhVCPeerIP OBJECT-TYPE
			SYNTAX IpAddress
			MAX-ACCESS read-only
			STATUS current
			DESCRIPTION
				"Description."
			::= { fhVCEntry 9 }

		
--   1.3.6.1.4.1.11408.11.1.6.1.1.1.10
-- 1.3.6.1.4.1.11408.11.1.6.1.1.1.10
		-- 1.3.6.1.4.1.11408.11.1.6.1.1.1.10
		fhVCLocalIP OBJECT-TYPE
			SYNTAX IpAddress
			MAX-ACCESS read-only
			STATUS current
			DESCRIPTION
				"Description."
			::= { fhVCEntry 10 }

		
--   1.3.6.1.4.1.11408.11.1.6.1.1.1.11
-- 1.3.6.1.4.1.11408.11.1.6.1.1.1.11
		-- 1.3.6.1.4.1.11408.11.1.6.1.1.1.11
		fhVCEncapType OBJECT-TYPE
			SYNTAX INTEGER
			MAX-ACCESS read-only
			STATUS current
			DESCRIPTION
				"Description."
			::= { fhVCEntry 11 }

		
--   1.3.6.1.4.1.11408.11.1.6.1.1.1.12
-- 1.3.6.1.4.1.11408.11.1.6.1.1.1.12
		-- 1.3.6.1.4.1.11408.11.1.6.1.1.1.12
		fhVCId OBJECT-TYPE
			SYNTAX Integer32
			MAX-ACCESS read-write
			STATUS current
			DESCRIPTION
				"Description."
			::= { fhVCEntry 12 }

		
--   1.3.6.1.4.1.11408.11.1.6.1.1.1.13
-- 1.3.6.1.4.1.11408.11.1.6.1.1.1.13
		-- 1.3.6.1.4.1.11408.11.1.6.1.1.1.13
		fhVCPeerVcID OBJECT-TYPE
			SYNTAX Integer32
			MAX-ACCESS read-write
			STATUS current
			DESCRIPTION
				"Description."
			::= { fhVCEntry 13 }

		
--   1.3.6.1.4.1.11408.11.1.6.1.1.1.14
-- 1.3.6.1.4.1.11408.11.1.6.1.1.1.14
		-- 1.3.6.1.4.1.11408.11.1.6.1.1.1.14
		fhVCAcIfName OBJECT-TYPE
			SYNTAX OCTET STRING
			MAX-ACCESS read-write
			STATUS current
			DESCRIPTION
				"Description."
			::= { fhVCEntry 14 }

		
--   1.3.6.1.4.1.11408.11.1.6.1.1.1.15
-- 1.3.6.1.4.1.11408.11.1.6.1.1.1.15
		-- 1.3.6.1.4.1.11408.11.1.6.1.1.1.15
		fhVCRemoteAcIfName OBJECT-TYPE
			SYNTAX OCTET STRING
			MAX-ACCESS read-write
			STATUS current
			DESCRIPTION
				"Description."
			::= { fhVCEntry 15 }

		
--   1.3.6.1.4.1.11408.11.1.6.1.1.1.16
-- 1.3.6.1.4.1.11408.11.1.6.1.1.1.16
		-- 1.3.6.1.4.1.11408.11.1.6.1.1.1.16
		fhVCActiveStatus OBJECT-TYPE
			SYNTAX Integer32
			MAX-ACCESS read-write
			STATUS current
			DESCRIPTION
				"Description."
			::= { fhVCEntry 16 }

		
--   1.3.6.1.4.1.11408.11.1.6.1.1.1.17
-- 1.3.6.1.4.1.11408.11.1.6.1.1.1.17
		-- 1.3.6.1.4.1.11408.11.1.6.1.1.1.17
		fhVCOperStatus OBJECT-TYPE
			SYNTAX Integer32
			MAX-ACCESS read-write
			STATUS current
			DESCRIPTION
				"Description."
			::= { fhVCEntry 17 }

		
--   1.3.6.1.4.1.11408.11.1.6.1.1.1.30
-- 1.3.6.1.4.1.11408.11.1.6.1.1.1.30
		-- 1.3.6.1.4.1.11408.11.1.6.1.1.1.30
		fhVCOutboundLabel OBJECT-TYPE
			SYNTAX Integer32
			MAX-ACCESS read-write
			STATUS current
			DESCRIPTION
				"Description."
			::= { fhVCEntry 30 }

		
--   1.3.6.1.4.1.11408.11.1.6.1.1.1.31
-- 1.3.6.1.4.1.11408.11.1.6.1.1.1.31
		-- 1.3.6.1.4.1.11408.11.1.6.1.1.1.31
		fhVCInboundLabel OBJECT-TYPE
			SYNTAX Integer32
			MAX-ACCESS read-write
			STATUS current
			DESCRIPTION
				"Description."
			::= { fhVCEntry 31 }

		
--   1.3.6.1.4.1.11408.11.1.6.1.1.1.32
-- 1.3.6.1.4.1.11408.11.1.6.1.1.1.32
		-- 1.3.6.1.4.1.11408.11.1.6.1.1.1.32
		fhVCTunnelIfIndex OBJECT-TYPE
			SYNTAX Integer32
			MAX-ACCESS read-write
			STATUS current
			DESCRIPTION
				"Description."
			::= { fhVCEntry 32 }

		
--   1.3.6.1.4.1.11408.11.1.6.1.1.1.33
-- 1.3.6.1.4.1.11408.11.1.6.1.1.1.33
		-- 1.3.6.1.4.1.11408.11.1.6.1.1.1.33
		fhVCTunnelID OBJECT-TYPE
			SYNTAX Integer32
			MAX-ACCESS read-write
			STATUS current
			DESCRIPTION
				"Description."
			::= { fhVCEntry 33 }

		
--   1.3.6.1.4.1.11408.11.1.6.1.1.1.37
-- 1.3.6.1.4.1.11408.11.1.6.1.1.1.37
		-- 1.3.6.1.4.1.11408.11.1.6.1.1.1.37
		fhVCTunnelTyep OBJECT-TYPE
			SYNTAX Integer32
			MAX-ACCESS read-only
			STATUS current
			DESCRIPTION
				"Description."
			::= { fhVCEntry 37 }

		
--   1.3.6.1.4.1.11408.11.1.6.1.2
-- 1.3.6.1.4.1.11408.11.1.6.1.2
		-- 1.3.6.1.4.1.11408.11.1.6.1.2
		fhMspwTable OBJECT-TYPE
			SYNTAX SEQUENCE OF FhMspwEntry
			MAX-ACCESS not-accessible
			STATUS current
			DESCRIPTION
				"Description."
			::= { fhVCType 2 }

		
--   1.3.6.1.4.1.11408.11.1.6.1.2.1
-- 1.3.6.1.4.1.11408.11.1.6.1.2.1
		-- 1.3.6.1.4.1.11408.11.1.6.1.2.1
		fhMspwEntry OBJECT-TYPE
			SYNTAX FhMspwEntry
			MAX-ACCESS not-accessible
			STATUS current
			DESCRIPTION
				"Description."
			INDEX { fhMSPWIndex }
			::= { fhMspwTable 1 }

		
		FhMspwEntry ::=
			SEQUENCE { 
				fhMSPWIndex
					Integer32,
				fhMSPWName
					OCTET STRING,
				fhMSPWVC1Name
					OCTET STRING,
				fhMSPWVC2Name
					OCTET STRING
			 }

--   1.3.6.1.4.1.11408.11.1.6.1.2.1.1
-- 1.3.6.1.4.1.11408.11.1.6.1.2.1.1
		-- 1.3.6.1.4.1.11408.11.1.6.1.2.1.1
		fhMSPWIndex OBJECT-TYPE
			SYNTAX Integer32
			MAX-ACCESS read-only
			STATUS current
			DESCRIPTION
				"Description."
			::= { fhMspwEntry 1 }

		
--   1.3.6.1.4.1.11408.11.1.6.1.2.1.2
-- 1.3.6.1.4.1.11408.11.1.6.1.2.1.2
		-- 1.3.6.1.4.1.11408.11.1.6.1.2.1.2
		fhMSPWName OBJECT-TYPE
			SYNTAX OCTET STRING
			MAX-ACCESS read-only
			STATUS current
			DESCRIPTION
				"Description."
			::= { fhMspwEntry 2 }

		
--   1.3.6.1.4.1.11408.11.1.6.1.2.1.3
-- 1.3.6.1.4.1.11408.11.1.6.1.2.1.3
		-- 1.3.6.1.4.1.11408.11.1.6.1.2.1.3
		fhMSPWVC1Name OBJECT-TYPE
			SYNTAX OCTET STRING
			MAX-ACCESS read-only
			STATUS current
			DESCRIPTION
				"Description."
			::= { fhMspwEntry 3 }

		
--   1.3.6.1.4.1.11408.11.1.6.1.2.1.4
-- 1.3.6.1.4.1.11408.11.1.6.1.2.1.4
		-- 1.3.6.1.4.1.11408.11.1.6.1.2.1.4
		fhMSPWVC2Name OBJECT-TYPE
			SYNTAX OCTET STRING
			MAX-ACCESS read-only
			STATUS current
			DESCRIPTION
				"Description."
			::= { fhMspwEntry 4 }

		
--   1.3.6.1.4.1.11408.11.1.6.3
-- 1.3.6.1.4.1.11408.11.1.6.3
		-- 1.3.6.1.4.1.11408.11.1.6.3
		fhVCTraps OBJECT IDENTIFIER ::= { fhVC 3 }

		
--   1.3.6.1.4.1.11408.11.1.6.3.1
-- 1.3.6.1.4.1.11408.11.1.6.3.1
		-- 1.3.6.1.4.1.11408.11.1.6.3.1
		fhVcTrap OBJECT IDENTIFIER ::= { fhVCTraps 1 }

		
--   1.3.6.1.4.1.11408.11.1.6.3.1.1
-- 1.3.6.1.4.1.11408.11.1.6.3.1.1
		-- 1.3.6.1.4.1.11408.11.1.6.3.1.1
		fhVCDown NOTIFICATION-TYPE
			STATUS current
			DESCRIPTION 
				"Description."
			::= { fhVcTrap 1 }

		
--   1.3.6.1.4.1.11408.11.1.6.3.1.2
-- 1.3.6.1.4.1.11408.11.1.6.3.1.2
		-- 1.3.6.1.4.1.11408.11.1.6.3.1.2
		fhVCUp NOTIFICATION-TYPE
			STATUS current
			DESCRIPTION 
				"Description."
			::= { fhVcTrap 2 }

		
--   1.3.6.1.4.1.11408.11.1.6.3.2
-- 1.3.6.1.4.1.11408.11.1.6.3.2
		-- 1.3.6.1.4.1.11408.11.1.6.3.2
		fhPwe3VCTraps OBJECT IDENTIFIER ::= { fhVCTraps 2 }

		
--   1.3.6.1.4.1.11408.11.1.6.3.2.1
-- 1.3.6.1.4.1.11408.11.1.6.3.2.1
		-- 1.3.6.1.4.1.11408.11.1.6.3.2.1
		fhPwe3VC_W2P NOTIFICATION-TYPE
			OBJECTS { VcId, VcType, PeerAddress, CtrlWord, SecondaryPwId, 
				ifName }
			STATUS current
			DESCRIPTION 
				"The board Pwe3VC_W2P will send this trap."
			::= { fhPwe3VCTraps 1 }

		
--   1.3.6.1.4.1.11408.11.1.6.3.2.2
-- 1.3.6.1.4.1.11408.11.1.6.3.2.2
		-- 1.3.6.1.4.1.11408.11.1.6.3.2.2
		fhPwe3VC_P2W NOTIFICATION-TYPE
			OBJECTS { VcId, VcType, PeerAddress, CtrlWord, PrimaryPwId, 
				ifName }
			STATUS current
			DESCRIPTION 
				"The board Pwe3VC_P2W will send this trap."
			::= { fhPwe3VCTraps 2 }

		
--   1.3.6.1.4.1.11408.11.1.8
-- 1.3.6.1.4.1.11408.11.1.8
		-- 1.3.6.1.4.1.11408.11.1.8
		fhMplsTunnel OBJECT IDENTIFIER ::= { fhDatacomm 8 }

		
--   1.3.6.1.4.1.11408.11.1.8.1
-- 1.3.6.1.4.1.11408.11.1.8.1
		-- 1.3.6.1.4.1.11408.11.1.8.1
		fhMplsTunnelTable OBJECT-TYPE
			SYNTAX SEQUENCE OF FhMplsTunnelEntry
			MAX-ACCESS not-accessible
			STATUS current
			DESCRIPTION
				"Description."
			::= { fhMplsTunnel 1 }

		
--   1.3.6.1.4.1.11408.11.1.8.1.1
-- 1.3.6.1.4.1.11408.11.1.8.1.1
		-- 1.3.6.1.4.1.11408.11.1.8.1.1
		fhMplsTunnelEntry OBJECT-TYPE
			SYNTAX FhMplsTunnelEntry
			MAX-ACCESS not-accessible
			STATUS current
			DESCRIPTION
				"Description."
			INDEX { fhMplsTunnelIndex }
			::= { fhMplsTunnelTable 1 }

		
		FhMplsTunnelEntry ::=
			SEQUENCE { 
				fhMplsTunnelIndex
					Integer32,
				fhMplsTunnelID
					Integer32,
				fhMplsTunnelStatus
					Integer32,
				fhMplsTunnelIngress
					IpAddress,
				fhMplsTunnelEgress
					IpAddress,
				fhMplsTunnelInPort
					Integer32,
				fhMplsTunnelOutPort
					Integer32,
				fhMplsTunnelInLabel
					Integer32,
				fhMplsTunnelOutLabel
					Integer32,
				fhMplsTunnelNexthop
					IpAddress,
				fhMplsTunnelVifIndex
					Integer32
			 }

--   1.3.6.1.4.1.11408.11.1.8.1.1.1
-- 1.3.6.1.4.1.11408.11.1.8.1.1.1
		-- 1.3.6.1.4.1.11408.11.1.8.1.1.1
		fhMplsTunnelIndex OBJECT-TYPE
			SYNTAX Integer32
			MAX-ACCESS read-write
			STATUS current
			DESCRIPTION
				"Description."
			::= { fhMplsTunnelEntry 1 }

		
--   1.3.6.1.4.1.11408.11.1.8.1.1.2
-- 1.3.6.1.4.1.11408.11.1.8.1.1.2
		-- 1.3.6.1.4.1.11408.11.1.8.1.1.2
		fhMplsTunnelID OBJECT-TYPE
			SYNTAX Integer32
			MAX-ACCESS read-write
			STATUS current
			DESCRIPTION
				"Description."
			::= { fhMplsTunnelEntry 2 }

		
--   1.3.6.1.4.1.11408.11.1.8.1.1.3
-- 1.3.6.1.4.1.11408.11.1.8.1.1.3
		-- 1.3.6.1.4.1.11408.11.1.8.1.1.3
		fhMplsTunnelStatus OBJECT-TYPE
			SYNTAX Integer32
			MAX-ACCESS read-write
			STATUS current
			DESCRIPTION
				"Description."
			::= { fhMplsTunnelEntry 3 }

		
--   1.3.6.1.4.1.11408.11.1.8.1.1.4
-- 1.3.6.1.4.1.11408.11.1.8.1.1.4
		-- 1.3.6.1.4.1.11408.11.1.8.1.1.4
		fhMplsTunnelIngress OBJECT-TYPE
			SYNTAX IpAddress
			MAX-ACCESS read-write
			STATUS current
			DESCRIPTION
				"Description."
			::= { fhMplsTunnelEntry 4 }

		
--   1.3.6.1.4.1.11408.11.1.8.1.1.5
-- 1.3.6.1.4.1.11408.11.1.8.1.1.5
		-- 1.3.6.1.4.1.11408.11.1.8.1.1.5
		fhMplsTunnelEgress OBJECT-TYPE
			SYNTAX IpAddress
			MAX-ACCESS read-write
			STATUS current
			DESCRIPTION
				"Description."
			::= { fhMplsTunnelEntry 5 }

		
--   1.3.6.1.4.1.11408.11.1.8.1.1.6
-- 1.3.6.1.4.1.11408.11.1.8.1.1.6
		-- 1.3.6.1.4.1.11408.11.1.8.1.1.6
		fhMplsTunnelInPort OBJECT-TYPE
			SYNTAX Integer32
			MAX-ACCESS read-write
			STATUS current
			DESCRIPTION
				"Description."
			::= { fhMplsTunnelEntry 6 }

		
--   1.3.6.1.4.1.11408.11.1.8.1.1.7
-- 1.3.6.1.4.1.11408.11.1.8.1.1.7
		-- 1.3.6.1.4.1.11408.11.1.8.1.1.7
		fhMplsTunnelOutPort OBJECT-TYPE
			SYNTAX Integer32
			MAX-ACCESS read-write
			STATUS current
			DESCRIPTION
				"Description."
			::= { fhMplsTunnelEntry 7 }

		
--   1.3.6.1.4.1.11408.11.1.8.1.1.8
-- 1.3.6.1.4.1.11408.11.1.8.1.1.8
		-- 1.3.6.1.4.1.11408.11.1.8.1.1.8
		fhMplsTunnelInLabel OBJECT-TYPE
			SYNTAX Integer32
			MAX-ACCESS read-write
			STATUS current
			DESCRIPTION
				"Description."
			::= { fhMplsTunnelEntry 8 }

		
--   1.3.6.1.4.1.11408.11.1.8.1.1.9
-- 1.3.6.1.4.1.11408.11.1.8.1.1.9
		-- 1.3.6.1.4.1.11408.11.1.8.1.1.9
		fhMplsTunnelOutLabel OBJECT-TYPE
			SYNTAX Integer32
			MAX-ACCESS read-write
			STATUS current
			DESCRIPTION
				"Description."
			::= { fhMplsTunnelEntry 9 }

		
--   1.3.6.1.4.1.11408.11.1.8.1.1.10
-- 1.3.6.1.4.1.11408.11.1.8.1.1.10
		-- 1.3.6.1.4.1.11408.11.1.8.1.1.10
		fhMplsTunnelNexthop OBJECT-TYPE
			SYNTAX IpAddress
			MAX-ACCESS read-write
			STATUS current
			DESCRIPTION
				"Description."
			::= { fhMplsTunnelEntry 10 }

		
--   1.3.6.1.4.1.11408.11.1.8.1.1.11
-- 1.3.6.1.4.1.11408.11.1.8.1.1.11
		-- 1.3.6.1.4.1.11408.11.1.8.1.1.11
		fhMplsTunnelVifIndex OBJECT-TYPE
			SYNTAX Integer32
			MAX-ACCESS read-only
			STATUS current
			DESCRIPTION
				"Description."
			::= { fhMplsTunnelEntry 11 }

		
--   1.3.6.1.4.1.11408.11.1.8.2
-- 1.3.6.1.4.1.11408.11.1.8.2
		-- 1.3.6.1.4.1.11408.11.1.8.2
		fhmplsL3Vpn OBJECT IDENTIFIER ::= { fhMplsTunnel 2 }

		
--   1.3.6.1.4.1.11408.11.1.9
-- 1.3.6.1.4.1.11408.11.1.9
		-- 1.3.6.1.4.1.11408.11.1.9
		fhVeGroup OBJECT IDENTIFIER ::= { fhDatacomm 9 }

		
--   1.3.6.1.4.1.11408.11.1.9.1
-- 1.3.6.1.4.1.11408.11.1.9.1
		-- 1.3.6.1.4.1.11408.11.1.9.1
		fhVeTable OBJECT-TYPE
			SYNTAX SEQUENCE OF FhVeEntry
			MAX-ACCESS not-accessible
			STATUS current
			DESCRIPTION
				"Description."
			::= { fhVeGroup 1 }

		
--   1.3.6.1.4.1.11408.11.1.9.1.1
-- 1.3.6.1.4.1.11408.11.1.9.1.1
		-- 1.3.6.1.4.1.11408.11.1.9.1.1
		fhVeEntry OBJECT-TYPE
			SYNTAX FhVeEntry
			MAX-ACCESS not-accessible
			STATUS current
			DESCRIPTION
				"Description."
			INDEX { fhVeGroupIndex }
			::= { fhVeTable 1 }

		
		FhVeEntry ::=
			SEQUENCE { 
				fhVeGroupIndex
					Integer32,
				fhVeL2Ifname
					OCTET STRING,
				fhVeL3Ifname
					OCTET STRING
			 }

--   1.3.6.1.4.1.11408.11.1.9.1.1.1
-- 1.3.6.1.4.1.11408.11.1.9.1.1.1
		-- 1.3.6.1.4.1.11408.11.1.9.1.1.1
		fhVeGroupIndex OBJECT-TYPE
			SYNTAX Integer32
			MAX-ACCESS read-write
			STATUS current
			DESCRIPTION
				"Description."
			::= { fhVeEntry 1 }

		
--   1.3.6.1.4.1.11408.11.1.9.1.1.2
-- 1.3.6.1.4.1.11408.11.1.9.1.1.2
		-- 1.3.6.1.4.1.11408.11.1.9.1.1.2
		fhVeL2Ifname OBJECT-TYPE
			SYNTAX OCTET STRING
			MAX-ACCESS read-write
			STATUS current
			DESCRIPTION
				"Description."
			::= { fhVeEntry 2 }

		
--   1.3.6.1.4.1.11408.11.1.9.1.1.3
-- 1.3.6.1.4.1.11408.11.1.9.1.1.3
		-- 1.3.6.1.4.1.11408.11.1.9.1.1.3
		fhVeL3Ifname OBJECT-TYPE
			SYNTAX OCTET STRING
			MAX-ACCESS read-write
			STATUS current
			DESCRIPTION
				"Description."
			::= { fhVeEntry 3 }

		
--   1.3.6.1.4.1.11408.11.1.10
-- 1.3.6.1.4.1.11408.11.1.10
		-- 1.3.6.1.4.1.11408.11.1.10
		fhQinQSubIfDot1q OBJECT IDENTIFIER ::= { fhDatacomm 10 }

		
--   1.3.6.1.4.1.11408.11.1.10.1
-- 1.3.6.1.4.1.11408.11.1.10.1
		-- 1.3.6.1.4.1.11408.11.1.10.1
		fhQinQSubIfDot1qTable OBJECT-TYPE
			SYNTAX SEQUENCE OF FhQinQSubIfDot1qEntry
			MAX-ACCESS not-accessible
			STATUS current
			DESCRIPTION
				"Description."
			::= { fhQinQSubIfDot1q 1 }

		
--   1.3.6.1.4.1.11408.11.1.10.1.1
-- 1.3.6.1.4.1.11408.11.1.10.1.1
		-- 1.3.6.1.4.1.11408.11.1.10.1.1
		fhQinQSubIfDot1qEntry OBJECT-TYPE
			SYNTAX FhQinQSubIfDot1qEntry
			MAX-ACCESS not-accessible
			STATUS current
			DESCRIPTION
				"Description."
			INDEX { fhQinQSubIfDot1qTermIfIndex }
			::= { fhQinQSubIfDot1qTable 1 }

		
		FhQinQSubIfDot1qEntry ::=
			SEQUENCE { 
				fhQinQSubIfDot1qTermIfIndex
					Integer32,
				fhQinQSubIfDot1qTermSvlanStart
					Integer32,
				fhQinQSubIfDot1qTermSvlanEnd
					Integer32,
				fhQinQSubIfDot1qTermCvlanStart
					Integer32,
				fhQinQSubIfDot1TermCvlanEnd
					Integer32,
				fhQinQSubIfDot1TermGroupId
					Integer32
			 }

--   1.3.6.1.4.1.11408.11.1.10.1.1.1
-- 1.3.6.1.4.1.11408.11.1.10.1.1.1
		-- 1.3.6.1.4.1.11408.11.1.10.1.1.1
		fhQinQSubIfDot1qTermIfIndex OBJECT-TYPE
			SYNTAX Integer32
			MAX-ACCESS read-only
			STATUS current
			DESCRIPTION
				"Description."
			::= { fhQinQSubIfDot1qEntry 1 }

		
--   1.3.6.1.4.1.11408.11.1.10.1.1.2
-- 1.3.6.1.4.1.11408.11.1.10.1.1.2
		-- 1.3.6.1.4.1.11408.11.1.10.1.1.2
		fhQinQSubIfDot1qTermSvlanStart OBJECT-TYPE
			SYNTAX Integer32
			MAX-ACCESS read-only
			STATUS current
			DESCRIPTION
				"Description."
			::= { fhQinQSubIfDot1qEntry 2 }

		
--   1.3.6.1.4.1.11408.11.1.10.1.1.3
-- 1.3.6.1.4.1.11408.11.1.10.1.1.3
		-- 1.3.6.1.4.1.11408.11.1.10.1.1.3
		fhQinQSubIfDot1qTermSvlanEnd OBJECT-TYPE
			SYNTAX Integer32
			MAX-ACCESS read-only
			STATUS current
			DESCRIPTION
				"Description."
			::= { fhQinQSubIfDot1qEntry 3 }

		
--   1.3.6.1.4.1.11408.11.1.10.1.1.4
-- 1.3.6.1.4.1.11408.11.1.10.1.1.4
		-- 1.3.6.1.4.1.11408.11.1.10.1.1.4
		fhQinQSubIfDot1qTermCvlanStart OBJECT-TYPE
			SYNTAX Integer32
			MAX-ACCESS read-only
			STATUS current
			DESCRIPTION
				"Description."
			::= { fhQinQSubIfDot1qEntry 4 }

		
--   1.3.6.1.4.1.11408.11.1.10.1.1.5
-- 1.3.6.1.4.1.11408.11.1.10.1.1.5
		-- 1.3.6.1.4.1.11408.11.1.10.1.1.5
		fhQinQSubIfDot1TermCvlanEnd OBJECT-TYPE
			SYNTAX Integer32
			MAX-ACCESS read-only
			STATUS current
			DESCRIPTION
				"Description."
			::= { fhQinQSubIfDot1qEntry 5 }

		
--   1.3.6.1.4.1.11408.11.1.10.1.1.6
-- 1.3.6.1.4.1.11408.11.1.10.1.1.6
		-- 1.3.6.1.4.1.11408.11.1.10.1.1.6
		fhQinQSubIfDot1TermGroupId OBJECT-TYPE
			SYNTAX Integer32
			MAX-ACCESS read-only
			STATUS current
			DESCRIPTION
				"Description."
			::= { fhQinQSubIfDot1qEntry 6 }

		
--   1.3.6.1.4.1.11408.11.1.11
-- 1.3.6.1.4.1.11408.11.1.11
		-- 1.3.6.1.4.1.11408.11.1.11
		fhTelnet OBJECT IDENTIFIER ::= { fhDatacomm 11 }

		
--   1.3.6.1.4.1.11408.11.1.11.2
-- 1.3.6.1.4.1.11408.11.1.11.2
		-- 1.3.6.1.4.1.11408.11.1.11.2
		fhUserTable OBJECT-TYPE
			SYNTAX SEQUENCE OF FhUserEntry
			MAX-ACCESS not-accessible
			STATUS current
			DESCRIPTION
				"Description."
			::= { fhTelnet 2 }

		
--   1.3.6.1.4.1.11408.11.1.11.2.1
-- 1.3.6.1.4.1.11408.11.1.11.2.1
		-- 1.3.6.1.4.1.11408.11.1.11.2.1
		fhUserEntry OBJECT-TYPE
			SYNTAX FhUserEntry
			MAX-ACCESS not-accessible
			STATUS current
			DESCRIPTION
				"Description."
			INDEX { fhUserIndex }
			::= { fhUserTable 1 }

		
		FhUserEntry ::=
			SEQUENCE { 
				fhUserIndex
					Integer32,
				fhUserName
					Integer32,
				fhUserEncrypted
					Integer32,
				fhUserPassword
					Integer32,
				fhUserPrivilege
					Integer32
			 }

--   1.3.6.1.4.1.11408.11.1.11.2.1.1
-- 1.3.6.1.4.1.11408.11.1.11.2.1.1
		-- 1.3.6.1.4.1.11408.11.1.11.2.1.1
		fhUserIndex OBJECT-TYPE
			SYNTAX Integer32
			MAX-ACCESS read-write
			STATUS current
			DESCRIPTION
				"Description."
			::= { fhUserEntry 1 }

		
--   1.3.6.1.4.1.11408.11.1.11.2.1.2
-- 1.3.6.1.4.1.11408.11.1.11.2.1.2
		-- 1.3.6.1.4.1.11408.11.1.11.2.1.2
		fhUserName OBJECT-TYPE
			SYNTAX Integer32
			MAX-ACCESS read-write
			STATUS current
			DESCRIPTION
				"Description."
			::= { fhUserEntry 2 }

		
--   1.3.6.1.4.1.11408.11.1.11.2.1.3
-- 1.3.6.1.4.1.11408.11.1.11.2.1.3
		-- 1.3.6.1.4.1.11408.11.1.11.2.1.3
		fhUserEncrypted OBJECT-TYPE
			SYNTAX Integer32
			MAX-ACCESS read-write
			STATUS current
			DESCRIPTION
				"Description."
			::= { fhUserEntry 3 }

		
--   1.3.6.1.4.1.11408.11.1.11.2.1.4
-- 1.3.6.1.4.1.11408.11.1.11.2.1.4
		-- 1.3.6.1.4.1.11408.11.1.11.2.1.4
		fhUserPassword OBJECT-TYPE
			SYNTAX Integer32
			MAX-ACCESS read-write
			STATUS current
			DESCRIPTION
				"Description."
			::= { fhUserEntry 4 }

		
--   1.3.6.1.4.1.11408.11.1.11.2.1.5
-- 1.3.6.1.4.1.11408.11.1.11.2.1.5
		-- 1.3.6.1.4.1.11408.11.1.11.2.1.5
		fhUserPrivilege OBJECT-TYPE
			SYNTAX Integer32
			MAX-ACCESS read-write
			STATUS current
			DESCRIPTION
				"Description."
			::= { fhUserEntry 5 }

		
--   1.3.6.1.4.1.11408.11.1.11.3
-- 1.3.6.1.4.1.11408.11.1.11.3
		-- 1.3.6.1.4.1.11408.11.1.11.3
		fhTelnetTraps OBJECT IDENTIFIER ::= { fhTelnet 3 }

		
--   1.3.6.1.4.1.11408.11.1.11.3.2
-- 1.3.6.1.4.1.11408.11.1.11.3.2
		-- 1.3.6.1.4.1.11408.11.1.11.3.2
		fhTelnetLoginSucess NOTIFICATION-TYPE
			STATUS current
			DESCRIPTION 
				"Description."
			::= { fhTelnetTraps 2 }

		
--   1.3.6.1.4.1.11408.11.1.11.3.3
-- 1.3.6.1.4.1.11408.11.1.11.3.3
		-- 1.3.6.1.4.1.11408.11.1.11.3.3
		fhTelnetLoginFail NOTIFICATION-TYPE
			STATUS current
			DESCRIPTION 
				"Description."
			::= { fhTelnetTraps 3 }

		
--   1.3.6.1.4.1.11408.11.1.11.3.4
-- 1.3.6.1.4.1.11408.11.1.11.3.4
		-- 1.3.6.1.4.1.11408.11.1.11.3.4
		fhTelnetLogout NOTIFICATION-TYPE
			STATUS current
			DESCRIPTION 
				"Description."
			::= { fhTelnetTraps 4 }

		
--   1.3.6.1.4.1.11408.11.1.12
-- 1.3.6.1.4.1.11408.11.1.12
		-- 1.3.6.1.4.1.11408.11.1.12
		fhDHCPRIP OBJECT IDENTIFIER ::= { fhDatacomm 12 }

		
--   1.3.6.1.4.1.11408.11.1.12.1
-- 1.3.6.1.4.1.11408.11.1.12.1
		-- 1.3.6.1.4.1.11408.11.1.12.1
		fhDHCPRIPTable OBJECT-TYPE
			SYNTAX SEQUENCE OF FhDHCPRIPEntry
			MAX-ACCESS not-accessible
			STATUS current
			DESCRIPTION
				"Description."
			::= { fhDHCPRIP 1 }

		
--   1.3.6.1.4.1.11408.11.1.12.1.1
-- 1.3.6.1.4.1.11408.11.1.12.1.1
		-- 1.3.6.1.4.1.11408.11.1.12.1.1
		fhDHCPRIPEntry OBJECT-TYPE
			SYNTAX FhDHCPRIPEntry
			MAX-ACCESS not-accessible
			STATUS current
			DESCRIPTION
				"Description."
			INDEX { fhDHCPRIPIfIndex }
			::= { fhDHCPRIPTable 1 }

		
		FhDHCPRIPEntry ::=
			SEQUENCE { 
				fhDHCPRIPIfIndex
					Integer32,
				fhDHCPRIPAddr1
					IpAddress,
				fhDHCPRIPAddr2
					IpAddress,
				fhDHCPRIPAddr3
					IpAddress,
				fhDHCPRIPAddr4
					IpAddress,
				fhDHCPRIPAddr5
					IpAddress,
				fhDHCPRIPAddr6
					IpAddress,
				fhDHCPRIPAddr7
					IpAddress,
				fhDHCPRIPAddr8
					IpAddress,
				fhDHCPRIPEntIndex
					Integer32
			 }

--   1.3.6.1.4.1.11408.11.1.12.1.1.1
-- 1.3.6.1.4.1.11408.11.1.12.1.1.1
		-- 1.3.6.1.4.1.11408.11.1.12.1.1.1
		fhDHCPRIPIfIndex OBJECT-TYPE
			SYNTAX Integer32
			MAX-ACCESS read-only
			STATUS current
			DESCRIPTION
				"Description."
			::= { fhDHCPRIPEntry 1 }

		
--   1.3.6.1.4.1.11408.11.1.12.1.1.2
-- 1.3.6.1.4.1.11408.11.1.12.1.1.2
		-- 1.3.6.1.4.1.11408.11.1.12.1.1.2
		fhDHCPRIPAddr1 OBJECT-TYPE
			SYNTAX IpAddress
			MAX-ACCESS read-only
			STATUS current
			DESCRIPTION
				"Description."
			::= { fhDHCPRIPEntry 2 }

		
--   1.3.6.1.4.1.11408.11.1.12.1.1.3
-- 1.3.6.1.4.1.11408.11.1.12.1.1.3
		-- 1.3.6.1.4.1.11408.11.1.12.1.1.3
		fhDHCPRIPAddr2 OBJECT-TYPE
			SYNTAX IpAddress
			MAX-ACCESS read-only
			STATUS current
			DESCRIPTION
				"Description."
			::= { fhDHCPRIPEntry 3 }

		
--   1.3.6.1.4.1.11408.11.1.12.1.1.4
-- 1.3.6.1.4.1.11408.11.1.12.1.1.4
		-- 1.3.6.1.4.1.11408.11.1.12.1.1.4
		fhDHCPRIPAddr3 OBJECT-TYPE
			SYNTAX IpAddress
			MAX-ACCESS read-only
			STATUS current
			DESCRIPTION
				"Description."
			::= { fhDHCPRIPEntry 4 }

		
--   1.3.6.1.4.1.11408.11.1.12.1.1.5
-- 1.3.6.1.4.1.11408.11.1.12.1.1.5
		-- 1.3.6.1.4.1.11408.11.1.12.1.1.5
		fhDHCPRIPAddr4 OBJECT-TYPE
			SYNTAX IpAddress
			MAX-ACCESS read-only
			STATUS current
			DESCRIPTION
				"Description."
			::= { fhDHCPRIPEntry 5 }

		
--   1.3.6.1.4.1.11408.11.1.12.1.1.6
-- 1.3.6.1.4.1.11408.11.1.12.1.1.6
		-- 1.3.6.1.4.1.11408.11.1.12.1.1.6
		fhDHCPRIPAddr5 OBJECT-TYPE
			SYNTAX IpAddress
			MAX-ACCESS read-only
			STATUS current
			DESCRIPTION
				"Description."
			::= { fhDHCPRIPEntry 6 }

		
--   1.3.6.1.4.1.11408.11.1.12.1.1.7
-- 1.3.6.1.4.1.11408.11.1.12.1.1.7
		-- 1.3.6.1.4.1.11408.11.1.12.1.1.7
		fhDHCPRIPAddr6 OBJECT-TYPE
			SYNTAX IpAddress
			MAX-ACCESS read-only
			STATUS current
			DESCRIPTION
				"Description."
			::= { fhDHCPRIPEntry 7 }

		
--   1.3.6.1.4.1.11408.11.1.12.1.1.8
-- 1.3.6.1.4.1.11408.11.1.12.1.1.8
		-- 1.3.6.1.4.1.11408.11.1.12.1.1.8
		fhDHCPRIPAddr7 OBJECT-TYPE
			SYNTAX IpAddress
			MAX-ACCESS read-only
			STATUS current
			DESCRIPTION
				"Description."
			::= { fhDHCPRIPEntry 8 }

		
--   1.3.6.1.4.1.11408.11.1.12.1.1.9
-- 1.3.6.1.4.1.11408.11.1.12.1.1.9
		-- 1.3.6.1.4.1.11408.11.1.12.1.1.9
		fhDHCPRIPAddr8 OBJECT-TYPE
			SYNTAX IpAddress
			MAX-ACCESS read-only
			STATUS current
			DESCRIPTION
				"Description."
			::= { fhDHCPRIPEntry 9 }

		
--   1.3.6.1.4.1.11408.11.1.12.1.1.10
-- 1.3.6.1.4.1.11408.11.1.12.1.1.10
		-- 1.3.6.1.4.1.11408.11.1.12.1.1.10
		fhDHCPRIPEntIndex OBJECT-TYPE
			SYNTAX Integer32
			MAX-ACCESS read-only
			STATUS current
			DESCRIPTION
				"Description."
			::= { fhDHCPRIPEntry 10 }

		
--  1.3.6.1.4.1.11408.11.1.12.2
		-- 1.3.6.1.4.1.11408.11.1.12.2
		fhDhcpRipTable OBJECT-TYPE
			SYNTAX SEQUENCE OF FhDhcpRipEntry
			MAX-ACCESS not-accessible
			STATUS current
			DESCRIPTION
				"Description."
			::= { fhDHCPRIP 2 }

		
--  1.3.6.1.4.1.11408.11.1.12.2.1
		-- 1.3.6.1.4.1.11408.11.1.12.2.1
		fhDhcpRipEntry OBJECT-TYPE
			SYNTAX FhDhcpRipEntry
			MAX-ACCESS not-accessible
			STATUS current
			DESCRIPTION
				"Description."
			INDEX { fhDhcpREntityIndex, fhDhcpRIpIfIndex, fhDhcpRipAddr }
			::= { fhDhcpRipTable 1 }

		
		FhDhcpRipEntry ::=
			SEQUENCE { 
				fhDhcpRipAddr
					IpAddress,
				fhDhcpRIpIfIndex
					Integer32,
				fhDhcpREntityIndex
					Integer32
			 }

--  1.3.6.1.4.1.11408.11.1.12.2.1.1
		-- 1.3.6.1.4.1.11408.11.1.12.2.1.1
		fhDhcpRipAddr OBJECT-TYPE
			SYNTAX IpAddress
			MAX-ACCESS read-only
			STATUS current
			DESCRIPTION
				"Description."
			::= { fhDhcpRipEntry 1 }

		
--  1.3.6.1.4.1.11408.11.1.12.2.1.2
		-- 1.3.6.1.4.1.11408.11.1.12.2.1.2
		fhDhcpRIpIfIndex OBJECT-TYPE
			SYNTAX Integer32
			MAX-ACCESS read-only
			STATUS current
			DESCRIPTION
				"Description."
			::= { fhDhcpRipEntry 2 }

		
--  1.3.6.1.4.1.11408.11.1.12.2.1.3
		-- 1.3.6.1.4.1.11408.11.1.12.2.1.3
		fhDhcpREntityIndex OBJECT-TYPE
			SYNTAX Integer32
			MAX-ACCESS read-only
			STATUS current
			DESCRIPTION
				"Description."
			::= { fhDhcpRipEntry 3 }

		
--   1.3.6.1.4.1.11408.11.1.13
-- 1.3.6.1.4.1.11408.11.1.13
		-- 1.3.6.1.4.1.11408.11.1.13
		fhBfdSession OBJECT IDENTIFIER ::= { fhDatacomm 13 }

		
--   1.3.6.1.4.1.11408.11.1.13.1
-- 1.3.6.1.4.1.11408.11.1.13.1
		-- 1.3.6.1.4.1.11408.11.1.13.1
		fhBfdSessConfTable OBJECT-TYPE
			SYNTAX SEQUENCE OF FhBfdSessConfEntry
			MAX-ACCESS not-accessible
			STATUS current
			DESCRIPTION
				"Description."
			::= { fhBfdSession 1 }

		
--   1.3.6.1.4.1.11408.11.1.13.1.1
-- 1.3.6.1.4.1.11408.11.1.13.1.1
		-- 1.3.6.1.4.1.11408.11.1.13.1.1
		fhBfdSessConfEntry OBJECT-TYPE
			SYNTAX FhBfdSessConfEntry
			MAX-ACCESS not-accessible
			STATUS current
			DESCRIPTION
				"Description."
			INDEX { fhBfdSessConfIndex }
			::= { fhBfdSessConfTable 1 }

		
		FhBfdSessConfEntry ::=
			SEQUENCE { 
				fhBfdSessConfIndex
					Integer32,
				fhBfdSessConfLocalDisc
					Integer32,
				fhBfdSessConfRemoteDisc
					Integer32,
				fhBfdSessConfPeerAddr
					IpAddress,
				fhBfdSessConfBindIfIndex
					Integer32,
				fhBfdSessConfMulti
					Integer32,
				fhBfdSessConfMinRxInterval
					Integer32,
				fhBfdSessConfMinTxInterval
					Integer32,
				fhBfdSessConfBfdType
					INTEGER,
				fhBfdSessConfVcID
					Integer32
			 }

--   1.3.6.1.4.1.11408.11.1.13.1.1.1
-- 1.3.6.1.4.1.11408.11.1.13.1.1.1
		-- 1.3.6.1.4.1.11408.11.1.13.1.1.1
		fhBfdSessConfIndex OBJECT-TYPE
			SYNTAX Integer32
			MAX-ACCESS read-write
			STATUS current
			DESCRIPTION
				"Description."
			::= { fhBfdSessConfEntry 1 }

		
--   1.3.6.1.4.1.11408.11.1.13.1.1.2
-- 1.3.6.1.4.1.11408.11.1.13.1.1.2
		-- 1.3.6.1.4.1.11408.11.1.13.1.1.2
		fhBfdSessConfLocalDisc OBJECT-TYPE
			SYNTAX Integer32
			MAX-ACCESS read-write
			STATUS current
			DESCRIPTION
				"Description."
			::= { fhBfdSessConfEntry 2 }

		
--   1.3.6.1.4.1.11408.11.1.13.1.1.3
-- 1.3.6.1.4.1.11408.11.1.13.1.1.3
		-- 1.3.6.1.4.1.11408.11.1.13.1.1.3
		fhBfdSessConfRemoteDisc OBJECT-TYPE
			SYNTAX Integer32
			MAX-ACCESS read-write
			STATUS current
			DESCRIPTION
				"Description."
			::= { fhBfdSessConfEntry 3 }

		
--   1.3.6.1.4.1.11408.11.1.13.1.1.4
-- 1.3.6.1.4.1.11408.11.1.13.1.1.4
		-- 1.3.6.1.4.1.11408.11.1.13.1.1.4
		fhBfdSessConfPeerAddr OBJECT-TYPE
			SYNTAX IpAddress
			MAX-ACCESS read-write
			STATUS current
			DESCRIPTION
				"Description."
			::= { fhBfdSessConfEntry 4 }

		
--   1.3.6.1.4.1.11408.11.1.13.1.1.5
-- 1.3.6.1.4.1.11408.11.1.13.1.1.5
		-- 1.3.6.1.4.1.11408.11.1.13.1.1.5
		fhBfdSessConfBindIfIndex OBJECT-TYPE
			SYNTAX Integer32
			MAX-ACCESS read-write
			STATUS current
			DESCRIPTION
				"Description."
			::= { fhBfdSessConfEntry 5 }

		
--   1.3.6.1.4.1.11408.11.1.13.1.1.6
-- 1.3.6.1.4.1.11408.11.1.13.1.1.6
		-- 1.3.6.1.4.1.11408.11.1.13.1.1.6
		fhBfdSessConfMulti OBJECT-TYPE
			SYNTAX Integer32
			MAX-ACCESS read-write
			STATUS current
			DESCRIPTION
				"Description."
			::= { fhBfdSessConfEntry 6 }

		
--   1.3.6.1.4.1.11408.11.1.13.1.1.7
-- 1.3.6.1.4.1.11408.11.1.13.1.1.7
		-- 1.3.6.1.4.1.11408.11.1.13.1.1.7
		fhBfdSessConfMinRxInterval OBJECT-TYPE
			SYNTAX Integer32
			MAX-ACCESS read-write
			STATUS current
			DESCRIPTION
				"Description."
			::= { fhBfdSessConfEntry 7 }

		
--   1.3.6.1.4.1.11408.11.1.13.1.1.8
-- 1.3.6.1.4.1.11408.11.1.13.1.1.8
		-- 1.3.6.1.4.1.11408.11.1.13.1.1.8
		fhBfdSessConfMinTxInterval OBJECT-TYPE
			SYNTAX Integer32
			MAX-ACCESS read-write
			STATUS current
			DESCRIPTION
				"Description."
			::= { fhBfdSessConfEntry 8 }

		
--   1.3.6.1.4.1.11408.11.1.13.1.1.9
-- 1.3.6.1.4.1.11408.11.1.13.1.1.9
		-- 1.3.6.1.4.1.11408.11.1.13.1.1.9
		fhBfdSessConfBfdType OBJECT-TYPE
			SYNTAX INTEGER
				{
				bfdForIP(1),
				bfdForPW(2),
				bfdForLSP(3)
				}
			MAX-ACCESS read-write
			STATUS current
			DESCRIPTION
				"Description."
			::= { fhBfdSessConfEntry 9 }

		
--   1.3.6.1.4.1.11408.11.1.13.1.1.10
-- 1.3.6.1.4.1.11408.11.1.13.1.1.10
		-- 1.3.6.1.4.1.11408.11.1.13.1.1.10
		fhBfdSessConfVcID OBJECT-TYPE
			SYNTAX Integer32
			MAX-ACCESS read-write
			STATUS current
			DESCRIPTION
				"Description."
			::= { fhBfdSessConfEntry 10 }

		
--   1.3.6.1.4.1.11408.11.1.14
-- 1.3.6.1.4.1.11408.11.1.14
		-- 1.3.6.1.4.1.11408.11.1.14
		fhVpls OBJECT IDENTIFIER ::= { fhDatacomm 14 }

		
--   1.3.6.1.4.1.11408.11.1.14.2
-- 1.3.6.1.4.1.11408.11.1.14.2
		-- 1.3.6.1.4.1.11408.11.1.14.2
		fhvplsTable OBJECT-TYPE
			SYNTAX SEQUENCE OF FhvplsEntry
			MAX-ACCESS not-accessible
			STATUS current
			DESCRIPTION
				"Description."
			::= { fhVpls 2 }

		
--   1.3.6.1.4.1.11408.11.1.14.2.1
-- 1.3.6.1.4.1.11408.11.1.14.2.1
		-- 1.3.6.1.4.1.11408.11.1.14.2.1
		fhvplsEntry OBJECT-TYPE
			SYNTAX FhvplsEntry
			MAX-ACCESS not-accessible
			STATUS current
			DESCRIPTION
				"Description."
			INDEX { fhVplsVsiName }
			::= { fhvplsTable 1 }

		
		FhvplsEntry ::=
			SEQUENCE { 
				fhVplsVsiID
					Integer32,
				fhVplsVsiName
					OCTET STRING,
				fhVplsVcType
					Integer32,
				fhVplsMtu
					Integer32,
				fhVplsDescription
					OCTET STRING,
				fhVplsMacLearnEnable
					Integer32
			 }

--   1.3.6.1.4.1.11408.11.1.14.2.1.1
-- 1.3.6.1.4.1.11408.11.1.14.2.1.1
		-- 1.3.6.1.4.1.11408.11.1.14.2.1.1
		fhVplsVsiID OBJECT-TYPE
			SYNTAX Integer32
			MAX-ACCESS read-only
			STATUS current
			DESCRIPTION
				"Description."
			::= { fhvplsEntry 1 }

		
--   1.3.6.1.4.1.11408.11.1.14.2.1.2
-- 1.3.6.1.4.1.11408.11.1.14.2.1.2
		-- 1.3.6.1.4.1.11408.11.1.14.2.1.2
		fhVplsVsiName OBJECT-TYPE
			SYNTAX OCTET STRING
			MAX-ACCESS read-only
			STATUS current
			DESCRIPTION
				"Description."
			::= { fhvplsEntry 2 }

		
--   1.3.6.1.4.1.11408.11.1.14.2.1.3
-- 1.3.6.1.4.1.11408.11.1.14.2.1.3
		-- 1.3.6.1.4.1.11408.11.1.14.2.1.3
		fhVplsVcType OBJECT-TYPE
			SYNTAX Integer32
			MAX-ACCESS read-only
			STATUS current
			DESCRIPTION
				"Description."
			::= { fhvplsEntry 3 }

		
--   1.3.6.1.4.1.11408.11.1.14.2.1.4
-- 1.3.6.1.4.1.11408.11.1.14.2.1.4
		-- 1.3.6.1.4.1.11408.11.1.14.2.1.4
		fhVplsMtu OBJECT-TYPE
			SYNTAX Integer32
			MAX-ACCESS read-only
			STATUS current
			DESCRIPTION
				"Description."
			::= { fhvplsEntry 4 }

		
--   1.3.6.1.4.1.11408.11.1.14.2.1.5
-- 1.3.6.1.4.1.11408.11.1.14.2.1.5
		-- 1.3.6.1.4.1.11408.11.1.14.2.1.5
		fhVplsDescription OBJECT-TYPE
			SYNTAX OCTET STRING
			MAX-ACCESS read-only
			STATUS current
			DESCRIPTION
				"Description."
			::= { fhvplsEntry 5 }

		
--   1.3.6.1.4.1.11408.11.1.14.2.1.6
-- 1.3.6.1.4.1.11408.11.1.14.2.1.6
		-- 1.3.6.1.4.1.11408.11.1.14.2.1.6
		fhVplsMacLearnEnable OBJECT-TYPE
			SYNTAX Integer32
			MAX-ACCESS read-only
			STATUS current
			DESCRIPTION
				"Description."
			::= { fhvplsEntry 6 }

		
--   1.3.6.1.4.1.11408.11.1.14.3
-- 1.3.6.1.4.1.11408.11.1.14.3
		-- 1.3.6.1.4.1.11408.11.1.14.3
		fhvplsAcTable OBJECT-TYPE
			SYNTAX SEQUENCE OF FhvplsAcEntry
			MAX-ACCESS not-accessible
			STATUS current
			DESCRIPTION
				"Description."
			::= { fhVpls 3 }

		
--   1.3.6.1.4.1.11408.11.1.14.3.1
-- 1.3.6.1.4.1.11408.11.1.14.3.1
		-- 1.3.6.1.4.1.11408.11.1.14.3.1
		fhvplsAcEntry OBJECT-TYPE
			SYNTAX FhvplsAcEntry
			MAX-ACCESS not-accessible
			STATUS current
			DESCRIPTION
				"Description."
			INDEX { fhVplsAcIfIndex, fhVplsAcVsiName }
			::= { fhvplsAcTable 1 }

		
		FhvplsAcEntry ::=
			SEQUENCE { 
				fhVplsAcIfIndex
					Integer32,
				fhVplsAcStatus
					Integer32,
				fhVplsAcUpStartTime
					TimeTicks,
				fhVplsAcUpSumTime
					TimeTicks,
				fhVplsAcVsiName
					OCTET STRING
			 }

--   1.3.6.1.4.1.11408.11.1.14.3.1.1
-- 1.3.6.1.4.1.11408.11.1.14.3.1.1
		-- 1.3.6.1.4.1.11408.11.1.14.3.1.1
		fhVplsAcIfIndex OBJECT-TYPE
			SYNTAX Integer32
			MAX-ACCESS read-only
			STATUS current
			DESCRIPTION
				"Description."
			::= { fhvplsAcEntry 1 }

		
--   1.3.6.1.4.1.11408.11.1.14.3.1.2
-- 1.3.6.1.4.1.11408.11.1.14.3.1.2
		-- 1.3.6.1.4.1.11408.11.1.14.3.1.2
		fhVplsAcStatus OBJECT-TYPE
			SYNTAX Integer32
			MAX-ACCESS read-only
			STATUS current
			DESCRIPTION
				"Description."
			::= { fhvplsAcEntry 2 }

		
--   1.3.6.1.4.1.11408.11.1.14.3.1.3
-- 1.3.6.1.4.1.11408.11.1.14.3.1.3
		-- 1.3.6.1.4.1.11408.11.1.14.3.1.3
		fhVplsAcUpStartTime OBJECT-TYPE
			SYNTAX TimeTicks
			MAX-ACCESS read-only
			STATUS current
			DESCRIPTION
				"Description."
			::= { fhvplsAcEntry 3 }

		
--   1.3.6.1.4.1.11408.11.1.14.3.1.4
-- 1.3.6.1.4.1.11408.11.1.14.3.1.4
		-- 1.3.6.1.4.1.11408.11.1.14.3.1.4
		fhVplsAcUpSumTime OBJECT-TYPE
			SYNTAX TimeTicks
			MAX-ACCESS read-only
			STATUS current
			DESCRIPTION
				"Description."
			::= { fhvplsAcEntry 4 }

		
--   1.3.6.1.4.1.11408.11.1.14.3.1.5
-- 1.3.6.1.4.1.11408.11.1.14.3.1.5
		-- 1.3.6.1.4.1.11408.11.1.14.3.1.5
		fhVplsAcVsiName OBJECT-TYPE
			SYNTAX OCTET STRING
			MAX-ACCESS read-only
			STATUS current
			DESCRIPTION
				"Description."
			::= { fhvplsAcEntry 5 }

		
--   1.3.6.1.4.1.11408.11.1.14.4
-- 1.3.6.1.4.1.11408.11.1.14.4
		-- 1.3.6.1.4.1.11408.11.1.14.4
		fhvplsPwTable OBJECT-TYPE
			SYNTAX SEQUENCE OF FhvplsPwEntry
			MAX-ACCESS not-accessible
			STATUS current
			DESCRIPTION
				"Description."
			::= { fhVpls 4 }

		
--   1.3.6.1.4.1.11408.11.1.14.4.1
-- 1.3.6.1.4.1.11408.11.1.14.4.1
		-- 1.3.6.1.4.1.11408.11.1.14.4.1
		fhvplsPwEntry OBJECT-TYPE
			SYNTAX FhvplsPwEntry
			MAX-ACCESS not-accessible
			STATUS current
			DESCRIPTION
				"Description."
			INDEX { fhVplsPwID, fhVplsPwRemoteIp, fhVplsPwVsiName }
			::= { fhvplsPwTable 1 }

		
		FhvplsPwEntry ::=
			SEQUENCE { 
				fhVplsPwID
					Integer32,
				fhVplsPwRemoteIp
					IpAddress,
				fhVplsPwTnlPolicy
					OCTET STRING,
				fhVplsPwHDivType
					Integer32,
				fhVplsPwInboundLabel
					Integer32,
				fhVplsPwOutboundLabel
					Integer32,
				fhVplsPwStatus
					Integer32,
				fhVplsPwVrIfIndex
					Integer32,
				fhVplsPwVrID
					Integer32,
				fhVplsPwUpStartTime
					TimeTicks,
				fhVplsPwUpSumTime
					TimeTicks,
				fhVplsPwVsiName
					OCTET STRING,
				fhVplsPwPeerTnlId
					Integer32,
				fhVplsPwTnlType
					Integer32
			 }

--   1.3.6.1.4.1.11408.11.1.14.4.1.1
-- 1.3.6.1.4.1.11408.11.1.14.4.1.1
		-- 1.3.6.1.4.1.11408.11.1.14.4.1.1
		fhVplsPwID OBJECT-TYPE
			SYNTAX Integer32
			MAX-ACCESS read-only
			STATUS current
			DESCRIPTION
				"Description."
			::= { fhvplsPwEntry 1 }

		
--   1.3.6.1.4.1.11408.11.1.14.4.1.2
-- 1.3.6.1.4.1.11408.11.1.14.4.1.2
		-- 1.3.6.1.4.1.11408.11.1.14.4.1.2
		fhVplsPwRemoteIp OBJECT-TYPE
			SYNTAX IpAddress
			MAX-ACCESS read-only
			STATUS current
			DESCRIPTION
				"Description."
			::= { fhvplsPwEntry 2 }

		
--   1.3.6.1.4.1.11408.11.1.14.4.1.3
-- 1.3.6.1.4.1.11408.11.1.14.4.1.3
		-- 1.3.6.1.4.1.11408.11.1.14.4.1.3
		fhVplsPwTnlPolicy OBJECT-TYPE
			SYNTAX OCTET STRING
			MAX-ACCESS read-only
			STATUS current
			DESCRIPTION
				"Description."
			::= { fhvplsPwEntry 3 }

		
--   1.3.6.1.4.1.11408.11.1.14.4.1.4
-- 1.3.6.1.4.1.11408.11.1.14.4.1.4
		-- 1.3.6.1.4.1.11408.11.1.14.4.1.4
		fhVplsPwHDivType OBJECT-TYPE
			SYNTAX Integer32
			MAX-ACCESS read-only
			STATUS current
			DESCRIPTION
				"Description."
			::= { fhvplsPwEntry 4 }

		
--   1.3.6.1.4.1.11408.11.1.14.4.1.6
-- 1.3.6.1.4.1.11408.11.1.14.4.1.6
		-- 1.3.6.1.4.1.11408.11.1.14.4.1.6
		fhVplsPwInboundLabel OBJECT-TYPE
			SYNTAX Integer32
			MAX-ACCESS read-only
			STATUS current
			DESCRIPTION
				"Description."
			::= { fhvplsPwEntry 6 }

		
--   1.3.6.1.4.1.11408.11.1.14.4.1.7
-- 1.3.6.1.4.1.11408.11.1.14.4.1.7
		-- 1.3.6.1.4.1.11408.11.1.14.4.1.7
		fhVplsPwOutboundLabel OBJECT-TYPE
			SYNTAX Integer32
			MAX-ACCESS read-only
			STATUS current
			DESCRIPTION
				"Description."
			::= { fhvplsPwEntry 7 }

		
--   1.3.6.1.4.1.11408.11.1.14.4.1.8
-- 1.3.6.1.4.1.11408.11.1.14.4.1.8
		-- 1.3.6.1.4.1.11408.11.1.14.4.1.8
		fhVplsPwStatus OBJECT-TYPE
			SYNTAX Integer32
			MAX-ACCESS read-only
			STATUS current
			DESCRIPTION
				"Description."
			::= { fhvplsPwEntry 8 }

		
--   1.3.6.1.4.1.11408.11.1.14.4.1.9
-- 1.3.6.1.4.1.11408.11.1.14.4.1.9
		-- 1.3.6.1.4.1.11408.11.1.14.4.1.9
		fhVplsPwVrIfIndex OBJECT-TYPE
			SYNTAX Integer32
			MAX-ACCESS read-only
			STATUS current
			DESCRIPTION
				"Description."
			::= { fhvplsPwEntry 9 }

		
--   1.3.6.1.4.1.11408.11.1.14.4.1.10
-- 1.3.6.1.4.1.11408.11.1.14.4.1.10
		-- 1.3.6.1.4.1.11408.11.1.14.4.1.10
		fhVplsPwVrID OBJECT-TYPE
			SYNTAX Integer32
			MAX-ACCESS read-only
			STATUS current
			DESCRIPTION
				"Description."
			::= { fhvplsPwEntry 10 }

		
--   1.3.6.1.4.1.11408.11.1.14.4.1.11
-- 1.3.6.1.4.1.11408.11.1.14.4.1.11
		-- 1.3.6.1.4.1.11408.11.1.14.4.1.11
		fhVplsPwUpStartTime OBJECT-TYPE
			SYNTAX TimeTicks
			MAX-ACCESS read-only
			STATUS current
			DESCRIPTION
				"Description."
			::= { fhvplsPwEntry 11 }

		
--   1.3.6.1.4.1.11408.11.1.14.4.1.12
-- 1.3.6.1.4.1.11408.11.1.14.4.1.12
		-- 1.3.6.1.4.1.11408.11.1.14.4.1.12
		fhVplsPwUpSumTime OBJECT-TYPE
			SYNTAX TimeTicks
			MAX-ACCESS read-only
			STATUS current
			DESCRIPTION
				"Description."
			::= { fhvplsPwEntry 12 }

		
--   1.3.6.1.4.1.11408.11.1.14.4.1.13
-- 1.3.6.1.4.1.11408.11.1.14.4.1.13
		-- 1.3.6.1.4.1.11408.11.1.14.4.1.13
		fhVplsPwVsiName OBJECT-TYPE
			SYNTAX OCTET STRING
			MAX-ACCESS read-only
			STATUS current
			DESCRIPTION
				"Description."
			::= { fhvplsPwEntry 13 }

		
--   1.3.6.1.4.1.11408.11.1.14.4.1.14
-- 1.3.6.1.4.1.11408.11.1.14.4.1.14
		-- 1.3.6.1.4.1.11408.11.1.14.4.1.14
		fhVplsPwPeerTnlId OBJECT-TYPE
			SYNTAX Integer32
			MAX-ACCESS read-only
			STATUS current
			DESCRIPTION
				"Description."
			::= { fhvplsPwEntry 14 }

		
--   1.3.6.1.4.1.11408.11.1.14.4.1.15
-- 1.3.6.1.4.1.11408.11.1.14.4.1.15
		-- 1.3.6.1.4.1.11408.11.1.14.4.1.15
		fhVplsPwTnlType OBJECT-TYPE
			SYNTAX Integer32
			MAX-ACCESS read-only
			STATUS current
			DESCRIPTION
				"Description."
			::= { fhvplsPwEntry 15 }

		
--   1.3.6.1.4.1.11408.11.1.15
-- 1.3.6.1.4.1.11408.11.1.15
		-- 1.3.6.1.4.1.11408.11.1.15
		fhOspfNbr OBJECT IDENTIFIER ::= { fhDatacomm 15 }

		
--   1.3.6.1.4.1.11408.11.1.15.1
-- 1.3.6.1.4.1.11408.11.1.15.1
		-- 1.3.6.1.4.1.11408.11.1.15.1
		fhOspfNbrTable OBJECT-TYPE
			SYNTAX SEQUENCE OF FhOspfNbrEntry
			MAX-ACCESS not-accessible
			STATUS current
			DESCRIPTION
				"Description."
			::= { fhOspfNbr 1 }

		
--   1.3.6.1.4.1.11408.11.1.15.1.1
-- 1.3.6.1.4.1.11408.11.1.15.1.1
		-- 1.3.6.1.4.1.11408.11.1.15.1.1
		fhOspfNbrEntry OBJECT-TYPE
			SYNTAX FhOspfNbrEntry
			MAX-ACCESS not-accessible
			STATUS current
			DESCRIPTION
				"Description."
			INDEX { fhOspfNbrIpAddr, fhOspfNbrAddressLessIndex }
			::= { fhOspfNbrTable 1 }

		
		FhOspfNbrEntry ::=
			SEQUENCE { 
				fhOspfNbrIpAddr
					IpAddress,
				fhOspfNbrAddressLessIndex
					Integer32,
				fhOspfNbrSelfIfName
					OCTET STRING
			 }

--   1.3.6.1.4.1.11408.11.1.15.1.1.1
-- 1.3.6.1.4.1.11408.11.1.15.1.1.1
		-- 1.3.6.1.4.1.11408.11.1.15.1.1.1
		fhOspfNbrIpAddr OBJECT-TYPE
			SYNTAX IpAddress
			MAX-ACCESS read-only
			STATUS current
			DESCRIPTION
				"Description."
			::= { fhOspfNbrEntry 1 }

		
--   1.3.6.1.4.1.11408.11.1.15.1.1.2
-- 1.3.6.1.4.1.11408.11.1.15.1.1.2
		-- 1.3.6.1.4.1.11408.11.1.15.1.1.2
		fhOspfNbrAddressLessIndex OBJECT-TYPE
			SYNTAX Integer32
			MAX-ACCESS read-only
			STATUS current
			DESCRIPTION
				"Description."
			::= { fhOspfNbrEntry 2 }

		
--   1.3.6.1.4.1.11408.11.1.15.1.1.3
-- 1.3.6.1.4.1.11408.11.1.15.1.1.3
		-- 1.3.6.1.4.1.11408.11.1.15.1.1.3
		fhOspfNbrSelfIfName OBJECT-TYPE
			SYNTAX OCTET STRING
			MAX-ACCESS read-only
			STATUS current
			DESCRIPTION
				"Description."
			::= { fhOspfNbrEntry 3 }

		
--   1.3.6.1.4.1.11408.11.1.16
-- 1.3.6.1.4.1.11408.11.1.16
		-- 1.3.6.1.4.1.11408.11.1.16
		fhBgpPeer OBJECT IDENTIFIER ::= { fhDatacomm 16 }

		
--   1.3.6.1.4.1.11408.11.1.16.1
-- 1.3.6.1.4.1.11408.11.1.16.1
		-- 1.3.6.1.4.1.11408.11.1.16.1
		fhBgpPeerTable OBJECT-TYPE
			SYNTAX SEQUENCE OF FhBgpPeerEntry
			MAX-ACCESS not-accessible
			STATUS current
			DESCRIPTION
				"Description."
			::= { fhBgpPeer 1 }

		
--   1.3.6.1.4.1.11408.11.1.16.1.1
-- 1.3.6.1.4.1.11408.11.1.16.1.1
		-- 1.3.6.1.4.1.11408.11.1.16.1.1
		fhBgpPeerEntry OBJECT-TYPE
			SYNTAX FhBgpPeerEntry
			MAX-ACCESS not-accessible
			STATUS current
			DESCRIPTION
				"Description."
			INDEX { fhBgpPeerLocalAddr, fhBgpPeerLocalPort, fhBgpPeerRemoteAddr, fhBgpPeerRemotePort, fhBgpPeerLocalAddrType, 
				fhBgpPeerRemoteAddrType, fhBgpPeerLocalAddrScopeID, fhBgpPeerEntIndex }
			::= { fhBgpPeerTable 1 }

		
		FhBgpPeerEntry ::=
			SEQUENCE { 
				fhBgpPeerIdentifier
					OCTET STRING,
				fhBgpPeerState
					Integer32,
				fhBgpPeerAdminStatus
					Integer32,
				fhBgpPeerNegotiatedVersion
					Gauge32,
				fhBgpPeerLocalAddr
					InetAddressType,
				fhBgpPeerLocalPort
					Gauge32,
				fhBgpPeerRemoteAddr
					InetAddress,
				fhBgpPeerRemotePort
					Gauge32,
				fhBgpPeerRemoteAs
					Gauge32,
				fhBgpPeerInUpdates
					Gauge32,
				fhBgpPeerOutUpdates
					Gauge32,
				fhBgpPeerInTotalMessages
					Gauge32,
				fhBgpPeerOutTotalMessages
					Gauge32,
				fhBgpPeerLastError
					OCTET STRING,
				fhBgpPeerFsmEstablishedTransitions
					Gauge32,
				fhBgpPeerFsmEstablishedTime
					Gauge32,
				fhBgpPeerConnectRetryInterval
					Gauge32,
				fhBgpPeerHoldTime
					Integer32,
				fhBgpPeerKeepAlive
					Integer32,
				fhBgpPeerHoldTimeConfigured
					Gauge32,
				fhBgpPeerKeepAliveConfigured
					Gauge32,
				fhBgpPeerMinASOriginationInterval
					Gauge32,
				fhBgpPeerMinRouteAdvertisementInterval
					Gauge32,
				fhBgpPeerInUpdateElapsedTime
					Gauge32,
				fhBgpPeerLocalAddrType
					Integer32,
				fhBgpPeerRemoteAddrType
					Integer32,
				fhBgpPeerLocalAddrScopeID
					Gauge32,
				fhBgpPeerEntIndex
					Gauge32,
				fhBgpPeerRecvRoutes
					Unsigned32,
				fhBgpPeerRecvRouteLocalActivePrefixs
					Unsigned32
			 }

--   1.3.6.1.4.1.11408.11.1.16.1.1.1
-- 1.3.6.1.4.1.11408.11.1.16.1.1.1
		-- 1.3.6.1.4.1.11408.11.1.16.1.1.1
		fhBgpPeerIdentifier OBJECT-TYPE
			SYNTAX OCTET STRING
			MAX-ACCESS read-only
			STATUS current
			DESCRIPTION
				"Description."
			::= { fhBgpPeerEntry 1 }

		
--   1.3.6.1.4.1.11408.11.1.16.1.1.2
-- 1.3.6.1.4.1.11408.11.1.16.1.1.2
		-- 1.3.6.1.4.1.11408.11.1.16.1.1.2
		fhBgpPeerState OBJECT-TYPE
			SYNTAX Integer32
			MAX-ACCESS read-only
			STATUS current
			DESCRIPTION
				"Description."
			::= { fhBgpPeerEntry 2 }

		
--   1.3.6.1.4.1.11408.11.1.16.1.1.3
-- 1.3.6.1.4.1.11408.11.1.16.1.1.3
		-- 1.3.6.1.4.1.11408.11.1.16.1.1.3
		fhBgpPeerAdminStatus OBJECT-TYPE
			SYNTAX Integer32
			MAX-ACCESS read-only
			STATUS current
			DESCRIPTION
				"Description."
			::= { fhBgpPeerEntry 3 }

		
--   1.3.6.1.4.1.11408.11.1.16.1.1.4
-- 1.3.6.1.4.1.11408.11.1.16.1.1.4
		-- 1.3.6.1.4.1.11408.11.1.16.1.1.4
		fhBgpPeerNegotiatedVersion OBJECT-TYPE
			SYNTAX Gauge32
			MAX-ACCESS read-only
			STATUS current
			DESCRIPTION
				"Description."
			::= { fhBgpPeerEntry 4 }

		
--   1.3.6.1.4.1.11408.11.1.16.1.1.5
-- 1.3.6.1.4.1.11408.11.1.16.1.1.5
		-- 1.3.6.1.4.1.11408.11.1.16.1.1.5
		fhBgpPeerLocalAddr OBJECT-TYPE
			SYNTAX InetAddressType
			MAX-ACCESS read-only
			STATUS current
			DESCRIPTION
				"Description."
			::= { fhBgpPeerEntry 5 }

		
--   1.3.6.1.4.1.11408.11.1.16.1.1.6
-- 1.3.6.1.4.1.11408.11.1.16.1.1.6
		-- 1.3.6.1.4.1.11408.11.1.16.1.1.6
		fhBgpPeerLocalPort OBJECT-TYPE
			SYNTAX Gauge32
			MAX-ACCESS read-only
			STATUS current
			DESCRIPTION
				"Description."
			::= { fhBgpPeerEntry 6 }

		
--   1.3.6.1.4.1.11408.11.1.16.1.1.7
-- 1.3.6.1.4.1.11408.11.1.16.1.1.7
		-- 1.3.6.1.4.1.11408.11.1.16.1.1.7
		fhBgpPeerRemoteAddr OBJECT-TYPE
			SYNTAX InetAddress
			MAX-ACCESS read-only
			STATUS current
			DESCRIPTION
				"Description."
			::= { fhBgpPeerEntry 7 }

		
--   1.3.6.1.4.1.11408.11.1.16.1.1.8
-- 1.3.6.1.4.1.11408.11.1.16.1.1.8
		-- 1.3.6.1.4.1.11408.11.1.16.1.1.8
		fhBgpPeerRemotePort OBJECT-TYPE
			SYNTAX Gauge32
			MAX-ACCESS read-only
			STATUS current
			DESCRIPTION
				"Description."
			::= { fhBgpPeerEntry 8 }

		
--   1.3.6.1.4.1.11408.11.1.16.1.1.9
-- 1.3.6.1.4.1.11408.11.1.16.1.1.9
		-- 1.3.6.1.4.1.11408.11.1.16.1.1.9
		fhBgpPeerRemoteAs OBJECT-TYPE
			SYNTAX Gauge32
			MAX-ACCESS read-only
			STATUS current
			DESCRIPTION
				"Description."
			::= { fhBgpPeerEntry 9 }

		
--   1.3.6.1.4.1.11408.11.1.16.1.1.10
-- 1.3.6.1.4.1.11408.11.1.16.1.1.10
		-- 1.3.6.1.4.1.11408.11.1.16.1.1.10
		fhBgpPeerInUpdates OBJECT-TYPE
			SYNTAX Gauge32
			MAX-ACCESS read-only
			STATUS current
			DESCRIPTION
				"Description."
			::= { fhBgpPeerEntry 10 }

		
--   1.3.6.1.4.1.11408.11.1.16.1.1.11
-- 1.3.6.1.4.1.11408.11.1.16.1.1.11
		-- 1.3.6.1.4.1.11408.11.1.16.1.1.11
		fhBgpPeerOutUpdates OBJECT-TYPE
			SYNTAX Gauge32
			MAX-ACCESS read-only
			STATUS current
			DESCRIPTION
				"Description."
			::= { fhBgpPeerEntry 11 }

		
--   1.3.6.1.4.1.11408.11.1.16.1.1.12
-- 1.3.6.1.4.1.11408.11.1.16.1.1.12
		-- 1.3.6.1.4.1.11408.11.1.16.1.1.12
		fhBgpPeerInTotalMessages OBJECT-TYPE
			SYNTAX Gauge32
			MAX-ACCESS read-only
			STATUS current
			DESCRIPTION
				"Description."
			::= { fhBgpPeerEntry 12 }

		
--   1.3.6.1.4.1.11408.11.1.16.1.1.13
-- 1.3.6.1.4.1.11408.11.1.16.1.1.13
		-- 1.3.6.1.4.1.11408.11.1.16.1.1.13
		fhBgpPeerOutTotalMessages OBJECT-TYPE
			SYNTAX Gauge32
			MAX-ACCESS read-only
			STATUS current
			DESCRIPTION
				"Description."
			::= { fhBgpPeerEntry 13 }

		
--   1.3.6.1.4.1.11408.11.1.16.1.1.14
-- 1.3.6.1.4.1.11408.11.1.16.1.1.14
		-- 1.3.6.1.4.1.11408.11.1.16.1.1.14
		fhBgpPeerLastError OBJECT-TYPE
			SYNTAX OCTET STRING
			MAX-ACCESS read-only
			STATUS current
			DESCRIPTION
				"Description."
			::= { fhBgpPeerEntry 14 }

		
--   1.3.6.1.4.1.11408.11.1.16.1.1.15
-- 1.3.6.1.4.1.11408.11.1.16.1.1.15
		-- 1.3.6.1.4.1.11408.11.1.16.1.1.15
		fhBgpPeerFsmEstablishedTransitions OBJECT-TYPE
			SYNTAX Gauge32
			MAX-ACCESS read-only
			STATUS current
			DESCRIPTION
				"Description."
			::= { fhBgpPeerEntry 15 }

		
--   1.3.6.1.4.1.11408.11.1.16.1.1.16
-- 1.3.6.1.4.1.11408.11.1.16.1.1.16
		-- 1.3.6.1.4.1.11408.11.1.16.1.1.16
		fhBgpPeerFsmEstablishedTime OBJECT-TYPE
			SYNTAX Gauge32
			MAX-ACCESS read-only
			STATUS current
			DESCRIPTION
				"Description."
			::= { fhBgpPeerEntry 16 }

		
--   1.3.6.1.4.1.11408.11.1.16.1.1.17
-- 1.3.6.1.4.1.11408.11.1.16.1.1.17
		-- 1.3.6.1.4.1.11408.11.1.16.1.1.17
		fhBgpPeerConnectRetryInterval OBJECT-TYPE
			SYNTAX Gauge32
			MAX-ACCESS read-only
			STATUS current
			DESCRIPTION
				"Description."
			::= { fhBgpPeerEntry 17 }

		
--   1.3.6.1.4.1.11408.11.1.16.1.1.18
-- 1.3.6.1.4.1.11408.11.1.16.1.1.18
		-- 1.3.6.1.4.1.11408.11.1.16.1.1.18
		fhBgpPeerHoldTime OBJECT-TYPE
			SYNTAX Integer32
			MAX-ACCESS read-only
			STATUS current
			DESCRIPTION
				"Description."
			::= { fhBgpPeerEntry 18 }

		
--   1.3.6.1.4.1.11408.11.1.16.1.1.19
-- 1.3.6.1.4.1.11408.11.1.16.1.1.19
		-- 1.3.6.1.4.1.11408.11.1.16.1.1.19
		fhBgpPeerKeepAlive OBJECT-TYPE
			SYNTAX Integer32
			MAX-ACCESS read-only
			STATUS current
			DESCRIPTION
				"Description."
			::= { fhBgpPeerEntry 19 }

		
--   1.3.6.1.4.1.11408.11.1.16.1.1.20
-- 1.3.6.1.4.1.11408.11.1.16.1.1.20
		-- 1.3.6.1.4.1.11408.11.1.16.1.1.20
		fhBgpPeerHoldTimeConfigured OBJECT-TYPE
			SYNTAX Gauge32
			MAX-ACCESS read-only
			STATUS current
			DESCRIPTION
				"Description."
			::= { fhBgpPeerEntry 20 }

		
--   1.3.6.1.4.1.11408.11.1.16.1.1.21
-- 1.3.6.1.4.1.11408.11.1.16.1.1.21
		-- 1.3.6.1.4.1.11408.11.1.16.1.1.21
		fhBgpPeerKeepAliveConfigured OBJECT-TYPE
			SYNTAX Gauge32
			MAX-ACCESS read-only
			STATUS current
			DESCRIPTION
				"Description."
			::= { fhBgpPeerEntry 21 }

		
--   1.3.6.1.4.1.11408.11.1.16.1.1.22
-- 1.3.6.1.4.1.11408.11.1.16.1.1.22
		-- 1.3.6.1.4.1.11408.11.1.16.1.1.22
		fhBgpPeerMinASOriginationInterval OBJECT-TYPE
			SYNTAX Gauge32
			MAX-ACCESS read-only
			STATUS current
			DESCRIPTION
				"Description."
			::= { fhBgpPeerEntry 22 }

		
--   1.3.6.1.4.1.11408.11.1.16.1.1.23
-- 1.3.6.1.4.1.11408.11.1.16.1.1.23
		-- 1.3.6.1.4.1.11408.11.1.16.1.1.23
		fhBgpPeerMinRouteAdvertisementInterval OBJECT-TYPE
			SYNTAX Gauge32
			MAX-ACCESS read-only
			STATUS current
			DESCRIPTION
				"Description."
			::= { fhBgpPeerEntry 23 }

		
--   1.3.6.1.4.1.11408.11.1.16.1.1.24
-- 1.3.6.1.4.1.11408.11.1.16.1.1.24
		-- 1.3.6.1.4.1.11408.11.1.16.1.1.24
		fhBgpPeerInUpdateElapsedTime OBJECT-TYPE
			SYNTAX Gauge32
			MAX-ACCESS read-only
			STATUS current
			DESCRIPTION
				"Description."
			::= { fhBgpPeerEntry 24 }

		
--   1.3.6.1.4.1.11408.11.1.16.1.1.25
-- 1.3.6.1.4.1.11408.11.1.16.1.1.25
		-- 1.3.6.1.4.1.11408.11.1.16.1.1.25
		fhBgpPeerLocalAddrType OBJECT-TYPE
			SYNTAX Integer32
			MAX-ACCESS read-only
			STATUS current
			DESCRIPTION
				"Description."
			::= { fhBgpPeerEntry 25 }

		
--   1.3.6.1.4.1.11408.11.1.16.1.1.26
-- 1.3.6.1.4.1.11408.11.1.16.1.1.26
		-- 1.3.6.1.4.1.11408.11.1.16.1.1.26
		fhBgpPeerRemoteAddrType OBJECT-TYPE
			SYNTAX Integer32
			MAX-ACCESS read-only
			STATUS current
			DESCRIPTION
				"Description."
			::= { fhBgpPeerEntry 26 }

		
--   1.3.6.1.4.1.11408.11.1.16.1.1.27
-- 1.3.6.1.4.1.11408.11.1.16.1.1.27
		-- 1.3.6.1.4.1.11408.11.1.16.1.1.27
		fhBgpPeerLocalAddrScopeID OBJECT-TYPE
			SYNTAX Gauge32
			MAX-ACCESS read-only
			STATUS current
			DESCRIPTION
				"Description."
			::= { fhBgpPeerEntry 27 }

		
--   1.3.6.1.4.1.11408.11.1.16.1.1.28
-- 1.3.6.1.4.1.11408.11.1.16.1.1.28
		-- 1.3.6.1.4.1.11408.11.1.16.1.1.28
		fhBgpPeerEntIndex OBJECT-TYPE
			SYNTAX Gauge32
			MAX-ACCESS read-only
			STATUS current
			DESCRIPTION
				"Description."
			::= { fhBgpPeerEntry 28 }

		
--   1.3.6.1.4.1.11408.11.1.16.1.1.29
-- 1.3.6.1.4.1.11408.11.1.16.1.1.29
		-- 1.3.6.1.4.1.11408.11.1.16.1.1.29
		fhBgpPeerRecvRoutes OBJECT-TYPE
			SYNTAX Unsigned32
			MAX-ACCESS read-only
			STATUS current
			DESCRIPTION
				"Description."
			::= { fhBgpPeerEntry 29 }

		
--   1.3.6.1.4.1.11408.11.1.16.1.1.30
-- 1.3.6.1.4.1.11408.11.1.16.1.1.30
		-- 1.3.6.1.4.1.11408.11.1.16.1.1.30
		fhBgpPeerRecvRouteLocalActivePrefixs OBJECT-TYPE
			SYNTAX Unsigned32
			MAX-ACCESS read-only
			STATUS current
			DESCRIPTION
				"Description."
			::= { fhBgpPeerEntry 30 }

		
--   1.3.6.1.4.1.11408.11.1.17
-- 1.3.6.1.4.1.11408.11.1.17
		-- 1.3.6.1.4.1.11408.11.1.17
		fhIsisSys OBJECT IDENTIFIER ::= { fhDatacomm 17 }

		
--   1.3.6.1.4.1.11408.11.1.17.1
-- 1.3.6.1.4.1.11408.11.1.17.1
		-- 1.3.6.1.4.1.11408.11.1.17.1
		fhIsisSysTable OBJECT-TYPE
			SYNTAX SEQUENCE OF FhIsisSysEntry
			MAX-ACCESS not-accessible
			STATUS current
			DESCRIPTION
				"Description."
			::= { fhIsisSys 1 }

		
--   1.3.6.1.4.1.11408.11.1.17.1.1
-- 1.3.6.1.4.1.11408.11.1.17.1.1
		-- 1.3.6.1.4.1.11408.11.1.17.1.1
		fhIsisSysEntry OBJECT-TYPE
			SYNTAX FhIsisSysEntry
			MAX-ACCESS not-accessible
			STATUS current
			DESCRIPTION
				"Description."
			INDEX { fhIsisSysInstance }
			::= { fhIsisSysTable 1 }

		
		FhIsisSysEntry ::=
			SEQUENCE { 
				fhIsisSysInstance
					Integer32,
				fhIsisSysVersion
					Integer32,
				fhIsisSysType
					Integer32,
				fhIsisSysID
					Integer32,
				fhIsisSysAdminState
					Integer32,
				fhIsisSysL2toL1Leaking
					Integer32,
				fhIsisSysMaxAge
					Integer32,
				fhIsisSysExistState
					Integer32
			 }

--   1.3.6.1.4.1.11408.11.1.17.1.1.1
-- 1.3.6.1.4.1.11408.11.1.17.1.1.1
		-- 1.3.6.1.4.1.11408.11.1.17.1.1.1
		fhIsisSysInstance OBJECT-TYPE
			SYNTAX Integer32
			MAX-ACCESS read-only
			STATUS current
			DESCRIPTION
				"Description."
			::= { fhIsisSysEntry 1 }

		
--   1.3.6.1.4.1.11408.11.1.17.1.1.2
-- 1.3.6.1.4.1.11408.11.1.17.1.1.2
		-- 1.3.6.1.4.1.11408.11.1.17.1.1.2
		fhIsisSysVersion OBJECT-TYPE
			SYNTAX Integer32
			MAX-ACCESS read-only
			STATUS current
			DESCRIPTION
				"Description."
			::= { fhIsisSysEntry 2 }

		
--   1.3.6.1.4.1.11408.11.1.17.1.1.3
-- 1.3.6.1.4.1.11408.11.1.17.1.1.3
		-- 1.3.6.1.4.1.11408.11.1.17.1.1.3
		fhIsisSysType OBJECT-TYPE
			SYNTAX Integer32
			MAX-ACCESS read-only
			STATUS current
			DESCRIPTION
				"Description."
			::= { fhIsisSysEntry 3 }

		
--   1.3.6.1.4.1.11408.11.1.17.1.1.4
-- 1.3.6.1.4.1.11408.11.1.17.1.1.4
		-- 1.3.6.1.4.1.11408.11.1.17.1.1.4
		fhIsisSysID OBJECT-TYPE
			SYNTAX Integer32
			MAX-ACCESS read-only
			STATUS current
			DESCRIPTION
				"Description."
			::= { fhIsisSysEntry 4 }

		
--   1.3.6.1.4.1.11408.11.1.17.1.1.5
-- 1.3.6.1.4.1.11408.11.1.17.1.1.5
		-- 1.3.6.1.4.1.11408.11.1.17.1.1.5
		fhIsisSysAdminState OBJECT-TYPE
			SYNTAX Integer32
			MAX-ACCESS read-only
			STATUS current
			DESCRIPTION
				"Description."
			::= { fhIsisSysEntry 5 }

		
--   1.3.6.1.4.1.11408.11.1.17.1.1.6
-- 1.3.6.1.4.1.11408.11.1.17.1.1.6
		-- 1.3.6.1.4.1.11408.11.1.17.1.1.6
		fhIsisSysL2toL1Leaking OBJECT-TYPE
			SYNTAX Integer32
			MAX-ACCESS read-only
			STATUS current
			DESCRIPTION
				"Description."
			::= { fhIsisSysEntry 6 }

		
--   1.3.6.1.4.1.11408.11.1.17.1.1.7
-- 1.3.6.1.4.1.11408.11.1.17.1.1.7
		-- 1.3.6.1.4.1.11408.11.1.17.1.1.7
		fhIsisSysMaxAge OBJECT-TYPE
			SYNTAX Integer32
			MAX-ACCESS read-only
			STATUS current
			DESCRIPTION
				"Description."
			::= { fhIsisSysEntry 7 }

		
--   1.3.6.1.4.1.11408.11.1.17.1.1.8
-- 1.3.6.1.4.1.11408.11.1.17.1.1.8
		-- 1.3.6.1.4.1.11408.11.1.17.1.1.8
		fhIsisSysExistState OBJECT-TYPE
			SYNTAX Integer32
			MAX-ACCESS read-only
			STATUS current
			DESCRIPTION
				"Description."
			::= { fhIsisSysEntry 8 }

		
--   1.3.6.1.4.1.11408.11.1.31
-- 1.3.6.1.4.1.11408.11.1.31
		-- 1.3.6.1.4.1.11408.11.1.31
		fhBgpInstance OBJECT IDENTIFIER ::= { fhDatacomm 31 }

		
--   1.3.6.1.4.1.11408.11.1.31.1
-- 1.3.6.1.4.1.11408.11.1.31.1
		-- 1.3.6.1.4.1.11408.11.1.31.1
		fhBgpInstanceTable OBJECT-TYPE
			SYNTAX SEQUENCE OF FhBgpInstanceEntry
			MAX-ACCESS not-accessible
			STATUS current
			DESCRIPTION
				"Description."
			::= { fhBgpInstance 1 }

		
--   1.3.6.1.4.1.11408.11.1.31.1.1
-- 1.3.6.1.4.1.11408.11.1.31.1.1
		-- 1.3.6.1.4.1.11408.11.1.31.1.1
		fhBgpInstanceEntry OBJECT-TYPE
			SYNTAX FhBgpInstanceEntry
			MAX-ACCESS not-accessible
			STATUS current
			DESCRIPTION
				"Description."
			INDEX { fhBgpInstanceId }
			::= { fhBgpInstanceTable 1 }

		
		FhBgpInstanceEntry ::=
			SEQUENCE { 
				fhBgpInstanceId
					Integer32,
				copyOffhBgpPeerState
					Integer32,
				copyOffhBgpPeerAdminStatus
					Integer32
			 }

--   1.3.6.1.4.1.11408.11.1.31.1.1.1
-- 1.3.6.1.4.1.11408.11.1.31.1.1.1
		-- 1.3.6.1.4.1.11408.11.1.31.1.1.1
		fhBgpInstanceId OBJECT-TYPE
			SYNTAX Integer32
			MAX-ACCESS read-only
			STATUS current
			DESCRIPTION
				"Description."
			::= { fhBgpInstanceEntry 1 }

		
--   1.3.6.1.4.1.11408.11.1.31.1.1.2
-- 1.3.6.1.4.1.11408.11.1.31.1.1.2
		-- 1.3.6.1.4.1.11408.11.1.31.1.1.2
		copyOffhBgpPeerState OBJECT-TYPE
			SYNTAX Integer32
			MAX-ACCESS read-only
			STATUS current
			DESCRIPTION
				"Description."
			::= { fhBgpInstanceEntry 2 }

		
--   1.3.6.1.4.1.11408.11.1.31.1.1.3
-- 1.3.6.1.4.1.11408.11.1.31.1.1.3
		-- 1.3.6.1.4.1.11408.11.1.31.1.1.3
		copyOffhBgpPeerAdminStatus OBJECT-TYPE
			SYNTAX Integer32
			MAX-ACCESS read-only
			STATUS current
			DESCRIPTION
				"Description."
			::= { fhBgpInstanceEntry 3 }

		
--   1.3.6.1.4.1.11408.11.1.32
-- 1.3.6.1.4.1.11408.11.1.32
		-- 1.3.6.1.4.1.11408.11.1.32
		fhOspfInstance OBJECT IDENTIFIER ::= { fhDatacomm 32 }

		
--   1.3.6.1.4.1.11408.11.1.32.1
-- 1.3.6.1.4.1.11408.11.1.32.1
		-- 1.3.6.1.4.1.11408.11.1.32.1
		ospfInstanceTable OBJECT-TYPE
			SYNTAX SEQUENCE OF OspfInstanceEntry
			MAX-ACCESS not-accessible
			STATUS current
			DESCRIPTION
				"Description."
			::= { fhOspfInstance 1 }

		
--   1.3.6.1.4.1.11408.11.1.32.1.1
-- 1.3.6.1.4.1.11408.11.1.32.1.1
		-- 1.3.6.1.4.1.11408.11.1.32.1.1
		ospfInstanceEntry OBJECT-TYPE
			SYNTAX OspfInstanceEntry
			MAX-ACCESS not-accessible
			STATUS current
			DESCRIPTION
				"Description."
			INDEX { ospfInstanceId }
			::= { ospfInstanceTable 1 }

		
		OspfInstanceEntry ::=
			SEQUENCE { 
				ospfInstanceId
					Integer32,
				ospfRouterId
					Integer32
			 }

--   1.3.6.1.4.1.11408.11.1.32.1.1.1
-- 1.3.6.1.4.1.11408.11.1.32.1.1.1
		-- 1.3.6.1.4.1.11408.11.1.32.1.1.1
		ospfInstanceId OBJECT-TYPE
			SYNTAX Integer32
			MAX-ACCESS read-only
			STATUS current
			DESCRIPTION
				"Description."
			::= { ospfInstanceEntry 1 }

		
--   1.3.6.1.4.1.11408.11.1.32.1.1.2
-- 1.3.6.1.4.1.11408.11.1.32.1.1.2
		-- 1.3.6.1.4.1.11408.11.1.32.1.1.2
		ospfRouterId OBJECT-TYPE
			SYNTAX Integer32
			MAX-ACCESS read-only
			STATUS current
			DESCRIPTION
				"Description."
			::= { ospfInstanceEntry 2 }

		
		-- 1.3.6.1.4.1.11408.11.1.33
		fhNgm OBJECT IDENTIFIER ::= { fhDatacomm 33 }

		
		-- 1.3.6.1.4.1.11408.11.1.33.1
		fhArpTable OBJECT-TYPE
			SYNTAX SEQUENCE OF FhArpEntry
			MAX-ACCESS not-accessible
			STATUS current
			DESCRIPTION
				"Description."
			::= { fhNgm 1 }

		
		-- 1.3.6.1.4.1.11408.11.1.33.1.1
		fhArpEntry OBJECT-TYPE
			SYNTAX FhArpEntry
			MAX-ACCESS not-accessible
			STATUS current
			DESCRIPTION
				"Description."
			INDEX { fhArpIfIndex, fhArpIpAdd, fhArpVrfId, fhNgmIndex }
			::= { fhArpTable 1 }

		
		FhArpEntry ::=
			SEQUENCE { 
				fhArpIfIndex
					Integer32,
				fhArpIpAdd
					IpAddress,
				fhArpMacAdd
					MacAddress,
				fhArpVrfId
					Integer32,
				fhArpType
					Integer32,
				fhArpVlanId
					Integer32,
				fhArpCvlanId
					Integer32,
				fhArpExpireTime
					Integer32,
				fhArpIfName
					OCTET STRING,
				fhNgmIndex
					Integer32
			 }

		-- 1.3.6.1.4.1.11408.11.1.33.1.1.1
		fhArpIfIndex OBJECT-TYPE
			SYNTAX Integer32
			MAX-ACCESS read-only
			STATUS current
			DESCRIPTION
				"Description."
			::= { fhArpEntry 1 }

		
		-- 1.3.6.1.4.1.11408.11.1.33.1.1.2
		fhArpIpAdd OBJECT-TYPE
			SYNTAX IpAddress
			MAX-ACCESS read-only
			STATUS current
			DESCRIPTION
				"Description."
			::= { fhArpEntry 2 }

		
		-- 1.3.6.1.4.1.11408.11.1.33.1.1.3
		fhArpMacAdd OBJECT-TYPE
			SYNTAX MacAddress
			MAX-ACCESS read-only
			STATUS current
			DESCRIPTION
				"Description."
			::= { fhArpEntry 3 }

		
		-- 1.3.6.1.4.1.11408.11.1.33.1.1.4
		fhArpVrfId OBJECT-TYPE
			SYNTAX Integer32
			MAX-ACCESS read-only
			STATUS current
			DESCRIPTION
				"Description."
			::= { fhArpEntry 4 }

		
		-- 1.3.6.1.4.1.11408.11.1.33.1.1.5
		fhArpType OBJECT-TYPE
			SYNTAX Integer32
			MAX-ACCESS read-only
			STATUS current
			DESCRIPTION
				"Description."
			::= { fhArpEntry 5 }

		
		-- 1.3.6.1.4.1.11408.11.1.33.1.1.6
		fhArpVlanId OBJECT-TYPE
			SYNTAX Integer32
			MAX-ACCESS read-only
			STATUS current
			DESCRIPTION
				"Description."
			::= { fhArpEntry 6 }

		
		-- 1.3.6.1.4.1.11408.11.1.33.1.1.7
		fhArpCvlanId OBJECT-TYPE
			SYNTAX Integer32
			MAX-ACCESS read-only
			STATUS current
			DESCRIPTION
				"Description."
			::= { fhArpEntry 7 }

		
		-- 1.3.6.1.4.1.11408.11.1.33.1.1.8
		fhArpExpireTime OBJECT-TYPE
			SYNTAX Integer32
			MAX-ACCESS read-only
			STATUS current
			DESCRIPTION
				"Description."
			::= { fhArpEntry 8 }

		
		-- 1.3.6.1.4.1.11408.11.1.33.1.1.9
		fhArpIfName OBJECT-TYPE
			SYNTAX OCTET STRING (SIZE (0..255))
			MAX-ACCESS read-only
			STATUS current
			DESCRIPTION
				"Description."
			::= { fhArpEntry 9 }

		
		-- 1.3.6.1.4.1.11408.11.1.33.1.1.11
		fhNgmIndex OBJECT-TYPE
			SYNTAX Integer32
			MAX-ACCESS not-accessible
			STATUS current
			DESCRIPTION
				"Description."
			::= { fhArpEntry 11 }

		
		-- 1.3.6.1.4.1.11408.11.1.33.2
		fhNdpTable OBJECT-TYPE
			SYNTAX SEQUENCE OF FhNdpEntry
			MAX-ACCESS not-accessible
			STATUS current
			DESCRIPTION
				"Description."
			::= { fhNgm 2 }

		
		-- 1.3.6.1.4.1.11408.11.1.33.2.1
		fhNdpEntry OBJECT-TYPE
			SYNTAX FhNdpEntry
			MAX-ACCESS not-accessible
			STATUS current
			DESCRIPTION
				"Description."
			INDEX { fhNdpIfIndex, fhNdpIpAdd, fhNdpVrfId, fhNgmIndex }
			::= { fhNdpTable 1 }

		
		FhNdpEntry ::=
			SEQUENCE { 
				fhNdpIfIndex
					Integer32,
				fhNdpIpAdd
					IpAddress,
				fhNdpMacAdd
					MacAddress,
				fhNdpVrfId
					Integer32,
				fhNdpType
					Integer32,
				fhNdpVlanId
					Integer32,
				fhNdpCvlanId
					Integer32,
				fhNdpExpireTime
					Integer32,
				fhNdpIfName
					OCTET STRING
			 }

		-- 1.3.6.1.4.1.11408.11.1.33.2.1.1
		fhNdpIfIndex OBJECT-TYPE
			SYNTAX Integer32
			MAX-ACCESS read-only
			STATUS current
			DESCRIPTION
				"Description."
			::= { fhNdpEntry 1 }

		
		-- 1.3.6.1.4.1.11408.11.1.33.2.1.2
		fhNdpIpAdd OBJECT-TYPE
			SYNTAX IpAddress
			MAX-ACCESS read-only
			STATUS current
			DESCRIPTION
				"Description."
			::= { fhNdpEntry 2 }

		
		-- 1.3.6.1.4.1.11408.11.1.33.2.1.3
		fhNdpMacAdd OBJECT-TYPE
			SYNTAX MacAddress (SIZE (0..255))
			MAX-ACCESS read-only
			STATUS current
			DESCRIPTION
				"Description."
			::= { fhNdpEntry 3 }

		
		-- 1.3.6.1.4.1.11408.11.1.33.2.1.4
		fhNdpVrfId OBJECT-TYPE
			SYNTAX Integer32
			MAX-ACCESS read-only
			STATUS current
			DESCRIPTION
				"Description."
			::= { fhNdpEntry 4 }

		
		-- 1.3.6.1.4.1.11408.11.1.33.2.1.5
		fhNdpType OBJECT-TYPE
			SYNTAX Integer32
			MAX-ACCESS read-only
			STATUS current
			DESCRIPTION
				"Description."
			::= { fhNdpEntry 5 }

		
		-- 1.3.6.1.4.1.11408.11.1.33.2.1.6
		fhNdpVlanId OBJECT-TYPE
			SYNTAX Integer32
			MAX-ACCESS read-only
			STATUS current
			DESCRIPTION
				"Description."
			::= { fhNdpEntry 6 }

		
		-- 1.3.6.1.4.1.11408.11.1.33.2.1.7
		fhNdpCvlanId OBJECT-TYPE
			SYNTAX Integer32
			MAX-ACCESS read-only
			STATUS current
			DESCRIPTION
				"Description."
			::= { fhNdpEntry 7 }

		
		-- 1.3.6.1.4.1.11408.11.1.33.2.1.8
		fhNdpExpireTime OBJECT-TYPE
			SYNTAX Integer32
			MAX-ACCESS read-only
			STATUS current
			DESCRIPTION
				"Description."
			::= { fhNdpEntry 8 }

		
		-- 1.3.6.1.4.1.11408.11.1.33.2.1.9
		fhNdpIfName OBJECT-TYPE
			SYNTAX OCTET STRING (SIZE (0..255))
			MAX-ACCESS read-only
			STATUS current
			DESCRIPTION
				"Description."
			::= { fhNdpEntry 9 }

		
--   1.3.6.1.4.1.11408.11.20
-- 1.3.6.1.4.1.11408.11.20
		-- 1.3.6.1.4.1.11408.11.20
		fhPublicOidToPrivate OBJECT IDENTIFIER ::= { fhMgmt 20 }

		
--   1.3.6.1.4.1.11408.11.20.1
-- 1.3.6.1.4.1.11408.11.20.1
		-- 1.3.6.1.4.1.11408.11.20.1
		fhPublicOidToPrivateIso OBJECT IDENTIFIER ::= { fhPublicOidToPrivate 1 }

		
--   1.3.6.1.4.1.11408.11.20.1.2
-- 1.3.6.1.4.1.11408.11.20.1.2
		-- 1.3.6.1.4.1.11408.11.20.1.2
		fhPublicOidToPrivateIso12 OBJECT IDENTIFIER ::= { fhPublicOidToPrivateIso 2 }

		
--   1.3.6.1.4.1.11408.11.20.1.2.1
-- 1.3.6.1.4.1.11408.11.20.1.2.1
		-- 1.3.6.1.4.1.11408.11.20.1.2.1
		private12Isis OBJECT IDENTIFIER ::= { fhPublicOidToPrivateIso12 1 }

		
--   1.3.6.1.4.1.11408.11.20.1.2.1.1
-- 1.3.6.1.4.1.11408.11.20.1.2.1.1
		-- 1.3.6.1.4.1.11408.11.20.1.2.1.1
		dclIsisDataBaseOverload NOTIFICATION-TYPE
			STATUS current
			DESCRIPTION 
				"Description."
			::= { private12Isis 1 }

		
--   1.3.6.1.4.1.11408.11.20.1.2.1.2
-- 1.3.6.1.4.1.11408.11.20.1.2.1.2
		-- 1.3.6.1.4.1.11408.11.20.1.2.1.2
		dclIsisManualAddrDrops NOTIFICATION-TYPE
			STATUS current
			DESCRIPTION 
				"Description."
			::= { private12Isis 2 }

		
--   1.3.6.1.4.1.11408.11.20.1.2.1.4
-- 1.3.6.1.4.1.11408.11.20.1.2.1.4
		-- 1.3.6.1.4.1.11408.11.20.1.2.1.4
		dclIsisMaxAreaAddrMis NOTIFICATION-TYPE
			STATUS current
			DESCRIPTION 
				"Description."
			::= { private12Isis 4 }

		
--   1.3.6.1.4.1.11408.11.20.1.2.1.10
-- 1.3.6.1.4.1.11408.11.20.1.2.1.10
		-- 1.3.6.1.4.1.11408.11.20.1.2.1.10
		dclIsisExceedMaxSeq NOTIFICATION-TYPE
			STATUS current
			DESCRIPTION 
				"Description."
			::= { private12Isis 10 }

		
--   1.3.6.1.4.1.11408.11.20.1.2.1.12
-- 1.3.6.1.4.1.11408.11.20.1.2.1.12
		-- 1.3.6.1.4.1.11408.11.20.1.2.1.12
		dclIsisCircuitInd NOTIFICATION-TYPE
			STATUS current
			DESCRIPTION 
				"Description."
			::= { private12Isis 12 }

		
--   1.3.6.1.4.1.11408.11.20.1.2.1.15
-- 1.3.6.1.4.1.11408.11.20.1.2.1.15
		-- 1.3.6.1.4.1.11408.11.20.1.2.1.15
		dclIsisCorruptedLsp NOTIFICATION-TYPE
			STATUS current
			DESCRIPTION 
				"Description."
			::= { private12Isis 15 }

		
--   1.3.6.1.4.1.11408.11.20.1.2.2
-- 1.3.6.1.4.1.11408.11.20.1.2.2
		-- 1.3.6.1.4.1.11408.11.20.1.2.2
		private12Ospf OBJECT IDENTIFIER ::= { fhPublicOidToPrivateIso12 2 }

		
--   1.3.6.1.4.1.11408.11.20.1.2.2.4
-- 1.3.6.1.4.1.11408.11.20.1.2.2.4
		-- 1.3.6.1.4.1.11408.11.20.1.2.2.4
		dclOspfnbrReStartChg NOTIFICATION-TYPE
			STATUS current
			DESCRIPTION 
				"Description."
			::= { private12Ospf 4 }

		
--   1.3.6.1.4.1.11408.11.20.1.2.2.6
-- 1.3.6.1.4.1.11408.11.20.1.2.2.6
		-- 1.3.6.1.4.1.11408.11.20.1.2.2.6
		dclOspfNssaTransChg NOTIFICATION-TYPE
			STATUS current
			DESCRIPTION 
				"Description."
			::= { private12Ospf 6 }

		
--   1.3.6.1.4.1.11408.11.20.1.2.2.7
-- 1.3.6.1.4.1.11408.11.20.1.2.2.7
		-- 1.3.6.1.4.1.11408.11.20.1.2.2.7
		dclOspfOperChg NOTIFICATION-TYPE
			STATUS current
			DESCRIPTION 
				"Description."
			::= { private12Ospf 7 }

		
--   1.3.6.1.4.1.11408.11.20.1.2.2.11
-- 1.3.6.1.4.1.11408.11.20.1.2.2.11
		-- 1.3.6.1.4.1.11408.11.20.1.2.2.11
		dclOspfVnbrReStartChg NOTIFICATION-TYPE
			STATUS current
			DESCRIPTION 
				"Description."
			::= { private12Ospf 11 }

		
--   1.3.6.1.4.1.11408.11.20.1.2.5
-- 1.3.6.1.4.1.11408.11.20.1.2.5
		-- 1.3.6.1.4.1.11408.11.20.1.2.5
		private12Ospfv3 OBJECT IDENTIFIER ::= { fhPublicOidToPrivateIso12 5 }

		
--   1.3.6.1.4.1.11408.11.20.1.2.5.1
-- 1.3.6.1.4.1.11408.11.20.1.2.5.1
		-- 1.3.6.1.4.1.11408.11.20.1.2.5.1
		dclOsp3IfConfigErr NOTIFICATION-TYPE
			STATUS current
			DESCRIPTION 
				"Description."
			::= { private12Ospfv3 1 }

		
--   1.3.6.1.4.1.11408.11.20.1.2.5.2
-- 1.3.6.1.4.1.11408.11.20.1.2.5.2
		-- 1.3.6.1.4.1.11408.11.20.1.2.5.2
		dclOsp3IfStateChg NOTIFICATION-TYPE
			STATUS current
			DESCRIPTION 
				"Description."
			::= { private12Ospfv3 2 }

		
--   1.3.6.1.4.1.11408.11.20.1.2.5.3
-- 1.3.6.1.4.1.11408.11.20.1.2.5.3
		-- 1.3.6.1.4.1.11408.11.20.1.2.5.3
		dclOsp3NbrRstrtChg NOTIFICATION-TYPE
			STATUS current
			DESCRIPTION 
				"Description."
			::= { private12Ospfv3 3 }

		
--   1.3.6.1.4.1.11408.11.20.1.2.5.4
-- 1.3.6.1.4.1.11408.11.20.1.2.5.4
		-- 1.3.6.1.4.1.11408.11.20.1.2.5.4
		dclOsp3NbrStateChg NOTIFICATION-TYPE
			STATUS current
			DESCRIPTION 
				"Description."
			::= { private12Ospfv3 4 }

		
--   1.3.6.1.4.1.11408.11.20.1.2.5.5
-- 1.3.6.1.4.1.11408.11.20.1.2.5.5
		-- 1.3.6.1.4.1.11408.11.20.1.2.5.5
		dclOsp3NssaTransChg NOTIFICATION-TYPE
			STATUS current
			DESCRIPTION 
				"Description."
			::= { private12Ospfv3 5 }

		
--   1.3.6.1.4.1.11408.11.20.1.2.5.6
-- 1.3.6.1.4.1.11408.11.20.1.2.5.6
		-- 1.3.6.1.4.1.11408.11.20.1.2.5.6
		dclOsp3OperChg NOTIFICATION-TYPE
			STATUS current
			DESCRIPTION 
				"Description."
			::= { private12Ospfv3 6 }

		
--   1.3.6.1.4.1.11408.11.20.1.2.5.7
-- 1.3.6.1.4.1.11408.11.20.1.2.5.7
		-- 1.3.6.1.4.1.11408.11.20.1.2.5.7
		dclOsp3VifConfigErr NOTIFICATION-TYPE
			STATUS current
			DESCRIPTION 
				"Description."
			::= { private12Ospfv3 7 }

		
--   1.3.6.1.4.1.11408.11.20.1.2.5.8
-- 1.3.6.1.4.1.11408.11.20.1.2.5.8
		-- 1.3.6.1.4.1.11408.11.20.1.2.5.8
		dclOsp3VifStateChg NOTIFICATION-TYPE
			STATUS current
			DESCRIPTION 
				"Description."
			::= { private12Ospfv3 8 }

		
--   1.3.6.1.4.1.11408.11.20.1.2.5.9
-- 1.3.6.1.4.1.11408.11.20.1.2.5.9
		-- 1.3.6.1.4.1.11408.11.20.1.2.5.9
		dclOsp3VnbrChg NOTIFICATION-TYPE
			STATUS current
			DESCRIPTION 
				"Description."
			::= { private12Ospfv3 9 }

		
--   1.3.6.1.4.1.11408.11.20.1.2.5.10
-- 1.3.6.1.4.1.11408.11.20.1.2.5.10
		-- 1.3.6.1.4.1.11408.11.20.1.2.5.10
		dclOsp3VnbrRstrtChg NOTIFICATION-TYPE
			STATUS current
			DESCRIPTION 
				"Description."
			::= { private12Ospfv3 10 }

		
--   1.3.6.1.4.1.11408.11.20.1.2.11
-- 1.3.6.1.4.1.11408.11.20.1.2.11
		-- 1.3.6.1.4.1.11408.11.20.1.2.11
		private12Lldp OBJECT IDENTIFIER ::= { fhPublicOidToPrivateIso12 11 }

		
--   1.3.6.1.4.1.11408.11.20.1.2.11.1
-- 1.3.6.1.4.1.11408.11.20.1.2.11.1
		-- 1.3.6.1.4.1.11408.11.20.1.2.11.1
		dclLldpRemTablesChg NOTIFICATION-TYPE
			STATUS current
			DESCRIPTION 
				"Description."
			::= { private12Lldp 1 }

		
--   1.3.6.1.4.1.11408.11.20.1.2.12
-- 1.3.6.1.4.1.11408.11.20.1.2.12
		-- 1.3.6.1.4.1.11408.11.20.1.2.12
		private12Pim OBJECT IDENTIFIER ::= { fhPublicOidToPrivateIso12 12 }

		
--   1.3.6.1.4.1.11408.11.20.1.2.12.1
-- 1.3.6.1.4.1.11408.11.20.1.2.12.1
		-- 1.3.6.1.4.1.11408.11.20.1.2.12.1
		dclPimNeighborLoss NOTIFICATION-TYPE
			STATUS current
			DESCRIPTION 
				"Description."
			::= { private12Pim 1 }

		
--   1.3.6.1.4.1.11408.11.20.1.2.12.2
-- 1.3.6.1.4.1.11408.11.20.1.2.12.2
		-- 1.3.6.1.4.1.11408.11.20.1.2.12.2
		dclPimIfStateChg NOTIFICATION-TYPE
			STATUS current
			DESCRIPTION 
				"Description."
			::= { private12Pim 2 }

		
--   1.3.6.1.4.1.11408.11.20.1.2.13
-- 1.3.6.1.4.1.11408.11.20.1.2.13
		-- 1.3.6.1.4.1.11408.11.20.1.2.13
		private12I3If OBJECT IDENTIFIER ::= { fhPublicOidToPrivateIso12 13 }

		
--   1.3.6.1.4.1.11408.11.20.1.2.13.3
-- 1.3.6.1.4.1.11408.11.20.1.2.13.3
		-- 1.3.6.1.4.1.11408.11.20.1.2.13.3
		dclStubI3IfLagDown NOTIFICATION-TYPE
			STATUS current
			DESCRIPTION 
				"Description."
			::= { private12I3If 3 }

		
--   1.3.6.1.4.1.11408.11.20.1.2.13.4
-- 1.3.6.1.4.1.11408.11.20.1.2.13.4
		-- 1.3.6.1.4.1.11408.11.20.1.2.13.4
		dclStubI3IfLagUp NOTIFICATION-TYPE
			STATUS current
			DESCRIPTION 
				"Description."
			::= { private12I3If 4 }

		
--   1.3.6.1.4.1.11408.11.20.1.3
-- 1.3.6.1.4.1.11408.11.20.1.3
		-- 1.3.6.1.4.1.11408.11.20.1.3
		fhPublicOidToPrivateIso13 OBJECT IDENTIFIER ::= { fhPublicOidToPrivateIso 3 }

		
--   1.3.6.1.4.1.11408.11.20.1.3.1
-- 1.3.6.1.4.1.11408.11.20.1.3.1
		-- 1.3.6.1.4.1.11408.11.20.1.3.1
		private13Isis OBJECT IDENTIFIER ::= { fhPublicOidToPrivateIso13 1 }

		
--   1.3.6.1.4.1.11408.11.20.1.3.1.1
-- 1.3.6.1.4.1.11408.11.20.1.3.1.1
		-- 1.3.6.1.4.1.11408.11.20.1.3.1.1
		isisDataBaseOverload NOTIFICATION-TYPE
			STATUS current
			DESCRIPTION 
				"Description."
			::= { private13Isis 1 }

		
--   1.3.6.1.4.1.11408.11.20.1.3.1.2
-- 1.3.6.1.4.1.11408.11.20.1.3.1.2
		-- 1.3.6.1.4.1.11408.11.20.1.3.1.2
		isisManualAddrDrops NOTIFICATION-TYPE
			STATUS current
			DESCRIPTION 
				"Description."
			::= { private13Isis 2 }

		
--   1.3.6.1.4.1.11408.11.20.1.3.1.3
-- 1.3.6.1.4.1.11408.11.20.1.3.1.3
		-- 1.3.6.1.4.1.11408.11.20.1.3.1.3
		isisLspErrDelete NOTIFICATION-TYPE
			STATUS current
			DESCRIPTION 
				"Description."
			::= { private13Isis 3 }

		
--   1.3.6.1.4.1.11408.11.20.1.3.1.5
-- 1.3.6.1.4.1.11408.11.20.1.3.1.5
		-- 1.3.6.1.4.1.11408.11.20.1.3.1.5
		isisIdLenMis NOTIFICATION-TYPE
			STATUS current
			DESCRIPTION 
				"Description."
			::= { private13Isis 5 }

		
--   1.3.6.1.4.1.11408.11.20.1.3.1.6
-- 1.3.6.1.4.1.11408.11.20.1.3.1.6
		-- 1.3.6.1.4.1.11408.11.20.1.3.1.6
		isisAreaMis NOTIFICATION-TYPE
			STATUS current
			DESCRIPTION 
				"Description."
			::= { private13Isis 6 }

		
--   1.3.6.1.4.1.11408.11.20.1.3.1.7
-- 1.3.6.1.4.1.11408.11.20.1.3.1.7
		-- 1.3.6.1.4.1.11408.11.20.1.3.1.7
		isisOwsLspPurge NOTIFICATION-TYPE
			STATUS current
			DESCRIPTION 
				"Description."
			::= { private13Isis 7 }

		
--   1.3.6.1.4.1.11408.11.20.1.3.1.8
-- 1.3.6.1.4.1.11408.11.20.1.3.1.8
		-- 1.3.6.1.4.1.11408.11.20.1.3.1.8
		isisSeqNumberFail NOTIFICATION-TYPE
			STATUS current
			DESCRIPTION 
				"Description."
			::= { private13Isis 8 }

		
--   1.3.6.1.4.1.11408.11.20.1.3.1.9
-- 1.3.6.1.4.1.11408.11.20.1.3.1.9
		-- 1.3.6.1.4.1.11408.11.20.1.3.1.9
		isisAuthTypeFail NOTIFICATION-TYPE
			STATUS current
			DESCRIPTION 
				"Description."
			::= { private13Isis 9 }

		
--   1.3.6.1.4.1.11408.11.20.1.3.1.10
-- 1.3.6.1.4.1.11408.11.20.1.3.1.10
		-- 1.3.6.1.4.1.11408.11.20.1.3.1.10
		isisAuthFail NOTIFICATION-TYPE
			STATUS current
			DESCRIPTION 
				"Description."
			::= { private13Isis 10 }

		
--   1.3.6.1.4.1.11408.11.20.1.3.1.11
-- 1.3.6.1.4.1.11408.11.20.1.3.1.11
		-- 1.3.6.1.4.1.11408.11.20.1.3.1.11
		isisVersionSkew NOTIFICATION-TYPE
			STATUS current
			DESCRIPTION 
				"Description."
			::= { private13Isis 11 }

		
--   1.3.6.1.4.1.11408.11.20.1.3.1.13
-- 1.3.6.1.4.1.11408.11.20.1.3.1.13
		-- 1.3.6.1.4.1.11408.11.20.1.3.1.13
		isisRejectedAdj NOTIFICATION-TYPE
			STATUS current
			DESCRIPTION 
				"Description."
			::= { private13Isis 13 }

		
--   1.3.6.1.4.1.11408.11.20.1.3.1.15
-- 1.3.6.1.4.1.11408.11.20.1.3.1.15
		-- 1.3.6.1.4.1.11408.11.20.1.3.1.15
		isisOrigLspSizeMis NOTIFICATION-TYPE
			STATUS current
			DESCRIPTION 
				"Description."
			::= { private13Isis 15 }

		
--   1.3.6.1.4.1.11408.11.20.1.3.1.16
-- 1.3.6.1.4.1.11408.11.20.1.3.1.16
		-- 1.3.6.1.4.1.11408.11.20.1.3.1.16
		isisProtoSupportMis NOTIFICATION-TYPE
			STATUS current
			DESCRIPTION 
				"Description."
			::= { private13Isis 16 }

		
--   1.3.6.1.4.1.11408.11.20.1.3.1.17
-- 1.3.6.1.4.1.11408.11.20.1.3.1.17
		-- 1.3.6.1.4.1.11408.11.20.1.3.1.17
		isisAdjacencyChg NOTIFICATION-TYPE
			STATUS current
			DESCRIPTION 
				"Description."
			::= { private13Isis 17 }

		
--   1.3.6.1.4.1.11408.11.20.1.3.2
-- 1.3.6.1.4.1.11408.11.20.1.3.2
		-- 1.3.6.1.4.1.11408.11.20.1.3.2
		private13Ospf OBJECT IDENTIFIER ::= { fhPublicOidToPrivateIso13 2 }

		
--   1.3.6.1.4.1.11408.11.20.1.3.2.1
-- 1.3.6.1.4.1.11408.11.20.1.3.2.1
		-- 1.3.6.1.4.1.11408.11.20.1.3.2.1
		ospfVifStateChg NOTIFICATION-TYPE
			STATUS current
			DESCRIPTION 
				"Description."
			::= { private13Ospf 1 }

		
--   1.3.6.1.4.1.11408.11.20.1.3.2.2
-- 1.3.6.1.4.1.11408.11.20.1.3.2.2
		-- 1.3.6.1.4.1.11408.11.20.1.3.2.2
		ospfNbrStateChg NOTIFICATION-TYPE
			STATUS current
			DESCRIPTION 
				"Description."
			::= { private13Ospf 2 }

		
--   1.3.6.1.4.1.11408.11.20.1.3.2.3
-- 1.3.6.1.4.1.11408.11.20.1.3.2.3
		-- 1.3.6.1.4.1.11408.11.20.1.3.2.3
		ospfVnbrStateChg NOTIFICATION-TYPE
			STATUS current
			DESCRIPTION 
				"Description."
			::= { private13Ospf 3 }

		
--   1.3.6.1.4.1.11408.11.20.1.3.2.4
-- 1.3.6.1.4.1.11408.11.20.1.3.2.4
		-- 1.3.6.1.4.1.11408.11.20.1.3.2.4
		ospfIfConfigError NOTIFICATION-TYPE
			STATUS current
			DESCRIPTION 
				"Description."
			::= { private13Ospf 4 }

		
--   1.3.6.1.4.1.11408.11.20.1.3.2.5
-- 1.3.6.1.4.1.11408.11.20.1.3.2.5
		-- 1.3.6.1.4.1.11408.11.20.1.3.2.5
		ospfVifConfigError NOTIFICATION-TYPE
			STATUS current
			DESCRIPTION 
				"Description."
			::= { private13Ospf 5 }

		
--   1.3.6.1.4.1.11408.11.20.1.3.2.6
-- 1.3.6.1.4.1.11408.11.20.1.3.2.6
		-- 1.3.6.1.4.1.11408.11.20.1.3.2.6
		ospfIfAuthFail NOTIFICATION-TYPE
			STATUS current
			DESCRIPTION 
				"Description."
			::= { private13Ospf 6 }

		
--   1.3.6.1.4.1.11408.11.20.1.3.2.7
-- 1.3.6.1.4.1.11408.11.20.1.3.2.7
		-- 1.3.6.1.4.1.11408.11.20.1.3.2.7
		ospfVifAuthFail NOTIFICATION-TYPE
			STATUS current
			DESCRIPTION 
				"Description."
			::= { private13Ospf 7 }

		
--   1.3.6.1.4.1.11408.11.20.1.3.2.12
-- 1.3.6.1.4.1.11408.11.20.1.3.2.12
		-- 1.3.6.1.4.1.11408.11.20.1.3.2.12
		ospfOriginateLsa NOTIFICATION-TYPE
			STATUS current
			DESCRIPTION 
				"Description."
			::= { private13Ospf 12 }

		
--   1.3.6.1.4.1.11408.11.20.1.3.2.14
-- 1.3.6.1.4.1.11408.11.20.1.3.2.14
		-- 1.3.6.1.4.1.11408.11.20.1.3.2.14
		ospfLsdbOverflow NOTIFICATION-TYPE
			STATUS current
			DESCRIPTION 
				"Description."
			::= { private13Ospf 14 }

		
--   1.3.6.1.4.1.11408.11.20.1.3.2.16
-- 1.3.6.1.4.1.11408.11.20.1.3.2.16
		-- 1.3.6.1.4.1.11408.11.20.1.3.2.16
		ospfIfStateChg NOTIFICATION-TYPE
			STATUS current
			DESCRIPTION 
				"Description."
			::= { private13Ospf 16 }

		
--   1.3.6.1.4.1.11408.11.20.1.3.3
-- 1.3.6.1.4.1.11408.11.20.1.3.3
		-- 1.3.6.1.4.1.11408.11.20.1.3.3
		private13Bgp OBJECT IDENTIFIER ::= { fhPublicOidToPrivateIso13 3 }

		
--   1.3.6.1.4.1.11408.11.20.1.3.3.1
-- 1.3.6.1.4.1.11408.11.20.1.3.3.1
		-- 1.3.6.1.4.1.11408.11.20.1.3.3.1
		bgpSessEstablished NOTIFICATION-TYPE
			STATUS current
			DESCRIPTION 
				"Description."
			::= { private13Bgp 1 }

		
--   1.3.6.1.4.1.11408.11.20.1.3.3.2
-- 1.3.6.1.4.1.11408.11.20.1.3.3.2
		-- 1.3.6.1.4.1.11408.11.20.1.3.3.2
		bgpPackward NOTIFICATION-TYPE
			STATUS current
			DESCRIPTION 
				"Description."
			::= { private13Bgp 2 }

		
--   1.3.6.1.4.1.11408.11.20.1.3.4
-- 1.3.6.1.4.1.11408.11.20.1.3.4
		-- 1.3.6.1.4.1.11408.11.20.1.3.4
		private13Ldp OBJECT IDENTIFIER ::= { fhPublicOidToPrivateIso13 4 }

		
--   1.3.6.1.4.1.11408.11.20.1.3.4.1
-- 1.3.6.1.4.1.11408.11.20.1.3.4.1
		-- 1.3.6.1.4.1.11408.11.20.1.3.4.1
		cldpSessThreshExcd NOTIFICATION-TYPE
			STATUS current
			DESCRIPTION 
				"Description."
			::= { private13Ldp 1 }

		
--   1.3.6.1.4.1.11408.11.20.1.3.4.2
-- 1.3.6.1.4.1.11408.11.20.1.3.4.2
		-- 1.3.6.1.4.1.11408.11.20.1.3.4.2
		cldpPathVecLimMis NOTIFICATION-TYPE
			STATUS current
			DESCRIPTION 
				"Description."
			::= { private13Ldp 2 }

		
--   1.3.6.1.4.1.11408.11.20.1.3.4.3
-- 1.3.6.1.4.1.11408.11.20.1.3.4.3
		-- 1.3.6.1.4.1.11408.11.20.1.3.4.3
		cldpSessionUp NOTIFICATION-TYPE
			STATUS current
			DESCRIPTION 
				"Description."
			::= { private13Ldp 3 }

		
--   1.3.6.1.4.1.11408.11.20.1.3.4.4
-- 1.3.6.1.4.1.11408.11.20.1.3.4.4
		-- 1.3.6.1.4.1.11408.11.20.1.3.4.4
		cldpSessionDown NOTIFICATION-TYPE
			STATUS current
			DESCRIPTION 
				"Description."
			::= { private13Ldp 4 }

		
--   1.3.6.1.4.1.11408.11.20.1.3.4.5
-- 1.3.6.1.4.1.11408.11.20.1.3.4.5
		-- 1.3.6.1.4.1.11408.11.20.1.3.4.5
		cldpSessUp NOTIFICATION-TYPE
			STATUS current
			DESCRIPTION 
				"Description."
			::= { private13Ldp 5 }

		
--   1.3.6.1.4.1.11408.11.20.1.3.4.6
-- 1.3.6.1.4.1.11408.11.20.1.3.4.6
		-- 1.3.6.1.4.1.11408.11.20.1.3.4.6
		cldpSessDown NOTIFICATION-TYPE
			STATUS current
			DESCRIPTION 
				"Description."
			::= { private13Ldp 6 }

		
--   1.3.6.1.4.1.11408.11.20.1.3.6
-- 1.3.6.1.4.1.11408.11.20.1.3.6
		-- 1.3.6.1.4.1.11408.11.20.1.3.6
		private13I3Link OBJECT IDENTIFIER ::= { fhPublicOidToPrivateIso13 6 }

		
--   1.3.6.1.4.1.11408.11.20.1.3.6.3
-- 1.3.6.1.4.1.11408.11.20.1.3.6.3
		-- 1.3.6.1.4.1.11408.11.20.1.3.6.3
		stubI3LinkDown NOTIFICATION-TYPE
			STATUS current
			DESCRIPTION 
				"Description."
			::= { private13I3Link 3 }

		
--   1.3.6.1.4.1.11408.11.20.1.3.6.4
-- 1.3.6.1.4.1.11408.11.20.1.3.6.4
		-- 1.3.6.1.4.1.11408.11.20.1.3.6.4
		stubI3Linkup NOTIFICATION-TYPE
			STATUS current
			DESCRIPTION 
				"Description."
			::= { private13I3Link 4 }

		
--   1.3.6.1.4.1.11408.11.20.1.3.7
-- 1.3.6.1.4.1.11408.11.20.1.3.7
		-- 1.3.6.1.4.1.11408.11.20.1.3.7
		private13IsisSystemId OBJECT IDENTIFIER ::= { fhPublicOidToPrivateIso13 7 }

		
--   1.3.6.1.4.1.11408.11.20.1.3.7.1
-- 1.3.6.1.4.1.11408.11.20.1.3.7.1
		-- 1.3.6.1.4.1.11408.11.20.1.3.7.1
		isisSystemIdConflict NOTIFICATION-TYPE
			STATUS current
			DESCRIPTION 
				"Description."
			::= { private13IsisSystemId 1 }

		
--   1.3.6.1.4.1.11408.11.20.1.3.8
-- 1.3.6.1.4.1.11408.11.20.1.3.8
		-- 1.3.6.1.4.1.11408.11.20.1.3.8
		private13MplsTunnel OBJECT IDENTIFIER ::= { fhPublicOidToPrivateIso13 8 }

		
--   1.3.6.1.4.1.11408.11.20.1.3.8.1
-- 1.3.6.1.4.1.11408.11.20.1.3.8.1
		-- 1.3.6.1.4.1.11408.11.20.1.3.8.1
		mplsTunnelUp NOTIFICATION-TYPE
			STATUS current
			DESCRIPTION 
				"Description."
			::= { private13MplsTunnel 1 }

		
--   1.3.6.1.4.1.11408.11.20.1.3.8.2
-- 1.3.6.1.4.1.11408.11.20.1.3.8.2
		-- 1.3.6.1.4.1.11408.11.20.1.3.8.2
		mplsTunnelDown NOTIFICATION-TYPE
			STATUS current
			DESCRIPTION 
				"Description."
			::= { private13MplsTunnel 2 }

		
--   1.3.6.1.4.1.11408.11.20.1.3.8.3
-- 1.3.6.1.4.1.11408.11.20.1.3.8.3
		-- 1.3.6.1.4.1.11408.11.20.1.3.8.3
		mplsTunnelRerouted NOTIFICATION-TYPE
			STATUS current
			DESCRIPTION 
				"Description."
			::= { private13MplsTunnel 3 }

		
--   1.3.6.1.4.1.11408.11.20.1.3.8.4
-- 1.3.6.1.4.1.11408.11.20.1.3.8.4
		-- 1.3.6.1.4.1.11408.11.20.1.3.8.4
		mplsTunnelReport NOTIFICATION-TYPE
			STATUS current
			DESCRIPTION 
				"Description."
			::= { private13MplsTunnel 4 }

		
--   1.3.6.1.4.1.11408.11.20.1.3.9
-- 1.3.6.1.4.1.11408.11.20.1.3.9
		-- 1.3.6.1.4.1.11408.11.20.1.3.9
		private13Vrrp OBJECT IDENTIFIER ::= { fhPublicOidToPrivateIso13 9 }

		
--   1.3.6.1.4.1.11408.11.20.1.3.9.1
-- 1.3.6.1.4.1.11408.11.20.1.3.9.1
		-- 1.3.6.1.4.1.11408.11.20.1.3.9.1
		vrrpStatus NOTIFICATION-TYPE
			STATUS current
			DESCRIPTION 
				"Description."
			::= { private13Vrrp 1 }

		
--   1.3.6.1.4.1.11408.11.20.1.3.10
-- 1.3.6.1.4.1.11408.11.20.1.3.10
		-- 1.3.6.1.4.1.11408.11.20.1.3.10
		private13Mpls OBJECT IDENTIFIER ::= { fhPublicOidToPrivateIso13 10 }

		
--   1.3.6.1.4.1.11408.11.20.1.3.10.3
-- 1.3.6.1.4.1.11408.11.20.1.3.10.3
		-- 1.3.6.1.4.1.11408.11.20.1.3.10.3
		mplsPwDelet NOTIFICATION-TYPE
			STATUS current
			DESCRIPTION 
				"Description."
			::= { private13Mpls 3 }

		
--   1.3.6.1.4.1.11408.11.20.1.3.10.101
-- 1.3.6.1.4.1.11408.11.20.1.3.10.101
		-- 1.3.6.1.4.1.11408.11.20.1.3.10.101
		mplsUnexpctdPwRcvd NOTIFICATION-TYPE
			STATUS current
			DESCRIPTION 
				"Description."
			::= { private13Mpls 101 }

		
	
	END

--
-- FIBERHOME-DATACOMM-MIB.my
--

ADF-1-MIB DEFINITIONS ::= BEGIN
IMPORTS
       MODULE-IDENTITY,OBJECT-TYPE
         FROM SNMPv2-SMI
         DisplayString, TimeStamp
         FROM SNMPv2-TC
         enterprises
         FROM RFC1155-SMI;

identity MODULE-IDENTITY
    LAST-UPDATED "201701310000Z"
    ORGANIZATION "www.adfweb.com"
    CONTACT-INFO
	 "via Strada Nuova, 17
    31010 Mareno di Piave (TV)
    ITALY
    email:    adfweb.com"
    DESCRIPTION
	"MIB objects for agent module "
    REVISION     "201701310000Z"
    DESCRIPTION
	"Corrected notification "
    REVISION     "200202060000Z"
    DESCRIPTION
	"First draft"
    ::= { adfweb 2 }
adfweb          OBJECT IDENTIFIER ::= { enterprises 49314 }
gateway OBJECT IDENTIFIER::= { adfweb 1 }
application OBJECT IDENTIFIER::= { gateway 1 }
data OBJECT IDENTIFIER::= { application 1 }
hellostring OBJECT-TYPE SYNTAX OCTET STRING MAX-ACCESS read-only  STATUS current  DESCRIPTION "" ::= { data 1}
countin  OBJECT-TYPE SYNTAX INTEGER       MAX-ACCESS read-only  STATUS current  DESCRIPTION "" ::= { data 2}
countout  OBJECT-TYPE SYNTAX INTEGER       MAX-ACCESS read-write STATUS current  DESCRIPTION "" ::= { data 3}
bufferin OBJECT IDENTIFIER::= { data 4 }
bufferinblk1 OBJECT-TYPE SYNTAX OCTET STRING MAX-ACCESS read-only STATUS current DESCRIPTION "data block n.1" ::= { bufferin 1 }
bufferinblk2 OBJECT-TYPE SYNTAX OCTET STRING MAX-ACCESS read-only STATUS current DESCRIPTION "data block n.2" ::= { bufferin 2 }
bufferinblk3 OBJECT-TYPE SYNTAX OCTET STRING MAX-ACCESS read-only STATUS current DESCRIPTION "data block n.3" ::= { bufferin 3 }
bufferinblk4 OBJECT-TYPE SYNTAX OCTET STRING MAX-ACCESS read-only STATUS current DESCRIPTION "data block n.4" ::= { bufferin 4 }
bufferinblk5 OBJECT-TYPE SYNTAX OCTET STRING MAX-ACCESS read-only STATUS current DESCRIPTION "data block n.5" ::= { bufferin 5 }
bufferinblk6 OBJECT-TYPE SYNTAX OCTET STRING MAX-ACCESS read-only STATUS current DESCRIPTION "data block n.6" ::= { bufferin 6 }
bufferinblk7 OBJECT-TYPE SYNTAX OCTET STRING MAX-ACCESS read-only STATUS current DESCRIPTION "data block n.7" ::= { bufferin 7 }
bufferinblk8 OBJECT-TYPE SYNTAX OCTET STRING MAX-ACCESS read-only STATUS current DESCRIPTION "data block n.8" ::= { bufferin 8 }
 bufferinval OBJECT IDENTIFIER::= { bufferin 9 }
powerFactor1 OBJECT-TYPE SYNTAX INTEGER MAX-ACCESS read-only STATUS current DESCRIPTION "powerFactor1" ::= { bufferinval 1 }
voltageLL1 OBJECT-TYPE SYNTAX INTEGER MAX-ACCESS read-only STATUS current DESCRIPTION "voltageLL1" ::= { bufferinval 2 }
voltageLN1 OBJECT-TYPE SYNTAX INTEGER MAX-ACCESS read-only STATUS current DESCRIPTION "voltageLN1" ::= { bufferinval 3 }
current1 OBJECT-TYPE SYNTAX INTEGER MAX-ACCESS read-only STATUS current DESCRIPTION "current1" ::= { bufferinval 4 }
frequency1 OBJECT-TYPE SYNTAX INTEGER MAX-ACCESS read-only STATUS current DESCRIPTION "frequency1" ::= { bufferinval 5 }
currentL11 OBJECT-TYPE SYNTAX INTEGER MAX-ACCESS read-only STATUS current DESCRIPTION "currentL11" ::= { bufferinval 6 }
currentL21 OBJECT-TYPE SYNTAX INTEGER MAX-ACCESS read-only STATUS current DESCRIPTION "currentL21" ::= { bufferinval 7 }
currentL31 OBJECT-TYPE SYNTAX INTEGER MAX-ACCESS read-only STATUS current DESCRIPTION "currentL31" ::= { bufferinval 8 }
currentN1 OBJECT-TYPE SYNTAX INTEGER MAX-ACCESS read-only STATUS current DESCRIPTION "currentN1" ::= { bufferinval 9 }
voltageL1L21 OBJECT-TYPE SYNTAX INTEGER MAX-ACCESS read-only STATUS current DESCRIPTION "voltageL1L21" ::= { bufferinval 10 }
voltageL2L31 OBJECT-TYPE SYNTAX INTEGER MAX-ACCESS read-only STATUS current DESCRIPTION "voltageL2L31" ::= { bufferinval 11 }
voltageL3L11 OBJECT-TYPE SYNTAX INTEGER MAX-ACCESS read-only STATUS current DESCRIPTION "voltageL3L11" ::= { bufferinval 12 }
voltageL1N1 OBJECT-TYPE SYNTAX INTEGER MAX-ACCESS read-only STATUS current DESCRIPTION "voltageL1N1" ::= { bufferinval 13 }
voltageL2N1 OBJECT-TYPE SYNTAX INTEGER MAX-ACCESS read-only STATUS current DESCRIPTION "voltageL2N1" ::= { bufferinval 14 }
voltageL3N1 OBJECT-TYPE SYNTAX INTEGER MAX-ACCESS read-only STATUS current DESCRIPTION "voltageL3N1" ::= { bufferinval 15 }
powerFactor2 OBJECT-TYPE SYNTAX INTEGER MAX-ACCESS read-only STATUS current DESCRIPTION "powerFactor2" ::= { bufferinval 16 }
voltageLL2 OBJECT-TYPE SYNTAX INTEGER MAX-ACCESS read-only STATUS current DESCRIPTION "voltageLL2" ::= { bufferinval 17 }
voltageLN2 OBJECT-TYPE SYNTAX INTEGER MAX-ACCESS read-only STATUS current DESCRIPTION "voltageLN2" ::= { bufferinval 18 }
current2 OBJECT-TYPE SYNTAX INTEGER MAX-ACCESS read-only STATUS current DESCRIPTION "current2" ::= { bufferinval 19 }
frequency2 OBJECT-TYPE SYNTAX INTEGER MAX-ACCESS read-only STATUS current DESCRIPTION "frequency2" ::= { bufferinval 20 }
currentL12 OBJECT-TYPE SYNTAX INTEGER MAX-ACCESS read-only STATUS current DESCRIPTION "currentL12" ::= { bufferinval 21 }
currentL22 OBJECT-TYPE SYNTAX INTEGER MAX-ACCESS read-only STATUS current DESCRIPTION "currentL22" ::= { bufferinval 22 }
currentL32 OBJECT-TYPE SYNTAX INTEGER MAX-ACCESS read-only STATUS current DESCRIPTION "currentL32" ::= { bufferinval 23 }
currentN2 OBJECT-TYPE SYNTAX INTEGER MAX-ACCESS read-only STATUS current DESCRIPTION "currentN2" ::= { bufferinval 24 }
voltageL1L22 OBJECT-TYPE SYNTAX INTEGER MAX-ACCESS read-only STATUS current DESCRIPTION "voltageL1L22" ::= { bufferinval 25 }
voltageL2L32 OBJECT-TYPE SYNTAX INTEGER MAX-ACCESS read-only STATUS current DESCRIPTION "voltageL2L32" ::= { bufferinval 26 }
voltageL3L12 OBJECT-TYPE SYNTAX INTEGER MAX-ACCESS read-only STATUS current DESCRIPTION "voltageL3L12" ::= { bufferinval 27 }
voltageL1N2 OBJECT-TYPE SYNTAX INTEGER MAX-ACCESS read-only STATUS current DESCRIPTION "voltageL1N2" ::= { bufferinval 28 }
voltageL2N2 OBJECT-TYPE SYNTAX INTEGER MAX-ACCESS read-only STATUS current DESCRIPTION "voltageL2N2" ::= { bufferinval 29 }
voltageL3N2 OBJECT-TYPE SYNTAX INTEGER MAX-ACCESS read-only STATUS current DESCRIPTION "voltageL3N2" ::= { bufferinval 30 }
powerFactor3 OBJECT-TYPE SYNTAX INTEGER MAX-ACCESS read-only STATUS current DESCRIPTION "powerFactor3" ::= { bufferinval 31 }
voltageLL3 OBJECT-TYPE SYNTAX INTEGER MAX-ACCESS read-only STATUS current DESCRIPTION "voltageLL3" ::= { bufferinval 32 }
voltageLN3 OBJECT-TYPE SYNTAX INTEGER MAX-ACCESS read-only STATUS current DESCRIPTION "voltageLN3" ::= { bufferinval 33 }
current3 OBJECT-TYPE SYNTAX INTEGER MAX-ACCESS read-only STATUS current DESCRIPTION "current3" ::= { bufferinval 34 }
frequency3 OBJECT-TYPE SYNTAX INTEGER MAX-ACCESS read-only STATUS current DESCRIPTION "frequency3" ::= { bufferinval 35 }
currentL13 OBJECT-TYPE SYNTAX INTEGER MAX-ACCESS read-only STATUS current DESCRIPTION "currentL13" ::= { bufferinval 36 }
currentL23 OBJECT-TYPE SYNTAX INTEGER MAX-ACCESS read-only STATUS current DESCRIPTION "currentL23" ::= { bufferinval 37 }
currentL33 OBJECT-TYPE SYNTAX INTEGER MAX-ACCESS read-only STATUS current DESCRIPTION "currentL33" ::= { bufferinval 38 }
currentN3 OBJECT-TYPE SYNTAX INTEGER MAX-ACCESS read-only STATUS current DESCRIPTION "currentN3" ::= { bufferinval 39 }
voltageL1L23 OBJECT-TYPE SYNTAX INTEGER MAX-ACCESS read-only STATUS current DESCRIPTION "voltageL1L23" ::= { bufferinval 40 }
voltageL2L33 OBJECT-TYPE SYNTAX INTEGER MAX-ACCESS read-only STATUS current DESCRIPTION "voltageL2L33" ::= { bufferinval 41 }
voltageL3L13 OBJECT-TYPE SYNTAX INTEGER MAX-ACCESS read-only STATUS current DESCRIPTION "voltageL3L13" ::= { bufferinval 42 }
voltageL1N3 OBJECT-TYPE SYNTAX INTEGER MAX-ACCESS read-only STATUS current DESCRIPTION "voltageL1N3" ::= { bufferinval 43 }
voltageL2N3 OBJECT-TYPE SYNTAX INTEGER MAX-ACCESS read-only STATUS current DESCRIPTION "voltageL2N3" ::= { bufferinval 44 }
voltageL3N3 OBJECT-TYPE SYNTAX INTEGER MAX-ACCESS read-only STATUS current DESCRIPTION "voltageL3N3" ::= { bufferinval 45 }
powerFactor4 OBJECT-TYPE SYNTAX INTEGER MAX-ACCESS read-only STATUS current DESCRIPTION "powerFactor4" ::= { bufferinval 46 }
voltageLL4 OBJECT-TYPE SYNTAX INTEGER MAX-ACCESS read-only STATUS current DESCRIPTION "voltageLL4" ::= { bufferinval 47 }
voltageLN4 OBJECT-TYPE SYNTAX INTEGER MAX-ACCESS read-only STATUS current DESCRIPTION "voltageLN4" ::= { bufferinval 48 }
current4 OBJECT-TYPE SYNTAX INTEGER MAX-ACCESS read-only STATUS current DESCRIPTION "current4" ::= { bufferinval 49 }
frequency4 OBJECT-TYPE SYNTAX INTEGER MAX-ACCESS read-only STATUS current DESCRIPTION "frequency4" ::= { bufferinval 50 }
currentL14 OBJECT-TYPE SYNTAX INTEGER MAX-ACCESS read-only STATUS current DESCRIPTION "currentL14" ::= { bufferinval 51 }
currentL24 OBJECT-TYPE SYNTAX INTEGER MAX-ACCESS read-only STATUS current DESCRIPTION "currentL24" ::= { bufferinval 52 }
currentL34 OBJECT-TYPE SYNTAX INTEGER MAX-ACCESS read-only STATUS current DESCRIPTION "currentL34" ::= { bufferinval 53 }
currentN4 OBJECT-TYPE SYNTAX INTEGER MAX-ACCESS read-only STATUS current DESCRIPTION "currentN4" ::= { bufferinval 54 }
voltageL1L24 OBJECT-TYPE SYNTAX INTEGER MAX-ACCESS read-only STATUS current DESCRIPTION "voltageL1L24" ::= { bufferinval 55 }
voltageL2L34 OBJECT-TYPE SYNTAX INTEGER MAX-ACCESS read-only STATUS current DESCRIPTION "voltageL2L34" ::= { bufferinval 56 }
voltageL3L14 OBJECT-TYPE SYNTAX INTEGER MAX-ACCESS read-only STATUS current DESCRIPTION "voltageL3L14" ::= { bufferinval 57 }
voltageL1N4 OBJECT-TYPE SYNTAX INTEGER MAX-ACCESS read-only STATUS current DESCRIPTION "voltageL1N4" ::= { bufferinval 58 }
voltageL2N4 OBJECT-TYPE SYNTAX INTEGER MAX-ACCESS read-only STATUS current DESCRIPTION "voltageL2N4" ::= { bufferinval 59 }
voltageL3N4 OBJECT-TYPE SYNTAX INTEGER MAX-ACCESS read-only STATUS current DESCRIPTION "voltageL3N4" ::= { bufferinval 60 }
powerFactor5 OBJECT-TYPE SYNTAX INTEGER MAX-ACCESS read-only STATUS current DESCRIPTION "powerFactor5" ::= { bufferinval 61 }
voltageLL5 OBJECT-TYPE SYNTAX INTEGER MAX-ACCESS read-only STATUS current DESCRIPTION "voltageLL5" ::= { bufferinval 62 }
voltageLN5 OBJECT-TYPE SYNTAX INTEGER MAX-ACCESS read-only STATUS current DESCRIPTION "voltageLN5" ::= { bufferinval 63 }
current5 OBJECT-TYPE SYNTAX INTEGER MAX-ACCESS read-only STATUS current DESCRIPTION "current5" ::= { bufferinval 64 }
frequency5 OBJECT-TYPE SYNTAX INTEGER MAX-ACCESS read-only STATUS current DESCRIPTION "frequency5" ::= { bufferinval 65 }
currentL15 OBJECT-TYPE SYNTAX INTEGER MAX-ACCESS read-only STATUS current DESCRIPTION "currentL15" ::= { bufferinval 66 }
currentL25 OBJECT-TYPE SYNTAX INTEGER MAX-ACCESS read-only STATUS current DESCRIPTION "currentL25" ::= { bufferinval 67 }
currentL35 OBJECT-TYPE SYNTAX INTEGER MAX-ACCESS read-only STATUS current DESCRIPTION "currentL35" ::= { bufferinval 68 }
currentN5 OBJECT-TYPE SYNTAX INTEGER MAX-ACCESS read-only STATUS current DESCRIPTION "currentN5" ::= { bufferinval 69 }
voltageL1L25 OBJECT-TYPE SYNTAX INTEGER MAX-ACCESS read-only STATUS current DESCRIPTION "voltageL1L25" ::= { bufferinval 70 }
voltageL2L35 OBJECT-TYPE SYNTAX INTEGER MAX-ACCESS read-only STATUS current DESCRIPTION "voltageL2L35" ::= { bufferinval 71 }
voltageL3L15 OBJECT-TYPE SYNTAX INTEGER MAX-ACCESS read-only STATUS current DESCRIPTION "voltageL3L15" ::= { bufferinval 72 }
voltageL1N5 OBJECT-TYPE SYNTAX INTEGER MAX-ACCESS read-only STATUS current DESCRIPTION "voltageL1N5" ::= { bufferinval 73 }
voltageL2N5 OBJECT-TYPE SYNTAX INTEGER MAX-ACCESS read-only STATUS current DESCRIPTION "voltageL2N5" ::= { bufferinval 74 }
voltageL3N5 OBJECT-TYPE SYNTAX INTEGER MAX-ACCESS read-only STATUS current DESCRIPTION "voltageL3N5" ::= { bufferinval 75 }
powerFactor6 OBJECT-TYPE SYNTAX INTEGER MAX-ACCESS read-only STATUS current DESCRIPTION "powerFactor6" ::= { bufferinval 76 }
voltageLL6 OBJECT-TYPE SYNTAX INTEGER MAX-ACCESS read-only STATUS current DESCRIPTION "voltageLL6" ::= { bufferinval 77 }
voltageLN6 OBJECT-TYPE SYNTAX INTEGER MAX-ACCESS read-only STATUS current DESCRIPTION "voltageLN6" ::= { bufferinval 78 }
current6 OBJECT-TYPE SYNTAX INTEGER MAX-ACCESS read-only STATUS current DESCRIPTION "current6" ::= { bufferinval 79 }
frequency6 OBJECT-TYPE SYNTAX INTEGER MAX-ACCESS read-only STATUS current DESCRIPTION "frequency6" ::= { bufferinval 80 }
currentL16 OBJECT-TYPE SYNTAX INTEGER MAX-ACCESS read-only STATUS current DESCRIPTION "currentL16" ::= { bufferinval 81 }
currentL26 OBJECT-TYPE SYNTAX INTEGER MAX-ACCESS read-only STATUS current DESCRIPTION "currentL26" ::= { bufferinval 82 }
currentL36 OBJECT-TYPE SYNTAX INTEGER MAX-ACCESS read-only STATUS current DESCRIPTION "currentL36" ::= { bufferinval 83 }
currentN6 OBJECT-TYPE SYNTAX INTEGER MAX-ACCESS read-only STATUS current DESCRIPTION "currentN6" ::= { bufferinval 84 }
voltageL1L26 OBJECT-TYPE SYNTAX INTEGER MAX-ACCESS read-only STATUS current DESCRIPTION "voltageL1L26" ::= { bufferinval 85 }
voltageL2L36 OBJECT-TYPE SYNTAX INTEGER MAX-ACCESS read-only STATUS current DESCRIPTION "voltageL2L36" ::= { bufferinval 86 }
voltageL3L16 OBJECT-TYPE SYNTAX INTEGER MAX-ACCESS read-only STATUS current DESCRIPTION "voltageL3L16" ::= { bufferinval 87 }
voltageL1N6 OBJECT-TYPE SYNTAX INTEGER MAX-ACCESS read-only STATUS current DESCRIPTION "voltageL1N6" ::= { bufferinval 88 }
voltageL2N6 OBJECT-TYPE SYNTAX INTEGER MAX-ACCESS read-only STATUS current DESCRIPTION "voltageL2N6" ::= { bufferinval 89 }
voltageL3N6 OBJECT-TYPE SYNTAX INTEGER MAX-ACCESS read-only STATUS current DESCRIPTION "voltageL3N6" ::= { bufferinval 90 }
powerFactor7 OBJECT-TYPE SYNTAX INTEGER MAX-ACCESS read-only STATUS current DESCRIPTION "powerFactor7" ::= { bufferinval 91 }
voltageLL7 OBJECT-TYPE SYNTAX INTEGER MAX-ACCESS read-only STATUS current DESCRIPTION "voltageLL7" ::= { bufferinval 92 }
voltageLN7 OBJECT-TYPE SYNTAX INTEGER MAX-ACCESS read-only STATUS current DESCRIPTION "voltageLN7" ::= { bufferinval 93 }
current7 OBJECT-TYPE SYNTAX INTEGER MAX-ACCESS read-only STATUS current DESCRIPTION "current7" ::= { bufferinval 94 }
frequency7 OBJECT-TYPE SYNTAX INTEGER MAX-ACCESS read-only STATUS current DESCRIPTION "frequency7" ::= { bufferinval 95 }
currentL17 OBJECT-TYPE SYNTAX INTEGER MAX-ACCESS read-only STATUS current DESCRIPTION "currentL17" ::= { bufferinval 96 }
currentL27 OBJECT-TYPE SYNTAX INTEGER MAX-ACCESS read-only STATUS current DESCRIPTION "currentL27" ::= { bufferinval 97 }
currentL37 OBJECT-TYPE SYNTAX INTEGER MAX-ACCESS read-only STATUS current DESCRIPTION "currentL37" ::= { bufferinval 98 }
currentN7 OBJECT-TYPE SYNTAX INTEGER MAX-ACCESS read-only STATUS current DESCRIPTION "currentN7" ::= { bufferinval 99 }
voltageL1L27 OBJECT-TYPE SYNTAX INTEGER MAX-ACCESS read-only STATUS current DESCRIPTION "voltageL1L27" ::= { bufferinval 100 }
voltageL2L37 OBJECT-TYPE SYNTAX INTEGER MAX-ACCESS read-only STATUS current DESCRIPTION "voltageL2L37" ::= { bufferinval 101 }
voltageL3L17 OBJECT-TYPE SYNTAX INTEGER MAX-ACCESS read-only STATUS current DESCRIPTION "voltageL3L17" ::= { bufferinval 102 }
voltageL1N7 OBJECT-TYPE SYNTAX INTEGER MAX-ACCESS read-only STATUS current DESCRIPTION "voltageL1N7" ::= { bufferinval 103 }
voltageL2N7 OBJECT-TYPE SYNTAX INTEGER MAX-ACCESS read-only STATUS current DESCRIPTION "voltageL2N7" ::= { bufferinval 104 }
voltageL3N7 OBJECT-TYPE SYNTAX INTEGER MAX-ACCESS read-only STATUS current DESCRIPTION "voltageL3N7" ::= { bufferinval 105 }
powerFactor8 OBJECT-TYPE SYNTAX INTEGER MAX-ACCESS read-only STATUS current DESCRIPTION "powerFactor8" ::= { bufferinval 106 }
voltageLL8 OBJECT-TYPE SYNTAX INTEGER MAX-ACCESS read-only STATUS current DESCRIPTION "voltageLL8" ::= { bufferinval 107 }
voltageLN8 OBJECT-TYPE SYNTAX INTEGER MAX-ACCESS read-only STATUS current DESCRIPTION "voltageLN8" ::= { bufferinval 108 }
current8 OBJECT-TYPE SYNTAX INTEGER MAX-ACCESS read-only STATUS current DESCRIPTION "current8" ::= { bufferinval 109 }
frequency8 OBJECT-TYPE SYNTAX INTEGER MAX-ACCESS read-only STATUS current DESCRIPTION "frequency8" ::= { bufferinval 110 }
currentL18 OBJECT-TYPE SYNTAX INTEGER MAX-ACCESS read-only STATUS current DESCRIPTION "currentL18" ::= { bufferinval 111 }
currentL28 OBJECT-TYPE SYNTAX INTEGER MAX-ACCESS read-only STATUS current DESCRIPTION "currentL28" ::= { bufferinval 112 }
currentL38 OBJECT-TYPE SYNTAX INTEGER MAX-ACCESS read-only STATUS current DESCRIPTION "currentL38" ::= { bufferinval 113 }
currentN8 OBJECT-TYPE SYNTAX INTEGER MAX-ACCESS read-only STATUS current DESCRIPTION "currentN8" ::= { bufferinval 114 }
voltageL1L28 OBJECT-TYPE SYNTAX INTEGER MAX-ACCESS read-only STATUS current DESCRIPTION "voltageL1L28" ::= { bufferinval 115 }
voltageL2L38 OBJECT-TYPE SYNTAX INTEGER MAX-ACCESS read-only STATUS current DESCRIPTION "voltageL2L38" ::= { bufferinval 116 }
voltageL3L18 OBJECT-TYPE SYNTAX INTEGER MAX-ACCESS read-only STATUS current DESCRIPTION "voltageL3L18" ::= { bufferinval 117 }
voltageL1N8 OBJECT-TYPE SYNTAX INTEGER MAX-ACCESS read-only STATUS current DESCRIPTION "voltageL1N8" ::= { bufferinval 118 }
voltageL2N8 OBJECT-TYPE SYNTAX INTEGER MAX-ACCESS read-only STATUS current DESCRIPTION "voltageL2N8" ::= { bufferinval 119 }
voltageL3N8 OBJECT-TYPE SYNTAX INTEGER MAX-ACCESS read-only STATUS current DESCRIPTION "voltageL3N8" ::= { bufferinval 120 }
powerFactor9 OBJECT-TYPE SYNTAX INTEGER MAX-ACCESS read-only STATUS current DESCRIPTION "powerFactor9" ::= { bufferinval 121 }
voltageLL9 OBJECT-TYPE SYNTAX INTEGER MAX-ACCESS read-only STATUS current DESCRIPTION "voltageLL9" ::= { bufferinval 122 }
voltageLN9 OBJECT-TYPE SYNTAX INTEGER MAX-ACCESS read-only STATUS current DESCRIPTION "voltageLN9" ::= { bufferinval 123 }
current9 OBJECT-TYPE SYNTAX INTEGER MAX-ACCESS read-only STATUS current DESCRIPTION "current9" ::= { bufferinval 124 }
frequency9 OBJECT-TYPE SYNTAX INTEGER MAX-ACCESS read-only STATUS current DESCRIPTION "frequency9" ::= { bufferinval 125 }
currentL19 OBJECT-TYPE SYNTAX INTEGER MAX-ACCESS read-only STATUS current DESCRIPTION "currentL19" ::= { bufferinval 126 }
currentL29 OBJECT-TYPE SYNTAX INTEGER MAX-ACCESS read-only STATUS current DESCRIPTION "currentL29" ::= { bufferinval 127 }
currentL39 OBJECT-TYPE SYNTAX INTEGER MAX-ACCESS read-only STATUS current DESCRIPTION "currentL39" ::= { bufferinval 128 }
currentN9 OBJECT-TYPE SYNTAX INTEGER MAX-ACCESS read-only STATUS current DESCRIPTION "currentN9" ::= { bufferinval 129 }
voltageL1L29 OBJECT-TYPE SYNTAX INTEGER MAX-ACCESS read-only STATUS current DESCRIPTION "voltageL1L29" ::= { bufferinval 130 }
voltageL2L39 OBJECT-TYPE SYNTAX INTEGER MAX-ACCESS read-only STATUS current DESCRIPTION "voltageL2L39" ::= { bufferinval 131 }
voltageL3L19 OBJECT-TYPE SYNTAX INTEGER MAX-ACCESS read-only STATUS current DESCRIPTION "voltageL3L19" ::= { bufferinval 132 }
voltageL1N9 OBJECT-TYPE SYNTAX INTEGER MAX-ACCESS read-only STATUS current DESCRIPTION "voltageL1N9" ::= { bufferinval 133 }
voltageL2N9 OBJECT-TYPE SYNTAX INTEGER MAX-ACCESS read-only STATUS current DESCRIPTION "voltageL2N9" ::= { bufferinval 134 }
voltageL3N9 OBJECT-TYPE SYNTAX INTEGER MAX-ACCESS read-only STATUS current DESCRIPTION "voltageL3N9" ::= { bufferinval 135 }
powerFactor10 OBJECT-TYPE SYNTAX INTEGER MAX-ACCESS read-only STATUS current DESCRIPTION "powerFactor10" ::= { bufferinval 136 }
voltageLL10 OBJECT-TYPE SYNTAX INTEGER MAX-ACCESS read-only STATUS current DESCRIPTION "voltageLL10" ::= { bufferinval 137 }
voltageLN10 OBJECT-TYPE SYNTAX INTEGER MAX-ACCESS read-only STATUS current DESCRIPTION "voltageLN10" ::= { bufferinval 138 }
current10 OBJECT-TYPE SYNTAX INTEGER MAX-ACCESS read-only STATUS current DESCRIPTION "current10" ::= { bufferinval 139 }
frequency10 OBJECT-TYPE SYNTAX INTEGER MAX-ACCESS read-only STATUS current DESCRIPTION "frequency10" ::= { bufferinval 140 }
currentL110 OBJECT-TYPE SYNTAX INTEGER MAX-ACCESS read-only STATUS current DESCRIPTION "currentL110" ::= { bufferinval 141 }
currentL210 OBJECT-TYPE SYNTAX INTEGER MAX-ACCESS read-only STATUS current DESCRIPTION "currentL210" ::= { bufferinval 142 }
currentL310 OBJECT-TYPE SYNTAX INTEGER MAX-ACCESS read-only STATUS current DESCRIPTION "currentL310" ::= { bufferinval 143 }
currentN10 OBJECT-TYPE SYNTAX INTEGER MAX-ACCESS read-only STATUS current DESCRIPTION "currentN10" ::= { bufferinval 144 }
voltageL1L210 OBJECT-TYPE SYNTAX INTEGER MAX-ACCESS read-only STATUS current DESCRIPTION "voltageL1L210" ::= { bufferinval 145 }
voltageL2L310 OBJECT-TYPE SYNTAX INTEGER MAX-ACCESS read-only STATUS current DESCRIPTION "voltageL2L310" ::= { bufferinval 146 }
voltageL3L110 OBJECT-TYPE SYNTAX INTEGER MAX-ACCESS read-only STATUS current DESCRIPTION "voltageL3L110" ::= { bufferinval 147 }
voltageL1N10 OBJECT-TYPE SYNTAX INTEGER MAX-ACCESS read-only STATUS current DESCRIPTION "voltageL1N10" ::= { bufferinval 148 }
voltageL2N10 OBJECT-TYPE SYNTAX INTEGER MAX-ACCESS read-only STATUS current DESCRIPTION "voltageL2N10" ::= { bufferinval 149 }
voltageL3N10 OBJECT-TYPE SYNTAX INTEGER MAX-ACCESS read-only STATUS current DESCRIPTION "voltageL3N10" ::= { bufferinval 150 }
powerFactor11 OBJECT-TYPE SYNTAX INTEGER MAX-ACCESS read-only STATUS current DESCRIPTION "powerFactor11" ::= { bufferinval 151 }
voltageLL11 OBJECT-TYPE SYNTAX INTEGER MAX-ACCESS read-only STATUS current DESCRIPTION "voltageLL11" ::= { bufferinval 152 }
voltageLN11 OBJECT-TYPE SYNTAX INTEGER MAX-ACCESS read-only STATUS current DESCRIPTION "voltageLN11" ::= { bufferinval 153 }
current11 OBJECT-TYPE SYNTAX INTEGER MAX-ACCESS read-only STATUS current DESCRIPTION "current11" ::= { bufferinval 154 }
frequency11 OBJECT-TYPE SYNTAX INTEGER MAX-ACCESS read-only STATUS current DESCRIPTION "frequency11" ::= { bufferinval 155 }
currentL111 OBJECT-TYPE SYNTAX INTEGER MAX-ACCESS read-only STATUS current DESCRIPTION "currentL111" ::= { bufferinval 156 }
currentL211 OBJECT-TYPE SYNTAX INTEGER MAX-ACCESS read-only STATUS current DESCRIPTION "currentL211" ::= { bufferinval 157 }
currentL311 OBJECT-TYPE SYNTAX INTEGER MAX-ACCESS read-only STATUS current DESCRIPTION "currentL311" ::= { bufferinval 158 }
currentN11 OBJECT-TYPE SYNTAX INTEGER MAX-ACCESS read-only STATUS current DESCRIPTION "currentN11" ::= { bufferinval 159 }
voltageL1L211 OBJECT-TYPE SYNTAX INTEGER MAX-ACCESS read-only STATUS current DESCRIPTION "voltageL1L211" ::= { bufferinval 160 }
voltageL2L311 OBJECT-TYPE SYNTAX INTEGER MAX-ACCESS read-only STATUS current DESCRIPTION "voltageL2L311" ::= { bufferinval 161 }
voltageL3L111 OBJECT-TYPE SYNTAX INTEGER MAX-ACCESS read-only STATUS current DESCRIPTION "voltageL3L111" ::= { bufferinval 162 }
voltageL1N11 OBJECT-TYPE SYNTAX INTEGER MAX-ACCESS read-only STATUS current DESCRIPTION "voltageL1N11" ::= { bufferinval 163 }
voltageL2N11 OBJECT-TYPE SYNTAX INTEGER MAX-ACCESS read-only STATUS current DESCRIPTION "voltageL2N11" ::= { bufferinval 164 }
voltageL3N11 OBJECT-TYPE SYNTAX INTEGER MAX-ACCESS read-only STATUS current DESCRIPTION "voltageL3N11" ::= { bufferinval 165 }
powerFactor12 OBJECT-TYPE SYNTAX INTEGER MAX-ACCESS read-only STATUS current DESCRIPTION "powerFactor12" ::= { bufferinval 166 }
voltageLL12 OBJECT-TYPE SYNTAX INTEGER MAX-ACCESS read-only STATUS current DESCRIPTION "voltageLL12" ::= { bufferinval 167 }
voltageLN12 OBJECT-TYPE SYNTAX INTEGER MAX-ACCESS read-only STATUS current DESCRIPTION "voltageLN12" ::= { bufferinval 168 }
current12 OBJECT-TYPE SYNTAX INTEGER MAX-ACCESS read-only STATUS current DESCRIPTION "current12" ::= { bufferinval 169 }
frequency12 OBJECT-TYPE SYNTAX INTEGER MAX-ACCESS read-only STATUS current DESCRIPTION "frequency12" ::= { bufferinval 170 }
currentL112 OBJECT-TYPE SYNTAX INTEGER MAX-ACCESS read-only STATUS current DESCRIPTION "currentL112" ::= { bufferinval 171 }
currentL212 OBJECT-TYPE SYNTAX INTEGER MAX-ACCESS read-only STATUS current DESCRIPTION "currentL212" ::= { bufferinval 172 }
currentL312 OBJECT-TYPE SYNTAX INTEGER MAX-ACCESS read-only STATUS current DESCRIPTION "currentL312" ::= { bufferinval 173 }
currentN12 OBJECT-TYPE SYNTAX INTEGER MAX-ACCESS read-only STATUS current DESCRIPTION "currentN12" ::= { bufferinval 174 }
voltageL1L212 OBJECT-TYPE SYNTAX INTEGER MAX-ACCESS read-only STATUS current DESCRIPTION "voltageL1L212" ::= { bufferinval 175 }
voltageL2L312 OBJECT-TYPE SYNTAX INTEGER MAX-ACCESS read-only STATUS current DESCRIPTION "voltageL2L312" ::= { bufferinval 176 }
voltageL3L112 OBJECT-TYPE SYNTAX INTEGER MAX-ACCESS read-only STATUS current DESCRIPTION "voltageL3L112" ::= { bufferinval 177 }
voltageL1N12 OBJECT-TYPE SYNTAX INTEGER MAX-ACCESS read-only STATUS current DESCRIPTION "voltageL1N12" ::= { bufferinval 178 }
voltageL2N12 OBJECT-TYPE SYNTAX INTEGER MAX-ACCESS read-only STATUS current DESCRIPTION "voltageL2N12" ::= { bufferinval 179 }
voltageL3N12 OBJECT-TYPE SYNTAX INTEGER MAX-ACCESS read-only STATUS current DESCRIPTION "voltageL3N12" ::= { bufferinval 180 }
powerFactor13 OBJECT-TYPE SYNTAX INTEGER MAX-ACCESS read-only STATUS current DESCRIPTION "powerFactor13" ::= { bufferinval 181 }
voltageLL13 OBJECT-TYPE SYNTAX INTEGER MAX-ACCESS read-only STATUS current DESCRIPTION "voltageLL13" ::= { bufferinval 182 }
voltageLN13 OBJECT-TYPE SYNTAX INTEGER MAX-ACCESS read-only STATUS current DESCRIPTION "voltageLN13" ::= { bufferinval 183 }
current13 OBJECT-TYPE SYNTAX INTEGER MAX-ACCESS read-only STATUS current DESCRIPTION "current13" ::= { bufferinval 184 }
frequency13 OBJECT-TYPE SYNTAX INTEGER MAX-ACCESS read-only STATUS current DESCRIPTION "frequency13" ::= { bufferinval 185 }
currentL113 OBJECT-TYPE SYNTAX INTEGER MAX-ACCESS read-only STATUS current DESCRIPTION "currentL113" ::= { bufferinval 186 }
currentL213 OBJECT-TYPE SYNTAX INTEGER MAX-ACCESS read-only STATUS current DESCRIPTION "currentL213" ::= { bufferinval 187 }
currentL313 OBJECT-TYPE SYNTAX INTEGER MAX-ACCESS read-only STATUS current DESCRIPTION "currentL313" ::= { bufferinval 188 }
currentN13 OBJECT-TYPE SYNTAX INTEGER MAX-ACCESS read-only STATUS current DESCRIPTION "currentN13" ::= { bufferinval 189 }
voltageL1L213 OBJECT-TYPE SYNTAX INTEGER MAX-ACCESS read-only STATUS current DESCRIPTION "voltageL1L213" ::= { bufferinval 190 }
voltageL2L313 OBJECT-TYPE SYNTAX INTEGER MAX-ACCESS read-only STATUS current DESCRIPTION "voltageL2L313" ::= { bufferinval 191 }
voltageL3L113 OBJECT-TYPE SYNTAX INTEGER MAX-ACCESS read-only STATUS current DESCRIPTION "voltageL3L113" ::= { bufferinval 192 }
voltageL1N13 OBJECT-TYPE SYNTAX INTEGER MAX-ACCESS read-only STATUS current DESCRIPTION "voltageL1N13" ::= { bufferinval 193 }
voltageL2N13 OBJECT-TYPE SYNTAX INTEGER MAX-ACCESS read-only STATUS current DESCRIPTION "voltageL2N13" ::= { bufferinval 194 }
voltageL3N13 OBJECT-TYPE SYNTAX INTEGER MAX-ACCESS read-only STATUS current DESCRIPTION "voltageL3N13" ::= { bufferinval 195 }
powerFactor14 OBJECT-TYPE SYNTAX INTEGER MAX-ACCESS read-only STATUS current DESCRIPTION "powerFactor14" ::= { bufferinval 196 }
voltageLL14 OBJECT-TYPE SYNTAX INTEGER MAX-ACCESS read-only STATUS current DESCRIPTION "voltageLL14" ::= { bufferinval 197 }
voltageLN14 OBJECT-TYPE SYNTAX INTEGER MAX-ACCESS read-only STATUS current DESCRIPTION "voltageLN14" ::= { bufferinval 198 }
current14 OBJECT-TYPE SYNTAX INTEGER MAX-ACCESS read-only STATUS current DESCRIPTION "current14" ::= { bufferinval 199 }
frequency14 OBJECT-TYPE SYNTAX INTEGER MAX-ACCESS read-only STATUS current DESCRIPTION "frequency14" ::= { bufferinval 200 }
currentL114 OBJECT-TYPE SYNTAX INTEGER MAX-ACCESS read-only STATUS current DESCRIPTION "currentL114" ::= { bufferinval 201 }
currentL214 OBJECT-TYPE SYNTAX INTEGER MAX-ACCESS read-only STATUS current DESCRIPTION "currentL214" ::= { bufferinval 202 }
currentL314 OBJECT-TYPE SYNTAX INTEGER MAX-ACCESS read-only STATUS current DESCRIPTION "currentL314" ::= { bufferinval 203 }
currentN14 OBJECT-TYPE SYNTAX INTEGER MAX-ACCESS read-only STATUS current DESCRIPTION "currentN14" ::= { bufferinval 204 }
voltageL1L214 OBJECT-TYPE SYNTAX INTEGER MAX-ACCESS read-only STATUS current DESCRIPTION "voltageL1L214" ::= { bufferinval 205 }
voltageL2L314 OBJECT-TYPE SYNTAX INTEGER MAX-ACCESS read-only STATUS current DESCRIPTION "voltageL2L314" ::= { bufferinval 206 }
voltageL3L114 OBJECT-TYPE SYNTAX INTEGER MAX-ACCESS read-only STATUS current DESCRIPTION "voltageL3L114" ::= { bufferinval 207 }
voltageL1N14 OBJECT-TYPE SYNTAX INTEGER MAX-ACCESS read-only STATUS current DESCRIPTION "voltageL1N14" ::= { bufferinval 208 }
voltageL2N14 OBJECT-TYPE SYNTAX INTEGER MAX-ACCESS read-only STATUS current DESCRIPTION "voltageL2N14" ::= { bufferinval 209 }
voltageL3N14 OBJECT-TYPE SYNTAX INTEGER MAX-ACCESS read-only STATUS current DESCRIPTION "voltageL3N14" ::= { bufferinval 210 }
powerFactor15 OBJECT-TYPE SYNTAX INTEGER MAX-ACCESS read-only STATUS current DESCRIPTION "powerFactor15" ::= { bufferinval 211 }
voltageLL15 OBJECT-TYPE SYNTAX INTEGER MAX-ACCESS read-only STATUS current DESCRIPTION "voltageLL15" ::= { bufferinval 212 }
voltageLN15 OBJECT-TYPE SYNTAX INTEGER MAX-ACCESS read-only STATUS current DESCRIPTION "voltageLN15" ::= { bufferinval 213 }
current15 OBJECT-TYPE SYNTAX INTEGER MAX-ACCESS read-only STATUS current DESCRIPTION "current15" ::= { bufferinval 214 }
frequency15 OBJECT-TYPE SYNTAX INTEGER MAX-ACCESS read-only STATUS current DESCRIPTION "frequency15" ::= { bufferinval 215 }
currentL115 OBJECT-TYPE SYNTAX INTEGER MAX-ACCESS read-only STATUS current DESCRIPTION "currentL115" ::= { bufferinval 216 }
currentL215 OBJECT-TYPE SYNTAX INTEGER MAX-ACCESS read-only STATUS current DESCRIPTION "currentL215" ::= { bufferinval 217 }
currentL315 OBJECT-TYPE SYNTAX INTEGER MAX-ACCESS read-only STATUS current DESCRIPTION "currentL315" ::= { bufferinval 218 }
currentN15 OBJECT-TYPE SYNTAX INTEGER MAX-ACCESS read-only STATUS current DESCRIPTION "currentN15" ::= { bufferinval 219 }
voltageL1L215 OBJECT-TYPE SYNTAX INTEGER MAX-ACCESS read-only STATUS current DESCRIPTION "voltageL1L215" ::= { bufferinval 220 }
voltageL2L315 OBJECT-TYPE SYNTAX INTEGER MAX-ACCESS read-only STATUS current DESCRIPTION "voltageL2L315" ::= { bufferinval 221 }
voltageL3L115 OBJECT-TYPE SYNTAX INTEGER MAX-ACCESS read-only STATUS current DESCRIPTION "voltageL3L115" ::= { bufferinval 222 }
voltageL1N15 OBJECT-TYPE SYNTAX INTEGER MAX-ACCESS read-only STATUS current DESCRIPTION "voltageL1N15" ::= { bufferinval 223 }
voltageL2N15 OBJECT-TYPE SYNTAX INTEGER MAX-ACCESS read-only STATUS current DESCRIPTION "voltageL2N15" ::= { bufferinval 224 }
voltageL3N15 OBJECT-TYPE SYNTAX INTEGER MAX-ACCESS read-only STATUS current DESCRIPTION "voltageL3N15" ::= { bufferinval 225 }
powerFactor16 OBJECT-TYPE SYNTAX INTEGER MAX-ACCESS read-only STATUS current DESCRIPTION "powerFactor16" ::= { bufferinval 226 }
voltageLL16 OBJECT-TYPE SYNTAX INTEGER MAX-ACCESS read-only STATUS current DESCRIPTION "voltageLL16" ::= { bufferinval 227 }
voltageLN16 OBJECT-TYPE SYNTAX INTEGER MAX-ACCESS read-only STATUS current DESCRIPTION "voltageLN16" ::= { bufferinval 228 }
current16 OBJECT-TYPE SYNTAX INTEGER MAX-ACCESS read-only STATUS current DESCRIPTION "current16" ::= { bufferinval 229 }
frequency16 OBJECT-TYPE SYNTAX INTEGER MAX-ACCESS read-only STATUS current DESCRIPTION "frequency16" ::= { bufferinval 230 }
currentL116 OBJECT-TYPE SYNTAX INTEGER MAX-ACCESS read-only STATUS current DESCRIPTION "currentL116" ::= { bufferinval 231 }
currentL216 OBJECT-TYPE SYNTAX INTEGER MAX-ACCESS read-only STATUS current DESCRIPTION "currentL216" ::= { bufferinval 232 }
currentL316 OBJECT-TYPE SYNTAX INTEGER MAX-ACCESS read-only STATUS current DESCRIPTION "currentL316" ::= { bufferinval 233 }
currentN16 OBJECT-TYPE SYNTAX INTEGER MAX-ACCESS read-only STATUS current DESCRIPTION "currentN16" ::= { bufferinval 234 }
voltageL1L216 OBJECT-TYPE SYNTAX INTEGER MAX-ACCESS read-only STATUS current DESCRIPTION "voltageL1L216" ::= { bufferinval 235 }
voltageL2L316 OBJECT-TYPE SYNTAX INTEGER MAX-ACCESS read-only STATUS current DESCRIPTION "voltageL2L316" ::= { bufferinval 236 }
voltageL3L116 OBJECT-TYPE SYNTAX INTEGER MAX-ACCESS read-only STATUS current DESCRIPTION "voltageL3L116" ::= { bufferinval 237 }
voltageL1N16 OBJECT-TYPE SYNTAX INTEGER MAX-ACCESS read-only STATUS current DESCRIPTION "voltageL1N16" ::= { bufferinval 238 }
voltageL2N16 OBJECT-TYPE SYNTAX INTEGER MAX-ACCESS read-only STATUS current DESCRIPTION "voltageL2N16" ::= { bufferinval 239 }
voltageL3N16 OBJECT-TYPE SYNTAX INTEGER MAX-ACCESS read-only STATUS current DESCRIPTION "voltageL3N16" ::= { bufferinval 240 }
powerFactor17 OBJECT-TYPE SYNTAX INTEGER MAX-ACCESS read-only STATUS current DESCRIPTION "powerFactor17" ::= { bufferinval 241 }
voltageLL17 OBJECT-TYPE SYNTAX INTEGER MAX-ACCESS read-only STATUS current DESCRIPTION "voltageLL17" ::= { bufferinval 242 }
voltageLN17 OBJECT-TYPE SYNTAX INTEGER MAX-ACCESS read-only STATUS current DESCRIPTION "voltageLN17" ::= { bufferinval 243 }
current17 OBJECT-TYPE SYNTAX INTEGER MAX-ACCESS read-only STATUS current DESCRIPTION "current17" ::= { bufferinval 244 }
frequency17 OBJECT-TYPE SYNTAX INTEGER MAX-ACCESS read-only STATUS current DESCRIPTION "frequency17" ::= { bufferinval 245 }
currentL117 OBJECT-TYPE SYNTAX INTEGER MAX-ACCESS read-only STATUS current DESCRIPTION "currentL117" ::= { bufferinval 246 }
currentL217 OBJECT-TYPE SYNTAX INTEGER MAX-ACCESS read-only STATUS current DESCRIPTION "currentL217" ::= { bufferinval 247 }
currentL317 OBJECT-TYPE SYNTAX INTEGER MAX-ACCESS read-only STATUS current DESCRIPTION "currentL317" ::= { bufferinval 248 }
currentN17 OBJECT-TYPE SYNTAX INTEGER MAX-ACCESS read-only STATUS current DESCRIPTION "currentN17" ::= { bufferinval 249 }
voltageL1L217 OBJECT-TYPE SYNTAX INTEGER MAX-ACCESS read-only STATUS current DESCRIPTION "voltageL1L217" ::= { bufferinval 250 }
voltageL2L317 OBJECT-TYPE SYNTAX INTEGER MAX-ACCESS read-only STATUS current DESCRIPTION "voltageL2L317" ::= { bufferinval 251 }
voltageL3L117 OBJECT-TYPE SYNTAX INTEGER MAX-ACCESS read-only STATUS current DESCRIPTION "voltageL3L117" ::= { bufferinval 252 }
voltageL1N17 OBJECT-TYPE SYNTAX INTEGER MAX-ACCESS read-only STATUS current DESCRIPTION "voltageL1N17" ::= { bufferinval 253 }
voltageL2N17 OBJECT-TYPE SYNTAX INTEGER MAX-ACCESS read-only STATUS current DESCRIPTION "voltageL2N17" ::= { bufferinval 254 }
voltageL3N17 OBJECT-TYPE SYNTAX INTEGER MAX-ACCESS read-only STATUS current DESCRIPTION "voltageL3N17" ::= { bufferinval 255 }
powerFactor18 OBJECT-TYPE SYNTAX INTEGER MAX-ACCESS read-only STATUS current DESCRIPTION "powerFactor18" ::= { bufferinval 256 }
voltageLL18 OBJECT-TYPE SYNTAX INTEGER MAX-ACCESS read-only STATUS current DESCRIPTION "voltageLL18" ::= { bufferinval 257 }
voltageLN18 OBJECT-TYPE SYNTAX INTEGER MAX-ACCESS read-only STATUS current DESCRIPTION "voltageLN18" ::= { bufferinval 258 }
current18 OBJECT-TYPE SYNTAX INTEGER MAX-ACCESS read-only STATUS current DESCRIPTION "current18" ::= { bufferinval 259 }
frequency18 OBJECT-TYPE SYNTAX INTEGER MAX-ACCESS read-only STATUS current DESCRIPTION "frequency18" ::= { bufferinval 260 }
currentL118 OBJECT-TYPE SYNTAX INTEGER MAX-ACCESS read-only STATUS current DESCRIPTION "currentL118" ::= { bufferinval 261 }
currentL218 OBJECT-TYPE SYNTAX INTEGER MAX-ACCESS read-only STATUS current DESCRIPTION "currentL218" ::= { bufferinval 262 }
currentL318 OBJECT-TYPE SYNTAX INTEGER MAX-ACCESS read-only STATUS current DESCRIPTION "currentL318" ::= { bufferinval 263 }
currentN18 OBJECT-TYPE SYNTAX INTEGER MAX-ACCESS read-only STATUS current DESCRIPTION "currentN18" ::= { bufferinval 264 }
voltageL1L218 OBJECT-TYPE SYNTAX INTEGER MAX-ACCESS read-only STATUS current DESCRIPTION "voltageL1L218" ::= { bufferinval 265 }
voltageL2L318 OBJECT-TYPE SYNTAX INTEGER MAX-ACCESS read-only STATUS current DESCRIPTION "voltageL2L318" ::= { bufferinval 266 }
voltageL3L118 OBJECT-TYPE SYNTAX INTEGER MAX-ACCESS read-only STATUS current DESCRIPTION "voltageL3L118" ::= { bufferinval 267 }
voltageL1N18 OBJECT-TYPE SYNTAX INTEGER MAX-ACCESS read-only STATUS current DESCRIPTION "voltageL1N18" ::= { bufferinval 268 }
voltageL2N18 OBJECT-TYPE SYNTAX INTEGER MAX-ACCESS read-only STATUS current DESCRIPTION "voltageL2N18" ::= { bufferinval 269 }
voltageL3N18 OBJECT-TYPE SYNTAX INTEGER MAX-ACCESS read-only STATUS current DESCRIPTION "voltageL3N18" ::= { bufferinval 270 }
powerFactor19 OBJECT-TYPE SYNTAX INTEGER MAX-ACCESS read-only STATUS current DESCRIPTION "powerFactor19" ::= { bufferinval 271 }
voltageLL19 OBJECT-TYPE SYNTAX INTEGER MAX-ACCESS read-only STATUS current DESCRIPTION "voltageLL19" ::= { bufferinval 272 }
voltageLN19 OBJECT-TYPE SYNTAX INTEGER MAX-ACCESS read-only STATUS current DESCRIPTION "voltageLN19" ::= { bufferinval 273 }
current19 OBJECT-TYPE SYNTAX INTEGER MAX-ACCESS read-only STATUS current DESCRIPTION "current19" ::= { bufferinval 274 }
frequency19 OBJECT-TYPE SYNTAX INTEGER MAX-ACCESS read-only STATUS current DESCRIPTION "frequency19" ::= { bufferinval 275 }
currentL119 OBJECT-TYPE SYNTAX INTEGER MAX-ACCESS read-only STATUS current DESCRIPTION "currentL119" ::= { bufferinval 276 }
currentL219 OBJECT-TYPE SYNTAX INTEGER MAX-ACCESS read-only STATUS current DESCRIPTION "currentL219" ::= { bufferinval 277 }
currentL319 OBJECT-TYPE SYNTAX INTEGER MAX-ACCESS read-only STATUS current DESCRIPTION "currentL319" ::= { bufferinval 278 }
currentN19 OBJECT-TYPE SYNTAX INTEGER MAX-ACCESS read-only STATUS current DESCRIPTION "currentN19" ::= { bufferinval 279 }
voltageL1L219 OBJECT-TYPE SYNTAX INTEGER MAX-ACCESS read-only STATUS current DESCRIPTION "voltageL1L219" ::= { bufferinval 280 }
voltageL2L319 OBJECT-TYPE SYNTAX INTEGER MAX-ACCESS read-only STATUS current DESCRIPTION "voltageL2L319" ::= { bufferinval 281 }
voltageL3L119 OBJECT-TYPE SYNTAX INTEGER MAX-ACCESS read-only STATUS current DESCRIPTION "voltageL3L119" ::= { bufferinval 282 }
voltageL1N19 OBJECT-TYPE SYNTAX INTEGER MAX-ACCESS read-only STATUS current DESCRIPTION "voltageL1N19" ::= { bufferinval 283 }
voltageL2N19 OBJECT-TYPE SYNTAX INTEGER MAX-ACCESS read-only STATUS current DESCRIPTION "voltageL2N19" ::= { bufferinval 284 }
voltageL3N19 OBJECT-TYPE SYNTAX INTEGER MAX-ACCESS read-only STATUS current DESCRIPTION "voltageL3N19" ::= { bufferinval 285 }
powerFactor20 OBJECT-TYPE SYNTAX INTEGER MAX-ACCESS read-only STATUS current DESCRIPTION "powerFactor20" ::= { bufferinval 286 }
voltageLL20 OBJECT-TYPE SYNTAX INTEGER MAX-ACCESS read-only STATUS current DESCRIPTION "voltageLL20" ::= { bufferinval 287 }
voltageLN20 OBJECT-TYPE SYNTAX INTEGER MAX-ACCESS read-only STATUS current DESCRIPTION "voltageLN20" ::= { bufferinval 288 }
current20 OBJECT-TYPE SYNTAX INTEGER MAX-ACCESS read-only STATUS current DESCRIPTION "current20" ::= { bufferinval 289 }
frequency20 OBJECT-TYPE SYNTAX INTEGER MAX-ACCESS read-only STATUS current DESCRIPTION "frequency20" ::= { bufferinval 290 }
currentL120 OBJECT-TYPE SYNTAX INTEGER MAX-ACCESS read-only STATUS current DESCRIPTION "currentL120" ::= { bufferinval 291 }
currentL220 OBJECT-TYPE SYNTAX INTEGER MAX-ACCESS read-only STATUS current DESCRIPTION "currentL220" ::= { bufferinval 292 }
currentL320 OBJECT-TYPE SYNTAX INTEGER MAX-ACCESS read-only STATUS current DESCRIPTION "currentL320" ::= { bufferinval 293 }
currentN20 OBJECT-TYPE SYNTAX INTEGER MAX-ACCESS read-only STATUS current DESCRIPTION "currentN20" ::= { bufferinval 294 }
voltageL1L220 OBJECT-TYPE SYNTAX INTEGER MAX-ACCESS read-only STATUS current DESCRIPTION "voltageL1L220" ::= { bufferinval 295 }
voltageL2L320 OBJECT-TYPE SYNTAX INTEGER MAX-ACCESS read-only STATUS current DESCRIPTION "voltageL2L320" ::= { bufferinval 296 }
voltageL3L120 OBJECT-TYPE SYNTAX INTEGER MAX-ACCESS read-only STATUS current DESCRIPTION "voltageL3L120" ::= { bufferinval 297 }
voltageL1N20 OBJECT-TYPE SYNTAX INTEGER MAX-ACCESS read-only STATUS current DESCRIPTION "voltageL1N20" ::= { bufferinval 298 }
voltageL2N20 OBJECT-TYPE SYNTAX INTEGER MAX-ACCESS read-only STATUS current DESCRIPTION "voltageL2N20" ::= { bufferinval 299 }
voltageL3N20 OBJECT-TYPE SYNTAX INTEGER MAX-ACCESS read-only STATUS current DESCRIPTION "voltageL3N20" ::= { bufferinval 300 }
powerFactor21 OBJECT-TYPE SYNTAX INTEGER MAX-ACCESS read-only STATUS current DESCRIPTION "powerFactor21" ::= { bufferinval 301 }
voltageLL21 OBJECT-TYPE SYNTAX INTEGER MAX-ACCESS read-only STATUS current DESCRIPTION "voltageLL21" ::= { bufferinval 302 }
voltageLN21 OBJECT-TYPE SYNTAX INTEGER MAX-ACCESS read-only STATUS current DESCRIPTION "voltageLN21" ::= { bufferinval 303 }
current21 OBJECT-TYPE SYNTAX INTEGER MAX-ACCESS read-only STATUS current DESCRIPTION "current21" ::= { bufferinval 304 }
frequency21 OBJECT-TYPE SYNTAX INTEGER MAX-ACCESS read-only STATUS current DESCRIPTION "frequency21" ::= { bufferinval 305 }
currentL121 OBJECT-TYPE SYNTAX INTEGER MAX-ACCESS read-only STATUS current DESCRIPTION "currentL121" ::= { bufferinval 306 }
currentL221 OBJECT-TYPE SYNTAX INTEGER MAX-ACCESS read-only STATUS current DESCRIPTION "currentL221" ::= { bufferinval 307 }
currentL321 OBJECT-TYPE SYNTAX INTEGER MAX-ACCESS read-only STATUS current DESCRIPTION "currentL321" ::= { bufferinval 308 }
currentN21 OBJECT-TYPE SYNTAX INTEGER MAX-ACCESS read-only STATUS current DESCRIPTION "currentN21" ::= { bufferinval 309 }
voltageL1L221 OBJECT-TYPE SYNTAX INTEGER MAX-ACCESS read-only STATUS current DESCRIPTION "voltageL1L221" ::= { bufferinval 310 }
voltageL2L321 OBJECT-TYPE SYNTAX INTEGER MAX-ACCESS read-only STATUS current DESCRIPTION "voltageL2L321" ::= { bufferinval 311 }
voltageL3L121 OBJECT-TYPE SYNTAX INTEGER MAX-ACCESS read-only STATUS current DESCRIPTION "voltageL3L121" ::= { bufferinval 312 }
voltageL1N21 OBJECT-TYPE SYNTAX INTEGER MAX-ACCESS read-only STATUS current DESCRIPTION "voltageL1N21" ::= { bufferinval 313 }
voltageL2N21 OBJECT-TYPE SYNTAX INTEGER MAX-ACCESS read-only STATUS current DESCRIPTION "voltageL2N21" ::= { bufferinval 314 }
voltageL3N21 OBJECT-TYPE SYNTAX INTEGER MAX-ACCESS read-only STATUS current DESCRIPTION "voltageL3N21" ::= { bufferinval 315 }
powerFactor22 OBJECT-TYPE SYNTAX INTEGER MAX-ACCESS read-only STATUS current DESCRIPTION "powerFactor22" ::= { bufferinval 316 }
voltageLL22 OBJECT-TYPE SYNTAX INTEGER MAX-ACCESS read-only STATUS current DESCRIPTION "voltageLL22" ::= { bufferinval 317 }
voltageLN22 OBJECT-TYPE SYNTAX INTEGER MAX-ACCESS read-only STATUS current DESCRIPTION "voltageLN22" ::= { bufferinval 318 }
current22 OBJECT-TYPE SYNTAX INTEGER MAX-ACCESS read-only STATUS current DESCRIPTION "current22" ::= { bufferinval 319 }
frequency22 OBJECT-TYPE SYNTAX INTEGER MAX-ACCESS read-only STATUS current DESCRIPTION "frequency22" ::= { bufferinval 320 }
currentL122 OBJECT-TYPE SYNTAX INTEGER MAX-ACCESS read-only STATUS current DESCRIPTION "currentL122" ::= { bufferinval 321 }
currentL222 OBJECT-TYPE SYNTAX INTEGER MAX-ACCESS read-only STATUS current DESCRIPTION "currentL222" ::= { bufferinval 322 }
currentL322 OBJECT-TYPE SYNTAX INTEGER MAX-ACCESS read-only STATUS current DESCRIPTION "currentL322" ::= { bufferinval 323 }
currentN22 OBJECT-TYPE SYNTAX INTEGER MAX-ACCESS read-only STATUS current DESCRIPTION "currentN22" ::= { bufferinval 324 }
voltageL1L222 OBJECT-TYPE SYNTAX INTEGER MAX-ACCESS read-only STATUS current DESCRIPTION "voltageL1L222" ::= { bufferinval 325 }
voltageL2L322 OBJECT-TYPE SYNTAX INTEGER MAX-ACCESS read-only STATUS current DESCRIPTION "voltageL2L322" ::= { bufferinval 326 }
voltageL3L122 OBJECT-TYPE SYNTAX INTEGER MAX-ACCESS read-only STATUS current DESCRIPTION "voltageL3L122" ::= { bufferinval 327 }
voltageL1N22 OBJECT-TYPE SYNTAX INTEGER MAX-ACCESS read-only STATUS current DESCRIPTION "voltageL1N22" ::= { bufferinval 328 }
voltageL2N22 OBJECT-TYPE SYNTAX INTEGER MAX-ACCESS read-only STATUS current DESCRIPTION "voltageL2N22" ::= { bufferinval 329 }
voltageL3N22 OBJECT-TYPE SYNTAX INTEGER MAX-ACCESS read-only STATUS current DESCRIPTION "voltageL3N22" ::= { bufferinval 330 }
powerFactor23 OBJECT-TYPE SYNTAX INTEGER MAX-ACCESS read-only STATUS current DESCRIPTION "powerFactor23" ::= { bufferinval 331 }
voltageLL23 OBJECT-TYPE SYNTAX INTEGER MAX-ACCESS read-only STATUS current DESCRIPTION "voltageLL23" ::= { bufferinval 332 }
voltageLN23 OBJECT-TYPE SYNTAX INTEGER MAX-ACCESS read-only STATUS current DESCRIPTION "voltageLN23" ::= { bufferinval 333 }
current23 OBJECT-TYPE SYNTAX INTEGER MAX-ACCESS read-only STATUS current DESCRIPTION "current23" ::= { bufferinval 334 }
frequency23 OBJECT-TYPE SYNTAX INTEGER MAX-ACCESS read-only STATUS current DESCRIPTION "frequency23" ::= { bufferinval 335 }
currentL123 OBJECT-TYPE SYNTAX INTEGER MAX-ACCESS read-only STATUS current DESCRIPTION "currentL123" ::= { bufferinval 336 }
currentL223 OBJECT-TYPE SYNTAX INTEGER MAX-ACCESS read-only STATUS current DESCRIPTION "currentL223" ::= { bufferinval 337 }
currentL323 OBJECT-TYPE SYNTAX INTEGER MAX-ACCESS read-only STATUS current DESCRIPTION "currentL323" ::= { bufferinval 338 }
currentN23 OBJECT-TYPE SYNTAX INTEGER MAX-ACCESS read-only STATUS current DESCRIPTION "currentN23" ::= { bufferinval 339 }
voltageL1L223 OBJECT-TYPE SYNTAX INTEGER MAX-ACCESS read-only STATUS current DESCRIPTION "voltageL1L223" ::= { bufferinval 340 }
voltageL2L323 OBJECT-TYPE SYNTAX INTEGER MAX-ACCESS read-only STATUS current DESCRIPTION "voltageL2L323" ::= { bufferinval 341 }
voltageL3L123 OBJECT-TYPE SYNTAX INTEGER MAX-ACCESS read-only STATUS current DESCRIPTION "voltageL3L123" ::= { bufferinval 342 }
voltageL1N23 OBJECT-TYPE SYNTAX INTEGER MAX-ACCESS read-only STATUS current DESCRIPTION "voltageL1N23" ::= { bufferinval 343 }
voltageL2N23 OBJECT-TYPE SYNTAX INTEGER MAX-ACCESS read-only STATUS current DESCRIPTION "voltageL2N23" ::= { bufferinval 344 }
voltageL3N23 OBJECT-TYPE SYNTAX INTEGER MAX-ACCESS read-only STATUS current DESCRIPTION "voltageL3N23" ::= { bufferinval 345 }
powerFactor24 OBJECT-TYPE SYNTAX INTEGER MAX-ACCESS read-only STATUS current DESCRIPTION "powerFactor24" ::= { bufferinval 346 }
voltageLL24 OBJECT-TYPE SYNTAX INTEGER MAX-ACCESS read-only STATUS current DESCRIPTION "voltageLL24" ::= { bufferinval 347 }
voltageLN24 OBJECT-TYPE SYNTAX INTEGER MAX-ACCESS read-only STATUS current DESCRIPTION "voltageLN24" ::= { bufferinval 348 }
current24 OBJECT-TYPE SYNTAX INTEGER MAX-ACCESS read-only STATUS current DESCRIPTION "current24" ::= { bufferinval 349 }
frequency24 OBJECT-TYPE SYNTAX INTEGER MAX-ACCESS read-only STATUS current DESCRIPTION "frequency24" ::= { bufferinval 350 }
currentL124 OBJECT-TYPE SYNTAX INTEGER MAX-ACCESS read-only STATUS current DESCRIPTION "currentL124" ::= { bufferinval 351 }
currentL224 OBJECT-TYPE SYNTAX INTEGER MAX-ACCESS read-only STATUS current DESCRIPTION "currentL224" ::= { bufferinval 352 }
currentL324 OBJECT-TYPE SYNTAX INTEGER MAX-ACCESS read-only STATUS current DESCRIPTION "currentL324" ::= { bufferinval 353 }
currentN24 OBJECT-TYPE SYNTAX INTEGER MAX-ACCESS read-only STATUS current DESCRIPTION "currentN24" ::= { bufferinval 354 }
voltageL1L224 OBJECT-TYPE SYNTAX INTEGER MAX-ACCESS read-only STATUS current DESCRIPTION "voltageL1L224" ::= { bufferinval 355 }
voltageL2L324 OBJECT-TYPE SYNTAX INTEGER MAX-ACCESS read-only STATUS current DESCRIPTION "voltageL2L324" ::= { bufferinval 356 }
voltageL3L124 OBJECT-TYPE SYNTAX INTEGER MAX-ACCESS read-only STATUS current DESCRIPTION "voltageL3L124" ::= { bufferinval 357 }
voltageL1N24 OBJECT-TYPE SYNTAX INTEGER MAX-ACCESS read-only STATUS current DESCRIPTION "voltageL1N24" ::= { bufferinval 358 }
voltageL2N24 OBJECT-TYPE SYNTAX INTEGER MAX-ACCESS read-only STATUS current DESCRIPTION "voltageL2N24" ::= { bufferinval 359 }
voltageL3N24 OBJECT-TYPE SYNTAX INTEGER MAX-ACCESS read-only STATUS current DESCRIPTION "voltageL3N24" ::= { bufferinval 360 }
powerFactor25 OBJECT-TYPE SYNTAX INTEGER MAX-ACCESS read-only STATUS current DESCRIPTION "powerFactor25" ::= { bufferinval 361 }
voltageLL25 OBJECT-TYPE SYNTAX INTEGER MAX-ACCESS read-only STATUS current DESCRIPTION "voltageLL25" ::= { bufferinval 362 }
current25 OBJECT-TYPE SYNTAX INTEGER MAX-ACCESS read-only STATUS current DESCRIPTION "current25" ::= { bufferinval 363 }
frequency25 OBJECT-TYPE SYNTAX INTEGER MAX-ACCESS read-only STATUS current DESCRIPTION "frequency25" ::= { bufferinval 364 }
currentL125 OBJECT-TYPE SYNTAX INTEGER MAX-ACCESS read-only STATUS current DESCRIPTION "currentL125" ::= { bufferinval 365 }
currentL225 OBJECT-TYPE SYNTAX INTEGER MAX-ACCESS read-only STATUS current DESCRIPTION "currentL225" ::= { bufferinval 366 }
currentL325 OBJECT-TYPE SYNTAX INTEGER MAX-ACCESS read-only STATUS current DESCRIPTION "currentL325" ::= { bufferinval 367 }
voltageL1L225 OBJECT-TYPE SYNTAX INTEGER MAX-ACCESS read-only STATUS current DESCRIPTION "voltageL1L225" ::= { bufferinval 368 }
voltageL2L325 OBJECT-TYPE SYNTAX INTEGER MAX-ACCESS read-only STATUS current DESCRIPTION "voltageL2L325" ::= { bufferinval 369 }
voltageL3L125 OBJECT-TYPE SYNTAX INTEGER MAX-ACCESS read-only STATUS current DESCRIPTION "voltageL3L125" ::= { bufferinval 370 }
powerFactor26 OBJECT-TYPE SYNTAX INTEGER MAX-ACCESS read-only STATUS current DESCRIPTION "powerFactor26" ::= { bufferinval 371 }
voltageLL26 OBJECT-TYPE SYNTAX INTEGER MAX-ACCESS read-only STATUS current DESCRIPTION "voltageLL26" ::= { bufferinval 372 }
current26 OBJECT-TYPE SYNTAX INTEGER MAX-ACCESS read-only STATUS current DESCRIPTION "current26" ::= { bufferinval 373 }
frequency26 OBJECT-TYPE SYNTAX INTEGER MAX-ACCESS read-only STATUS current DESCRIPTION "frequency26" ::= { bufferinval 374 }
currentL126 OBJECT-TYPE SYNTAX INTEGER MAX-ACCESS read-only STATUS current DESCRIPTION "currentL126" ::= { bufferinval 375 }
currentL226 OBJECT-TYPE SYNTAX INTEGER MAX-ACCESS read-only STATUS current DESCRIPTION "currentL226" ::= { bufferinval 376 }
currentL326 OBJECT-TYPE SYNTAX INTEGER MAX-ACCESS read-only STATUS current DESCRIPTION "currentL326" ::= { bufferinval 377 }
voltageL1L226 OBJECT-TYPE SYNTAX INTEGER MAX-ACCESS read-only STATUS current DESCRIPTION "voltageL1L226" ::= { bufferinval 378 }
voltageL2L326 OBJECT-TYPE SYNTAX INTEGER MAX-ACCESS read-only STATUS current DESCRIPTION "voltageL2L326" ::= { bufferinval 379 }
voltageL3L126 OBJECT-TYPE SYNTAX INTEGER MAX-ACCESS read-only STATUS current DESCRIPTION "voltageL3L126" ::= { bufferinval 380 }
powerFactor27 OBJECT-TYPE SYNTAX INTEGER MAX-ACCESS read-only STATUS current DESCRIPTION "powerFactor27" ::= { bufferinval 381 }
voltageLL27 OBJECT-TYPE SYNTAX INTEGER MAX-ACCESS read-only STATUS current DESCRIPTION "voltageLL27" ::= { bufferinval 382 }
voltageLN27 OBJECT-TYPE SYNTAX INTEGER MAX-ACCESS read-only STATUS current DESCRIPTION "voltageLN27" ::= { bufferinval 383 }
current27 OBJECT-TYPE SYNTAX INTEGER MAX-ACCESS read-only STATUS current DESCRIPTION "current27" ::= { bufferinval 384 }
frequency27 OBJECT-TYPE SYNTAX INTEGER MAX-ACCESS read-only STATUS current DESCRIPTION "frequency27" ::= { bufferinval 385 }
currentL127 OBJECT-TYPE SYNTAX INTEGER MAX-ACCESS read-only STATUS current DESCRIPTION "currentL127" ::= { bufferinval 386 }
currentL227 OBJECT-TYPE SYNTAX INTEGER MAX-ACCESS read-only STATUS current DESCRIPTION "currentL227" ::= { bufferinval 387 }
currentL327 OBJECT-TYPE SYNTAX INTEGER MAX-ACCESS read-only STATUS current DESCRIPTION "currentL327" ::= { bufferinval 388 }
currentN27 OBJECT-TYPE SYNTAX INTEGER MAX-ACCESS read-only STATUS current DESCRIPTION "currentN27" ::= { bufferinval 389 }
voltageL1L227 OBJECT-TYPE SYNTAX INTEGER MAX-ACCESS read-only STATUS current DESCRIPTION "voltageL1L227" ::= { bufferinval 390 }
voltageL2L327 OBJECT-TYPE SYNTAX INTEGER MAX-ACCESS read-only STATUS current DESCRIPTION "voltageL2L327" ::= { bufferinval 391 }
voltageL3L127 OBJECT-TYPE SYNTAX INTEGER MAX-ACCESS read-only STATUS current DESCRIPTION "voltageL3L127" ::= { bufferinval 392 }
voltageL1N27 OBJECT-TYPE SYNTAX INTEGER MAX-ACCESS read-only STATUS current DESCRIPTION "voltageL1N27" ::= { bufferinval 393 }
voltageL2N27 OBJECT-TYPE SYNTAX INTEGER MAX-ACCESS read-only STATUS current DESCRIPTION "voltageL2N27" ::= { bufferinval 394 }
voltageL3N27 OBJECT-TYPE SYNTAX INTEGER MAX-ACCESS read-only STATUS current DESCRIPTION "voltageL3N27" ::= { bufferinval 395 }
powerFactor28 OBJECT-TYPE SYNTAX INTEGER MAX-ACCESS read-only STATUS current DESCRIPTION "powerFactor28" ::= { bufferinval 396 }
voltageLL28 OBJECT-TYPE SYNTAX INTEGER MAX-ACCESS read-only STATUS current DESCRIPTION "voltageLL28" ::= { bufferinval 397 }
voltageLN28 OBJECT-TYPE SYNTAX INTEGER MAX-ACCESS read-only STATUS current DESCRIPTION "voltageLN28" ::= { bufferinval 398 }
current28 OBJECT-TYPE SYNTAX INTEGER MAX-ACCESS read-only STATUS current DESCRIPTION "current28" ::= { bufferinval 399 }
frequency28 OBJECT-TYPE SYNTAX INTEGER MAX-ACCESS read-only STATUS current DESCRIPTION "frequency28" ::= { bufferinval 400 }
currentL128 OBJECT-TYPE SYNTAX INTEGER MAX-ACCESS read-only STATUS current DESCRIPTION "currentL128" ::= { bufferinval 401 }
currentL228 OBJECT-TYPE SYNTAX INTEGER MAX-ACCESS read-only STATUS current DESCRIPTION "currentL228" ::= { bufferinval 402 }
currentL328 OBJECT-TYPE SYNTAX INTEGER MAX-ACCESS read-only STATUS current DESCRIPTION "currentL328" ::= { bufferinval 403 }
currentN28 OBJECT-TYPE SYNTAX INTEGER MAX-ACCESS read-only STATUS current DESCRIPTION "currentN28" ::= { bufferinval 404 }
voltageL1L228 OBJECT-TYPE SYNTAX INTEGER MAX-ACCESS read-only STATUS current DESCRIPTION "voltageL1L228" ::= { bufferinval 405 }
voltageL2L328 OBJECT-TYPE SYNTAX INTEGER MAX-ACCESS read-only STATUS current DESCRIPTION "voltageL2L328" ::= { bufferinval 406 }
voltageL3L128 OBJECT-TYPE SYNTAX INTEGER MAX-ACCESS read-only STATUS current DESCRIPTION "voltageL3L128" ::= { bufferinval 407 }
voltageL1N28 OBJECT-TYPE SYNTAX INTEGER MAX-ACCESS read-only STATUS current DESCRIPTION "voltageL1N28" ::= { bufferinval 408 }
voltageL2N28 OBJECT-TYPE SYNTAX INTEGER MAX-ACCESS read-only STATUS current DESCRIPTION "voltageL2N28" ::= { bufferinval 409 }
voltageL3N28 OBJECT-TYPE SYNTAX INTEGER MAX-ACCESS read-only STATUS current DESCRIPTION "voltageL3N28" ::= { bufferinval 410 }

bufferout OBJECT IDENTIFIER::= { data 5 }
bufferoutblk1 OBJECT-TYPE SYNTAX OCTET STRING MAX-ACCESS read-write STATUS current DESCRIPTION "data block n.1" ::= { bufferout 1 }
bufferoutblk2 OBJECT-TYPE SYNTAX OCTET STRING MAX-ACCESS read-write STATUS current DESCRIPTION "data block n.2" ::= { bufferout 2 }
bufferoutblk3 OBJECT-TYPE SYNTAX OCTET STRING MAX-ACCESS read-write STATUS current DESCRIPTION "data block n.3" ::= { bufferout 3 }
bufferoutblk4 OBJECT-TYPE SYNTAX OCTET STRING MAX-ACCESS read-write STATUS current DESCRIPTION "data block n.4" ::= { bufferout 4 }
bufferoutblk5 OBJECT-TYPE SYNTAX OCTET STRING MAX-ACCESS read-write STATUS current DESCRIPTION "data block n.5" ::= { bufferout 5 }
bufferoutblk6 OBJECT-TYPE SYNTAX OCTET STRING MAX-ACCESS read-write STATUS current DESCRIPTION "data block n.6" ::= { bufferout 6 }
bufferoutblk7 OBJECT-TYPE SYNTAX OCTET STRING MAX-ACCESS read-write STATUS current DESCRIPTION "data block n.7" ::= { bufferout 7 }
bufferoutblk8 OBJECT-TYPE SYNTAX OCTET STRING MAX-ACCESS read-write STATUS current DESCRIPTION "data block n.8" ::= { bufferout 8 }
 bufferoutval OBJECT IDENTIFIER::= { bufferout 9 }
traps OBJECT IDENTIFIER::= { application 2 }
 trapsval OBJECT IDENTIFIER::= { traps 1 }
trapval1 NOTIFICATION-TYPE SYNTAX INTEGER MAX-ACCESS read-only STATUS current DESCRIPTION "powerFactor1" ::= { trapsval 1 }
trapval2 NOTIFICATION-TYPE SYNTAX INTEGER MAX-ACCESS read-only STATUS current DESCRIPTION "voltageLL1" ::= { trapsval 2 }
trapval3 NOTIFICATION-TYPE SYNTAX INTEGER MAX-ACCESS read-only STATUS current DESCRIPTION "voltageLN1" ::= { trapsval 3 }
trapval4 NOTIFICATION-TYPE SYNTAX INTEGER MAX-ACCESS read-only STATUS current DESCRIPTION "current1" ::= { trapsval 4 }
trapval5 NOTIFICATION-TYPE SYNTAX INTEGER MAX-ACCESS read-only STATUS current DESCRIPTION "frequency1" ::= { trapsval 5 }
trapval6 NOTIFICATION-TYPE SYNTAX INTEGER MAX-ACCESS read-only STATUS current DESCRIPTION "currentL11" ::= { trapsval 6 }
trapval7 NOTIFICATION-TYPE SYNTAX INTEGER MAX-ACCESS read-only STATUS current DESCRIPTION "currentL21" ::= { trapsval 7 }
trapval8 NOTIFICATION-TYPE SYNTAX INTEGER MAX-ACCESS read-only STATUS current DESCRIPTION "currentL31" ::= { trapsval 8 }
trapval9 NOTIFICATION-TYPE SYNTAX INTEGER MAX-ACCESS read-only STATUS current DESCRIPTION "currentN1" ::= { trapsval 9 }
trapval10 NOTIFICATION-TYPE SYNTAX INTEGER MAX-ACCESS read-only STATUS current DESCRIPTION "voltageL1L21" ::= { trapsval 10 }
trapval11 NOTIFICATION-TYPE SYNTAX INTEGER MAX-ACCESS read-only STATUS current DESCRIPTION "voltageL2L31" ::= { trapsval 11 }
trapval12 NOTIFICATION-TYPE SYNTAX INTEGER MAX-ACCESS read-only STATUS current DESCRIPTION "voltageL3L11" ::= { trapsval 12 }
trapval13 NOTIFICATION-TYPE SYNTAX INTEGER MAX-ACCESS read-only STATUS current DESCRIPTION "voltageL1N1" ::= { trapsval 13 }
trapval14 NOTIFICATION-TYPE SYNTAX INTEGER MAX-ACCESS read-only STATUS current DESCRIPTION "voltageL2N1" ::= { trapsval 14 }
trapval15 NOTIFICATION-TYPE SYNTAX INTEGER MAX-ACCESS read-only STATUS current DESCRIPTION "voltageL3N1" ::= { trapsval 15 }
trapval16 NOTIFICATION-TYPE SYNTAX INTEGER MAX-ACCESS read-only STATUS current DESCRIPTION "powerFactor2" ::= { trapsval 16 }
trapval17 NOTIFICATION-TYPE SYNTAX INTEGER MAX-ACCESS read-only STATUS current DESCRIPTION "voltageLL2" ::= { trapsval 17 }
trapval18 NOTIFICATION-TYPE SYNTAX INTEGER MAX-ACCESS read-only STATUS current DESCRIPTION "voltageLN2" ::= { trapsval 18 }
trapval19 NOTIFICATION-TYPE SYNTAX INTEGER MAX-ACCESS read-only STATUS current DESCRIPTION "current2" ::= { trapsval 19 }
trapval20 NOTIFICATION-TYPE SYNTAX INTEGER MAX-ACCESS read-only STATUS current DESCRIPTION "frequency2" ::= { trapsval 20 }
trapval21 NOTIFICATION-TYPE SYNTAX INTEGER MAX-ACCESS read-only STATUS current DESCRIPTION "currentL12" ::= { trapsval 21 }
trapval22 NOTIFICATION-TYPE SYNTAX INTEGER MAX-ACCESS read-only STATUS current DESCRIPTION "currentL22" ::= { trapsval 22 }
trapval23 NOTIFICATION-TYPE SYNTAX INTEGER MAX-ACCESS read-only STATUS current DESCRIPTION "currentL32" ::= { trapsval 23 }
trapval24 NOTIFICATION-TYPE SYNTAX INTEGER MAX-ACCESS read-only STATUS current DESCRIPTION "currentN2" ::= { trapsval 24 }
trapval25 NOTIFICATION-TYPE SYNTAX INTEGER MAX-ACCESS read-only STATUS current DESCRIPTION "voltageL1L22" ::= { trapsval 25 }
trapval26 NOTIFICATION-TYPE SYNTAX INTEGER MAX-ACCESS read-only STATUS current DESCRIPTION "voltageL2L32" ::= { trapsval 26 }
trapval27 NOTIFICATION-TYPE SYNTAX INTEGER MAX-ACCESS read-only STATUS current DESCRIPTION "voltageL3L12" ::= { trapsval 27 }
trapval28 NOTIFICATION-TYPE SYNTAX INTEGER MAX-ACCESS read-only STATUS current DESCRIPTION "voltageL1N2" ::= { trapsval 28 }
trapval29 NOTIFICATION-TYPE SYNTAX INTEGER MAX-ACCESS read-only STATUS current DESCRIPTION "voltageL2N2" ::= { trapsval 29 }
trapval30 NOTIFICATION-TYPE SYNTAX INTEGER MAX-ACCESS read-only STATUS current DESCRIPTION "voltageL3N2" ::= { trapsval 30 }
trapval31 NOTIFICATION-TYPE SYNTAX INTEGER MAX-ACCESS read-only STATUS current DESCRIPTION "powerFactor3" ::= { trapsval 31 }
trapval32 NOTIFICATION-TYPE SYNTAX INTEGER MAX-ACCESS read-only STATUS current DESCRIPTION "voltageLL3" ::= { trapsval 32 }
trapval33 NOTIFICATION-TYPE SYNTAX INTEGER MAX-ACCESS read-only STATUS current DESCRIPTION "voltageLN3" ::= { trapsval 33 }
trapval34 NOTIFICATION-TYPE SYNTAX INTEGER MAX-ACCESS read-only STATUS current DESCRIPTION "current3" ::= { trapsval 34 }
trapval35 NOTIFICATION-TYPE SYNTAX INTEGER MAX-ACCESS read-only STATUS current DESCRIPTION "frequency3" ::= { trapsval 35 }
trapval36 NOTIFICATION-TYPE SYNTAX INTEGER MAX-ACCESS read-only STATUS current DESCRIPTION "currentL13" ::= { trapsval 36 }
trapval37 NOTIFICATION-TYPE SYNTAX INTEGER MAX-ACCESS read-only STATUS current DESCRIPTION "currentL23" ::= { trapsval 37 }
trapval38 NOTIFICATION-TYPE SYNTAX INTEGER MAX-ACCESS read-only STATUS current DESCRIPTION "currentL33" ::= { trapsval 38 }
trapval39 NOTIFICATION-TYPE SYNTAX INTEGER MAX-ACCESS read-only STATUS current DESCRIPTION "currentN3" ::= { trapsval 39 }
trapval40 NOTIFICATION-TYPE SYNTAX INTEGER MAX-ACCESS read-only STATUS current DESCRIPTION "voltageL1L23" ::= { trapsval 40 }
trapval41 NOTIFICATION-TYPE SYNTAX INTEGER MAX-ACCESS read-only STATUS current DESCRIPTION "voltageL2L33" ::= { trapsval 41 }
trapval42 NOTIFICATION-TYPE SYNTAX INTEGER MAX-ACCESS read-only STATUS current DESCRIPTION "voltageL3L13" ::= { trapsval 42 }
trapval43 NOTIFICATION-TYPE SYNTAX INTEGER MAX-ACCESS read-only STATUS current DESCRIPTION "voltageL1N3" ::= { trapsval 43 }
trapval44 NOTIFICATION-TYPE SYNTAX INTEGER MAX-ACCESS read-only STATUS current DESCRIPTION "voltageL2N3" ::= { trapsval 44 }
trapval45 NOTIFICATION-TYPE SYNTAX INTEGER MAX-ACCESS read-only STATUS current DESCRIPTION "voltageL3N3" ::= { trapsval 45 }
trapval46 NOTIFICATION-TYPE SYNTAX INTEGER MAX-ACCESS read-only STATUS current DESCRIPTION "powerFactor4" ::= { trapsval 46 }
trapval47 NOTIFICATION-TYPE SYNTAX INTEGER MAX-ACCESS read-only STATUS current DESCRIPTION "voltageLL4" ::= { trapsval 47 }
trapval48 NOTIFICATION-TYPE SYNTAX INTEGER MAX-ACCESS read-only STATUS current DESCRIPTION "voltageLN4" ::= { trapsval 48 }
trapval49 NOTIFICATION-TYPE SYNTAX INTEGER MAX-ACCESS read-only STATUS current DESCRIPTION "current4" ::= { trapsval 49 }
trapval50 NOTIFICATION-TYPE SYNTAX INTEGER MAX-ACCESS read-only STATUS current DESCRIPTION "frequency4" ::= { trapsval 50 }
trapval51 NOTIFICATION-TYPE SYNTAX INTEGER MAX-ACCESS read-only STATUS current DESCRIPTION "currentL14" ::= { trapsval 51 }
trapval52 NOTIFICATION-TYPE SYNTAX INTEGER MAX-ACCESS read-only STATUS current DESCRIPTION "currentL24" ::= { trapsval 52 }
trapval53 NOTIFICATION-TYPE SYNTAX INTEGER MAX-ACCESS read-only STATUS current DESCRIPTION "currentL34" ::= { trapsval 53 }
trapval54 NOTIFICATION-TYPE SYNTAX INTEGER MAX-ACCESS read-only STATUS current DESCRIPTION "currentN4" ::= { trapsval 54 }
trapval55 NOTIFICATION-TYPE SYNTAX INTEGER MAX-ACCESS read-only STATUS current DESCRIPTION "voltageL1L24" ::= { trapsval 55 }
trapval56 NOTIFICATION-TYPE SYNTAX INTEGER MAX-ACCESS read-only STATUS current DESCRIPTION "voltageL2L34" ::= { trapsval 56 }
trapval57 NOTIFICATION-TYPE SYNTAX INTEGER MAX-ACCESS read-only STATUS current DESCRIPTION "voltageL3L14" ::= { trapsval 57 }
trapval58 NOTIFICATION-TYPE SYNTAX INTEGER MAX-ACCESS read-only STATUS current DESCRIPTION "voltageL1N4" ::= { trapsval 58 }
trapval59 NOTIFICATION-TYPE SYNTAX INTEGER MAX-ACCESS read-only STATUS current DESCRIPTION "voltageL2N4" ::= { trapsval 59 }
trapval60 NOTIFICATION-TYPE SYNTAX INTEGER MAX-ACCESS read-only STATUS current DESCRIPTION "voltageL3N4" ::= { trapsval 60 }
trapval61 NOTIFICATION-TYPE SYNTAX INTEGER MAX-ACCESS read-only STATUS current DESCRIPTION "powerFactor5" ::= { trapsval 61 }
trapval62 NOTIFICATION-TYPE SYNTAX INTEGER MAX-ACCESS read-only STATUS current DESCRIPTION "voltageLL5" ::= { trapsval 62 }
trapval63 NOTIFICATION-TYPE SYNTAX INTEGER MAX-ACCESS read-only STATUS current DESCRIPTION "voltageLN5" ::= { trapsval 63 }
trapval64 NOTIFICATION-TYPE SYNTAX INTEGER MAX-ACCESS read-only STATUS current DESCRIPTION "current5" ::= { trapsval 64 }
trapval65 NOTIFICATION-TYPE SYNTAX INTEGER MAX-ACCESS read-only STATUS current DESCRIPTION "frequency5" ::= { trapsval 65 }
trapval66 NOTIFICATION-TYPE SYNTAX INTEGER MAX-ACCESS read-only STATUS current DESCRIPTION "currentL15" ::= { trapsval 66 }
trapval67 NOTIFICATION-TYPE SYNTAX INTEGER MAX-ACCESS read-only STATUS current DESCRIPTION "currentL25" ::= { trapsval 67 }
trapval68 NOTIFICATION-TYPE SYNTAX INTEGER MAX-ACCESS read-only STATUS current DESCRIPTION "currentL35" ::= { trapsval 68 }
trapval69 NOTIFICATION-TYPE SYNTAX INTEGER MAX-ACCESS read-only STATUS current DESCRIPTION "currentN5" ::= { trapsval 69 }
trapval70 NOTIFICATION-TYPE SYNTAX INTEGER MAX-ACCESS read-only STATUS current DESCRIPTION "voltageL1L25" ::= { trapsval 70 }
trapval71 NOTIFICATION-TYPE SYNTAX INTEGER MAX-ACCESS read-only STATUS current DESCRIPTION "voltageL2L35" ::= { trapsval 71 }
trapval72 NOTIFICATION-TYPE SYNTAX INTEGER MAX-ACCESS read-only STATUS current DESCRIPTION "voltageL3L15" ::= { trapsval 72 }
trapval73 NOTIFICATION-TYPE SYNTAX INTEGER MAX-ACCESS read-only STATUS current DESCRIPTION "voltageL1N5" ::= { trapsval 73 }
trapval74 NOTIFICATION-TYPE SYNTAX INTEGER MAX-ACCESS read-only STATUS current DESCRIPTION "voltageL2N5" ::= { trapsval 74 }
trapval75 NOTIFICATION-TYPE SYNTAX INTEGER MAX-ACCESS read-only STATUS current DESCRIPTION "voltageL3N5" ::= { trapsval 75 }
trapval76 NOTIFICATION-TYPE SYNTAX INTEGER MAX-ACCESS read-only STATUS current DESCRIPTION "powerFactor6" ::= { trapsval 76 }
trapval77 NOTIFICATION-TYPE SYNTAX INTEGER MAX-ACCESS read-only STATUS current DESCRIPTION "voltageLL6" ::= { trapsval 77 }
trapval78 NOTIFICATION-TYPE SYNTAX INTEGER MAX-ACCESS read-only STATUS current DESCRIPTION "voltageLN6" ::= { trapsval 78 }
trapval79 NOTIFICATION-TYPE SYNTAX INTEGER MAX-ACCESS read-only STATUS current DESCRIPTION "current6" ::= { trapsval 79 }
trapval80 NOTIFICATION-TYPE SYNTAX INTEGER MAX-ACCESS read-only STATUS current DESCRIPTION "frequency6" ::= { trapsval 80 }
trapval81 NOTIFICATION-TYPE SYNTAX INTEGER MAX-ACCESS read-only STATUS current DESCRIPTION "currentL16" ::= { trapsval 81 }
trapval82 NOTIFICATION-TYPE SYNTAX INTEGER MAX-ACCESS read-only STATUS current DESCRIPTION "currentL26" ::= { trapsval 82 }
trapval83 NOTIFICATION-TYPE SYNTAX INTEGER MAX-ACCESS read-only STATUS current DESCRIPTION "currentL36" ::= { trapsval 83 }
trapval84 NOTIFICATION-TYPE SYNTAX INTEGER MAX-ACCESS read-only STATUS current DESCRIPTION "currentN6" ::= { trapsval 84 }
trapval85 NOTIFICATION-TYPE SYNTAX INTEGER MAX-ACCESS read-only STATUS current DESCRIPTION "voltageL1L26" ::= { trapsval 85 }
trapval86 NOTIFICATION-TYPE SYNTAX INTEGER MAX-ACCESS read-only STATUS current DESCRIPTION "voltageL2L36" ::= { trapsval 86 }
trapval87 NOTIFICATION-TYPE SYNTAX INTEGER MAX-ACCESS read-only STATUS current DESCRIPTION "voltageL3L16" ::= { trapsval 87 }
trapval88 NOTIFICATION-TYPE SYNTAX INTEGER MAX-ACCESS read-only STATUS current DESCRIPTION "voltageL1N6" ::= { trapsval 88 }
trapval89 NOTIFICATION-TYPE SYNTAX INTEGER MAX-ACCESS read-only STATUS current DESCRIPTION "voltageL2N6" ::= { trapsval 89 }
trapval90 NOTIFICATION-TYPE SYNTAX INTEGER MAX-ACCESS read-only STATUS current DESCRIPTION "voltageL3N6" ::= { trapsval 90 }
trapval91 NOTIFICATION-TYPE SYNTAX INTEGER MAX-ACCESS read-only STATUS current DESCRIPTION "powerFactor7" ::= { trapsval 91 }
trapval92 NOTIFICATION-TYPE SYNTAX INTEGER MAX-ACCESS read-only STATUS current DESCRIPTION "voltageLL7" ::= { trapsval 92 }
trapval93 NOTIFICATION-TYPE SYNTAX INTEGER MAX-ACCESS read-only STATUS current DESCRIPTION "voltageLN7" ::= { trapsval 93 }
trapval94 NOTIFICATION-TYPE SYNTAX INTEGER MAX-ACCESS read-only STATUS current DESCRIPTION "current7" ::= { trapsval 94 }
trapval95 NOTIFICATION-TYPE SYNTAX INTEGER MAX-ACCESS read-only STATUS current DESCRIPTION "frequency7" ::= { trapsval 95 }
trapval96 NOTIFICATION-TYPE SYNTAX INTEGER MAX-ACCESS read-only STATUS current DESCRIPTION "currentL17" ::= { trapsval 96 }
trapval97 NOTIFICATION-TYPE SYNTAX INTEGER MAX-ACCESS read-only STATUS current DESCRIPTION "currentL27" ::= { trapsval 97 }
trapval98 NOTIFICATION-TYPE SYNTAX INTEGER MAX-ACCESS read-only STATUS current DESCRIPTION "currentL37" ::= { trapsval 98 }
trapval99 NOTIFICATION-TYPE SYNTAX INTEGER MAX-ACCESS read-only STATUS current DESCRIPTION "currentN7" ::= { trapsval 99 }
trapval100 NOTIFICATION-TYPE SYNTAX INTEGER MAX-ACCESS read-only STATUS current DESCRIPTION "voltageL1L27" ::= { trapsval 100 }
trapval101 NOTIFICATION-TYPE SYNTAX INTEGER MAX-ACCESS read-only STATUS current DESCRIPTION "voltageL2L37" ::= { trapsval 101 }
trapval102 NOTIFICATION-TYPE SYNTAX INTEGER MAX-ACCESS read-only STATUS current DESCRIPTION "voltageL3L17" ::= { trapsval 102 }
trapval103 NOTIFICATION-TYPE SYNTAX INTEGER MAX-ACCESS read-only STATUS current DESCRIPTION "voltageL1N7" ::= { trapsval 103 }
trapval104 NOTIFICATION-TYPE SYNTAX INTEGER MAX-ACCESS read-only STATUS current DESCRIPTION "voltageL2N7" ::= { trapsval 104 }
trapval105 NOTIFICATION-TYPE SYNTAX INTEGER MAX-ACCESS read-only STATUS current DESCRIPTION "voltageL3N7" ::= { trapsval 105 }
trapval106 NOTIFICATION-TYPE SYNTAX INTEGER MAX-ACCESS read-only STATUS current DESCRIPTION "powerFactor8" ::= { trapsval 106 }
trapval107 NOTIFICATION-TYPE SYNTAX INTEGER MAX-ACCESS read-only STATUS current DESCRIPTION "voltageLL8" ::= { trapsval 107 }
trapval108 NOTIFICATION-TYPE SYNTAX INTEGER MAX-ACCESS read-only STATUS current DESCRIPTION "voltageLN8" ::= { trapsval 108 }
trapval109 NOTIFICATION-TYPE SYNTAX INTEGER MAX-ACCESS read-only STATUS current DESCRIPTION "current8" ::= { trapsval 109 }
trapval110 NOTIFICATION-TYPE SYNTAX INTEGER MAX-ACCESS read-only STATUS current DESCRIPTION "frequency8" ::= { trapsval 110 }
trapval111 NOTIFICATION-TYPE SYNTAX INTEGER MAX-ACCESS read-only STATUS current DESCRIPTION "currentL18" ::= { trapsval 111 }
trapval112 NOTIFICATION-TYPE SYNTAX INTEGER MAX-ACCESS read-only STATUS current DESCRIPTION "currentL28" ::= { trapsval 112 }
trapval113 NOTIFICATION-TYPE SYNTAX INTEGER MAX-ACCESS read-only STATUS current DESCRIPTION "currentL38" ::= { trapsval 113 }
trapval114 NOTIFICATION-TYPE SYNTAX INTEGER MAX-ACCESS read-only STATUS current DESCRIPTION "currentN8" ::= { trapsval 114 }
trapval115 NOTIFICATION-TYPE SYNTAX INTEGER MAX-ACCESS read-only STATUS current DESCRIPTION "voltageL1L28" ::= { trapsval 115 }
trapval116 NOTIFICATION-TYPE SYNTAX INTEGER MAX-ACCESS read-only STATUS current DESCRIPTION "voltageL2L38" ::= { trapsval 116 }
trapval117 NOTIFICATION-TYPE SYNTAX INTEGER MAX-ACCESS read-only STATUS current DESCRIPTION "voltageL3L18" ::= { trapsval 117 }
trapval118 NOTIFICATION-TYPE SYNTAX INTEGER MAX-ACCESS read-only STATUS current DESCRIPTION "voltageL1N8" ::= { trapsval 118 }
trapval119 NOTIFICATION-TYPE SYNTAX INTEGER MAX-ACCESS read-only STATUS current DESCRIPTION "voltageL2N8" ::= { trapsval 119 }
trapval120 NOTIFICATION-TYPE SYNTAX INTEGER MAX-ACCESS read-only STATUS current DESCRIPTION "voltageL3N8" ::= { trapsval 120 }
trapval121 NOTIFICATION-TYPE SYNTAX INTEGER MAX-ACCESS read-only STATUS current DESCRIPTION "powerFactor9" ::= { trapsval 121 }
trapval122 NOTIFICATION-TYPE SYNTAX INTEGER MAX-ACCESS read-only STATUS current DESCRIPTION "voltageLL9" ::= { trapsval 122 }
trapval123 NOTIFICATION-TYPE SYNTAX INTEGER MAX-ACCESS read-only STATUS current DESCRIPTION "voltageLN9" ::= { trapsval 123 }
trapval124 NOTIFICATION-TYPE SYNTAX INTEGER MAX-ACCESS read-only STATUS current DESCRIPTION "current9" ::= { trapsval 124 }
trapval125 NOTIFICATION-TYPE SYNTAX INTEGER MAX-ACCESS read-only STATUS current DESCRIPTION "frequency9" ::= { trapsval 125 }
trapval126 NOTIFICATION-TYPE SYNTAX INTEGER MAX-ACCESS read-only STATUS current DESCRIPTION "currentL19" ::= { trapsval 126 }
trapval127 NOTIFICATION-TYPE SYNTAX INTEGER MAX-ACCESS read-only STATUS current DESCRIPTION "currentL29" ::= { trapsval 127 }
trapval128 NOTIFICATION-TYPE SYNTAX INTEGER MAX-ACCESS read-only STATUS current DESCRIPTION "currentL39" ::= { trapsval 128 }
trapval129 NOTIFICATION-TYPE SYNTAX INTEGER MAX-ACCESS read-only STATUS current DESCRIPTION "currentN9" ::= { trapsval 129 }
trapval130 NOTIFICATION-TYPE SYNTAX INTEGER MAX-ACCESS read-only STATUS current DESCRIPTION "voltageL1L29" ::= { trapsval 130 }
trapval131 NOTIFICATION-TYPE SYNTAX INTEGER MAX-ACCESS read-only STATUS current DESCRIPTION "voltageL2L39" ::= { trapsval 131 }
trapval132 NOTIFICATION-TYPE SYNTAX INTEGER MAX-ACCESS read-only STATUS current DESCRIPTION "voltageL3L19" ::= { trapsval 132 }
trapval133 NOTIFICATION-TYPE SYNTAX INTEGER MAX-ACCESS read-only STATUS current DESCRIPTION "voltageL1N9" ::= { trapsval 133 }
trapval134 NOTIFICATION-TYPE SYNTAX INTEGER MAX-ACCESS read-only STATUS current DESCRIPTION "voltageL2N9" ::= { trapsval 134 }
trapval135 NOTIFICATION-TYPE SYNTAX INTEGER MAX-ACCESS read-only STATUS current DESCRIPTION "voltageL3N9" ::= { trapsval 135 }
trapval136 NOTIFICATION-TYPE SYNTAX INTEGER MAX-ACCESS read-only STATUS current DESCRIPTION "powerFactor10" ::= { trapsval 136 }
trapval137 NOTIFICATION-TYPE SYNTAX INTEGER MAX-ACCESS read-only STATUS current DESCRIPTION "voltageLL10" ::= { trapsval 137 }
trapval138 NOTIFICATION-TYPE SYNTAX INTEGER MAX-ACCESS read-only STATUS current DESCRIPTION "voltageLN10" ::= { trapsval 138 }
trapval139 NOTIFICATION-TYPE SYNTAX INTEGER MAX-ACCESS read-only STATUS current DESCRIPTION "current10" ::= { trapsval 139 }
trapval140 NOTIFICATION-TYPE SYNTAX INTEGER MAX-ACCESS read-only STATUS current DESCRIPTION "frequency10" ::= { trapsval 140 }
trapval141 NOTIFICATION-TYPE SYNTAX INTEGER MAX-ACCESS read-only STATUS current DESCRIPTION "currentL110" ::= { trapsval 141 }
trapval142 NOTIFICATION-TYPE SYNTAX INTEGER MAX-ACCESS read-only STATUS current DESCRIPTION "currentL210" ::= { trapsval 142 }
trapval143 NOTIFICATION-TYPE SYNTAX INTEGER MAX-ACCESS read-only STATUS current DESCRIPTION "currentL310" ::= { trapsval 143 }
trapval144 NOTIFICATION-TYPE SYNTAX INTEGER MAX-ACCESS read-only STATUS current DESCRIPTION "currentN10" ::= { trapsval 144 }
trapval145 NOTIFICATION-TYPE SYNTAX INTEGER MAX-ACCESS read-only STATUS current DESCRIPTION "voltageL1L210" ::= { trapsval 145 }
trapval146 NOTIFICATION-TYPE SYNTAX INTEGER MAX-ACCESS read-only STATUS current DESCRIPTION "voltageL2L310" ::= { trapsval 146 }
trapval147 NOTIFICATION-TYPE SYNTAX INTEGER MAX-ACCESS read-only STATUS current DESCRIPTION "voltageL3L110" ::= { trapsval 147 }
trapval148 NOTIFICATION-TYPE SYNTAX INTEGER MAX-ACCESS read-only STATUS current DESCRIPTION "voltageL1N10" ::= { trapsval 148 }
trapval149 NOTIFICATION-TYPE SYNTAX INTEGER MAX-ACCESS read-only STATUS current DESCRIPTION "voltageL2N10" ::= { trapsval 149 }
trapval150 NOTIFICATION-TYPE SYNTAX INTEGER MAX-ACCESS read-only STATUS current DESCRIPTION "voltageL3N10" ::= { trapsval 150 }
trapval151 NOTIFICATION-TYPE SYNTAX INTEGER MAX-ACCESS read-only STATUS current DESCRIPTION "powerFactor11" ::= { trapsval 151 }
trapval152 NOTIFICATION-TYPE SYNTAX INTEGER MAX-ACCESS read-only STATUS current DESCRIPTION "voltageLL11" ::= { trapsval 152 }
trapval153 NOTIFICATION-TYPE SYNTAX INTEGER MAX-ACCESS read-only STATUS current DESCRIPTION "voltageLN11" ::= { trapsval 153 }
trapval154 NOTIFICATION-TYPE SYNTAX INTEGER MAX-ACCESS read-only STATUS current DESCRIPTION "current11" ::= { trapsval 154 }
trapval155 NOTIFICATION-TYPE SYNTAX INTEGER MAX-ACCESS read-only STATUS current DESCRIPTION "frequency11" ::= { trapsval 155 }
trapval156 NOTIFICATION-TYPE SYNTAX INTEGER MAX-ACCESS read-only STATUS current DESCRIPTION "currentL111" ::= { trapsval 156 }
trapval157 NOTIFICATION-TYPE SYNTAX INTEGER MAX-ACCESS read-only STATUS current DESCRIPTION "currentL211" ::= { trapsval 157 }
trapval158 NOTIFICATION-TYPE SYNTAX INTEGER MAX-ACCESS read-only STATUS current DESCRIPTION "currentL311" ::= { trapsval 158 }
trapval159 NOTIFICATION-TYPE SYNTAX INTEGER MAX-ACCESS read-only STATUS current DESCRIPTION "currentN11" ::= { trapsval 159 }
trapval160 NOTIFICATION-TYPE SYNTAX INTEGER MAX-ACCESS read-only STATUS current DESCRIPTION "voltageL1L211" ::= { trapsval 160 }
trapval161 NOTIFICATION-TYPE SYNTAX INTEGER MAX-ACCESS read-only STATUS current DESCRIPTION "voltageL2L311" ::= { trapsval 161 }
trapval162 NOTIFICATION-TYPE SYNTAX INTEGER MAX-ACCESS read-only STATUS current DESCRIPTION "voltageL3L111" ::= { trapsval 162 }
trapval163 NOTIFICATION-TYPE SYNTAX INTEGER MAX-ACCESS read-only STATUS current DESCRIPTION "voltageL1N11" ::= { trapsval 163 }
trapval164 NOTIFICATION-TYPE SYNTAX INTEGER MAX-ACCESS read-only STATUS current DESCRIPTION "voltageL2N11" ::= { trapsval 164 }
trapval165 NOTIFICATION-TYPE SYNTAX INTEGER MAX-ACCESS read-only STATUS current DESCRIPTION "voltageL3N11" ::= { trapsval 165 }
trapval166 NOTIFICATION-TYPE SYNTAX INTEGER MAX-ACCESS read-only STATUS current DESCRIPTION "powerFactor12" ::= { trapsval 166 }
trapval167 NOTIFICATION-TYPE SYNTAX INTEGER MAX-ACCESS read-only STATUS current DESCRIPTION "voltageLL12" ::= { trapsval 167 }
trapval168 NOTIFICATION-TYPE SYNTAX INTEGER MAX-ACCESS read-only STATUS current DESCRIPTION "voltageLN12" ::= { trapsval 168 }
trapval169 NOTIFICATION-TYPE SYNTAX INTEGER MAX-ACCESS read-only STATUS current DESCRIPTION "current12" ::= { trapsval 169 }
trapval170 NOTIFICATION-TYPE SYNTAX INTEGER MAX-ACCESS read-only STATUS current DESCRIPTION "frequency12" ::= { trapsval 170 }
trapval171 NOTIFICATION-TYPE SYNTAX INTEGER MAX-ACCESS read-only STATUS current DESCRIPTION "currentL112" ::= { trapsval 171 }
trapval172 NOTIFICATION-TYPE SYNTAX INTEGER MAX-ACCESS read-only STATUS current DESCRIPTION "currentL212" ::= { trapsval 172 }
trapval173 NOTIFICATION-TYPE SYNTAX INTEGER MAX-ACCESS read-only STATUS current DESCRIPTION "currentL312" ::= { trapsval 173 }
trapval174 NOTIFICATION-TYPE SYNTAX INTEGER MAX-ACCESS read-only STATUS current DESCRIPTION "currentN12" ::= { trapsval 174 }
trapval175 NOTIFICATION-TYPE SYNTAX INTEGER MAX-ACCESS read-only STATUS current DESCRIPTION "voltageL1L212" ::= { trapsval 175 }
trapval176 NOTIFICATION-TYPE SYNTAX INTEGER MAX-ACCESS read-only STATUS current DESCRIPTION "voltageL2L312" ::= { trapsval 176 }
trapval177 NOTIFICATION-TYPE SYNTAX INTEGER MAX-ACCESS read-only STATUS current DESCRIPTION "voltageL3L112" ::= { trapsval 177 }
trapval178 NOTIFICATION-TYPE SYNTAX INTEGER MAX-ACCESS read-only STATUS current DESCRIPTION "voltageL1N12" ::= { trapsval 178 }
trapval179 NOTIFICATION-TYPE SYNTAX INTEGER MAX-ACCESS read-only STATUS current DESCRIPTION "voltageL2N12" ::= { trapsval 179 }
trapval180 NOTIFICATION-TYPE SYNTAX INTEGER MAX-ACCESS read-only STATUS current DESCRIPTION "voltageL3N12" ::= { trapsval 180 }
trapval181 NOTIFICATION-TYPE SYNTAX INTEGER MAX-ACCESS read-only STATUS current DESCRIPTION "powerFactor13" ::= { trapsval 181 }
trapval182 NOTIFICATION-TYPE SYNTAX INTEGER MAX-ACCESS read-only STATUS current DESCRIPTION "voltageLL13" ::= { trapsval 182 }
trapval183 NOTIFICATION-TYPE SYNTAX INTEGER MAX-ACCESS read-only STATUS current DESCRIPTION "voltageLN13" ::= { trapsval 183 }
trapval184 NOTIFICATION-TYPE SYNTAX INTEGER MAX-ACCESS read-only STATUS current DESCRIPTION "current13" ::= { trapsval 184 }
trapval185 NOTIFICATION-TYPE SYNTAX INTEGER MAX-ACCESS read-only STATUS current DESCRIPTION "frequency13" ::= { trapsval 185 }
trapval186 NOTIFICATION-TYPE SYNTAX INTEGER MAX-ACCESS read-only STATUS current DESCRIPTION "currentL113" ::= { trapsval 186 }
trapval187 NOTIFICATION-TYPE SYNTAX INTEGER MAX-ACCESS read-only STATUS current DESCRIPTION "currentL213" ::= { trapsval 187 }
trapval188 NOTIFICATION-TYPE SYNTAX INTEGER MAX-ACCESS read-only STATUS current DESCRIPTION "currentL313" ::= { trapsval 188 }
trapval189 NOTIFICATION-TYPE SYNTAX INTEGER MAX-ACCESS read-only STATUS current DESCRIPTION "currentN13" ::= { trapsval 189 }
trapval190 NOTIFICATION-TYPE SYNTAX INTEGER MAX-ACCESS read-only STATUS current DESCRIPTION "voltageL1L213" ::= { trapsval 190 }
trapval191 NOTIFICATION-TYPE SYNTAX INTEGER MAX-ACCESS read-only STATUS current DESCRIPTION "voltageL2L313" ::= { trapsval 191 }
trapval192 NOTIFICATION-TYPE SYNTAX INTEGER MAX-ACCESS read-only STATUS current DESCRIPTION "voltageL3L113" ::= { trapsval 192 }
trapval193 NOTIFICATION-TYPE SYNTAX INTEGER MAX-ACCESS read-only STATUS current DESCRIPTION "voltageL1N13" ::= { trapsval 193 }
trapval194 NOTIFICATION-TYPE SYNTAX INTEGER MAX-ACCESS read-only STATUS current DESCRIPTION "voltageL2N13" ::= { trapsval 194 }
trapval195 NOTIFICATION-TYPE SYNTAX INTEGER MAX-ACCESS read-only STATUS current DESCRIPTION "voltageL3N13" ::= { trapsval 195 }
trapval196 NOTIFICATION-TYPE SYNTAX INTEGER MAX-ACCESS read-only STATUS current DESCRIPTION "powerFactor14" ::= { trapsval 196 }
trapval197 NOTIFICATION-TYPE SYNTAX INTEGER MAX-ACCESS read-only STATUS current DESCRIPTION "voltageLL14" ::= { trapsval 197 }
trapval198 NOTIFICATION-TYPE SYNTAX INTEGER MAX-ACCESS read-only STATUS current DESCRIPTION "voltageLN14" ::= { trapsval 198 }
trapval199 NOTIFICATION-TYPE SYNTAX INTEGER MAX-ACCESS read-only STATUS current DESCRIPTION "current14" ::= { trapsval 199 }
trapval200 NOTIFICATION-TYPE SYNTAX INTEGER MAX-ACCESS read-only STATUS current DESCRIPTION "frequency14" ::= { trapsval 200 }
trapval201 NOTIFICATION-TYPE SYNTAX INTEGER MAX-ACCESS read-only STATUS current DESCRIPTION "currentL114" ::= { trapsval 201 }
trapval202 NOTIFICATION-TYPE SYNTAX INTEGER MAX-ACCESS read-only STATUS current DESCRIPTION "currentL214" ::= { trapsval 202 }
trapval203 NOTIFICATION-TYPE SYNTAX INTEGER MAX-ACCESS read-only STATUS current DESCRIPTION "currentL314" ::= { trapsval 203 }
trapval204 NOTIFICATION-TYPE SYNTAX INTEGER MAX-ACCESS read-only STATUS current DESCRIPTION "currentN14" ::= { trapsval 204 }
trapval205 NOTIFICATION-TYPE SYNTAX INTEGER MAX-ACCESS read-only STATUS current DESCRIPTION "voltageL1L214" ::= { trapsval 205 }
trapval206 NOTIFICATION-TYPE SYNTAX INTEGER MAX-ACCESS read-only STATUS current DESCRIPTION "voltageL2L314" ::= { trapsval 206 }
trapval207 NOTIFICATION-TYPE SYNTAX INTEGER MAX-ACCESS read-only STATUS current DESCRIPTION "voltageL3L114" ::= { trapsval 207 }
trapval208 NOTIFICATION-TYPE SYNTAX INTEGER MAX-ACCESS read-only STATUS current DESCRIPTION "voltageL1N14" ::= { trapsval 208 }
trapval209 NOTIFICATION-TYPE SYNTAX INTEGER MAX-ACCESS read-only STATUS current DESCRIPTION "voltageL2N14" ::= { trapsval 209 }
trapval210 NOTIFICATION-TYPE SYNTAX INTEGER MAX-ACCESS read-only STATUS current DESCRIPTION "voltageL3N14" ::= { trapsval 210 }
trapval211 NOTIFICATION-TYPE SYNTAX INTEGER MAX-ACCESS read-only STATUS current DESCRIPTION "powerFactor15" ::= { trapsval 211 }
trapval212 NOTIFICATION-TYPE SYNTAX INTEGER MAX-ACCESS read-only STATUS current DESCRIPTION "voltageLL15" ::= { trapsval 212 }
trapval213 NOTIFICATION-TYPE SYNTAX INTEGER MAX-ACCESS read-only STATUS current DESCRIPTION "voltageLN15" ::= { trapsval 213 }
trapval214 NOTIFICATION-TYPE SYNTAX INTEGER MAX-ACCESS read-only STATUS current DESCRIPTION "current15" ::= { trapsval 214 }
trapval215 NOTIFICATION-TYPE SYNTAX INTEGER MAX-ACCESS read-only STATUS current DESCRIPTION "frequency15" ::= { trapsval 215 }
trapval216 NOTIFICATION-TYPE SYNTAX INTEGER MAX-ACCESS read-only STATUS current DESCRIPTION "currentL115" ::= { trapsval 216 }
trapval217 NOTIFICATION-TYPE SYNTAX INTEGER MAX-ACCESS read-only STATUS current DESCRIPTION "currentL215" ::= { trapsval 217 }
trapval218 NOTIFICATION-TYPE SYNTAX INTEGER MAX-ACCESS read-only STATUS current DESCRIPTION "currentL315" ::= { trapsval 218 }
trapval219 NOTIFICATION-TYPE SYNTAX INTEGER MAX-ACCESS read-only STATUS current DESCRIPTION "currentN15" ::= { trapsval 219 }
trapval220 NOTIFICATION-TYPE SYNTAX INTEGER MAX-ACCESS read-only STATUS current DESCRIPTION "voltageL1L215" ::= { trapsval 220 }
trapval221 NOTIFICATION-TYPE SYNTAX INTEGER MAX-ACCESS read-only STATUS current DESCRIPTION "voltageL2L315" ::= { trapsval 221 }
trapval222 NOTIFICATION-TYPE SYNTAX INTEGER MAX-ACCESS read-only STATUS current DESCRIPTION "voltageL3L115" ::= { trapsval 222 }
trapval223 NOTIFICATION-TYPE SYNTAX INTEGER MAX-ACCESS read-only STATUS current DESCRIPTION "voltageL1N15" ::= { trapsval 223 }
trapval224 NOTIFICATION-TYPE SYNTAX INTEGER MAX-ACCESS read-only STATUS current DESCRIPTION "voltageL2N15" ::= { trapsval 224 }
trapval225 NOTIFICATION-TYPE SYNTAX INTEGER MAX-ACCESS read-only STATUS current DESCRIPTION "voltageL3N15" ::= { trapsval 225 }
trapval226 NOTIFICATION-TYPE SYNTAX INTEGER MAX-ACCESS read-only STATUS current DESCRIPTION "powerFactor16" ::= { trapsval 226 }
trapval227 NOTIFICATION-TYPE SYNTAX INTEGER MAX-ACCESS read-only STATUS current DESCRIPTION "voltageLL16" ::= { trapsval 227 }
trapval228 NOTIFICATION-TYPE SYNTAX INTEGER MAX-ACCESS read-only STATUS current DESCRIPTION "voltageLN16" ::= { trapsval 228 }
trapval229 NOTIFICATION-TYPE SYNTAX INTEGER MAX-ACCESS read-only STATUS current DESCRIPTION "current16" ::= { trapsval 229 }
trapval230 NOTIFICATION-TYPE SYNTAX INTEGER MAX-ACCESS read-only STATUS current DESCRIPTION "frequency16" ::= { trapsval 230 }
trapval231 NOTIFICATION-TYPE SYNTAX INTEGER MAX-ACCESS read-only STATUS current DESCRIPTION "currentL116" ::= { trapsval 231 }
trapval232 NOTIFICATION-TYPE SYNTAX INTEGER MAX-ACCESS read-only STATUS current DESCRIPTION "currentL216" ::= { trapsval 232 }
trapval233 NOTIFICATION-TYPE SYNTAX INTEGER MAX-ACCESS read-only STATUS current DESCRIPTION "currentL316" ::= { trapsval 233 }
trapval234 NOTIFICATION-TYPE SYNTAX INTEGER MAX-ACCESS read-only STATUS current DESCRIPTION "currentN16" ::= { trapsval 234 }
trapval235 NOTIFICATION-TYPE SYNTAX INTEGER MAX-ACCESS read-only STATUS current DESCRIPTION "voltageL1L216" ::= { trapsval 235 }
trapval236 NOTIFICATION-TYPE SYNTAX INTEGER MAX-ACCESS read-only STATUS current DESCRIPTION "voltageL2L316" ::= { trapsval 236 }
trapval237 NOTIFICATION-TYPE SYNTAX INTEGER MAX-ACCESS read-only STATUS current DESCRIPTION "voltageL3L116" ::= { trapsval 237 }
trapval238 NOTIFICATION-TYPE SYNTAX INTEGER MAX-ACCESS read-only STATUS current DESCRIPTION "voltageL1N16" ::= { trapsval 238 }
trapval239 NOTIFICATION-TYPE SYNTAX INTEGER MAX-ACCESS read-only STATUS current DESCRIPTION "voltageL2N16" ::= { trapsval 239 }
trapval240 NOTIFICATION-TYPE SYNTAX INTEGER MAX-ACCESS read-only STATUS current DESCRIPTION "voltageL3N16" ::= { trapsval 240 }
trapval241 NOTIFICATION-TYPE SYNTAX INTEGER MAX-ACCESS read-only STATUS current DESCRIPTION "powerFactor17" ::= { trapsval 241 }
trapval242 NOTIFICATION-TYPE SYNTAX INTEGER MAX-ACCESS read-only STATUS current DESCRIPTION "voltageLL17" ::= { trapsval 242 }
trapval243 NOTIFICATION-TYPE SYNTAX INTEGER MAX-ACCESS read-only STATUS current DESCRIPTION "voltageLN17" ::= { trapsval 243 }
trapval244 NOTIFICATION-TYPE SYNTAX INTEGER MAX-ACCESS read-only STATUS current DESCRIPTION "current17" ::= { trapsval 244 }
trapval245 NOTIFICATION-TYPE SYNTAX INTEGER MAX-ACCESS read-only STATUS current DESCRIPTION "frequency17" ::= { trapsval 245 }
trapval246 NOTIFICATION-TYPE SYNTAX INTEGER MAX-ACCESS read-only STATUS current DESCRIPTION "currentL117" ::= { trapsval 246 }
trapval247 NOTIFICATION-TYPE SYNTAX INTEGER MAX-ACCESS read-only STATUS current DESCRIPTION "currentL217" ::= { trapsval 247 }
trapval248 NOTIFICATION-TYPE SYNTAX INTEGER MAX-ACCESS read-only STATUS current DESCRIPTION "currentL317" ::= { trapsval 248 }
trapval249 NOTIFICATION-TYPE SYNTAX INTEGER MAX-ACCESS read-only STATUS current DESCRIPTION "currentN17" ::= { trapsval 249 }
trapval250 NOTIFICATION-TYPE SYNTAX INTEGER MAX-ACCESS read-only STATUS current DESCRIPTION "voltageL1L217" ::= { trapsval 250 }
trapval251 NOTIFICATION-TYPE SYNTAX INTEGER MAX-ACCESS read-only STATUS current DESCRIPTION "voltageL2L317" ::= { trapsval 251 }
trapval252 NOTIFICATION-TYPE SYNTAX INTEGER MAX-ACCESS read-only STATUS current DESCRIPTION "voltageL3L117" ::= { trapsval 252 }
trapval253 NOTIFICATION-TYPE SYNTAX INTEGER MAX-ACCESS read-only STATUS current DESCRIPTION "voltageL1N17" ::= { trapsval 253 }
trapval254 NOTIFICATION-TYPE SYNTAX INTEGER MAX-ACCESS read-only STATUS current DESCRIPTION "voltageL2N17" ::= { trapsval 254 }
trapval255 NOTIFICATION-TYPE SYNTAX INTEGER MAX-ACCESS read-only STATUS current DESCRIPTION "voltageL3N17" ::= { trapsval 255 }
trapval256 NOTIFICATION-TYPE SYNTAX INTEGER MAX-ACCESS read-only STATUS current DESCRIPTION "powerFactor18" ::= { trapsval 256 }
trapval257 NOTIFICATION-TYPE SYNTAX INTEGER MAX-ACCESS read-only STATUS current DESCRIPTION "voltageLL18" ::= { trapsval 257 }
trapval258 NOTIFICATION-TYPE SYNTAX INTEGER MAX-ACCESS read-only STATUS current DESCRIPTION "voltageLN18" ::= { trapsval 258 }
trapval259 NOTIFICATION-TYPE SYNTAX INTEGER MAX-ACCESS read-only STATUS current DESCRIPTION "current18" ::= { trapsval 259 }
trapval260 NOTIFICATION-TYPE SYNTAX INTEGER MAX-ACCESS read-only STATUS current DESCRIPTION "frequency18" ::= { trapsval 260 }
trapval261 NOTIFICATION-TYPE SYNTAX INTEGER MAX-ACCESS read-only STATUS current DESCRIPTION "currentL118" ::= { trapsval 261 }
trapval262 NOTIFICATION-TYPE SYNTAX INTEGER MAX-ACCESS read-only STATUS current DESCRIPTION "currentL218" ::= { trapsval 262 }
trapval263 NOTIFICATION-TYPE SYNTAX INTEGER MAX-ACCESS read-only STATUS current DESCRIPTION "currentL318" ::= { trapsval 263 }
trapval264 NOTIFICATION-TYPE SYNTAX INTEGER MAX-ACCESS read-only STATUS current DESCRIPTION "currentN18" ::= { trapsval 264 }
trapval265 NOTIFICATION-TYPE SYNTAX INTEGER MAX-ACCESS read-only STATUS current DESCRIPTION "voltageL1L218" ::= { trapsval 265 }
trapval266 NOTIFICATION-TYPE SYNTAX INTEGER MAX-ACCESS read-only STATUS current DESCRIPTION "voltageL2L318" ::= { trapsval 266 }
trapval267 NOTIFICATION-TYPE SYNTAX INTEGER MAX-ACCESS read-only STATUS current DESCRIPTION "voltageL3L118" ::= { trapsval 267 }
trapval268 NOTIFICATION-TYPE SYNTAX INTEGER MAX-ACCESS read-only STATUS current DESCRIPTION "voltageL1N18" ::= { trapsval 268 }
trapval269 NOTIFICATION-TYPE SYNTAX INTEGER MAX-ACCESS read-only STATUS current DESCRIPTION "voltageL2N18" ::= { trapsval 269 }
trapval270 NOTIFICATION-TYPE SYNTAX INTEGER MAX-ACCESS read-only STATUS current DESCRIPTION "voltageL3N18" ::= { trapsval 270 }
trapval271 NOTIFICATION-TYPE SYNTAX INTEGER MAX-ACCESS read-only STATUS current DESCRIPTION "powerFactor19" ::= { trapsval 271 }
trapval272 NOTIFICATION-TYPE SYNTAX INTEGER MAX-ACCESS read-only STATUS current DESCRIPTION "voltageLL19" ::= { trapsval 272 }
trapval273 NOTIFICATION-TYPE SYNTAX INTEGER MAX-ACCESS read-only STATUS current DESCRIPTION "voltageLN19" ::= { trapsval 273 }
trapval274 NOTIFICATION-TYPE SYNTAX INTEGER MAX-ACCESS read-only STATUS current DESCRIPTION "current19" ::= { trapsval 274 }
trapval275 NOTIFICATION-TYPE SYNTAX INTEGER MAX-ACCESS read-only STATUS current DESCRIPTION "frequency19" ::= { trapsval 275 }
trapval276 NOTIFICATION-TYPE SYNTAX INTEGER MAX-ACCESS read-only STATUS current DESCRIPTION "currentL119" ::= { trapsval 276 }
trapval277 NOTIFICATION-TYPE SYNTAX INTEGER MAX-ACCESS read-only STATUS current DESCRIPTION "currentL219" ::= { trapsval 277 }
trapval278 NOTIFICATION-TYPE SYNTAX INTEGER MAX-ACCESS read-only STATUS current DESCRIPTION "currentL319" ::= { trapsval 278 }
trapval279 NOTIFICATION-TYPE SYNTAX INTEGER MAX-ACCESS read-only STATUS current DESCRIPTION "currentN19" ::= { trapsval 279 }
trapval280 NOTIFICATION-TYPE SYNTAX INTEGER MAX-ACCESS read-only STATUS current DESCRIPTION "voltageL1L219" ::= { trapsval 280 }
trapval281 NOTIFICATION-TYPE SYNTAX INTEGER MAX-ACCESS read-only STATUS current DESCRIPTION "voltageL2L319" ::= { trapsval 281 }
trapval282 NOTIFICATION-TYPE SYNTAX INTEGER MAX-ACCESS read-only STATUS current DESCRIPTION "voltageL3L119" ::= { trapsval 282 }
trapval283 NOTIFICATION-TYPE SYNTAX INTEGER MAX-ACCESS read-only STATUS current DESCRIPTION "voltageL1N19" ::= { trapsval 283 }
trapval284 NOTIFICATION-TYPE SYNTAX INTEGER MAX-ACCESS read-only STATUS current DESCRIPTION "voltageL2N19" ::= { trapsval 284 }
trapval285 NOTIFICATION-TYPE SYNTAX INTEGER MAX-ACCESS read-only STATUS current DESCRIPTION "voltageL3N19" ::= { trapsval 285 }
trapval286 NOTIFICATION-TYPE SYNTAX INTEGER MAX-ACCESS read-only STATUS current DESCRIPTION "powerFactor20" ::= { trapsval 286 }
trapval287 NOTIFICATION-TYPE SYNTAX INTEGER MAX-ACCESS read-only STATUS current DESCRIPTION "voltageLL20" ::= { trapsval 287 }
trapval288 NOTIFICATION-TYPE SYNTAX INTEGER MAX-ACCESS read-only STATUS current DESCRIPTION "voltageLN20" ::= { trapsval 288 }
trapval289 NOTIFICATION-TYPE SYNTAX INTEGER MAX-ACCESS read-only STATUS current DESCRIPTION "current20" ::= { trapsval 289 }
trapval290 NOTIFICATION-TYPE SYNTAX INTEGER MAX-ACCESS read-only STATUS current DESCRIPTION "frequency20" ::= { trapsval 290 }
trapval291 NOTIFICATION-TYPE SYNTAX INTEGER MAX-ACCESS read-only STATUS current DESCRIPTION "currentL120" ::= { trapsval 291 }
trapval292 NOTIFICATION-TYPE SYNTAX INTEGER MAX-ACCESS read-only STATUS current DESCRIPTION "currentL220" ::= { trapsval 292 }
trapval293 NOTIFICATION-TYPE SYNTAX INTEGER MAX-ACCESS read-only STATUS current DESCRIPTION "currentL320" ::= { trapsval 293 }
trapval294 NOTIFICATION-TYPE SYNTAX INTEGER MAX-ACCESS read-only STATUS current DESCRIPTION "currentN20" ::= { trapsval 294 }
trapval295 NOTIFICATION-TYPE SYNTAX INTEGER MAX-ACCESS read-only STATUS current DESCRIPTION "voltageL1L220" ::= { trapsval 295 }
trapval296 NOTIFICATION-TYPE SYNTAX INTEGER MAX-ACCESS read-only STATUS current DESCRIPTION "voltageL2L320" ::= { trapsval 296 }
trapval297 NOTIFICATION-TYPE SYNTAX INTEGER MAX-ACCESS read-only STATUS current DESCRIPTION "voltageL3L120" ::= { trapsval 297 }
trapval298 NOTIFICATION-TYPE SYNTAX INTEGER MAX-ACCESS read-only STATUS current DESCRIPTION "voltageL1N20" ::= { trapsval 298 }
trapval299 NOTIFICATION-TYPE SYNTAX INTEGER MAX-ACCESS read-only STATUS current DESCRIPTION "voltageL2N20" ::= { trapsval 299 }
trapval300 NOTIFICATION-TYPE SYNTAX INTEGER MAX-ACCESS read-only STATUS current DESCRIPTION "voltageL3N20" ::= { trapsval 300 }
trapval301 NOTIFICATION-TYPE SYNTAX INTEGER MAX-ACCESS read-only STATUS current DESCRIPTION "powerFactor21" ::= { trapsval 301 }
trapval302 NOTIFICATION-TYPE SYNTAX INTEGER MAX-ACCESS read-only STATUS current DESCRIPTION "voltageLL21" ::= { trapsval 302 }
trapval303 NOTIFICATION-TYPE SYNTAX INTEGER MAX-ACCESS read-only STATUS current DESCRIPTION "voltageLN21" ::= { trapsval 303 }
trapval304 NOTIFICATION-TYPE SYNTAX INTEGER MAX-ACCESS read-only STATUS current DESCRIPTION "current21" ::= { trapsval 304 }
trapval305 NOTIFICATION-TYPE SYNTAX INTEGER MAX-ACCESS read-only STATUS current DESCRIPTION "frequency21" ::= { trapsval 305 }
trapval306 NOTIFICATION-TYPE SYNTAX INTEGER MAX-ACCESS read-only STATUS current DESCRIPTION "currentL121" ::= { trapsval 306 }
trapval307 NOTIFICATION-TYPE SYNTAX INTEGER MAX-ACCESS read-only STATUS current DESCRIPTION "currentL221" ::= { trapsval 307 }
trapval308 NOTIFICATION-TYPE SYNTAX INTEGER MAX-ACCESS read-only STATUS current DESCRIPTION "currentL321" ::= { trapsval 308 }
trapval309 NOTIFICATION-TYPE SYNTAX INTEGER MAX-ACCESS read-only STATUS current DESCRIPTION "currentN21" ::= { trapsval 309 }
trapval310 NOTIFICATION-TYPE SYNTAX INTEGER MAX-ACCESS read-only STATUS current DESCRIPTION "voltageL1L221" ::= { trapsval 310 }
trapval311 NOTIFICATION-TYPE SYNTAX INTEGER MAX-ACCESS read-only STATUS current DESCRIPTION "voltageL2L321" ::= { trapsval 311 }
trapval312 NOTIFICATION-TYPE SYNTAX INTEGER MAX-ACCESS read-only STATUS current DESCRIPTION "voltageL3L121" ::= { trapsval 312 }
trapval313 NOTIFICATION-TYPE SYNTAX INTEGER MAX-ACCESS read-only STATUS current DESCRIPTION "voltageL1N21" ::= { trapsval 313 }
trapval314 NOTIFICATION-TYPE SYNTAX INTEGER MAX-ACCESS read-only STATUS current DESCRIPTION "voltageL2N21" ::= { trapsval 314 }
trapval315 NOTIFICATION-TYPE SYNTAX INTEGER MAX-ACCESS read-only STATUS current DESCRIPTION "voltageL3N21" ::= { trapsval 315 }
trapval316 NOTIFICATION-TYPE SYNTAX INTEGER MAX-ACCESS read-only STATUS current DESCRIPTION "powerFactor22" ::= { trapsval 316 }
trapval317 NOTIFICATION-TYPE SYNTAX INTEGER MAX-ACCESS read-only STATUS current DESCRIPTION "voltageLL22" ::= { trapsval 317 }
trapval318 NOTIFICATION-TYPE SYNTAX INTEGER MAX-ACCESS read-only STATUS current DESCRIPTION "voltageLN22" ::= { trapsval 318 }
trapval319 NOTIFICATION-TYPE SYNTAX INTEGER MAX-ACCESS read-only STATUS current DESCRIPTION "current22" ::= { trapsval 319 }
trapval320 NOTIFICATION-TYPE SYNTAX INTEGER MAX-ACCESS read-only STATUS current DESCRIPTION "frequency22" ::= { trapsval 320 }
trapval321 NOTIFICATION-TYPE SYNTAX INTEGER MAX-ACCESS read-only STATUS current DESCRIPTION "currentL122" ::= { trapsval 321 }
trapval322 NOTIFICATION-TYPE SYNTAX INTEGER MAX-ACCESS read-only STATUS current DESCRIPTION "currentL222" ::= { trapsval 322 }
trapval323 NOTIFICATION-TYPE SYNTAX INTEGER MAX-ACCESS read-only STATUS current DESCRIPTION "currentL322" ::= { trapsval 323 }
trapval324 NOTIFICATION-TYPE SYNTAX INTEGER MAX-ACCESS read-only STATUS current DESCRIPTION "currentN22" ::= { trapsval 324 }
trapval325 NOTIFICATION-TYPE SYNTAX INTEGER MAX-ACCESS read-only STATUS current DESCRIPTION "voltageL1L222" ::= { trapsval 325 }
trapval326 NOTIFICATION-TYPE SYNTAX INTEGER MAX-ACCESS read-only STATUS current DESCRIPTION "voltageL2L322" ::= { trapsval 326 }
trapval327 NOTIFICATION-TYPE SYNTAX INTEGER MAX-ACCESS read-only STATUS current DESCRIPTION "voltageL3L122" ::= { trapsval 327 }
trapval328 NOTIFICATION-TYPE SYNTAX INTEGER MAX-ACCESS read-only STATUS current DESCRIPTION "voltageL1N22" ::= { trapsval 328 }
trapval329 NOTIFICATION-TYPE SYNTAX INTEGER MAX-ACCESS read-only STATUS current DESCRIPTION "voltageL2N22" ::= { trapsval 329 }
trapval330 NOTIFICATION-TYPE SYNTAX INTEGER MAX-ACCESS read-only STATUS current DESCRIPTION "voltageL3N22" ::= { trapsval 330 }
trapval331 NOTIFICATION-TYPE SYNTAX INTEGER MAX-ACCESS read-only STATUS current DESCRIPTION "powerFactor23" ::= { trapsval 331 }
trapval332 NOTIFICATION-TYPE SYNTAX INTEGER MAX-ACCESS read-only STATUS current DESCRIPTION "voltageLL23" ::= { trapsval 332 }
trapval333 NOTIFICATION-TYPE SYNTAX INTEGER MAX-ACCESS read-only STATUS current DESCRIPTION "voltageLN23" ::= { trapsval 333 }
trapval334 NOTIFICATION-TYPE SYNTAX INTEGER MAX-ACCESS read-only STATUS current DESCRIPTION "current23" ::= { trapsval 334 }
trapval335 NOTIFICATION-TYPE SYNTAX INTEGER MAX-ACCESS read-only STATUS current DESCRIPTION "frequency23" ::= { trapsval 335 }
trapval336 NOTIFICATION-TYPE SYNTAX INTEGER MAX-ACCESS read-only STATUS current DESCRIPTION "currentL123" ::= { trapsval 336 }
trapval337 NOTIFICATION-TYPE SYNTAX INTEGER MAX-ACCESS read-only STATUS current DESCRIPTION "currentL223" ::= { trapsval 337 }
trapval338 NOTIFICATION-TYPE SYNTAX INTEGER MAX-ACCESS read-only STATUS current DESCRIPTION "currentL323" ::= { trapsval 338 }
trapval339 NOTIFICATION-TYPE SYNTAX INTEGER MAX-ACCESS read-only STATUS current DESCRIPTION "currentN23" ::= { trapsval 339 }
trapval340 NOTIFICATION-TYPE SYNTAX INTEGER MAX-ACCESS read-only STATUS current DESCRIPTION "voltageL1L223" ::= { trapsval 340 }
trapval341 NOTIFICATION-TYPE SYNTAX INTEGER MAX-ACCESS read-only STATUS current DESCRIPTION "voltageL2L323" ::= { trapsval 341 }
trapval342 NOTIFICATION-TYPE SYNTAX INTEGER MAX-ACCESS read-only STATUS current DESCRIPTION "voltageL3L123" ::= { trapsval 342 }
trapval343 NOTIFICATION-TYPE SYNTAX INTEGER MAX-ACCESS read-only STATUS current DESCRIPTION "voltageL1N23" ::= { trapsval 343 }
trapval344 NOTIFICATION-TYPE SYNTAX INTEGER MAX-ACCESS read-only STATUS current DESCRIPTION "voltageL2N23" ::= { trapsval 344 }
trapval345 NOTIFICATION-TYPE SYNTAX INTEGER MAX-ACCESS read-only STATUS current DESCRIPTION "voltageL3N23" ::= { trapsval 345 }
trapval346 NOTIFICATION-TYPE SYNTAX INTEGER MAX-ACCESS read-only STATUS current DESCRIPTION "powerFactor24" ::= { trapsval 346 }
trapval347 NOTIFICATION-TYPE SYNTAX INTEGER MAX-ACCESS read-only STATUS current DESCRIPTION "voltageLL24" ::= { trapsval 347 }
trapval348 NOTIFICATION-TYPE SYNTAX INTEGER MAX-ACCESS read-only STATUS current DESCRIPTION "voltageLN24" ::= { trapsval 348 }
trapval349 NOTIFICATION-TYPE SYNTAX INTEGER MAX-ACCESS read-only STATUS current DESCRIPTION "current24" ::= { trapsval 349 }
trapval350 NOTIFICATION-TYPE SYNTAX INTEGER MAX-ACCESS read-only STATUS current DESCRIPTION "frequency24" ::= { trapsval 350 }
trapval351 NOTIFICATION-TYPE SYNTAX INTEGER MAX-ACCESS read-only STATUS current DESCRIPTION "currentL124" ::= { trapsval 351 }
trapval352 NOTIFICATION-TYPE SYNTAX INTEGER MAX-ACCESS read-only STATUS current DESCRIPTION "currentL224" ::= { trapsval 352 }
trapval353 NOTIFICATION-TYPE SYNTAX INTEGER MAX-ACCESS read-only STATUS current DESCRIPTION "currentL324" ::= { trapsval 353 }
trapval354 NOTIFICATION-TYPE SYNTAX INTEGER MAX-ACCESS read-only STATUS current DESCRIPTION "currentN24" ::= { trapsval 354 }
trapval355 NOTIFICATION-TYPE SYNTAX INTEGER MAX-ACCESS read-only STATUS current DESCRIPTION "voltageL1L224" ::= { trapsval 355 }
trapval356 NOTIFICATION-TYPE SYNTAX INTEGER MAX-ACCESS read-only STATUS current DESCRIPTION "voltageL2L324" ::= { trapsval 356 }
trapval357 NOTIFICATION-TYPE SYNTAX INTEGER MAX-ACCESS read-only STATUS current DESCRIPTION "voltageL3L124" ::= { trapsval 357 }
trapval358 NOTIFICATION-TYPE SYNTAX INTEGER MAX-ACCESS read-only STATUS current DESCRIPTION "voltageL1N24" ::= { trapsval 358 }
trapval359 NOTIFICATION-TYPE SYNTAX INTEGER MAX-ACCESS read-only STATUS current DESCRIPTION "voltageL2N24" ::= { trapsval 359 }
trapval360 NOTIFICATION-TYPE SYNTAX INTEGER MAX-ACCESS read-only STATUS current DESCRIPTION "voltageL3N24" ::= { trapsval 360 }
trapval361 NOTIFICATION-TYPE SYNTAX INTEGER MAX-ACCESS read-only STATUS current DESCRIPTION "powerFactor25" ::= { trapsval 361 }
trapval362 NOTIFICATION-TYPE SYNTAX INTEGER MAX-ACCESS read-only STATUS current DESCRIPTION "voltageLL25" ::= { trapsval 362 }
trapval363 NOTIFICATION-TYPE SYNTAX INTEGER MAX-ACCESS read-only STATUS current DESCRIPTION "current25" ::= { trapsval 363 }
trapval364 NOTIFICATION-TYPE SYNTAX INTEGER MAX-ACCESS read-only STATUS current DESCRIPTION "frequency25" ::= { trapsval 364 }
trapval365 NOTIFICATION-TYPE SYNTAX INTEGER MAX-ACCESS read-only STATUS current DESCRIPTION "currentL125" ::= { trapsval 365 }
trapval366 NOTIFICATION-TYPE SYNTAX INTEGER MAX-ACCESS read-only STATUS current DESCRIPTION "currentL225" ::= { trapsval 366 }
trapval367 NOTIFICATION-TYPE SYNTAX INTEGER MAX-ACCESS read-only STATUS current DESCRIPTION "currentL325" ::= { trapsval 367 }
trapval368 NOTIFICATION-TYPE SYNTAX INTEGER MAX-ACCESS read-only STATUS current DESCRIPTION "voltageL1L225" ::= { trapsval 368 }
trapval369 NOTIFICATION-TYPE SYNTAX INTEGER MAX-ACCESS read-only STATUS current DESCRIPTION "voltageL2L325" ::= { trapsval 369 }
trapval370 NOTIFICATION-TYPE SYNTAX INTEGER MAX-ACCESS read-only STATUS current DESCRIPTION "voltageL3L125" ::= { trapsval 370 }
trapval371 NOTIFICATION-TYPE SYNTAX INTEGER MAX-ACCESS read-only STATUS current DESCRIPTION "powerFactor26" ::= { trapsval 371 }
trapval372 NOTIFICATION-TYPE SYNTAX INTEGER MAX-ACCESS read-only STATUS current DESCRIPTION "voltageLL26" ::= { trapsval 372 }
trapval373 NOTIFICATION-TYPE SYNTAX INTEGER MAX-ACCESS read-only STATUS current DESCRIPTION "current26" ::= { trapsval 373 }
trapval374 NOTIFICATION-TYPE SYNTAX INTEGER MAX-ACCESS read-only STATUS current DESCRIPTION "frequency26" ::= { trapsval 374 }
trapval375 NOTIFICATION-TYPE SYNTAX INTEGER MAX-ACCESS read-only STATUS current DESCRIPTION "currentL126" ::= { trapsval 375 }
trapval376 NOTIFICATION-TYPE SYNTAX INTEGER MAX-ACCESS read-only STATUS current DESCRIPTION "currentL226" ::= { trapsval 376 }
trapval377 NOTIFICATION-TYPE SYNTAX INTEGER MAX-ACCESS read-only STATUS current DESCRIPTION "currentL326" ::= { trapsval 377 }
trapval378 NOTIFICATION-TYPE SYNTAX INTEGER MAX-ACCESS read-only STATUS current DESCRIPTION "voltageL1L226" ::= { trapsval 378 }
trapval379 NOTIFICATION-TYPE SYNTAX INTEGER MAX-ACCESS read-only STATUS current DESCRIPTION "voltageL2L326" ::= { trapsval 379 }
trapval380 NOTIFICATION-TYPE SYNTAX INTEGER MAX-ACCESS read-only STATUS current DESCRIPTION "voltageL3L126" ::= { trapsval 380 }
END

-- This file is corresponding to Release 9.1.10.101 from 2014/08/11 00:00:00


-- (C)opyright 1991-2014 bintec elmeg GmbH, All Rights Reserved
-- $Revision: 1.10 $ 

BIANCA-BRICK-OPT-MIB DEFINITIONS ::= BEGIN

	IMPORTS
	    NetworkAddress, IpAddress, Counter, Gauge, TimeTicks, enterprises
		FROM RFC1155-SMI

            DisplayString
                FROM RFC1158-MIB

            Date, HexValue, BitValue
                FROM BINTEC-MIB

	    OBJECT-TYPE
		FROM RFC-1212;

	--  This MIB module uses the extended OBJECT-TYPE macro as
	--  defined in [14];


	--  MIB-II (same prefix as MIB-I)
	bintec 		OBJECT IDENTIFIER ::= { enterprises 272 }
	bibo		OBJECT IDENTIFIER ::= { bintec 4 }
	admin		OBJECT IDENTIFIER
	    ::= { bibo 1 }

        admin-2 OBJECT IDENTIFIER
            ::= { bibo 22 }

        extadmin        OBJECT IDENTIFIER
            ::= { admin-2 1 }

    -- Admin Group

    -- Some variables for administration of the BIANCA/BRICK

	biboExtAdmCompanyCode OBJECT-TYPE
	    SYNTAX  BitValue
	    ACCESS  read-write
	    STATUS  mandatory
	    DESCRIPTION
	        "This variable contains a bit field that allows to
		 selectively enable/disable features.
		 Default value is 0.
	        "
	    DEFVAL { 0 }
	::= { extadmin 6 }

--  Application

 	biboAdmAppTable OBJECT-TYPE
 	    SYNTAX  SEQUENCE OF BiboAdmAppEntry
 	    ACCESS  not-accessible
 	    STATUS  mandatory
 
 	    DESCRIPTION
 		"The biboAdmAppTable lists a source address by application
         and interface.

         Creating entries: Entries are created by setting an
         application name to biboAdmAppName.

         Deleting entries: Entries are removed by setting the
         appropriate biboAdmAppName field to 'delete'."
 	::= { admin 46 }
 
        biboAdmAppEntry OBJECT-TYPE
	    SYNTAX  BiboAdmAppEntry
 	    ACCESS  not-accessible
 	    STATUS  mandatory
 	    DESCRIPTION
 		  ""
 	    INDEX   { biboAdmAppSrcAddr }
 	::= { biboAdmAppTable 1 }

 	BiboAdmAppEntry ::= SEQUENCE {
 	    biboAdmAppName 				INTEGER,
	    biboAdmAppSrcAddr				IpAddress,
	    biboAdmAppIfIndex				INTEGER
 	}

	biboAdmAppName OBJECT-TYPE
	    SYNTAX  INTEGER { 
		tftp(1), 
		snmp(2),
		tacacsp(3),
		time(4),
		delete(15)
	    } 
	    ACCESS  read-write
	    STATUS  mandatory

	    DESCRIPTION
		"This object specifies the application name."
	    DEFVAL { tftp }
	::= { biboAdmAppEntry 1 }

 
 	biboAdmAppSrcAddr OBJECT-TYPE
 	    SYNTAX  IpAddress
 	    ACCESS  read-write
 	    STATUS  mandatory
 
 	    DESCRIPTION
 		"This object specifies the source Ip-Address used by
		biboAdmAppName and biboAdmAppIfIndex."
 	::= { biboAdmAppEntry 2 }

	biboAdmAppIfIndex OBJECT-TYPE
	    SYNTAX  INTEGER 
	    ACCESS  read-write
	    STATUS  mandatory

	    DESCRIPTION
		"This object specifies the target index of the interface
		 used by the application."
	::= { biboAdmAppEntry 3 }



END

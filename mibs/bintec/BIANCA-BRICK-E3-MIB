-- This file is corresponding to Release 9.1.10.101 from 2014/08/11 00:00:00


-- (C)opyright 1991-2014 bintec elmeg GmbH, All Rights Reserved
-- $RCSfile: mibe3,v $ 
-- $Revision: 1.7 $ 

BIANCA-BRICK-E3-MIB DEFINITIONS ::= BEGIN
 
        IMPORTS
            Counter, enterprises
                FROM RFC1155-SMI

            Date, HexValue
                FROM BINTEC-MIB
 
            OBJECT-TYPE
                FROM RFC-1212;

    bintec 	OBJECT IDENTIFIER ::= { enterprises 272 }
    bibo	OBJECT IDENTIFIER ::= { bintec 4 }
    e3		OBJECT IDENTIFIER 
	::= { bibo 42 }


    -- Interfaces Group

    -- Management Information for the E3 Subsystem 


        e3IfTable OBJECT-TYPE
            SYNTAX  SEQUENCE OF E3IfEntry
            ACCESS  not-accessible
            STATUS  mandatory
            DESCRIPTION
		"The e3IfTable contains information relating to the 
                interfaces available on the system. Each entry corresponds to
                an available e3 interface. Entries cannot be added or 
		deleted by the user. 

                Creating entries: Entries are created by the system
                automatically when a new e3 module is installed.

                Deleting entries: Entries are removed by the system
                after the appropriate e3 module is removed."
	::= { e3 1 }

	e3IfEntry OBJECT-TYPE
            SYNTAX  E3IfEntry
            ACCESS  not-accessible
            STATUS  mandatory
            DESCRIPTION
		""
	    INDEX   { e3IfIndex }
	::= { e3IfTable 1 }

	E3IfEntry ::=
            SEQUENCE {
		-- configuration
                e3IfIndex		INTEGER,
		e3IfType		INTEGER,

		e3IfClock		INTEGER,

		e3IfL2Mode		INTEGER,
		e3IfTestPattern		INTEGER,
		e3IfLoopback 		INTEGER,
		e3IfBundle		INTEGER,
		e3IfCableLength		INTEGER,
		e3IfCRCMode		INTEGER,

		-- status variables
		e3IfL1State		INTEGER,

		-- statistics
		e3IfRxPackets		Counter,
		e3IfRxOctets		Counter,
		e3IfTxPackets		Counter,
		e3IfTxOctets		Counter,

		e3IfRxResets		Counter,
		e3IfRxAborts		Counter,
		e3IfRxOverruns		Counter,
		e3IfRxCRCErrors		Counter,
		e3IfRxGiantFrames	Counter,

		e3IfTxResets		Counter,
		e3IfTxAborts		Counter,
		e3IfTxUnderruns		Counter,
		e3IfTxGiantFrames	Counter
            }

	e3IfIndex OBJECT-TYPE
            SYNTAX  INTEGER
            ACCESS  read-only
            STATUS  mandatory
            DESCRIPTION
                "The unique interface index of the e3/ds3 interface."
	::= { e3IfEntry 1 }

	-- configuration

	e3IfType OBJECT-TYPE
	    SYNTAX  INTEGER {
	       	off(1),
		e3-unframed(2),
		ds3-unframed(3),
		sts1-unframed(4)
	    }
            ACCESS  read-write
            STATUS  mandatory
            DESCRIPTION
                "The e3 physical interface type
 		 off(1)		interface is switched offline and the 
				line interface unit is switched off.
		 e3-unframed(2) Synchronous 34.368 MBit/s fullduplex,
				with HDB3 line coding.
		 ds3-unframed(3) Synchronous 44.736 MBit/s fullduplex,
				with B3ZS line coding.
		 sts1-unframed(4) Synchronous 51.840 MBit/s fullduplex,
				with B3ZS line coding.
		"
	    DEFVAL { e3-unframed }
	::= { e3IfEntry 2 }

	e3IfClock OBJECT-TYPE
            SYNTAX  INTEGER { intern(1), extern(2), extern-preferred(3) }
            ACCESS  read-write
            STATUS  mandatory
            DESCRIPTION
                "The clock source of the E3/DS3 connection.
		 intern(1)	Your router provides the master clock
				of the E3/DS3 connection.
		 extern(2)	Your telephone company or the remote
				DSU provides the master clock of the 
				E3/DS3 connection.
		 extern-preferred(3) The same like 'extern'."
	    DEFVAL { extern }
	::= { e3IfEntry 5 }
		
	e3IfL2Mode OBJECT-TYPE
            SYNTAX  INTEGER { dte(1), dce(2), auto(3) }
            ACCESS  read-write
            STATUS  mandatory
            DESCRIPTION
                "The X.75 layer 2 mode. This value has influence on the
		 HDLC address field (first byte of a HDCL frame). When
		 configured as DTE the address in a command frame is
		 0x01, when configured as DCE it is 0x03. For
		 response frames it is vice versa. When configured as
		 AUTO, layer 2 is set according to the e3IfClock setting.
   		    dte(1)	HDLC address 0x01
		    dce(2)	HDLC address 0x03
		    auto(3)	= DCE if e3IfClock is set to intern,
				= DTE otherwise
		"
	    DEFVAL { auto }
	::= { e3IfEntry 10 }

	e3IfTestPattern OBJECT-TYPE
            SYNTAX  INTEGER { normal(1), ones(2), alt-0-1(3), prbs(4) }
            ACCESS  read-write
            STATUS  mandatory
            DESCRIPTION
                "This variable configures which test pattern should be
		transmitted.
		normal(1)	normal data, no test pattern is transmitted.
		ones(2) 	Transmit unframed all ones.
		alt-0-1(3)	Transmit unframed 101010... pattern in
				E3 mode and transmit AIS in DS3 mode.
		prbs(4)		Transmit PRBS pattern per ITU O.151.
				In E3 mode 2^23 -1 PRBS pattern is used.
				In DS3 mode 2^15 -1 PRBS pattern is used.
		"
	    DEFVAL { normal }
	::= { e3IfEntry 11 }

	e3IfLoopback OBJECT-TYPE
            SYNTAX  INTEGER { noloop(1), remoteloop(2), localloop(3) }
            ACCESS  read-write
            STATUS  mandatory
            DESCRIPTION
                "This variable represents the loopback configuration
		 of the E3/DS3 interface.
		 noloop(1)	No loopback is configured, normal data
				is transmitted and received.
		 remoteloop(2)	The received data is transmitted again.
				Receiving works normal.
		 localloop(3)	The transmitted data is received
		 		Transmitting works normal."
	    DEFVAL { noloop }
	::= { e3IfEntry 12 }

	e3IfBundle OBJECT-TYPE
	    SYNTAX  INTEGER (0..255)
	    ACCESS  read-write
	    STATUS  mandatory
	    DESCRIPTION
		"Index of the bundle to aggregate the interface and 
		 channels of other interfaces
		 to one interface."
	    DEFVAL { 0 }
	::= { e3IfEntry 14 }

	e3IfCableLength OBJECT-TYPE
            SYNTAX  INTEGER { short(1), long(2) }
            ACCESS  read-write
            STATUS  mandatory
            DESCRIPTION
                "'short' should be used for a cable lenght less then 225 feet.
		'long' should be used otherwise. With 'short' the Tx signal is 
		preattenutated similar to the attenuation of 225 feet 
		coaxial cable. The setting has no effect in E3 mode"
	    DEFVAL { short }
	::= { e3IfEntry 15 }

	e3IfCRCMode OBJECT-TYPE
	    SYNTAX  INTEGER { crc16(1), crc32(2) }
	    ACCESS  read-write
	    STATUS  mandatory
	    DESCRIPTION
		"The type of CRC checksum of the HDLC frames.
		crc16(1)	16 Bit CRC 
		crc32(2)	32 Bit CRC"
	    DEFVAL { crc16 }
	::= { e3IfEntry 16 }


	-- status information

	e3IfL1State OBJECT-TYPE
            SYNTAX  INTEGER { down(1), up(2), prbs(3), nolicense(4) }
            ACCESS  read-only
            STATUS  mandatory
            DESCRIPTION
                "The e3 physical layer state
 		  down(1)	physical layer is inactive
                  up(2)		physical layer is active
                  prbs(3)	physical layer is active, a PRBS signal
				is detected
		  nolicense(4)  a license must be configured to activate
				the interface."

	::= { e3IfEntry 19 }

	e3IfRxPackets OBJECT-TYPE
            SYNTAX  Counter
            ACCESS  read-only
            STATUS  mandatory
            DESCRIPTION
                "Count of received valid HDLC Frames."
	::= { e3IfEntry 20 }

	e3IfRxOctets OBJECT-TYPE
            SYNTAX  Counter
            ACCESS  read-only
            STATUS  mandatory
            DESCRIPTION
		"Count of received bytes."
	::= { e3IfEntry 21 }

	e3IfTxPackets OBJECT-TYPE
            SYNTAX  Counter
            ACCESS  read-only
            STATUS  mandatory
            DESCRIPTION
                "Count of transmitted valid HDLC Frames."
	::= { e3IfEntry 22 }

	e3IfTxOctets OBJECT-TYPE
            SYNTAX  Counter
            ACCESS  read-only
            STATUS  mandatory
            DESCRIPTION
		"Count of transmitted bytes."
	::= { e3IfEntry 23 }

	e3IfRxResets OBJECT-TYPE
            SYNTAX  Counter
            ACCESS  read-only
            STATUS  mandatory
            DESCRIPTION
		"Count of receiver resets. Under rare circumstances it
		might be necessary to reset the receiver to work
		properly." 
	::= { e3IfEntry 24 }

	e3IfRxAborts OBJECT-TYPE
            SYNTAX  Counter
            ACCESS  read-only
            STATUS  mandatory
            DESCRIPTION
		"Count of receiver aborts. The sender of a frame can
		indicate a frame as aborted with a special Abort
		sequence." 
	::= { e3IfEntry 25 }

	e3IfRxOverruns OBJECT-TYPE
            SYNTAX  Counter
            ACCESS  read-only
            STATUS  mandatory
            DESCRIPTION
		"Count of receiver overruns. If the e3 port is unable
		to grant sufficiently soon/often the bus, the
		RxFIFO may fill up. This leads to loss of data." 
	::= { e3IfEntry 26 }

	e3IfRxCRCErrors OBJECT-TYPE
            SYNTAX  Counter
            ACCESS  read-only
            STATUS  mandatory
            DESCRIPTION
		"Count of corrupted frames. Errors due to interference
		on the e3 cable."
	::= { e3IfEntry 27 }

	e3IfRxGiantFrames OBJECT-TYPE
            SYNTAX  Counter
            ACCESS  read-only
            STATUS  mandatory
            DESCRIPTION
		"Count of received frames with illegal framesize. This
 		 can occur if a frame delimiter is destroyed." 
	::= { e3IfEntry 28 }

	e3IfTxResets OBJECT-TYPE
            SYNTAX  Counter
            ACCESS  read-only
            STATUS  mandatory
            DESCRIPTION
		"Count of transmitter resets. Under rare circumstances
		it might be necessary to reset the transmitter to work
		properly." 
	::= { e3IfEntry 29 }

	e3IfTxAborts OBJECT-TYPE
            SYNTAX  Counter
            ACCESS  read-only
            STATUS  mandatory
            DESCRIPTION
		"Count of transmitter aborts. While sending a frame it
		might be necessary to indicate this frame as aborted. In
		this case the receiver regards this frame as illegal." 
	::= { e3IfEntry 30 }

	e3IfTxUnderruns OBJECT-TYPE
            SYNTAX  Counter
            ACCESS  read-only
            STATUS  mandatory
            DESCRIPTION
		"Count of transmitter underruns. The e3 data for the
		e3 port is supplied too slowly." 
	::= { e3IfEntry 31 }

	e3IfTxGiantFrames OBJECT-TYPE
            SYNTAX  Counter
            ACCESS  read-only
            STATUS  mandatory
            DESCRIPTION
		"Count of transmitted frames with illegal
		framesize. This can occur if an upper module creates
		packets with more than the maximum allowed packet size."
	::= { e3IfEntry 32 }

END

-- This file is corresponding to Release 9.1.10.101 from 2014/08/11 00:00:00


---------------------------------------------------------------------------
-- (C)opyright 2008-2014 bintec-elmeg.com GmbH, all rights reserved
-- $RCSfile: mib-qos,v $
-- $Revision: 1.11 $
-- $Date: 2014-02-07 11:21:02 $
---------------------------------------------------------------------------

BINTEC-QOS-MIB DEFINITIONS ::= BEGIN

IMPORTS
    MODULE-IDENTITY, OBJECT-TYPE, NOTIFICATION-TYPE,
    Integer32, Unsigned32, Counter32, Counter64, IpAddress, TimeTicks,
    mib-2, enterprises
	FROM SNMPv2-SMI

    DisplayString, TimeStamp, PhysAddress
	FROM SNMPv2-TC

    qos, Date, BitValue, HexValue
	FROM BINTEC-MIB

    MODULE-COMPLIANCE, OBJECT-GROUP, NOTIFICATION-GROUP
	FROM SNMPv2-CONF;


---------------------------------------------------------------------------

qosMIB MODULE-IDENTITY
    LAST-UPDATED	"200802260000Z"
    ORGANIZATION	"bintec elmeg GmbH"
    CONTACT-INFO
	    "EMail:	info@bintec-elmeg.com
	     Web:	www.bintec-elmeg.com"
    DESCRIPTION
            "The MIB module for IP QoS entity."
    REVISION		"200802260000Z"
    DESCRIPTION
            "Management Information for QoS Subsystem"
    ::= { qos 250 }

---------------------------------------------------------------------------
-- OID groups & all tables 
---------------------------------------------------------------------------
	-- qosIfTable 				qos 1
	-- qosIfStatTable			qos 2
	-- qosPolicyTable			qos 3
	-- qosPolicyStatTable			qos 4
	-- qosTosStatTable			qos 5
	-- qosMIB				qos 250

---------------------------------------------------------------------------
-- qosIfTable
---------------------------------------------------------------------------

	qosIfTable OBJECT-TYPE
	    SYNTAX	SEQUENCE OF QosIfEntry
	    MAX-ACCESS	not-accessible
	    STATUS	current
	    DESCRIPTION
		"The qosIfTable enables QoS policies on the interface
		 specified by qosIfIndex (interface index).

                 Creating entries: Entries are created by assigning a
                 value to the qosIfIndex object.

                 Deleting entries: Entries are removed by setting an
                 entry's qosIfType object to 'delete'."
	::= { qos 1 }

	qosIfEntry	OBJECT-TYPE
	    SYNTAX	QosIfEntry
	    MAX-ACCESS	not-accessible
	    STATUS	current
	    DESCRIPTION
		""
	    INDEX	{ qosIfIndex }
	::= { qosIfTable 1 }

	QosIfEntry ::=
	    SEQUENCE {
		qosIfIndex				INTEGER,
		qosIfType				INTEGER,
		qosIfMaxTxRate				INTEGER,
		qosIfTxRatePerVoipCall			INTEGER,
		qosIfTxHeaderSize			INTEGER,
		qosIfTxEncapOffset			INTEGER,
		qosIfTxEncapMaxPadding			INTEGER
	    }

	qosIfIndex	OBJECT-TYPE
	    SYNTAX	INTEGER
	    MAX-ACCESS	read-write
	    STATUS	current

	    DESCRIPTION
                "Unique interface index"
	::= { qosIfEntry 1 }

	qosIfType	OBJECT-TYPE
	    SYNTAX	INTEGER { 
		pq(1),
		wrr(2),
		wfq(3),
    --		diff-serv(4),
		disabled(8),
		delete(9)
	    } 
            MAX-ACCESS	read-write
            STATUS	current

            DESCRIPTION
                "This object defines the queueing and scheduling algorithm
		 used on the related interface, possible values:
		 pq(1)		= priority queueing
		 wrr(2)		= weighted round-robin scheduling
		 wfq(3)		= weighted fair queuing scheduling
		 disable(8)	= disable this entry
		 delete(9)	= delete this entry."
            DEFVAL	{ pq }
	::= { qosIfEntry 2 }

	qosIfMaxTxRate	OBJECT-TYPE
	    SYNTAX	INTEGER
            MAX-ACCESS	read-write
            STATUS	current

            DESCRIPTION
                "This object enables traffic shaping on the related interface,
		 if set to zero (0) there is no shaping active. Otherwise this
		 variable defines the maximum amount of bits per second to
		 be transmitted."
            DEFVAL	{ 0 }
	::= { qosIfEntry 3 }

	qosIfTxRatePerVoipCall OBJECT-TYPE
	    SYNTAX	INTEGER
            MAX-ACCESS	read-write
            STATUS	current

            DESCRIPTION
                "Determines the amount of bandwidth (in bits per second)
		 reserved dynamically by the QoS-scheduler for each accounted
		 VoIP call (see qosIfStatCurrVoipCalls) in order to minimize
		 latency / jitter for this type of data."
            DEFVAL	{ 0 }
	::= { qosIfEntry 4 }

-- OID 5 already used as qosIfDescr in another branch

	qosIfTxHeaderSize OBJECT-TYPE
	    SYNTAX	INTEGER (0..100)
            MAX-ACCESS	read-write
            STATUS	current

            DESCRIPTION
                "Number of (lower layer protocol header) bytes per packet
		 to be considered when calculating the bandwidth consumption."
            DEFVAL	{ 0 }
	::= { qosIfEntry 6 }

	qosIfTxEncapOffset OBJECT-TYPE
	    SYNTAX	INTEGER (0..100)
            MAX-ACCESS	read-write
            STATUS	current

            DESCRIPTION
                "Number of protocol header bytes per packet to be
		 considered when calculating the bandwidth consumption."
            DEFVAL	{ 0 }
	::= { qosIfEntry 7 }

	qosIfTxEncapMaxPadding OBJECT-TYPE
	    SYNTAX	INTEGER (0..100)
            MAX-ACCESS	read-write
            STATUS	current

            DESCRIPTION
                "The maximum number of padding bytes per packet to be
		 considered when calculating the bandwidth consumption.
		 Note that the calcluation is done after adding
		 qosIfTxEncapOffset bytes but before adding qosIfTxHeaderSize
		 finally."
            DEFVAL	{ 0 }
	::= { qosIfEntry 8 }


    -- qosIfStatTable

	qosIfStatTable OBJECT-TYPE
	    SYNTAX	SEQUENCE OF QosIfStatEntry
	    MAX-ACCESS	not-accessible
	    STATUS	current
	    DESCRIPTION
		"The qosIfStatTable contains statistical QoS-specific
		 information for the interface specified by qosIfStatIndex
		 (interface index). Only the system can add or delete
                 entries to this table."
	::= { qos 2 }

	qosIfStatEntry	OBJECT-TYPE
	    SYNTAX	QosIfStatEntry
	    MAX-ACCESS	not-accessible
	    STATUS	current
	    DESCRIPTION
		""
	    INDEX   { qosIfStatIndex }
	::= { qosIfStatTable 1 }

	QosIfStatEntry ::=
	    SEQUENCE {
		qosIfStatIndex				INTEGER,
		qosIfStatOutPkts			Counter32,
		qosIfStatPktsQueued			Counter32,
		qosIfStatOctetsQueued			Counter32,
		qosIfStatPktsDropped			Counter32,
		qosIfStatState				INTEGER,
		qosIfStatTxRate				INTEGER,
		qosIfStatCurrVoipCalls			INTEGER,
		qosIfStatHCOutOctets			Counter64,
		qosIfStatHCOctetsDropped		Counter64
	    }

	qosIfStatIndex	OBJECT-TYPE
	    SYNTAX	INTEGER
	    MAX-ACCESS	read-only
	    STATUS	current

	    DESCRIPTION
                "The unique interface index."
	::= { qosIfStatEntry 1 }


	qosIfStatOutPkts OBJECT-TYPE
	    SYNTAX	Counter32
	    MAX-ACCESS	read-only
	    STATUS	current

	    DESCRIPTION
                "The number of packets transmitted on the related interface
		 since its last change to the 'up' state."
	::= { qosIfStatEntry 2 }

-- obsolete qosIfStatOutOctets OBJECT-TYPE ::= { qosIfStatEntry 3 }

-- obsolete qosIfStatInPkts OBJECT-TYPE ::= { qosIfStatEntry 4 }

-- obsolete qosIfStatInOctets OBJECT-TYPE ::= { qosIfStatEntry 5 }

	qosIfStatPktsQueued OBJECT-TYPE
	    SYNTAX	Counter32
	    MAX-ACCESS	read-only
	    STATUS	current

	    DESCRIPTION
                "The number of data packets enqueued and waiting to be sent
		 across the related interface."
	::= { qosIfStatEntry 6 }

	qosIfStatOctetsQueued OBJECT-TYPE
	    SYNTAX	Counter32
	    MAX-ACCESS	read-only
	    STATUS	current

	    DESCRIPTION
                "The amount of data (in octets) enqueued waiting to be sent
		 across the related interface."
	::= { qosIfStatEntry 7 }

	qosIfStatPktsDropped OBJECT-TYPE
	    SYNTAX	Counter32
	    MAX-ACCESS	read-only
	    STATUS	current

	    DESCRIPTION
                "The number of data packets dropped during congestion."
	::= { qosIfStatEntry 8 }

-- obsolete qosIfStatOctetsDropped OBJECT-TYPE ::= { qosIfStatEntry 9 }

	qosIfStatState	OBJECT-TYPE
	    SYNTAX	INTEGER { 
		running(1),
		reset(2),
		resetall(3)
	    } 
            MAX-ACCESS	read-write
            STATUS	current

	    DESCRIPTION
		"This object allows statistics to be reinitialized.

		 Possible values:
		 running(1) 	= no reset of statistics
		 reset(2)	= reset all counters in this entry except
				  counters for queued packets and octets.
		 resetall(3)	= perform the same action as reset(2) and
				  additionally perform reset action on
				  associated entries of the qosPolicyStatTable
				  and qosTosStatTable for the same interface.
		
		When the reset action is over, this object is automatically
		restored to its 'running(1)' default state."
            DEFVAL	{ running }
	::= { qosIfStatEntry 10 }

	qosIfStatTxRate	OBJECT-TYPE
	    SYNTAX	INTEGER
	    MAX-ACCESS	read-only
	    STATUS	current

	    DESCRIPTION
                "The upload speed (amount of bits per second) of the
		 associated interface."
	::= { qosIfStatEntry 11 }

	qosIfStatCurrVoipCalls OBJECT-TYPE
	    SYNTAX	INTEGER (0..64)
	    MAX-ACCESS	read-only
	    STATUS	current

	    DESCRIPTION
                "The current number of VoIP Calls routed via the associated
		 interface."
	::= { qosIfStatEntry 12 }

	qosIfStatHCOutOctets OBJECT-TYPE
	    SYNTAX	Counter64
	    MAX-ACCESS	read-only
	    STATUS	current

	    DESCRIPTION
                "The number of octets transmitted on the related interface
		 since its last change to the 'up' state."
	::= { qosIfStatEntry 13 }

	qosIfStatHCOctetsDropped OBJECT-TYPE
	    SYNTAX	Counter64
	    MAX-ACCESS	read-only
	    STATUS	current

	    DESCRIPTION
                "The representation of qosIfStatPktsDropped in octets."
	::= { qosIfStatEntry 14 }


    -- qosPolicyTable

	qosPolicyTable	OBJECT-TYPE
	    SYNTAX	SEQUENCE OF QosPolicyEntry
	    MAX-ACCESS	not-accessible
	    STATUS	current
	    DESCRIPTION
		"The qosPolicyTable enables QoS policies for the packet
		 class specified by qosPolicyIfIndex (interface index),
		 qosPolicyType and qosPolicyClassId.

                 Creating entries: Entries are created by assigning a
                 value to the qosPolicyIfIndex object.

                 Deleting entries: Entries are removed by setting an
                 entry's qosPolicyType object to 'delete'."
	::= { qos 3 }

	qosPolicyEntry	OBJECT-TYPE
	    SYNTAX	QosPolicyEntry
	    MAX-ACCESS	not-accessible
	    STATUS	current
	    DESCRIPTION
		""
	    INDEX   { qosPolicyIfIndex }
	::= { qosPolicyTable 1 }

	QosPolicyEntry ::=
	    SEQUENCE {
		qosPolicyIfIndex			INTEGER,
		qosPolicyType				INTEGER,
		qosPolicyClassId			INTEGER,
		qosPolicyPriority			INTEGER,
		qosPolicyWeight				INTEGER,
    		qosPolicyShaper				INTEGER,
		qosPolicyCongestionAvoidance		INTEGER,
		qosPolicyDropAlgorithm			INTEGER,
		qosPolicyRttMode			INTEGER,
		qosPolicyTxRate				INTEGER,
		qosPolicyTxRateLimitation		INTEGER,
		qosPolicyTxBurstSize			INTEGER,
		qosPolicyLowerThreshold			INTEGER,
		qosPolicyUpperThreshold			INTEGER,
		qosPolicyDescr				DisplayString
	    }

	qosPolicyIfIndex OBJECT-TYPE
	    SYNTAX	INTEGER
	    MAX-ACCESS	read-write
	    STATUS	current

	    DESCRIPTION
                "The unique interface index"
	::= { qosPolicyEntry 1 }

	qosPolicyType	OBJECT-TYPE
	    SYNTAX	INTEGER { 
		class-based(1),
		high-priority(2),
    		default(3),
		delete(4)
	    } 
            MAX-ACCESS	read-write
            STATUS	current

            DESCRIPTION
                "This objects defines in conjunction with ipQoSClassId and
		 qosPolicyClassId the related type of packet classes for
		 this QoS policy, possible values:
		 class-based(1) 	= policy for non-high-priority packets
		 high-priority(2)	= policy for high-priority packets
		 default(3)		= policy for packets not matching
		 			  otherwise."
            DEFVAL	{ class-based }
	::= { qosPolicyEntry 2 }

	qosPolicyClassId OBJECT-TYPE
	    SYNTAX	INTEGER  (1..255)
            MAX-ACCESS	read-write
            STATUS	current

            DESCRIPTION
                "Defines in conjunction with ipQoSClassId and qosPolicyType
		 the QoS policy to be applied on the classified IP traffic."
	::= { qosPolicyEntry 3 }

	qosPolicyPriority OBJECT-TYPE
	    SYNTAX	INTEGER  (0..255)
            MAX-ACCESS	read-write
            STATUS	current

            DESCRIPTION
                "The relative priority for this packet class to be used for
		 the packet scheduling as described via qosIfType."
	::= { qosPolicyEntry 4 }

	qosPolicyWeight	OBJECT-TYPE
	    SYNTAX	INTEGER  (0..255)
            MAX-ACCESS	read-write
            STATUS	current

            DESCRIPTION
                "The relative weight for this packet class to be used for
		 the packet scheduling as described via qosIfType."
            DEFVAL	{ 1 }
	::= { qosPolicyEntry 5 }

	qosPolicyShaper	OBJECT-TYPE
	    SYNTAX	INTEGER {
		none(1),
		token-bucket(2)
  --		leaky-bucket(3)
	    } 
	    MAX-ACCESS	read-write
	    STATUS	current

	    DESCRIPTION
	        "This objects describes the traffic-shaping algorithm to be
		 used in order to limit the bandwidth for the related packet
		 class, possible values:
		 none(1) 		= no shaping defined
		 token-bucket(2) 	= token-bucket traffic shaper."
	    DEFVAL	{ token-bucket }
	::= { qosPolicyEntry 6 }

	qosPolicyCongestionAvoidance OBJECT-TYPE
	    SYNTAX	INTEGER { 
		none(1),
    		weighted-random(2)
	    } 
            MAX-ACCESS	read-write
            STATUS	current

            DESCRIPTION
                "This objects defines a packet dropping algorithm to use if
		 more than qosPolicyLowerThreshold octets are enqueued."
            DEFVAL	{ none }
	::= { qosPolicyEntry 7 }

-- obsolete qosPolicyExceedAction OBJECT-TYPE ::= { qosPolicyEntry 8 }

	qosPolicyDropAlgorithm OBJECT-TYPE
	    SYNTAX	INTEGER { 
    		tail-drop(1),
    		head-drop(2),
    		random-drop(3)
	    } 
            MAX-ACCESS	read-write
            STATUS	current

            DESCRIPTION
                "This objects defines the packet dropping algorithm to apply
		 if more than qosPolicyUpperThreshold octets are currently
		 enqueued, possible values:
		 tail-drop(1) 	= drop all newly arriving packets
		 head-drop(2)   = drop packets at the queue head
			 	  enqueue newly arriving packets
		 random-drop(3) = drop arriving or enqueued packets
				  randomly."
            DEFVAL	{ tail-drop }
	::= { qosPolicyEntry 9 }

        qosPolicyRttMode OBJECT-TYPE
            SYNTAX      INTEGER {
                enabled(1),
                disabled(2)
            }
            MAX-ACCESS  read-write
            STATUS      current

            DESCRIPTION
                "This objects defines whether real-time transmission is enabled
                 for this queue or not, possible values:
                 enabled(1)     = RTT is enabled
                 disabled(2)    = RTT is disabled."
            DEFVAL      { disabled }
        ::= { qosPolicyEntry 10 }


-- obsolete qosPolicyTxMinRate OBJECT-TYPE ::= { qosPolicyEntry 16 }

	qosPolicyTxRate	OBJECT-TYPE
	    SYNTAX	INTEGER
            MAX-ACCESS	read-write
            STATUS	current

            DESCRIPTION
                "This object enables bandwidth limitation for the related
		 class, if set to zero (0) there is no limitation policy.
		 Otherwise this variable defines the maximum amount of bits
		 per second to be send."
            DEFVAL	{ 0 }
	::= { qosPolicyEntry 17 }

	qosPolicyTxRateLimitation OBJECT-TYPE
	    SYNTAX	INTEGER {
    		not-bounded(1),
    		bounded(2)
	    } 
            MAX-ACCESS	read-write
            STATUS	current

            DESCRIPTION
                "This objects determines the policy for the related class if
		 the transmission rate limit defined by qosPolicyTxRate is
		 reached. When set to not-bounded(1) allocation of remaining
		 bandwidth not consumed by other classes is allowed. When set
		 to bounded(2), qosPolicyTxRate is strict limitation for the
		 long-term bandwidth consumption."
            DEFVAL	{ not-bounded }
	::= { qosPolicyEntry 18 }

	qosPolicyTxBurstSize OBJECT-TYPE
	    SYNTAX	INTEGER
            MAX-ACCESS	read-write
            STATUS	current

            DESCRIPTION
                "The maximum number of octets in a single transmission burst."
            DEFVAL	{ 0 }
	::= { qosPolicyEntry 19 }

	qosPolicyLowerThreshold OBJECT-TYPE
	    SYNTAX	INTEGER  (0..262143)
            MAX-ACCESS	read-write
            STATUS	current

            DESCRIPTION
                "This variable defines the lower or minimum queue depth
		 threshold for packet dropping algorithm used for congestion
		 avoidance (see qosPolicyCongestionAvoidance)."
            DEFVAL	{ 0 }
	::= { qosPolicyEntry 20 }

	qosPolicyUpperThreshold OBJECT-TYPE
	    SYNTAX	INTEGER  (0..262143)
            MAX-ACCESS	read-write
            STATUS	current

            DESCRIPTION
                "This variable defines the upper or maximum queue depth
		 threshold at which - depending on qosPolicyDropAlgorithm -
		 all newly arriving or packets enqueued former will be
		 dropped."
            DEFVAL	{ 16384 }
	::= { qosPolicyEntry 21 }

	qosPolicyDescr OBJECT-TYPE
	    SYNTAX	DisplayString (SIZE (0..255))
            MAX-ACCESS	read-write
            STATUS	current

            DESCRIPTION
                "A textual string describing this QoS policy."
	::= { qosPolicyEntry 22 }


    -- qosPolicyStatTable

	qosPolicyStatTable OBJECT-TYPE
	    SYNTAX	SEQUENCE OF QosPolicyStatEntry
	    MAX-ACCESS	not-accessible
	    STATUS	current
	    DESCRIPTION
		"The qosPolicyStatTable contains statistical QoS-specific
		 information for the policy specified by qosPolicyStatIfIndex
		 (interface index), qosPolicyStatType and qosPolicyStatClassId.
		 Only the system can add or delete entries to this table."
	::= { qos 4 }

	qosPolicyStatEntry OBJECT-TYPE
	    SYNTAX	QosPolicyStatEntry
	    MAX-ACCESS	not-accessible
	    STATUS	current
	    DESCRIPTION
		""
	    INDEX	{ qosPolicyStatIfIndex }
	::= { qosPolicyStatTable 1 }

	QosPolicyStatEntry ::=
	    SEQUENCE {
		qosPolicyStatIfIndex			INTEGER,
		qosPolicyStatType			INTEGER,
		qosPolicyStatClassId			INTEGER,
		qosPolicyStatOutPkts			Counter32,
		qosPolicyStatPktsQueued			Counter32,
		qosPolicyStatOctetsQueued		Counter32,
		qosPolicyStatPktsDropped		Counter32,
		qosPolicyStatState			INTEGER,
		qosPolicyStatThroughput			INTEGER,
		qosPolicyStatHCOutOctets		Counter64,
		qosPolicyStatHCOctetsDropped		Counter64,
		qosPolicyStatRttRate			INTEGER,
		qosPolicyStatDescr			DisplayString
	    }

	qosPolicyStatIfIndex OBJECT-TYPE
	    SYNTAX	INTEGER
	    MAX-ACCESS	read-only
	    STATUS	current

	    DESCRIPTION
                "The unique interface index"
	::= { qosPolicyStatEntry 1 }

	qosPolicyStatType OBJECT-TYPE
	    SYNTAX	INTEGER { 
		class-based(1),
		high-priority(2),
    		default(3)
	    } 
            MAX-ACCESS	read-only
            STATUS	current

            DESCRIPTION
                "The related type of packet classes for this QoS policy
		 (see qosPolicyType for further explanation)."
            DEFVAL	{ class-based }
	::= { qosPolicyStatEntry 2 }

	qosPolicyStatClassId OBJECT-TYPE
	    SYNTAX	INTEGER
	    MAX-ACCESS	read-only
	    STATUS	current

	    DESCRIPTION
                "Unique packet class ID"
	::= { qosPolicyStatEntry 3 }

	qosPolicyStatOutPkts OBJECT-TYPE
	    SYNTAX	Counter32
	    MAX-ACCESS	read-only
	    STATUS	current

	    DESCRIPTION
                "The number of packets sent belonging to the related
		 packet class."
	::= { qosPolicyStatEntry 4 }

-- obsolete qosPolicyStatOutOctets OBJECT-TYPE ::= { qosPolicyStatEntry 5 }

-- obsolete qosPolicyStatInPkts OBJECT-TYPE ::= { qosPolicyStatEntry 6 }

-- obsolete qosPolicyStatInOctets OBJECT-TYPE ::= { qosPolicyStatEntry 7 }

	qosPolicyStatPktsQueued OBJECT-TYPE
	    SYNTAX	Counter32
	    MAX-ACCESS	read-only
	    STATUS	current

	    DESCRIPTION
                "The number of data packets of the related class enqueued
		 and waiting to be sent."
	::= { qosPolicyStatEntry 8 }

	qosPolicyStatOctetsQueued OBJECT-TYPE
	    SYNTAX	Counter32
	    MAX-ACCESS	read-only
	    STATUS	current

	    DESCRIPTION
                "The representation of qosPolicyStatPktsQueued in octets."
	::= { qosPolicyStatEntry 9 }

	qosPolicyStatPktsDropped OBJECT-TYPE
	    SYNTAX	Counter32
	    MAX-ACCESS	read-only
	    STATUS	current

	    DESCRIPTION
                "The number of data packets of the related class dropped
		 during congestion."
	::= { qosPolicyStatEntry 10 }

-- obsolete qosPolicyStatOctetsDropped OBJECT-TYPE ::= { qosPolicyStatEntry 11 }

-- obsolete qosPolicyStatQlen OBJECT-TYPE ::= { qosPolicyStatEntry 12 }

-- obsolete qosPolicyStatMaxQlen OBJECT-TYPE ::= { qosPolicyStatEntry 13 }

-- obsolete qosPolicyStatAvgdQlen OBJECT-TYPE ::= { qosPolicyStatEntry 14 }

	qosPolicyStatState OBJECT-TYPE
	    SYNTAX	INTEGER { 
		running(1),
		reset(2)
	    } 
            MAX-ACCESS	read-write
            STATUS	current

	    DESCRIPTION
		"This object allows statistics to be reinitialized.

		 Possible values:
		 running(1) 	= no reset of statistics
		 reset(2)	= reset all counters in this entry except
				  counters for queued packets and octets.
		
		When the reset action is over, this object is automatically
		restored to its 'running(1)' default state."
            DEFVAL	{ running }
	::= { qosPolicyStatEntry 15 }

	qosPolicyStatThroughput OBJECT-TYPE
	    SYNTAX	INTEGER
            MAX-ACCESS	read-only
            STATUS	current

	    DESCRIPTION
		"The actual amout of bits transmitted per second."
            DEFVAL	{ 0 }
	::= { qosPolicyStatEntry 16 }

	qosPolicyStatHCOutOctets OBJECT-TYPE
	    SYNTAX	Counter64
	    MAX-ACCESS	read-only
	    STATUS	current

	    DESCRIPTION
                "The representation of qosPolicyStatOutPkts in octets."
	::= { qosPolicyStatEntry 17 }

	qosPolicyStatHCOctetsDropped OBJECT-TYPE
	    SYNTAX	Counter64
	    MAX-ACCESS	read-only
	    STATUS	current

	    DESCRIPTION
                "The representation of qosPolicyStatPktsDropped in octets"
	::= { qosPolicyStatEntry 18 }

	qosPolicyStatRttRate OBJECT-TYPE
	    SYNTAX	INTEGER
	    UNITS	"bps"
            MAX-ACCESS	read-only
            STATUS	current

	    DESCRIPTION
		"The current RTT traffic rate (in bits per second)
		 for this queue in case of activated real-time mode."
            DEFVAL	{ 0 }
	::= { qosPolicyStatEntry 19 }

	qosPolicyStatDescr OBJECT-TYPE
	    SYNTAX	DisplayString (SIZE (0..255))
            MAX-ACCESS	read-only
            STATUS	current

            DESCRIPTION
                "A textual string describing this QoS policy, copied from
		 associated qosPolicyTable entry."
	::= { qosPolicyStatEntry 20 }


    -- qosTosStatTable

	qosTosStatTable	OBJECT-TYPE
	    SYNTAX	SEQUENCE OF QosTosStatEntry
	    MAX-ACCESS	not-accessible
	    STATUS	current
	    DESCRIPTION
		"The qosTosStatTable contains statistical QoS-specific
		 information by qosTosStatTos (index) for each interface 
		 specified by qosTosStatIfIndex (interface index).
		 Only the system can add or delete entries to this table."
	::= { qos 5 }

	qosTosStatEntry	OBJECT-TYPE
	    SYNTAX	QosTosStatEntry
	    MAX-ACCESS	not-accessible
	    STATUS	current
	    DESCRIPTION
		""
	    INDEX	{ qosTosStatIfIndex, qosTosStatTos }
	::= { qosTosStatTable 1 }

	QosTosStatEntry ::=
	    SEQUENCE {
		qosTosStatIfIndex		INTEGER,
		qosTosStatTos			INTEGER,
		qosTosStatOutPkts		Counter32,
		qosTosStatInPkts		Counter32,
		qosTosStatPktsDropped		Counter32,
		qosTosStatState			INTEGER,
		qosTosStatHCOutOctets		Counter64,
  		qosTosStatHCInOctets		Counter64,
		qosTosStatHCOctetsDropped	Counter64
	    }

	qosTosStatIfIndex OBJECT-TYPE
	    SYNTAX	INTEGER
	    MAX-ACCESS	read-only
	    STATUS	current

	    DESCRIPTION
		"The unique interface index for which statistics are managed."
	::= { qosTosStatEntry 1 }

	qosTosStatTos	OBJECT-TYPE
	    SYNTAX	INTEGER (0..255) 
	    MAX-ACCESS	read-only
	    STATUS	current

	    DESCRIPTION
		"The TOS value for which statistics are managed."
	::= { qosTosStatEntry 2 }

	qosTosStatOutPkts OBJECT-TYPE
	    SYNTAX	Counter32
	    MAX-ACCESS	read-only
	    STATUS	current

	    DESCRIPTION
		"The number of packets sent with a TOS set to qosTosStatTos 
		on the qosTosStatIfIndex interface."
	::= { qosTosStatEntry 3 }

-- obsolete qosTosStatOutOctets OBJECT-TYPE ::= { qosTosStatEntry 4 }

  	qosTosStatInPkts OBJECT-TYPE
  	    SYNTAX	Counter32
  	    MAX-ACCESS	read-only
  	    STATUS	current
  
  	    DESCRIPTION
		"The number of packets received with a TOS set to
		qosTosStatTos on the qosTosStatIfIndex interface."
  	::= { qosTosStatEntry 5 }
  
-- obsolete qosTosStatInOctets OBJECT-TYPE ::= { qosTosStatEntry 6 }

	qosTosStatPktsDropped OBJECT-TYPE
	    SYNTAX	Counter32
	    MAX-ACCESS	read-only
	    STATUS	current

	    DESCRIPTION
		"The number of outgoing packets dropped with a TOS set to
		qosTosStatTos on the qosTosStatIfIndex interface."
	::= { qosTosStatEntry 7 }

-- obsolete qosTosStatOctetsDropped OBJECT-TYPE ::= { qosTosStatEntry 8 }

	qosTosStatState	OBJECT-TYPE
	    SYNTAX	INTEGER { 
		running(1),
		reset(2)
	    } 
            MAX-ACCESS	read-write
            STATUS	current

	    DESCRIPTION
		"This object allows statistics to be reinitialized.

		 Possible values:
		 running(1) 	= no reset of statistics
		 reset(2)	= reset all counters in this entry.
		
		When the reset action is over, this object is automatically
		restored to its 'running(1)' default state."
            DEFVAL	{ running }
	::= { qosTosStatEntry 9 }

	qosTosStatHCOutOctets OBJECT-TYPE
	    SYNTAX	Counter64
	    MAX-ACCESS	read-only
	    STATUS	current

	    DESCRIPTION
		"The number of octets sent in packets with a TOS set to
		qosTosStatTos on the qosTosStatIfIndex interface."
	::= { qosTosStatEntry 10 }

  	qosTosStatHCInOctets OBJECT-TYPE
  	    SYNTAX	Counter64
  	    MAX-ACCESS	read-only
  	    STATUS	current
  
  	    DESCRIPTION
		"The number of octets received in packets with a TOS set to
		qosTosStatTos on the qosTosStatIfIndex interface."
  	::= { qosTosStatEntry 11 }

	qosTosStatHCOctetsDropped OBJECT-TYPE
	    SYNTAX	Counter64
	    MAX-ACCESS	read-only
	    STATUS	current

	    DESCRIPTION
		"The number of octets in outgoing packets dropped with a TOS
		set to qosTosStatTos on the qosTosStatIfIndex interface."
	::= { qosTosStatEntry 12 }

---------------------------------------------------------------------------
END

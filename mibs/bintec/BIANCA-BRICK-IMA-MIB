-- This file is corresponding to Release 9.1.10.101 from 2014/08/11 00:00:00


-- (C)opyright 1991-2014 bintec elmeg GmbH, All Rights Reserved
-- extracted from the IMA Specification V1.1 AF-PHY-0086.001 of the 
-- ATM Forum
-- $RCSfile: mib-ima,v $
-- $Revision: 1.7 $

BIANCA-BRICK-IMA-MIB DEFINITIONS ::= BEGIN

        IMPORTS
	    Integer32 FROM SNMPv2-SMI
            IpAddress, Counter, Gauge, TimeTicks, enterprises
                FROM RFC1155-SMI

            DisplayString
                FROM RFC1158-MIB
 
	    PhysAddress 
		FROM RFC1213-MIB

            OBJECT-TYPE
                FROM RFC-1212

	    ima
		FROM BINTEC-MIB;

    ImaGroupSymmetry ::= TEXTUAL-CONVENTION
	  STATUS      current
	  DESCRIPTION
	    "The group symmetry mode adjusted during the group start-up."
	  REFERENCE
	    "ATM Forum IMA v1.1, Section 5.2.2.7 on page 35"
	  SYNTAX      INTEGER {
	    symmetricOperation(1),
	    asymmetricOperation(2),
	    asymmetricConfiguration(3) }

    ImaFrameLength ::= TEXTUAL-CONVENTION
	  STATUS      current
	  DESCRIPTION
	    "Length of the IMA frames."
	  REFERENCE
	    "ATM Forum IMA v1.1, Section 5.2.2.4.2 on page 34"
	  SYNTAX       INTEGER {
	    m32(32),
	    m64(64),
	    m128(128),
	    m256(256) }

    MilliSeconds ::= TEXTUAL-CONVENTION
	  STATUS      current
	  DESCRIPTION
	    "Time in milliseconds"
	  SYNTAX      Integer32

    imaGroupTable OBJECT-TYPE
	  SYNTAX      SEQUENCE OF ImaGroupEntry
	  MAX-ACCESS not-accessible
	   STATUS      current
	   DESCRIPTION
	     "The IMA Group Configuration table."
	   ::= { ima 1 }

    imaGroupEntry OBJECT-TYPE
	  SYNTAX      ImaGroupEntry
	  MAX-ACCESS not-accessible
	  STATUS      current
	  DESCRIPTION
	    "An entry in the IMA Group table."
	  INDEX       { imaGroupIndex }
	  ::= { imaGroupTable 1 }


    ImaGroupEntry ::= SEQUENCE {
	  imaGroupIndex               INTEGER (1..2147483647),
	  imaGroupSymmetry            ImaGroupSymmetry,
	  imaGroupMinNumTxLinks       INTEGER (1..32),
	  imaGroupMinNumRxLinks       INTEGER (1..32),
	  imaGroupTxFrameLength       ImaFrameLength,
	  imaGroupDiffDelayMax        MilliSeconds,
	  imaGroupAlphaValue          INTEGER (1..2),
	  imaGroupBetaValue           INTEGER (1..5),
	  imaGroupGammaValue          INTEGER (1..5),
	  imaGroupErrorsLinkDown      INTEGER (0..100000),
	  imaGroupErrorIntervalLinkDown INTEGER (15..3600),
	  imaGroupErrorsLinkUp        INTEGER (0..100000),
	  imaGroupErrorIntervalLinkUp INTEGER (15..3600),
	  imaGroupMinLinkDownTime     INTEGER (0..3600)}

    imaGroupIndex OBJECT-TYPE
	  SYNTAX      INTEGER (1..2147483647)
	  MAX-ACCESS read-only
	  STATUS      current
	  DESCRIPTION
	    "A unique value for the IMA Group."
	  DEFVAL { 1 }
	  ::= { imaGroupEntry 1 }

    imaGroupSymmetry OBJECT-TYPE
	  SYNTAX      ImaGroupSymmetry
	  MAX-ACCESS read-create
	  STATUS      current
	  DESCRIPTION
	    "Symmetry of the IMA group."
	  REFERENCE
	    "ATM Forum IMA v1.1, Section 5.2.2.7 on page 35"
	  DEFVAL { symmetricOperation }
	  ::= { imaGroupEntry 7 }

    imaGroupMinNumTxLinks OBJECT-TYPE
	  SYNTAX      INTEGER (1..32)
	  MAX-ACCESS read-create
	  STATUS      current
	  DESCRIPTION
	    "Minimum number of transmit links required to be Active for
	    the IMA group to be in the Operational state."
	  REFERENCE
	    "ATM Forum IMA v1.1, Section 10.2.1.1 on page 55"
	  DEFVAL { 1 }
	  ::= { imaGroupEntry 8 }

    imaGroupMinNumRxLinks OBJECT-TYPE
	  SYNTAX      INTEGER (1..32)
	  MAX-ACCESS read-create
	  STATUS      current
	  DESCRIPTION
	      "Minimum number of receive links required to be Active for
	      the IMA group to be in the Operational state."
	  REFERENCE
	      "ATM Forum IMA v1.1, Section 10.2.1.1 on page 55"
	  DEFVAL { 1 }
	  ::= { imaGroupEntry 9 }

    imaGroupTxFrameLength OBJECT-TYPE
	  SYNTAX      ImaFrameLength
	  MAX-ACCESS read-create
	  STATUS      current
	  DESCRIPTION
	    "The frame length to be used by the IMA group in the transmit
	    direction. Can only be set when the IMA group is startup."
	  REFERENCE
	    "ATM Forum IMA v1.1, Section 5.2.2.4.2 on page 34"
	  DEFVAL { m128 }
	  ::= { imaGroupEntry 17 }

    imaGroupDiffDelayMax OBJECT-TYPE
	  SYNTAX      MilliSeconds
	  MAX-ACCESS read-create
	  STATUS      current
	  DESCRIPTION
	    "The maximum number of milliseconds of differential delay among
	    the links that will be tolerated on this interface."
	  REFERENCE
	    "ATM Forum IMA v1.1, Section 9.2 on page 45"
	  DEFVAL { 25 }
	  ::= { imaGroupEntry 19 }

    imaGroupAlphaValue OBJECT-TYPE
	  SYNTAX       INTEGER (1..2)
	  MAX-ACCESS read-create
	  STATUS       current
	  DESCRIPTION
	    "This indicates the 'alpha' value used to specify the number
	    of consecutive invalid ICP cells to be detected before moving
	    to the IMA Hunt state from the IMA Sync state."
	  REFERENCE
	    "ATM Forum IMA v1.1, Section 11 on page 68"
	  DEFVAL { 2 }
	  ::= { imaGroupEntry 22 }

    imaGroupBetaValue OBJECT-TYPE
	  SYNTAX       INTEGER (1..5)
	  MAX-ACCESS read-create
	  STATUS       current
	  DESCRIPTION
	    "This indicates the 'beta' value used to specify the number
	    of consecutive errored ICP cells to be detected before moving
	    to the IMA Hunt state from the IMA Sync state."
	  REFERENCE
	    "ATM Forum IMA v1.1, Section 11 on page 68"
	  DEFVAL { 2 }
	  ::= { imaGroupEntry 23 }

    imaGroupGammaValue OBJECT-TYPE
	  SYNTAX       INTEGER (1..5)
	  MAX-ACCESS read-create
	  STATUS       current
	  DESCRIPTION
	    "This indicates the 'gamma' value used to specify the number
	    of consecutive valid ICP cells to be detected before moving
	    to the IMA Sync state from the IMA PreSync state."
	  REFERENCE
	    "ATM Forum IMA v1.1, Section 11 on page 68"
	  DEFVAL { 1 }
	  ::= { imaGroupEntry 24 }

    imaGroupErrorsLinkDown OBJECT-TYPE
	  SYNTAX       INTEGER (0..100000)
	  MAX-ACCESS read-create
	  STATUS       current
	  DESCRIPTION
	    "This indicates the threshold of the number of ATM header 
	    errors per 100000 ATM cells, at which a link is inhibited.
	    The number is compared with average value of received 
	    ATM header errors in the last time. The length of the 
	    considered time interval is configured in 
	    imaGroupErrorIntervalLinkDown." 
	  DEFVAL { 10 }
	  ::= { imaGroupEntry 25 }

    imaGroupErrorIntervalLinkDown OBJECT-TYPE
	  SYNTAX       INTEGER (15..3600)
	  MAX-ACCESS read-create
	  STATUS       current
	  DESCRIPTION
	    "This indicates the duration of the measure interval in 
	    seconds for the ATM header error counter. That is used 
	    for calculating an average, which is then compared with the 
	    imaGroupErrorsLinkDown value."
	  DEFVAL { 60 }
	  ::= { imaGroupEntry 26 }

    imaGroupErrorsLinkUp OBJECT-TYPE
	  SYNTAX       INTEGER (0..100000)
	  MAX-ACCESS read-create
	  STATUS       current
	  DESCRIPTION
	    "This indicates the threshold of the number of ATM header 
	    errors per 100000 ATM cells, at which a link is enabled again.
	    The number is compared with average value of received 
	    ATM header errors in the last time. The length of the 
	    considered time interval is configured in 
	    imaGroupErrorIntervalLinkUp." 
	  DEFVAL { 10 }
	  ::= { imaGroupEntry 27 }

    imaGroupErrorIntervalLinkUp OBJECT-TYPE
	  SYNTAX       INTEGER (15..3600)
	  MAX-ACCESS read-create
	  STATUS       current
	  DESCRIPTION
	    "This indicates the duration of the measure interval in
	    seconds for the ATM header error counter. That is used 
	    for calculating an average, which is then compared with the 
	    imaGroupErrorsLinkUp value."
	  DEFVAL { 60 }
	  ::= { imaGroupEntry 28 }

    imaGroupMinLinkDownTime OBJECT-TYPE
	  SYNTAX       INTEGER (0..3600)
	  MAX-ACCESS read-create
	  STATUS       current
	  DESCRIPTION
	    "This indicates the minimum waiting time in seconds before 
	    a link can be enabled again, after it has been inhibited."
	  DEFVAL { 1 }
	  ::= { imaGroupEntry 29 }


END

-- This file is corresponding to Release 9.1.10.101 from 2014/08/11 00:00:00


---------------------------------------------------------------------------
-- (C)opyright 2006-2014 bintec elmeg GmbH
-- $RCSfile: mib-mps,v $
-- $Revision: 1.51 $
-- $Date: 2014-06-24 14:17:36 $

FEC-MPS-MIB DEFINITIONS ::= BEGIN

IMPORTS
    MODULE-IDENTITY, OBJECT-TYPE, NOTIFICATION-TYPE,
    Integer32, Unsigned32, Counter32, Counter64, IpAddress, TimeTicks,
    mib-2, enterprises
        FROM SNMPv2-SMI

    InterfaceIndex, InterfaceIndexOrZero
        FROM IF-MIB

    DisplayString, TimeStamp, TruthValue, MacAddress
        FROM SNMPv2-TC

    bibo, Date, BitValue, HexValue
        FROM BINTEC-MIB

    MODULE-COMPLIANCE, OBJECT-GROUP, NOTIFICATION-GROUP
        FROM SNMPv2-CONF;

---------------------------------------------------------------------------
mpsMIB MODULE-IDENTITY
    LAST-UPDATED "201406240000Z"
    ORGANIZATION "bintec elmeg GmbH"
    CONTACT-INFO
            "EMail:   info@bintec-elmeg.com
             Web:     www.bintec-elmeg.com
            "
    DESCRIPTION
            "This MIB file contains administration MIBs for MPS phone subsystem."

    REVISION      "201006100000Z"
    DESCRIPTION
            "Added global voice over IP configuration under OID mpsVoIPConfig." 

    REVISION      "201105200000Z"
    DESCRIPTION
            "Add rerouting application settings." 

    ::= { bibo 53 }

---------------------------------------------------------------------------
-- mps OID groups & all tables
mpsSetup        OBJECT IDENTIFIER ::= { mpsMIB 1 }
                -- mpsSysConfig                         1
                -- mpsSysTimer                          2
                -- mpsSysCharge                         3
                -- not used                             4 //mpsSysCalendarTable
                -- mpsSysUserConfig                     5
mpsNumber       OBJECT IDENTIFIER ::= { mpsMIB 2 }
                -- mpsEmergencyNumberTable              1
                -- mpsDirectCallNumberTable             2
                -- mpsWhitelistNumberTable              3
                -- mpsBlacklistNumberTable              4
                -- mpsSpecialNumberTable                5
                -- mpsSystemNumberTable                 6
mpsCommon       OBJECT IDENTIFIER ::= { mpsMIB 3 }
                -- mpsDeviceTable                       1
                -- mpsDeviceVirtualTable                2
                -- mpsTrunkGroupTable                   3
                -- mpsTrunkGroupVoIPTable               4
                -- mpsTrunkGroupPOTSTable               6
                -- mpsTrunkNumberTable                  7
                -- mpsTrunkNumberUserTable              8
                -- mpsTrunkNumberModeTable              9
                -- mpsTrunkBundleTable                 10
                -- mpsTrunkBundleEntryTable            11
mpsSubscriber   OBJECT IDENTIFIER ::= { mpsMIB 4 }
                -- mpsSubscriberNumberTable                     1
                -- mpsSubscriberNumberSimpleTable               2
                -- not used                                     3
                -- mpsSubscriberNumberCompositePrefixTable      4
                -- mpsCallThroughTable                          5
mpsGroup        OBJECT IDENTIFIER ::= { mpsMIB 5 }
                -- mpsGroupTable                        1
                -- mpsGroupModeTable                    2
                -- mpsGroupModeChainTable               3
                -- mpsGroupActiveTable                  4
                -- mpsGroupUserTable                    5
                -- mpsGroupStatusTable                  6
mpsExtension    OBJECT IDENTIFIER ::= { mpsMIB 6 }
                -- mpsExtensionTable                    1
                -- mpsExtensionAdminTable               2
                -- mpsExtensionUserTable                3
                -- mpsExtensionSourceTable              4
                -- mpsExtensionABTable                  5
                -- mpsExtensionVoIPTable                6
                -- mpsExtensionTrunkRouteTable          7
                -- mpsExtensionTrunkAccessTable         8
                -- mpsExtensionDiversionTable           9
                -- mpsExtensionCAPITable               10
                -- mpsCAPIClientTable                  11
                -- mpsExtensionModeTable               12
                -- mpsClassOfServiceTable              13
                -- mpsUserTable                        14
                -- mpsCoSTrunkRouteTable               15
                -- mpsParallelRingingTable             16
                -- mpsExtensionStatusTable             17
                -- mpsUserUserTable                    18
mpsDoorIntercom OBJECT IDENTIFIER ::= { mpsMIB 7 }
                -- mpsDoorIntercomTable                 1
                -- mpsDoorIntercomSourceTable           2
                -- mpsDoorIntercomUserTable             3
                -- mpsDoorIntercomModeTable             4
                -- mpsDoorIntercomModeChainTable        5
mpsVoIP         OBJECT IDENTIFIER ::= { mpsMIB 8 }
                -- mpsNetworkTable                      1
                -- mpsCodecPropertyTable                2
                -- mpsVoIPConfig                        3
mpsPhonebook    OBJECT IDENTIFIER ::= { mpsMIB 9 }
                -- mpsPhonebookTable                    1
                -- mpsUserPhonebookTable                2
mpsArs          OBJECT IDENTIFIER ::= { mpsMIB 10 }
                -- mpsArsRoutingConfig                  1
                -- mpsArsZoneDetailsTable               2
                -- mpsArsZoneTable                      3
                -- mpsArsRoutingTable                   4
                -- mpsArsRoutingDetailsTable            5
                -- mpsArsCarrierTable                   6
mpsFaxSwitch    OBJECT IDENTIFIER ::= { mpsMIB 11 }
                -- mpsFaxSwitchTable                    1
                -- mpsFaxSwitchModeTable                2
                -- mpsFaxSwitchUserTable                3
mpsCalendar     OBJECT IDENTIFIER ::= { mpsMIB 12 }
                -- mpsCalendarTable                     1
                -- mpsCalSettingTable                   2
                -- mpsCalDetailTable                    3
                -- mpsPublicHolidayTable                4
mpsReRoute      OBJECT IDENTIFIER ::= { mpsMIB 13 }
                -- mpsReRouteTable                      1
                -- not used                             2
                -- mpsAnnDisaTable                      3
                -- mpsWaveFileTable                     4
                -- mpsReRouteApplTable                  5
                -- mpsReRouteApplModeTable              6
mpsTerminal     OBJECT IDENTIFIER ::= { mpsMIB 14 }
                -- mpsTerminalTable                     1
                -- mpsExtensionTerminalTable            2
                -- mpsTerminalStatusTable               3
                -- mpsTerminalCmdTable...               4
mpsHotel        OBJECT IDENTIFIER ::= { mpsMIB 16 }
                -- mpsHotelConfig                       1
                -- mpsHotelWakeUp                       2
                -- mpsHotelTable                        3
mpsCall         OBJECT IDENTIFIER ::= { mpsMIB 17 }
                -- mpsCallTransactionTable              1
mpsAlarm        OBJECT IDENTIFIER ::= { mpsMIB 18 }
                -- mpsSwitchingContactTable             1
                -- mpsAlarmInputTable                   2

---------------------------------------------------------------------------
-- mps types
DirectCallIndex                   ::= INTEGER (1..65535)
DirectCallIndexOrZero             ::= INTEGER (0..65535)
TrunkGroupIndex                   ::= INTEGER (1..65535)
TrunkGroupIndexOrZero             ::= INTEGER (0..65535)
TrunkNumberIndex                  ::= INTEGER (1..65535)
TrunkNumberIndexOrZero            ::= INTEGER (0..65535)
TrunkBundleIndex                  ::= INTEGER (1..65535)
SubscriberNumberIndex             ::= INTEGER
GroupIndex                        ::= INTEGER (1..99)
GroupIndexOrZero                  ::= INTEGER (0..99)
GroupModeIndex                    ::= INTEGER (1..10)
ExtensionIndex                    ::= INTEGER (1..65535)
ExtensionIndexOrZero              ::= INTEGER (0..65535)
CAPIClientIndex                   ::= INTEGER (1..65535)
CAPIClientIndexOrZero             ::= INTEGER (0..65535)
DoorIntercomIndex                 ::= INTEGER (1..10)
DoorIntercomIndexOrZero           ::= INTEGER (0..10)
DoorIntercomModeIndex             ::= INTEGER (1..10)
DoorButtonIndex                   ::= INTEGER (1..4)
NetworkIndex                      ::= INTEGER (1..18)
ZoneIndex                         ::= Unsigned32
RouteIndex                        ::= Unsigned32
CarrierIndex                      ::= Unsigned32
FaxSwitchIndex                    ::= INTEGER (1..65535)
FaxSwitchIndexOrZero              ::= INTEGER (0..65535)
FaxSwitchModeIndex                ::= INTEGER (1..2)
CalendarIndex                     ::= INTEGER (1..65535)
CalendarIndexOrZero               ::= INTEGER (0..65535)
CalSetIndex                       ::= INTEGER (1..65535)
ReRouteIndex                      ::= INTEGER (1..65535)
ReRouteIndexOrZero                ::= INTEGER (0..65535)
ReRouteApplIndex                  ::= INTEGER (1..65535)
ReRouteApplIndexOrZero            ::= INTEGER (0..65535)
CoSIndex                          ::= INTEGER (1..65535)
CoSIndexOrZero                    ::= INTEGER (0..65535)
PickupGroup                       ::= INTEGER (0..99)
FeatureGroup                      ::= INTEGER (0..99)
UserIndex                         ::= INTEGER (1..65535)
UserIndexOrZero                   ::= INTEGER (0..65535)
TerminalIndex                     ::= INTEGER (1..65535)
TerminalIndexOrZero               ::= INTEGER (0..65535)
CodecIndex                        ::= INTEGER (1..65535)
CodecIndexOrZero                  ::= INTEGER (0..65535)
SwitchingContactIndex             ::= INTEGER (1..2)
SwitchingContactIndexOrZero       ::= INTEGER (0..2)
OEMDeviceType                     ::= INTEGER {none(1),
                                               openstage(2),
                                               gigaset(3)
                                              }
---------------------------------------------------------------------------

---------------------------------------------------------------------------
mpsSysConfig OBJECT IDENTIFIER ::= { mpsSetup 1 }

    mpsSysConfigCountry OBJECT-TYPE
        SYNTAX          INTEGER {
                            germany(1),
                            netherlands(2),
                            united-kindom(3),
                            belgium(4),
                            italy(5),
                            denmark(6),
                            spain(7),
                            sweden(8),
                            norway(9),
                            france(10),
                            portugal(11),
                            austria(12),
                            switzerland(13),
                            czech(14),
                            slovenia(15),
                            poland(16),
                            hungary(17),
                            greece(18)
                        }
        MAX-ACCESS      read-write
        STATUS          current
        DESCRIPTION
            "This variable contains the country code settings of the PBX,
             e.g. change CLIP information at calls to exter,
             change impedance settings at internal analogue ports.
             "
        DEFVAL { germany }
        ::= { mpsSysConfig 1 }

    mpsSysConfigSetExchangeDate OBJECT-TYPE
        SYNTAX          INTEGER { no(1), pbx(2), time-server(3) }
        MAX-ACCESS      read-write
        STATUS          obsolete
        DESCRIPTION
            "Accept time and date is off, acceppt from exchange or accept 
             from time server. "
        DEFVAL { pbx }
        ::= { mpsSysConfig 2 }

    mpsSysConfigFacilities OBJECT-TYPE
        SYNTAX          BITS {
                            highRingerFrequency(0),
                            handoverBusyExtension(1),
                            handoverBusyMusicOnHold(2),
                            connExtExt(3)
                        }
        MAX-ACCESS read-write
        STATUS current
        DESCRIPTION
            "System facilities:
		highRingerFrequency:	a/b extension ringing frequency (0=50
		Hz, 1=25 Hz)
		handoverBusyExtension:	This value determines if handover to
					busy extension is possible
		handoverBusyMusicOnHold:This value determines if the caller
					hears tone or MoH
		connExtExt:		Two external subscribers are to be
					connected after hang up.
            "
        ::= { mpsSysConfig 3 }

    mpsSysConfigAreaCode OBJECT-TYPE
        SYNTAX          DisplayString (SIZE(0..10))
        MAX-ACCESS      read-write
        STATUS          current
        DESCRIPTION
            "This variable contains the digits for the area code (national
	     number, e.g. '5171')."
        ::= { mpsSysConfig 4 }

    mpsSysConfigCountryCode OBJECT-TYPE
        SYNTAX          DisplayString (SIZE(0..6))
        MAX-ACCESS      read-write
        STATUS          current
        DESCRIPTION
            "This variable contains the digits for the country code
	     (international number, e.g '49')."
        ::= { mpsSysConfig 5 }

    mpsSysConfigCodeInternationalPrefix OBJECT-TYPE
        SYNTAX          DisplayString (SIZE(0..2))
        MAX-ACCESS      read-write
        STATUS          current
        DESCRIPTION
            "This variable contains the digits for international prefix code."
        ::= { mpsSysConfig 6 }

    mpsSysConfigCodeNationalPrefix OBJECT-TYPE
        SYNTAX          DisplayString (SIZE(0..1))
        MAX-ACCESS      read-write
        STATUS          current
        DESCRIPTION
            "This variable contains the digit for national prefix code."
        ::= { mpsSysConfig 7 }

    mpsSysConfigCityCode OBJECT-TYPE
        SYNTAX          DisplayString (SIZE(0..8))
        MAX-ACCESS      read-write
        STATUS          current
        DESCRIPTION
            "This variable contains the digit for the city code prefix.
		Extension with dial authorisation = 'local' can only dial numbers
		with this prefix."
        ::= { mpsSysConfig 8 }

    mpsSysConfigLanguage OBJECT-TYPE
        SYNTAX          INTEGER {
                            german(1),
                            english(3),
                            italian(5)
                         }
        MAX-ACCESS      read-write
        STATUS          current
        DESCRIPTION
            "This variable contains the language code setting, e.g for system
	     provided menue."
        DEFVAL { german }
        ::= { mpsSysConfig 9 }

    mpsSysConfigDefaultTargetType OBJECT-TYPE
        SYNTAX          INTEGER { group(1), extension(2), none(3) }
        MAX-ACCESS      read-write
        STATUS          current
        DESCRIPTION
            "This variable contains the default target type of system, if no
	     incoming external call distribution match. 'off' means busy
	     signalling to external subscriber."
        DEFVAL { none }
        ::= { mpsSysConfig 10 }

    mpsSysConfigDefaultTargetIndex OBJECT-TYPE
        SYNTAX          INTEGER (0..65535)
        MAX-ACCESS      read-write
        STATUS          current
        DESCRIPTION
            "This variable contains index of the target table or zero (busy
             signalling),
             mpsSysConfigDefaultTargetType=group       : index = mpsGroupIndex.
             mpsSysConfigDefaultTargetType=extension   : index = ExtensionIndex."
        DEFVAL { 0 }
        ::= { mpsSysConfig 11 }

     mpsSysConfigExtMoHVolume OBJECT-TYPE
        SYNTAX          INTEGER (-5..3)
        MAX-ACCESS      read-write
        STATUS          current
        DESCRIPTION
            "This variable contains the volume adjustment level for the external
             MoH played back via the audio-in jack (approximately in 3 dB steps):
             negative values -> attenuate during playback
             0               -> original playback
             positive values -> amplify during playback"
        DEFVAL { 0 }
        ::= { mpsSysConfig 12 }

    mpsSysConfigPreselectionCode OBJECT-TYPE
        SYNTAX          DisplayString (SIZE(0..10))
        MAX-ACCESS      read-write
        STATUS          current
        DESCRIPTION
            "This variable contains the digits for system preselection
             (call-by-call)."
        ::= { mpsSysConfig 13 }

---------------------------------------------------------------------------
mpsSysTimer OBJECT IDENTIFIER ::= { mpsSetup 2 }

    mpsSysTimerCFNR OBJECT-TYPE
        SYNTAX          INTEGER (1..99)
        MAX-ACCESS      read-write
        STATUS          current
        DESCRIPTION
            "This variable contains the length of timer in seconds of call
             forwarding no reply."
        DEFVAL { 15 }
        ::= { mpsSysTimer 1 }

    mpsSysTimerExternalDoorIntercomTimeout OBJECT-TYPE
        SYNTAX          INTEGER {
                            off(1), s60(2), s120(3), s180(4), s240(5), s300(6)
                        }
        UNITS           "s"
        MAX-ACCESS      read-write
        STATUS          current
        DESCRIPTION
            "This variable contains the length of timer in seconds."
        DEFVAL { s180 }
        ::= { mpsSysTimer 2 }

    mpsSysTimerRecallTimeout OBJECT-TYPE
        SYNTAX          INTEGER (10..179)
        UNITS           "s"
        MAX-ACCESS      read-write
        STATUS          current
        DESCRIPTION
            "This variable contains the length of timer in seconds."
        DEFVAL { 30 }
        ::= { mpsSysTimer 3 }

    mpsSysTimerRecallBusyTimeout OBJECT-TYPE
        SYNTAX          INTEGER (10..600)
        UNITS           "s"
        MAX-ACCESS      read-write
        STATUS          current
        DESCRIPTION
            "This variable contains the length of timer in seconds."
        DEFVAL { 30 }
        ::= { mpsSysTimer 4 }

    mpsSysTimerDirectCall OBJECT-TYPE
        SYNTAX          INTEGER (1..30)
        UNITS           "s"
        MAX-ACCESS      read-write
        STATUS          current
        DESCRIPTION
            "This variable contains the length of timer in seconds."
        DEFVAL { 5 }
        ::= { mpsSysTimer 5 }

    mpsSysTimerExternalAlarmCallTimeout OBJECT-TYPE
        SYNTAX          INTEGER {
                            off(1), s60(2), s120(3), s180(4), s240(5), s300(6)
                        }
        MAX-ACCESS      read-write
        STATUS          obsolete
        DESCRIPTION
            "This variable contains the length of timer.

	     For further implementations this global variable (that never
	     shown via GUI until now) is obsolete und swapped to the
	     mpsAlarmInputTable."
        DEFVAL { s180 }
        ::= { mpsSysTimer 6 }

    mpsSysTimerDropCallNoReply OBJECT-TYPE
        SYNTAX          INTEGER (1..120)
        UNITS           "s"
        MAX-ACCESS      read-write
        STATUS          current
        DESCRIPTION
            "This variable contains the length of timer in seconds."
        DEFVAL { 20 }
        ::= { mpsSysTimer 7 }

    mpsSysTimerDTMFAck OBJECT-TYPE
        SYNTAX          INTEGER (5..60)
        UNITS           "s"
        MAX-ACCESS      read-write
        STATUS          current
        DESCRIPTION
            "This variable contains the length of timer in seconds."
        DEFVAL { 20 }
        ::= { mpsSysTimer 8 }

    mpsSysTimerDiallingBreakGSM OBJECT-TYPE
        SYNTAX          INTEGER (0..5)
        UNITS           "s"
        MAX-ACCESS      read-write
        STATUS          current
        DESCRIPTION
            "This variable contains the length of timer in seconds."
        DEFVAL { 2 }
        ::= { mpsSysTimer 9 }

    mpsSysTimerSystemPark OBJECT-TYPE
        SYNTAX          INTEGER (10..600)
        UNITS           "s"
        MAX-ACCESS      read-write
        STATUS          current
        DESCRIPTION
            "This variable contains the length of timer in seconds."
        DEFVAL { 30 }
        ::= { mpsSysTimer 10 }

---------------------------------------------------------------------------
mpsSysCharge OBJECT IDENTIFIER ::= { mpsSetup 3 }

    mpsSysChargeProtocol OBJECT-TYPE
        SYNTAX          INTEGER {
                            keypad-and-functional(1),
                            no-keypad(2),
                            no-functional(3)
                        }
        MAX-ACCESS      read-write
        STATUS          current
        DESCRIPTION
            "This value determine the charging protocol on the internal isdn 
             ports. You have three options here: KEYPAD protocol - Charge data 
             is transferred such that it can be displayed directly by the 
             terminal device.
             Functional protocol - Charge data is transferred with binary 
             encoding and must be decoded by the terminal device. 
             Both - Both of these protocols are recognized (default settings 
             for the PBX system."
        DEFVAL { keypad-and-functional }
        ::= { mpsSysCharge 1 }

    mpsSysChargeFrequency OBJECT-TYPE
        SYNTAX          INTEGER { no(1), f12khz(2), f16khz(3) }
        MAX-ACCESS      read-write
        STATUS          obsolete
        DESCRIPTION
            "This value determine the frequency of the charge pulse for 
             analogue terminals."
        DEFVAL { no }
        ::= { mpsSysCharge 2 }

    mpsSysChargeIncomingCall OBJECT-TYPE
        SYNTAX          TruthValue
        MAX-ACCESS      read-write
        STATUS          obsolete
        DESCRIPTION
            "You can define whether acquisition is to be made for all 
             connection (1), or only when a project number is input (2)."
        DEFVAL { false }
        ::= { mpsSysCharge 3 }

    mpsSysChargeMultiplier OBJECT-TYPE
        SYNTAX          Unsigned32
        MAX-ACCESS      read-write
        STATUS          current
        DESCRIPTION
            "Charge rate multiplier. 
             e.g. 1 Unit = 0,064 -> mpsSysChargeMultiplier = 64,
                           mpsSysChargeExponent = -3.
                  1 Unit = 1,200 -> mpsSysChargeMultiplier = 12,
                           mpsSysChargeExponent = -1"
        DEFVAL { 0 }
        ::= { mpsSysCharge 4 }

    mpsSysChargeExponent OBJECT-TYPE
        SYNTAX          INTEGER (-3..3)
        MAX-ACCESS      read-write
        STATUS          current
        DESCRIPTION
            "Charge rate exponent. 
             e.g. 1 Unit = 0,064 -> mpsSysChargeMultiplier = 64,
                           mpsSysChargeExponent = -3.
                  1 Unit = 1,200 -> mpsSysChargeMultiplier = 12,
                           mpsSysChargeExponent = -1"
        DEFVAL { -3 }
        ::= { mpsSysCharge 5 }

    mpsSysChargeCurrencyName OBJECT-TYPE
        SYNTAX          DisplayString (SIZE(0..3))
        MAX-ACCESS      read-write
        STATUS          current
        DESCRIPTION
            "This currency name will be displayed by the terminal."
        ::= { mpsSysCharge 6 }

    mpsSysChargeExtensionIndex OBJECT-TYPE
        SYNTAX          ExtensionIndexOrZero
        MAX-ACCESS      read-write
        STATUS          obsolete
        DESCRIPTION
            "You can define an extension index at which internal telephone the 
             communication data overflow is to be signaled per uus1 message."
        ::= { mpsSysCharge 7 }

    mpsSysChargeHiddenDigitsCountA OBJECT-TYPE
        SYNTAX          INTEGER (-1..20)
        MAX-ACCESS      read-write
        STATUS          current
        DESCRIPTION
            "You can enter the number of hidden digit positions 
             for incoming calls. The positions (numbers) are 
             concealed from right to left (from the end of the 
             number).
                -1 = hide all
            "
        DEFVAL { 0 }
        ::= { mpsSysCharge 8 }

    mpsSysChargeHiddenDigitsCountB OBJECT-TYPE
        SYNTAX          INTEGER (-1..20)
        MAX-ACCESS      read-write
        STATUS          current
        DESCRIPTION
            "You can enter the number of hidden digit positions 
             for outgoing calls. The positions (numbers) are 
             concealed from right to left (from the end of the 
             number).
                -1 = hide all
            "
        DEFVAL { 0 }
        ::= { mpsSysCharge 9 }

    mpsSysChargeSaveOutgoingCall OBJECT-TYPE
        SYNTAX          INTEGER { never(1), all(2), withProjectCode(3) }
        MAX-ACCESS      read-write
        STATUS          current
        DESCRIPTION
            "System setting for saving call data records for outgoing calls:
             never(1)          : no call data records for outgoing calls saved.
             all(2)            : save call data records for all outgoing calls.
             withProjectCode(3): save call data records for outgoing calls only
             with project codes."
        DEFVAL { never }
        ::= { mpsSysCharge 10 }

    mpsSysChargeSaveIncomingCall OBJECT-TYPE
        SYNTAX          INTEGER { never(1), all(2), withProjectCode(3) }
        MAX-ACCESS      read-write
        STATUS          current
        DESCRIPTION
            "System setting for saving call data records for incoming calls:
             never(1)          : no call data records for incoming calls saved.
             all(2)            : save call data records for all incoming calls.
             withProjectCode(3): save call data records for incoming calls only
             with project codes."
        DEFVAL { never }
        ::= { mpsSysCharge 11 }

    mpsSysChargePrintingHost OBJECT-TYPE
        SYNTAX          DisplayString
        MAX-ACCESS      read-write
        STATUS          current
        DESCRIPTION
            "This variable contains the host name for printing call data record.
             For local printing (serial printer), set to 'localhost'.
             For disable leave string empty."
        ::= { mpsSysCharge 12 }

    mpsSysChargePrintingTcpPort OBJECT-TYPE
        SYNTAX          INTEGER
        MAX-ACCESS      read-write
        STATUS          current
        DESCRIPTION
            "This variable contains the tcp port for printing call data record.
             For local printing (serial printer), set to an arbitrary port
             matching that one in soipConfigTable."
        DEFVAL { 0 }
        ::= { mpsSysCharge 13 }

---------------------------------------------------------------------------
mpsSysCalendarTable OBJECT-TYPE
    SYNTAX      SEQUENCE OF MpsSysCalendarEntry
    MAX-ACCESS  not-accessible
    STATUS      current
    DESCRIPTION
        "This table contains information for each circuit switching time of the
         calendar."
    ::= { mpsSetup 4 }

    mpsSysCalendarEntry OBJECT-TYPE
        SYNTAX          MpsSysCalendarEntry 
        MAX-ACCESS      not-accessible
        STATUS          obsolete
        DESCRIPTION
            ""
        INDEX { mpsSysCalendarIndex, mpsSysCalendarDay, mpsSysCalendarPosition }
        ::= { mpsSysCalendarTable 1 }

    MpsSysCalendarEntry ::=
        SEQUENCE {
            mpsSysCalendarIndex                 INTEGER, 
            mpsSysCalendarDay                   INTEGER, 
            mpsSysCalendarPosition              INTEGER, 
            mpsSysCalendarHour                  INTEGER, 
            mpsSysCalendarMinute                INTEGER, 
            mpsSysCalendarMode                  GroupModeIndex,
            mpsSysCalendarAdminStatus           INTEGER
        }

    mpsSysCalendarIndex OBJECT-TYPE
        SYNTAX          INTEGER
        MAX-ACCESS      read-write
        STATUS          obsolete
        DESCRIPTION
            "A unique value for each calendar."
        ::= { mpsSysCalendarEntry 1 }

    mpsSysCalendarDay OBJECT-TYPE
        SYNTAX          INTEGER {
                            monday(1),
                            tuesday(2),
                            wednesday(3),
                            thursday(4),
                            friday(5),
                            saturday(6),
                            sunday(7)
                        }
        MAX-ACCESS      read-write
        STATUS          obsolete
        DESCRIPTION
            "A unique value for each day of the calendar."
        DEFVAL { monday }
        ::= { mpsSysCalendarEntry 2 }

    mpsSysCalendarPosition OBJECT-TYPE
        SYNTAX          INTEGER
        MAX-ACCESS      read-write
        STATUS          obsolete
        DESCRIPTION
            "A unique value for each calendar, day and position."
        ::= { mpsSysCalendarEntry 3 }

    mpsSysCalendarHour OBJECT-TYPE
        SYNTAX          INTEGER
        MAX-ACCESS      read-write
        STATUS          obsolete
        DESCRIPTION
            "This variable contains the hour for the switching time."
        ::= { mpsSysCalendarEntry 4 }

    mpsSysCalendarMinute OBJECT-TYPE
        SYNTAX          INTEGER
        MAX-ACCESS      read-write
        STATUS          obsolete
        DESCRIPTION
            "This variable contains the minutes for the switching time."
        ::= { mpsSysCalendarEntry 5 }

    mpsSysCalendarMode OBJECT-TYPE
        SYNTAX          GroupModeIndex
        MAX-ACCESS      read-write
        STATUS          obsolete
        DESCRIPTION
            "This variable contains the mode, to which the calendar will be 
             switched."
        ::= { mpsSysCalendarEntry 6 }

    mpsSysCalendarAdminStatus OBJECT-TYPE
        SYNTAX          INTEGER {
                            enable(1),
                            delete(2)
                        }
        MAX-ACCESS      read-write
        STATUS          obsolete
        DESCRIPTION
            "Just for MIB entry deletion."
        DEFVAL { enable }
        ::= { mpsSysCalendarEntry 7 }

---------------------------------------------------------------------------
mpsSysUserConfig OBJECT IDENTIFIER ::= { mpsSetup 5 }

    mpsSysUserConfigPIN OBJECT-TYPE
        SYNTAX          DisplayString (SIZE(4))
        MAX-ACCESS      read-write
        STATUS          current
        DESCRIPTION
            "This variable contains the system PIN code for configuration.
             'none' = inactive (can not be dialed)."
        DEFVAL { "none" }
        ::= { mpsSysUserConfig 1 }

    mpsSysUserConfigExternPIN OBJECT-TYPE
        SYNTAX          DisplayString (SIZE(6))
        MAX-ACCESS      read-write
        STATUS          current
        DESCRIPTION
            "This variable contains the system PIN code for remote control."
        DEFVAL { "000000" }
        ::= { mpsSysUserConfig 2 }

    mpsSysUserConfigFacilities OBJECT-TYPE
        SYNTAX          BITS { remoteConfig(0), remoteAccess(1), callRecordPrinting(2) }
        MAX-ACCESS      read-write
        STATUS          current
        DESCRIPTION
            "System facilities. (1) enabled or (0) disabled:
                remoteConfig      : Remote switching/ remote control.
                remoteAccess      : Remote access.
                callRecordPrinting: Print call data records.
            "
        ::= { mpsSysUserConfig 3 }

    mpsSysUserConfigCoS OBJECT-TYPE
        SYNTAX          INTEGER { standard(1), optional(2) }
        MAX-ACCESS      read-write
        STATUS          current
        DESCRIPTION
            "This variable contains the current Class Of Service mode."
        DEFVAL { standard }
        ::= { mpsSysUserConfig 4 }

    mpsSysUserConfigPBXMode OBJECT-TYPE
        SYNTAX          INTEGER { day(1), night(2) }
        MAX-ACCESS      read-write
        STATUS          current
        DESCRIPTION
            "This variable contains the current PBX mode."
        DEFVAL { day }
        ::= { mpsSysUserConfig 5 }

    mpsSysUserConfigNightGroupMode OBJECT-TYPE
        SYNTAX          INTEGER (0..4)
        MAX-ACCESS      read-write
        STATUS          current
        DESCRIPTION
            "This variable contains the active group mode when the
             mpsSysConfigPBXMode = night.
             0 = night mode for groups is off, individual settings used (day)."
        DEFVAL { 1 }
        ::= { mpsSysUserConfig 6 }

    mpsSysUserConfigNightDoorIntercomMode OBJECT-TYPE
        SYNTAX          INTEGER (0..4)
        MAX-ACCESS      read-write
        STATUS          current
        DESCRIPTION
            "This variable contains the active DoorIntercom mode when variable
	     mpsSysConfigPBXMode is set to night.
             Value 0 means night mode for door intercom units is off, individual
	     settings used (day)."
        DEFVAL { 1 }
        ::= { mpsSysUserConfig 7 }

    mpsSysUserConfigNightTrunkMode OBJECT-TYPE
        SYNTAX          INTEGER (0..4)
        MAX-ACCESS      read-write
        STATUS          current
        DESCRIPTION
            "This variable contains the active trunk mode when variable
	     mpsSysConfigPBXMode is set to night and mpsTrunkNumberTarget is set
	     to re-route.
             0 = night mode for trunk rerouting is off, individual settings used
             (day)."
        DEFVAL { 1 }
        ::= { mpsSysUserConfig 8 }

    mpsSysUserConfigNightExtensionMode OBJECT-TYPE
        SYNTAX          INTEGER (0..4)
        MAX-ACCESS      read-write
        STATUS          current
        DESCRIPTION
            "This variable contains the active extension mode when variable
	     mpsSysConfigPBXMode is set to night and rerouting is active.
             0 = night mode for extension is off, individual settings used
	     (day)."
        DEFVAL { 1 }
        ::= { mpsSysUserConfig 9 }

    mpsSysUserConfigNightGlobalReRouteMode OBJECT-TYPE
        SYNTAX          INTEGER (0..4)
        MAX-ACCESS      read-write
        STATUS          current
        DESCRIPTION
            "This variable contains the active reroute mode when variable
	     mpsSysConfigPBXMode is set to night and global rerouting is
	     available.
             0 = night mode for global rerouting is off, individual settings
	     used (day)."
        DEFVAL { 1 }
        ::= { mpsSysUserConfig 10 }

    mpsSysUserConfigDayGlobalReRouteMode OBJECT-TYPE
        SYNTAX          INTEGER (1..4)
        MAX-ACCESS      read-write
        STATUS          current
        DESCRIPTION
            "This variable contains the active global reroute mode when variable
	     mpsSysConfigPBXMode is set to day and global rerouting is
	     available."
        DEFVAL { 1 }
        ::= { mpsSysUserConfig 11 }
	
	mpsSysUserConfigNightAlarmInputMode OBJECT-TYPE
        SYNTAX          INTEGER (0..2)
        MAX-ACCESS      read-write
        STATUS          current
        DESCRIPTION
            "This variable contains the active alarm input mode when variable
	     mpsSysConfigPBXMode is set to night.
             0 = night mode for alarm input is off, so use the individual
	     settings."
        DEFVAL { 1 }
        ::= { mpsSysUserConfig 12 }

---------------------------------------------------------------------------
mpsEmergencyNumberTable OBJECT-TYPE
    SYNTAX      SEQUENCE OF MpsEmergencyNumberEntry
    MAX-ACCESS  not-accessible
    STATUS      current
    DESCRIPTION
        "This Table contains the numbers of emergency calls. Emergency numbers 
         can be dialed, even if all B-channels of the PBX are busy."
    ::= { mpsNumber 1 }

    mpsEmergencyNumberEntry OBJECT-TYPE
        SYNTAX          MpsEmergencyNumberEntry 
        MAX-ACCESS      not-accessible
        STATUS          current
        DESCRIPTION
            ""
        INDEX { mpsEmergencyNumberIndex }
        ::= { mpsEmergencyNumberTable 1 }

    MpsEmergencyNumberEntry ::=
        SEQUENCE {
            mpsEmergencyNumberIndex             Unsigned32, 
            mpsEmergencyNumberTarget            DisplayString, 
            mpsEmergencyNumberDescr             DisplayString, 
            mpsEmergencyNumberAdminStatus       INTEGER
        }

    mpsEmergencyNumberIndex OBJECT-TYPE
        SYNTAX          Unsigned32
        MAX-ACCESS      read-write
        STATUS          current
        DESCRIPTION
            "A unique value for each emergency number."
        ::= { mpsEmergencyNumberEntry 1 }

    mpsEmergencyNumberTarget OBJECT-TYPE
        SYNTAX          DisplayString (SIZE(0..24))
        MAX-ACCESS      read-write
        STATUS          current
        DESCRIPTION
            "Contains the emergency number."
        ::= { mpsEmergencyNumberEntry 2 }

    mpsEmergencyNumberDescr OBJECT-TYPE
        SYNTAX          DisplayString (SIZE(0..20))
        MAX-ACCESS      read-write
        STATUS          current
        DESCRIPTION
            "Contains the description of emergency number."
        ::= { mpsEmergencyNumberEntry 3 }

    mpsEmergencyNumberAdminStatus OBJECT-TYPE
        SYNTAX          INTEGER { enable(1), delete(2) }
        MAX-ACCESS      read-write
        STATUS          current
        DESCRIPTION
            "Just for MIB entry deletion."
        DEFVAL { enable }
        ::= { mpsEmergencyNumberEntry 4 }

---------------------------------------------------------------------------
mpsDirectCallNumberTable OBJECT-TYPE
    SYNTAX      SEQUENCE OF MpsDirectCallNumberEntry
    MAX-ACCESS  not-accessible
    STATUS      current
    DESCRIPTION
        "This table contains the numbers for direct calls."
    ::= { mpsNumber 2 }

    mpsDirectCallNumberEntry OBJECT-TYPE
        SYNTAX          MpsDirectCallNumberEntry 
        MAX-ACCESS      not-accessible
        STATUS          current
        DESCRIPTION
            ""
        INDEX { mpsDirectCallNumberIndex }
        ::= { mpsDirectCallNumberTable 1 }

    MpsDirectCallNumberEntry ::=
        SEQUENCE {
            mpsDirectCallNumberIndex            DirectCallIndex, 
            mpsDirectCallNumberTarget           DisplayString, 
            mpsDirectCallNumberDescr            DisplayString, 
            mpsDirectCallNumberAdminStatus      INTEGER
        }

    mpsDirectCallNumberIndex OBJECT-TYPE
        SYNTAX          DirectCallIndex
        MAX-ACCESS      read-write
        STATUS          current
        DESCRIPTION
            "A unique value for each direct call number. This index can be 
             selected within the mpsExtensionUserTable."
        ::= { mpsDirectCallNumberEntry 1 }

    mpsDirectCallNumberTarget OBJECT-TYPE
        SYNTAX          DisplayString (SIZE(0..24))
        MAX-ACCESS      read-write
        STATUS          current
        DESCRIPTION
            "Contains the direct call number."
        ::= { mpsDirectCallNumberEntry 2 }

   mpsDirectCallNumberDescr OBJECT-TYPE
        SYNTAX          DisplayString (SIZE(0..20))
        MAX-ACCESS      read-write
        STATUS          current
        DESCRIPTION
            "Contains the description of direct call."
        ::= { mpsDirectCallNumberEntry 3 }

    mpsDirectCallNumberAdminStatus OBJECT-TYPE
        SYNTAX          INTEGER { enable(1), delete(2) }
        MAX-ACCESS      read-write
        STATUS          current
        DESCRIPTION
            "Just for MIB entry deletion."
        DEFVAL { enable }
        ::= { mpsDirectCallNumberEntry 4 }

---------------------------------------------------------------------------
mpsWhitelistNumberTable OBJECT-TYPE
    SYNTAX      SEQUENCE OF MpsWhitelistNumberEntry
    MAX-ACCESS  not-accessible
    STATUS      current
    DESCRIPTION
        "This table contains the unrestricted numbers for outgoing calls. 
         For each extension can be choosen, if unrestricted filter is enabled or 
         disabled."
    ::= { mpsNumber 3 }

    mpsWhitelistNumberEntry OBJECT-TYPE
        SYNTAX          MpsWhitelistNumberEntry 
        MAX-ACCESS      not-accessible
        STATUS          current
        DESCRIPTION
            ""
        INDEX { mpsWhitelistNumberIndex }
        ::= { mpsWhitelistNumberTable 1 }

    MpsWhitelistNumberEntry ::=
        SEQUENCE {
            mpsWhitelistNumberIndex             Unsigned32, 
            mpsWhitelistNumberTarget            DisplayString, 
            mpsWhitelistNumberAdminStatus       INTEGER
        }

    mpsWhitelistNumberIndex OBJECT-TYPE
        SYNTAX          Unsigned32
        MAX-ACCESS      read-write
        STATUS          current
        DESCRIPTION
            "A unique value for each unrestricted number."
        ::= { mpsWhitelistNumberEntry 1 }

    mpsWhitelistNumberTarget OBJECT-TYPE
        SYNTAX          DisplayString (SIZE(0..16))
        MAX-ACCESS      read-write
        STATUS          current
        DESCRIPTION
            "The unrestricted number or prefix number."
        ::= { mpsWhitelistNumberEntry 2 }

    mpsWhitelistNumberAdminStatus OBJECT-TYPE
        SYNTAX          INTEGER { enable(1), delete(2) }
        MAX-ACCESS      read-write
        STATUS          current
        DESCRIPTION
            "Just for MIB entry deletion."
        DEFVAL { enable }
        ::= { mpsWhitelistNumberEntry 3 }

---------------------------------------------------------------------------
mpsBlacklistNumberTable OBJECT-TYPE
    SYNTAX      SEQUENCE OF MpsBlacklistNumberEntry
    MAX-ACCESS  not-accessible
    STATUS      current
    DESCRIPTION
        "This table contains the restricted numbers for outgoing calls. 
         For each extension can be choosen, if restricted filter is enabled or 
         disabled."
    ::= { mpsNumber 4 }

    mpsBlacklistNumberEntry OBJECT-TYPE
        SYNTAX          MpsBlacklistNumberEntry 
        MAX-ACCESS      not-accessible
        STATUS          current
        DESCRIPTION
            ""
        INDEX { mpsBlacklistNumberIndex }
        ::= { mpsBlacklistNumberTable 1 }

    MpsBlacklistNumberEntry ::=
        SEQUENCE {
            mpsBlacklistNumberIndex             Unsigned32, 
            mpsBlacklistNumberTarget            DisplayString, 
            mpsBlacklistNumberAdminStatus       INTEGER
        }

    mpsBlacklistNumberIndex OBJECT-TYPE
        SYNTAX          Unsigned32
        MAX-ACCESS      read-write
        STATUS          current
        DESCRIPTION
            "A unique value for each restricted number."
        ::= { mpsBlacklistNumberEntry 1 }

    mpsBlacklistNumberTarget OBJECT-TYPE
        SYNTAX          DisplayString (SIZE(0..16))
        MAX-ACCESS      read-write
        STATUS          current
        DESCRIPTION
            "The restricted number or prefix number."
        ::= { mpsBlacklistNumberEntry 2 }

    mpsBlacklistNumberAdminStatus OBJECT-TYPE
        SYNTAX          INTEGER { enable(1), delete(2) }
        MAX-ACCESS      read-write
        STATUS          current
        DESCRIPTION
            "Just for MIB entry deletion."
        DEFVAL { enable }
        ::= { mpsBlacklistNumberEntry 3 }

---------------------------------------------------------------------------
mpsSpecialNumberTable OBJECT-TYPE
    SYNTAX      SEQUENCE OF MpsSpecialNumberEntry
    MAX-ACCESS  not-accessible
    STATUS      current
    DESCRIPTION
        "This table contains the information for special numbers (TNetBox, 
         SMS-Server)."
    ::= { mpsNumber 5 }

    mpsSpecialNumberEntry OBJECT-TYPE
        SYNTAX          MpsSpecialNumberEntry 
        MAX-ACCESS      not-accessible
        STATUS          obsolete
        DESCRIPTION
            ""
        INDEX { mpsSpecialNumberType, mpsSpecialNumberPrio }
        ::= { mpsSpecialNumberTable 1 }

    MpsSpecialNumberEntry ::=
        SEQUENCE {
            mpsSpecialNumberType                INTEGER, 
            mpsSpecialNumberPrio                INTEGER, 
            mpsSpecialNumberTarget              DisplayString, 
            mpsSpecialNumberAdminStatus         INTEGER
        }

    mpsSpecialNumberType OBJECT-TYPE
        SYNTAX          INTEGER { tNetBox(1), sms(2) }
        MAX-ACCESS      read-write
        STATUS          obsolete
        DESCRIPTION
            "This variable contains the type of the number."
        DEFVAL{ tNetBox }
        ::= { mpsSpecialNumberEntry 1 }

    mpsSpecialNumberPrio OBJECT-TYPE
        SYNTAX          INTEGER
        MAX-ACCESS      read-write
        STATUS          obsolete
        DESCRIPTION
            "A unique value for each type a prio."
        ::= { mpsSpecialNumberEntry 2 }

    mpsSpecialNumberTarget OBJECT-TYPE
        SYNTAX          DisplayString (SIZE(0..16))
        MAX-ACCESS      read-write
        STATUS          obsolete
        DESCRIPTION
            "The digits of the special number."
        ::= { mpsSpecialNumberEntry 3 }

    mpsSpecialNumberAdminStatus OBJECT-TYPE
        SYNTAX          INTEGER { enable(1), delete(2) }
        MAX-ACCESS      read-write
        STATUS          obsolete
        DESCRIPTION
            "Just for MIB entry deletion."
        DEFVAL { enable }
        ::= { mpsSpecialNumberEntry 4 }

---------------------------------------------------------------------------
mpsSystemNumberTable OBJECT-TYPE
    SYNTAX      SEQUENCE OF MpsSystemNumberEntry
    MAX-ACCESS  not-accessible
    STATUS      current
    DESCRIPTION
        "This table contains additional system numbers."
    ::= { mpsNumber 6 }

    mpsSystemNumberEntry OBJECT-TYPE
        SYNTAX          MpsSystemNumberEntry 
        MAX-ACCESS      not-accessible
        STATUS          current
        DESCRIPTION
            ""
        INDEX { mpsSystemNumberIndex}
        ::= { mpsSystemNumberTable 1 }

    MpsSystemNumberEntry ::=
        SEQUENCE {
            mpsSystemNumberIndex                Unsigned32, 
            mpsSystemNumberType                 INTEGER, 
            mpsSystemNumberNumber               DisplayString, 
            mpsSystemNumberAdminStatus          INTEGER,
            mpsSystemNumberPosition             Unsigned32
        }

    mpsSystemNumberIndex OBJECT-TYPE
        SYNTAX          Unsigned32
        MAX-ACCESS      read-write
        STATUS          current
        DESCRIPTION
            "A unique value for each system number."
        ::= { mpsSystemNumberEntry 1 }

    mpsSystemNumberType OBJECT-TYPE
        SYNTAX          INTEGER {
                                 service-number(1),
                                 trunk-access(2),
                                 pickup(3),
                                 specific-pickup(4),
                                 project-code(5),
                                 speed-dial(6),
                                 open-inquiry(7),
                                 bundle-req(8),
                                 systel-update-fw(9)
                                }
        MAX-ACCESS      read-write
        STATUS          current
        DESCRIPTION
            "Type of system number.
             service-number(1)   : internal service number.
             trunk-access(2)     : line access digit to external line.
             pickup(3)           : pickup an internal call. 
             specific-pickup(4)  : pickup an internal call via extension number.
             project-code(5)     : stored in accounting data.
             speed-dial(6)       : telephone call via speed dial number.
             open-inquiry(7)     : system parking number.
             bundle-req(8)       : access code for external trunk bundles.
             systel-update-fw(9) : update system phone firmware."
        DEFVAL { service-number }
        ::= { mpsSystemNumberEntry 2 }

    mpsSystemNumberNumber OBJECT-TYPE
        SYNTAX          DisplayString (SIZE(0..16))
        MAX-ACCESS      read-write
        STATUS          current
        DESCRIPTION
            "The digits of the system number."
        ::= { mpsSystemNumberEntry 3 }

    mpsSystemNumberAdminStatus OBJECT-TYPE
        SYNTAX          INTEGER { enable(1), delete(2) }
        MAX-ACCESS      read-write
        STATUS          current
        DESCRIPTION
            "Just for MIB entry deletion."
        DEFVAL { enable }
        ::= { mpsSystemNumberEntry 4 }

    mpsSystemNumberPosition OBJECT-TYPE
        SYNTAX          Unsigned32
        MAX-ACCESS      read-write
        STATUS          current
        DESCRIPTION
            "A counter for open-inquiry(7) and bundle-req(8)
             (mpsSystemNumberType).
             If mpsSystemNumberType = bundle-req, mpsSystemNumberPosition
             referecenes to mpsTrunkBundleTable."
        ::= { mpsSystemNumberEntry 5 }

---------------------------------------------------------------------------
mpsDeviceTable OBJECT-TYPE
    SYNTAX      SEQUENCE OF MpsDeviceEntry
    MAX-ACCESS  not-accessible
    STATUS      current
    DESCRIPTION
        "This table contains information about each call control interface
         (device internal and external)."
    ::= { mpsCommon 1 }

    mpsDeviceEntry OBJECT-TYPE
        SYNTAX          MpsDeviceEntry 
        MAX-ACCESS      not-accessible
        STATUS          current
        DESCRIPTION
            ""
        INDEX { mpsDeviceIfIndex }
        ::= { mpsDeviceTable 1 }

    MpsDeviceEntry ::= 
        SEQUENCE {
            mpsDeviceIfIndex            InterfaceIndex, 
            mpsDeviceMode               INTEGER, 
            mpsDeviceDisplayName        DisplayString, 
            mpsDeviceBundle             INTEGER, 
            mpsDeviceTrunkGroup         TrunkGroupIndexOrZero, 
            mpsDeviceDefaultExtension   ExtensionIndexOrZero, 
            mpsDeviceBusMode            INTEGER, 
            mpsDeviceClipNoScreening    INTEGER,
            mpsDeviceAdminStatus        INTEGER,
            mpsDeviceLayer2AlwaysOn     TruthValue,
            mpsDeviceType               INTEGER
        }

    mpsDeviceIfIndex OBJECT-TYPE
        SYNTAX          InterfaceIndex
        MAX-ACCESS      read-write
        STATUS          current
        DESCRIPTION
            "A unique value for each device."
        ::= { mpsDeviceEntry 1 }

    mpsDeviceMode OBJECT-TYPE
        SYNTAX          INTEGER {
                            none(1),
                            itrunk-pmp(2),
                            itrunk-pp(3),
                            iline-pmp(4),
                            iline-pp(5),
                            analine(6),
                            itrunk-pp-S2m(7),
                            dectline(8),
                            anatrunk(9)
                        }
        MAX-ACCESS      read-write
        STATUS          current
        DESCRIPTION
            "Contains mode of the device.
             itrunk-pmp(2)   : isdn extern, point-to-multipoint
             itrunk-pp(3)    : isdn extern, point-to-point
             iline-pmp(4)    : isdn intern, point-to-multipoint
             iline-pp(5)     : isdn intern, point-to-point
             analine(6)      : analoque intern, FXS
             itrunk-pp-S2m(7): isdn extern, primary rate interfaces
             dectline(8)     : dect intern
             anatrunk(9)     : analoque extern, FXO"
        DEFVAL { none }
        ::= { mpsDeviceEntry 2 }

    mpsDeviceDisplayName OBJECT-TYPE
        SYNTAX          DisplayString (SIZE(0..32))
        MAX-ACCESS      read-write
        STATUS          current
        DESCRIPTION
            "Display name of the device."
        ::= { mpsDeviceEntry 3 }

    mpsDeviceBundle OBJECT-TYPE
        SYNTAX          INTEGER
        MAX-ACCESS      read-write
        STATUS          obsolete
        DESCRIPTION
            "This variable contains the bundle number of the device."
        DEFVAL { 0 }
        ::= { mpsDeviceEntry 4 }

    mpsDeviceTrunkGroup OBJECT-TYPE
        SYNTAX          TrunkGroupIndexOrZero
        MAX-ACCESS      read-write
        STATUS          current
        DESCRIPTION
            "A unique value for each trunk group index
             (reference to mpsTrunkGroupTable)."
        ::= { mpsDeviceEntry 5 }

    mpsDeviceDefaultExtension OBJECT-TYPE
        SYNTAX          ExtensionIndexOrZero
        MAX-ACCESS      read-write
        STATUS          current
        DESCRIPTION
            "Defines the extension to be used for outgoing calls
             without calling party number (reference to mpsExtensionTable)."
        ::= { mpsDeviceEntry 6 }

    mpsDeviceBusMode OBJECT-TYPE
        SYNTAX          INTEGER {
                            standard(1),
                            extended(2)
                        }
        MAX-ACCESS      read-write
        STATUS          obsolete
        DESCRIPTION
            "The configuration of the internal isdn device port is standard(1) 
             or extended(2)"
        DEFVAL { standard }
        ::= { mpsDeviceEntry 7 }

    mpsDeviceClipNoScreening OBJECT-TYPE
        SYNTAX          INTEGER {
                            no(1),
                            individual(2),
                            global(3)
                        }
        MAX-ACCESS      read-write
        STATUS          obsolete
        DESCRIPTION
            "This value determine when the mpsDeviceMode = itrunk-pp, wether 
             ClipNoScreening is disabled(1) or individual(2) or global(3)."
        DEFVAL { no }
        ::= { mpsDeviceEntry 8 }

    mpsDeviceAdminStatus OBJECT-TYPE
        SYNTAX          INTEGER {
                            enable(1),
                            delete(2),
                            disable(3)
                        }
        MAX-ACCESS      read-write
        STATUS          current
        DESCRIPTION
            "Just for MIB entry deletion."
        DEFVAL { enable }
        ::= { mpsDeviceEntry 9 }

    mpsDeviceLayer2AlwaysOn OBJECT-TYPE
        SYNTAX          TruthValue
        MAX-ACCESS      read-write
        STATUS  current
        DESCRIPTION
            "This value determine if the Layer2 for this external isdn port is 
             keept permanently active (true) or not (false)."
        DEFVAL { false }
        ::= { mpsDeviceEntry 10 }


    mpsDeviceType OBJECT-TYPE
        SYNTAX          INTEGER {
                            tdm(1),
                            ip(2),
                            capi(3)
                        }
        MAX-ACCESS      read-write
        STATUS          current
        DESCRIPTION
            "Set to 'tdm' for physical interfaces (isdn, pots) and set to 'ip'
             or 'capi' for virtual interfaces."
        DEFVAL { tdm }
        ::= { mpsDeviceEntry 11 }

---------------------------------------------------------------------------
mpsDeviceVirtualTable OBJECT-TYPE
    SYNTAX      SEQUENCE OF MpsDeviceVirtualEntry
    MAX-ACCESS  not-accessible
    STATUS      current
    DESCRIPTION
        "This table contains information for each virtual device."
    ::= { mpsCommon 2 }

    mpsDeviceVirtualEntry OBJECT-TYPE
        SYNTAX          MpsDeviceVirtualEntry 
        MAX-ACCESS      not-accessible
        STATUS          obsolete
        DESCRIPTION
            ""
        INDEX { mpsDeviceVirtualIndex }
        ::= { mpsDeviceVirtualTable 1 }

    MpsDeviceVirtualEntry ::= 
        SEQUENCE {
            mpsDeviceVirtualIndex              INTEGER, 
            mpsDeviceVirtualMode               INTEGER, 
            mpsDeviceVirtualDefaultExtension   ExtensionIndexOrZero,
            mpsDeviceVirtualAdminStatus        INTEGER 
        }

    mpsDeviceVirtualIndex OBJECT-TYPE
        SYNTAX          INTEGER
        MAX-ACCESS      read-write
        STATUS          obsolete
        DESCRIPTION
            "A unique value for each virtual device."
        ::= { mpsDeviceVirtualEntry 1 }

    mpsDeviceVirtualMode OBJECT-TYPE
        SYNTAX          INTEGER {
                            capi(1),
                            ipline-pmp(2),
                            router(3),
                            iptrunk(4)
                        }
        MAX-ACCESS      read-write
        STATUS          obsolete
        DESCRIPTION
            "Contains mode of the device."
        DEFVAL { capi }
        ::= { mpsDeviceVirtualEntry 2 }

    mpsDeviceVirtualDefaultExtension OBJECT-TYPE
        SYNTAX          ExtensionIndexOrZero
        MAX-ACCESS      read-write
        STATUS          obsolete
        DESCRIPTION
            "Contains the extension index of an internal device port, for 
             default."
        ::= { mpsDeviceVirtualEntry 3 }

    mpsDeviceVirtualAdminStatus OBJECT-TYPE
        SYNTAX          INTEGER {
                            enable(1),
                            delete(2),
                            disable(3)
                        }
        MAX-ACCESS      read-write
        STATUS          obsolete
        DESCRIPTION
            "Just for MIB entry deletion."
        DEFVAL { enable }
        ::= { mpsDeviceVirtualEntry 4 }

---------------------------------------------------------------------------
mpsTrunkGroupTable OBJECT-TYPE
    SYNTAX      SEQUENCE OF MpsTrunkGroupEntry
    MAX-ACCESS  not-accessible
    STATUS      current
    DESCRIPTION
        "This table contains global information about external trunk groups."
    ::= { mpsCommon 3 }

    mpsTrunkGroupEntry OBJECT-TYPE
        SYNTAX          MpsTrunkGroupEntry 
        MAX-ACCESS      not-accessible
        STATUS          current
        DESCRIPTION
            ""
        INDEX { mpsTrunkGroupIndex }
        ::= { mpsTrunkGroupTable 1 }

    MpsTrunkGroupEntry ::=
        SEQUENCE {
            mpsTrunkGroupIndex                          TrunkGroupIndex, 
            mpsTrunkGroupLayer2AlwaysOn                 TruthValue, 
            mpsTrunkGroupDefaultTargetType              INTEGER, 
            mpsTrunkGroupDefaultTargetGroupIndex        GroupIndexOrZero, 
            mpsTrunkGroupDefaultTargetExtensionIndex    ExtensionIndexOrZero, 
            mpsTrunkGroupAdminStatus                    INTEGER,
            mpsTrunkGroupOutSigMode                     INTEGER,
            mpsTrunkGroupBaseNumber                     DisplayString,
            mpsTrunkGroupFixedOutNumber                 DisplayString,
            mpsTrunkGroupDisplayName                    DisplayString,
            mpsTrunkGroupFacilities                     BITS,
            mpsTrunkGroupOutNumberType                  INTEGER,
            mpsTrunkGroupInterfaceType                  INTEGER
        }

    mpsTrunkGroupIndex OBJECT-TYPE
        SYNTAX          TrunkGroupIndex
        MAX-ACCESS      read-write
        STATUS          current
        DESCRIPTION
            "A unique value for each trunk group."
        ::= { mpsTrunkGroupEntry 1 }

    mpsTrunkGroupLayer2AlwaysOn OBJECT-TYPE
        SYNTAX          TruthValue
        MAX-ACCESS      read-write
        STATUS  obsolete
        DESCRIPTION
            "This value determine if the Layer2 for this external isdn port is 
             always on (1) or off (2)."
        DEFVAL { false }
        ::= { mpsTrunkGroupEntry 2 }

    mpsTrunkGroupDefaultTargetType OBJECT-TYPE
        SYNTAX          INTEGER { group(1), extension(2), global(3), none(4) }
        MAX-ACCESS      read-write
        STATUS          current
        DESCRIPTION
            "This variable contains the target type for misdialing, 
             default is group. 'none'  means no routing (busy signalling).
             'global' -> use system target 'mpsSysConfigDefaultTargetType'. "
        DEFVAL { group }
        ::= { mpsTrunkGroupEntry 3 }

    mpsTrunkGroupDefaultTargetGroupIndex OBJECT-TYPE
        SYNTAX          GroupIndexOrZero
        MAX-ACCESS      read-write
        STATUS          current
        DESCRIPTION
            "This variable contains the default target group index if the 
             mpsTrunkGroupDefaultTargetType = group (1)."
        ::= { mpsTrunkGroupEntry 4 }

    mpsTrunkGroupDefaultTargetExtensionIndex OBJECT-TYPE
        SYNTAX          ExtensionIndexOrZero
        MAX-ACCESS      read-write
        STATUS          current
        DESCRIPTION
            "This variable contains the default target extension index if the 
             mpsTrunkGroupDefaultTargetType = extension(2)."
        ::= { mpsTrunkGroupEntry 5 }

    mpsTrunkGroupAdminStatus OBJECT-TYPE
        SYNTAX          INTEGER { enable(1), delete(2) }
        MAX-ACCESS      read-write
        STATUS          current
        DESCRIPTION
            "Just for MIB entry deletion."
        DEFVAL { enable }
        ::= { mpsTrunkGroupEntry 6 }

    mpsTrunkGroupOutSigMode OBJECT-TYPE
        SYNTAX          INTEGER { standard(1), cnsGlobal(2), cnsIndividual(3), fixedDDI(4) }
        MAX-ACCESS      read-write
        STATUS          current
        DESCRIPTION
            "This variable contains the outgoing signalling mode for this
             TrunkGroup.
             standard(1)     : standard signalling
             cnsGlobal(2)    : for all outgoing calls, the global CLIP no
                               screening number will be used.
             cnsIndividual(3): for outgoing calls, individual settings can be
                               used.
             fixedDDI(4)     : for all outgoing calls, the
                               mpsTrunkGroupBaseNumber +
                               mpsTrunkGroupFixedOutNumber will be used."
        DEFVAL { standard }
        ::= { mpsTrunkGroupEntry 7 }

    mpsTrunkGroupBaseNumber OBJECT-TYPE
        SYNTAX          DisplayString (SIZE(0..20))
        MAX-ACCESS      read-write
        STATUS          current
        DESCRIPTION
            "This variable contains the base number of the point-to-point port."
        ::= { mpsTrunkGroupEntry 8 }

    mpsTrunkGroupFixedOutNumber OBJECT-TYPE
        SYNTAX          DisplayString (SIZE(0..20))
        MAX-ACCESS      read-write
        STATUS          current
        DESCRIPTION
            "This variable contains the number for fixed outgoing number
             signalling.
             1. mpsTrunkGroupOutSigMode = fixedDDI : the fixed DDI for outgoing
                                                     calls.
             2. mpsTrunkGroupOutSigMode = cnsGlobal: the global CLIP no screening
                                                     number. "
        ::= { mpsTrunkGroupEntry 9 }

    mpsTrunkGroupDisplayName OBJECT-TYPE
        SYNTAX          DisplayString (SIZE(0..32))
        MAX-ACCESS      read-write
        STATUS          current
        DESCRIPTION
            "Display name of the trunk group."
        ::= { mpsTrunkGroupEntry 10 }

    mpsTrunkGroupFacilities OBJECT-TYPE
        SYNTAX          BITS {
                            ignoreBaseNumber(0),
                            suppressBaseNumber(1),
                            cnsSendRemoteCallerNumber(2),
                            suppressNotify(3)
                        }
        MAX-ACCESS      read-write
        STATUS          current
        DESCRIPTION
        "Special facilities for trunks.
                ignoreBaseNumber  : for P-P-trunks - ignore base number for
                                    incoming calls.
                suppressBaseNumber: for P-P-trunks - don't send base number for
                                    outgoing calls.
                cnsSendRemoteCallerNumber: An incoming external call is forwarded
                                           to extern via 2nd b-channel to this
                                           trunk group, the original (extern)
                                           party was send as calling party number
                                           instead of the outgoing number for
                                           this trunk.
                suppressNotify: don't send HOLD/RETRIEVE notifications to ISDN
                                trunk."
        ::= { mpsTrunkGroupEntry 11 }

    mpsTrunkGroupOutNumberType OBJECT-TYPE
        SYNTAX          INTEGER { default(1),
                                  unknown(2),
                                  subscriber(3),
                                  national(4) }
        MAX-ACCESS      read-write
        STATUS          current
        DESCRIPTION
            "This variable contains the type of number of the calling party for
             outgoing calls.
             'default' means the type of number will be set by the PBX,
             otherwise use unknown, subscriber or national for fix setting."
        DEFVAL { default }
        ::= { mpsTrunkGroupEntry 12 }

   mpsTrunkGroupInterfaceType OBJECT-TYPE
        SYNTAX          INTEGER {
                            isdn-pmp(1),
                            isdn-pp(2),
                            voip-pmp(3),
                            voip-pp(4),
                            pots(5)
                        }
        MAX-ACCESS      read-write
        STATUS          current
        DESCRIPTION
            "This variable contains the interface type, for which type of
             interface this trunk group can be used.
             isdn-pmp(1) : isdn extern, point-to-multipoint
             isdn-pp(2)  : isdn extern, point-to-point
             voip-pmp(3) : VoIP extern, point-to-multipoint
             voip-pp(4)  : VoIP extern, point-to-point
             pots(5)     : analoque extern, FXO "
        DEFVAL { isdn-pmp }
        ::= { mpsTrunkGroupEntry 13 }

---------------------------------------------------------------------------
mpsTrunkGroupVoIPTable OBJECT-TYPE
    SYNTAX      SEQUENCE OF MpsTrunkGroupVoIPEntry
    MAX-ACCESS  not-accessible
    STATUS      current
    DESCRIPTION
        "This table contains information about external VoIP provider."
    ::= { mpsCommon 4 }

    mpsTrunkGroupVoIPEntry OBJECT-TYPE
        SYNTAX          MpsTrunkGroupVoIPEntry 
        MAX-ACCESS      not-accessible
        STATUS          current
        DESCRIPTION
            ""
        INDEX { mpsTrunkGroupVoIPIndex }
        ::= { mpsTrunkGroupVoIPTable 1 }

    MpsTrunkGroupVoIPEntry ::=
        SEQUENCE {
            mpsTrunkGroupVoIPIndex               TrunkGroupIndex, 
            mpsTrunkGroupVoIPIfIndex             InterfaceIndex,
            mpsTrunkGroupVoIPType                INTEGER,
            mpsTrunkGroupVoIPMode                INTEGER,
            mpsTrunkGroupVoIPDescr               DisplayString, 
            mpsTrunkGroupVoIPBundle              Unsigned32, 
            mpsTrunkGroupVoIPDomain              DisplayString, 
            mpsTrunkGroupVoIPIpAddress           IpAddress, 
            mpsTrunkGroupVoIPUserAccount         DisplayString, 
            mpsTrunkGroupVoIPAuthName            DisplayString, 
            mpsTrunkGroupVoIPAuthPassword        DisplayString, 
            mpsTrunkGroupVoIPFacilities          BITS, 
            mpsTrunkGroupVoIPNetwork             NetworkIndex, 
            mpsTrunkGroupVoIPInviteTimeout       Unsigned32, 
            mpsTrunkGroupVoIPAdminStatus         INTEGER,
            mpsTrunkGroupVoIPOperationStatus     INTEGER,
            mpsTrunkGroupVoIPTestCommand         INTEGER,
            mpsTrunkGroupVoIPTestResult          INTEGER,
            mpsTrunkGroupVoIPCurrentCalls        Counter32,
            mpsTrunkGroupVoIPReregisterTimer     INTEGER,
            mpsTrunkGroupVoIPCodecs              BitValue,
            mpsTrunkGroupVoIPCodecOrder          INTEGER,
            mpsTrunkGroupVoIPProxy               DisplayString,
            mpsTrunkGroupVoIPSTUNServer          DisplayString,
            mpsTrunkGroupVoIPMaxSimCalls         INTEGER,
            mpsTrunkGroupVoIPReplaceSrc          DisplayString,
            mpsTrunkGroupVoIPReplaceDest         DisplayString,
            mpsTrunkGroupVoIPCodecProperties     CodecIndexOrZero,
            mpsTrunkGroupVoIPRealm               DisplayString,
            mpsTrunkGroupVoIPFromRealm           DisplayString,
            mpsTrunkGroupVoIPCLIP                BITS
        }

    mpsTrunkGroupVoIPIndex OBJECT-TYPE
        SYNTAX          TrunkGroupIndex
        MAX-ACCESS      read-write
        STATUS          current
        DESCRIPTION
            "A unique value for each trunk group."
        ::= { mpsTrunkGroupVoIPEntry 1 }

    mpsTrunkGroupVoIPType OBJECT-TYPE
        SYNTAX          INTEGER {
                            sip(1),
                            h323(2)
                        }
        MAX-ACCESS      read-write
        STATUS          current
        DESCRIPTION
            "This value determines the type of the VoIP provider."
        DEFVAL { sip }
        ::= { mpsTrunkGroupVoIPEntry 2 }

    mpsTrunkGroupVoIPMode OBJECT-TYPE
        SYNTAX          INTEGER {
                            pmp(1),
                            pp(2)
                        }
        MAX-ACCESS      read-write
        STATUS          current
        DESCRIPTION
            "This value determine the mode of the VoIP."
        DEFVAL { pmp }
        ::= { mpsTrunkGroupVoIPEntry 3 }

    mpsTrunkGroupVoIPDescr OBJECT-TYPE
        SYNTAX          DisplayString (SIZE(0..20))
        MAX-ACCESS      read-write
        STATUS          current
        DESCRIPTION
            "This variable contains a textual description of the VoIP provider."
        ::= { mpsTrunkGroupVoIPEntry 4 }

    mpsTrunkGroupVoIPBundle OBJECT-TYPE
        SYNTAX          Unsigned32
        MAX-ACCESS      read-write
        STATUS          obsolete
        DESCRIPTION
            "This variable contains the number of the bundle for this provider."
        DEFVAL { 0 }
        ::= { mpsTrunkGroupVoIPEntry 5 }

    mpsTrunkGroupVoIPDomain OBJECT-TYPE
        SYNTAX          DisplayString (SIZE(0..64))
        MAX-ACCESS      read-write
        STATUS          current
        DESCRIPTION
            "This variable contains name, port and transport of the registrar.
             example: 192.0.0.1:5060;tcp  or  phone30.bintec.de:5060;upd
            "
        ::= { mpsTrunkGroupVoIPEntry 6 }

    mpsTrunkGroupVoIPIpAddress OBJECT-TYPE
        SYNTAX          IpAddress
        MAX-ACCESS      read-write
        STATUS          current
        DESCRIPTION
            "This variable contains IP adress of the registrar."
        ::= { mpsTrunkGroupVoIPEntry 7 }

    mpsTrunkGroupVoIPUserAccount OBJECT-TYPE
        SYNTAX          DisplayString (SIZE(0..64))
        MAX-ACCESS      read-write
        STATUS          current
        DESCRIPTION
            "This variable contains the user account."
        ::= { mpsTrunkGroupVoIPEntry 8 }

    mpsTrunkGroupVoIPAuthName OBJECT-TYPE
        SYNTAX          DisplayString (SIZE(0..64))
        MAX-ACCESS      read-write
        STATUS          current
        DESCRIPTION
            "This variable contains authorisation name."
        ::= { mpsTrunkGroupVoIPEntry 9 }

   mpsTrunkGroupVoIPAuthPassword OBJECT-TYPE
        SYNTAX          DisplayString (SIZE(0..64))
        MAX-ACCESS      read-write
        STATUS          current
        DESCRIPTION
            "This variable contains authorisation password."
        ::= { mpsTrunkGroupVoIPEntry 10 }

    mpsTrunkGroupVoIPFacilities OBJECT-TYPE
        SYNTAX          BITS {
                            internationalNumber(0), clir(1), useUserID(2),
                            notRegistered(3), logInProxy(4), compression(5),
                            useAreaCode(6), noHoldRetrieve(7),
			    replaceIntPrefix(8), clrProvBind(9), natPing(10),
			    g726coding(11), earlyConnect(12), srtp(13),
			    noT38(14), callDeflection(15), sendUpdate(16),
			    sendUserAccinPpreferred(17),
			    sendUserAccinPasserted(18)
                        }
        MAX-ACCESS      read-write
        STATUS          current
        DESCRIPTION
        "Special facilities of the IP provider.
                internationalNumber:    Generate international phone number.
                CLIR:                   1 -> Deactivate number suppression.
                UseUserID:              Use UserID as phone number.
                notRegistered:          Not registered with VoIP provider.
                logInProxy:             Allow login of a proxy.
                compression:            voice compression
                useAreaCode:            add area code to dialed number
                noHoldRetrieve:         no hold/retrieve message to the provider
                replaceIntPrefix:       replace intern. prefix (e.g. '00)
                                        with '+'
                clrProvBind:            clear provider binding
                natPing:                If set to 0 no NAT ping packets will be
                                        send. Set to 1 periodic NAT ping packets
                                        will be send.
                g726coding:             0 -> I.366
                                        1 -> RFC 3551/X.420
                earlyConnect:           allow early SIP connect
                srtp:                   allow SRTP negotiation
                noT38:                  1 -> FAX via T.38 disabled
                callDeflection:         redirect an unanswered call to another
                                        endpoint during the call setup phase
					(code 302)
                sendUpdate:             send SIP UPDATE
		sendUserAccinPpreferred:Always send user account in
					P-Preferred-identity header field
		sendUserAccinPasserted: Always send user account in
					P-Asserted-identity header field
            "
        ::= { mpsTrunkGroupVoIPEntry 11 }

    mpsTrunkGroupVoIPNetwork OBJECT-TYPE
        SYNTAX          NetworkIndex
        MAX-ACCESS      read-write
        STATUS          obsolete
        DESCRIPTION
            "This variable contains the special location index."
        ::= { mpsTrunkGroupVoIPEntry 12 }

    mpsTrunkGroupVoIPInviteTimeout OBJECT-TYPE
        SYNTAX          Unsigned32 
        UNITS           "s"
        MAX-ACCESS      read-write
        STATUS          current
        DESCRIPTION
            "This variable contains the length of the end of dial timer."
        DEFVAL { 5 }
        ::= { mpsTrunkGroupVoIPEntry 13 }

    mpsTrunkGroupVoIPAdminStatus OBJECT-TYPE
        SYNTAX          INTEGER { enable(1), disable(2), delete(3) }
        MAX-ACCESS      read-write
        STATUS          current
        DESCRIPTION
            "VoIP Provider is active or not active. 
             Set to delete, to discard the whole entry."
        DEFVAL { enable }
        ::= { mpsTrunkGroupVoIPEntry 14 }

    mpsTrunkGroupVoIPOperationStatus OBJECT-TYPE
        SYNTAX          INTEGER { 
                             notregistered(1), 
                             registering(2), 
                             registered(3), 
                             reregistering(4) 
                         }
        MAX-ACCESS      read-only
        STATUS          current
        DESCRIPTION
            "This variable contains the actual operation status.
                    notregistered :   client is not registered
                    registering   :   notregistered, registration pending
                    registered    :   client is registered
                    reregistering :   registered, reregistration pending
            "
        DEFVAL { notregistered }
        ::= { mpsTrunkGroupVoIPEntry 15 }

    mpsTrunkGroupVoIPTestCommand OBJECT-TYPE
        SYNTAX          INTEGER { idle(1), test(2) }
        MAX-ACCESS      read-write
        STATUS          current
        DESCRIPTION
            "This variable contains the current status.  Set to test, to test the
             VoIP provider.
             Automatically set to 'idle' when complete."
        DEFVAL { idle }
        ::= { mpsTrunkGroupVoIPEntry 16 }

    mpsTrunkGroupVoIPTestResult OBJECT-TYPE
        SYNTAX          INTEGER { idle(1), progress(2), success(3), error(4) }
        MAX-ACCESS      read-only
        STATUS          current
        DESCRIPTION
            "This variable contains the current status."
        DEFVAL { idle }
        ::= { mpsTrunkGroupVoIPEntry 17 }

    mpsTrunkGroupVoIPCurrentCalls OBJECT-TYPE
        SYNTAX          Counter32
        MAX-ACCESS      read-only
        STATUS          current
        DESCRIPTION
            "This variable contains the current calls."
        DEFVAL { 0 }
        ::= { mpsTrunkGroupVoIPEntry 18 }

    mpsTrunkGroupVoIPReregisterTimer OBJECT-TYPE
        SYNTAX          INTEGER (1..86400)
        UNITS           "s"
        MAX-ACCESS      read-write
        STATUS          current
        DESCRIPTION
            "This variable contains reregistering timer in seconds."
        DEFVAL { 60 }
        ::= { mpsTrunkGroupVoIPEntry 19 }

    mpsTrunkGroupVoIPCodecs OBJECT-TYPE
        SYNTAX          BitValue
        MAX-ACCESS      read-write
        STATUS          current
       
        DESCRIPTION
            "The supported Codecs of the Provider
            set one or more of the following bit values:
             ulaw       (1)
             alaw       (2)
             g729       (4)
             g726       (8)
             g726_16   (16)
             g726_32   (32)
             g726_40   (64)
             g728     (128)
             g723_63  (256)
             g723_53  (512)
             g729_e  (1024)
             gsm     (2048)
             dtmf    (4096)

             Default ulaw, alaw, g.729 and dtmf."
        DEFVAL { 4103 }
        ::= { mpsTrunkGroupVoIPEntry 20 } 

    mpsTrunkGroupVoIPCodecOrder OBJECT-TYPE
        SYNTAX  INTEGER {
            default(1),
            quality(2),
            lowest(3),
            highest(4)
        }
        MAX-ACCESS      read-write
        STATUS          current
        DESCRIPTION
            " Sorting the codecs 
              default -> system default order
              quality -> highest quality first
              lowest  -> lowest bandwidth first
              highest -> highest bandwidth first"
                  
        DEFVAL { default }
        ::= { mpsTrunkGroupVoIPEntry 21 } 

    mpsTrunkGroupVoIPProxy OBJECT-TYPE
        SYNTAX          DisplayString (SIZE(0..64))
        MAX-ACCESS      read-write
        STATUS          current
        DESCRIPTION
            "This variable contains name, port and transport of the outbound
             proxy.
             example: 192.0.0.1:5060;tcp  or  phone30.bintec.de:5060;upd
            "
        ::= { mpsTrunkGroupVoIPEntry 22 }

    mpsTrunkGroupVoIPSTUNServer OBJECT-TYPE
        SYNTAX          DisplayString (SIZE(0..64))
        MAX-ACCESS      read-write
        STATUS          current
        DESCRIPTION
            "This variable contains name and portof the STUN server.
             example: 192.0.0.1:5060  or  phone30.bintec.de:5060
            "
        ::= { mpsTrunkGroupVoIPEntry 23 }

    mpsTrunkGroupVoIPMaxSimCalls OBJECT-TYPE
        SYNTAX          INTEGER
        MAX-ACCESS      read-write
        STATUS          current
        DESCRIPTION
            "This variable contains the maximum of simultaneous connection for
             this provider.
             0 = no limitation. "
        DEFVAL { 0 }
        ::= { mpsTrunkGroupVoIPEntry 24 }

    mpsTrunkGroupVoIPReplaceSrc OBJECT-TYPE
        SYNTAX          DisplayString (SIZE(0..16))
        MAX-ACCESS      read-write
        STATUS          current
        DESCRIPTION
            "This variable contains the source string for substitution of the
             incoming number prefix.
             If the incoming number prefix is equal to this string, the incoming
             number prefix will be replaced with the string in
             mpsTrunkGroupVoIPReplaceDest."
        ::= { mpsTrunkGroupVoIPEntry 25 }

    mpsTrunkGroupVoIPReplaceDest OBJECT-TYPE
        SYNTAX          DisplayString (SIZE(0..16))
        MAX-ACCESS      read-write
        STATUS          current
        DESCRIPTION
            "String substitution, if the incoming number prefix is equal to the
             mpsTrunkGroupVoIPReplaceSrc string."
        ::= { mpsTrunkGroupVoIPEntry 26 }

    mpsTrunkGroupVoIPIfIndex OBJECT-TYPE
        SYNTAX          InterfaceIndex
        MAX-ACCESS      read-write
        STATUS          current
        DESCRIPTION
            "Reference to the interface index mpsDeviceIfIndex of the
             mspDeviceTable ."
        ::= { mpsTrunkGroupVoIPEntry 27 }

    mpsTrunkGroupVoIPCodecProperties OBJECT-TYPE
        SYNTAX          CodecIndexOrZero
        MAX-ACCESS      read-write
        STATUS          current
        DESCRIPTION
            "A reference to mpsCodecPropertyTable for codec properties.
             If '0' use system default."
        DEFVAL { 0 }
        ::= { mpsTrunkGroupVoIPEntry 28 }

    mpsTrunkGroupVoIPRealm OBJECT-TYPE
        SYNTAX          DisplayString (SIZE(0..64))
        MAX-ACCESS      read-write
        STATUS          current
        DESCRIPTION
            "The Realm/Domain of the provider.
             This domain is used e.g. at registration or authentication instead
             of registration domain."
        ::= { mpsTrunkGroupVoIPEntry 29 }

    mpsTrunkGroupVoIPFromRealm OBJECT-TYPE
        SYNTAX          DisplayString (SIZE(0..64))
        MAX-ACCESS      read-write
        STATUS          current
        DESCRIPTION
            "The From Realm/Domain of the provider.
             This domain is used after the '@' in the From 
             information element in the SIP header."
        ::= { mpsTrunkGroupVoIPEntry 30 }

    mpsTrunkGroupVoIPCLIP OBJECT-TYPE
        SYNTAX          BITS {
                            display(0),
                            user(1),
                            p-preferred-identity(2),
                            p-asserted-identity(3)
                        }
        MAX-ACCESS      read-write
        STATUS          current
        DESCRIPTION
        "Use the phone number instead of the user account in the SIP header 
         to indidcate the caller identity.
         This is provider dependent:
                display              : transfer in DISPLAY of the FROM header
                                       field.
                user                 : transfer in USER (account) field in the
                                       FROM header field.
                p-preferred-identity : transfer in the P-Preferred-Identity
                                       header field.
                p-asserted-identity  : transfer in the P-Asserted-Identity
                                       header field.
            "
        ::= { mpsTrunkGroupVoIPEntry 31 }

---------------------------------------------------------------------------
mpsTrunkGroupPOTSTable OBJECT-TYPE
    SYNTAX      SEQUENCE OF MpsTrunkGroupPOTSEntry
    MAX-ACCESS  not-accessible
    STATUS      current
    DESCRIPTION
        "This table contains advanced information of the external pots trunk
         groups."
    ::= { mpsCommon 6 }

    mpsTrunkGroupPOTSEntry OBJECT-TYPE
        SYNTAX          MpsTrunkGroupPOTSEntry 
        MAX-ACCESS      not-accessible
        STATUS          obsolete
        DESCRIPTION
            ""
        INDEX { mpsTrunkGroupPOTSIndex }
        ::= { mpsTrunkGroupPOTSTable 1 }

    MpsTrunkGroupPOTSEntry ::=
        SEQUENCE {
            mpsTrunkGroupPOTSIndex                          TrunkGroupIndex, 
            mpsTrunkGroupPOTSDialingType                    INTEGER, 
            mpsTrunkGroupPOTSWait2Dial                      INTEGER,
            mpsTrunkGroupPOTSBusytoneDetection              TruthValue,
            mpsTrunkGroupPOTSBusytoneTimeSlice              INTEGER,
            mpsTrunkGroupPOTSClip                           INTEGER,
            mpsTrunkGroupPOTSChargeFrequency                INTEGER,
            mpsTrunkGroupPOTSEndOfDial                      INTEGER,
            mpsTrunkGroupPOTSAdminStatus                    INTEGER,
            mpsTrunkGroupPOTSFaxSwitchIndex                 FaxSwitchIndexOrZero,
            mpsTrunkGroupPOTSUefs                           TruthValue
        }


    mpsTrunkGroupPOTSIndex OBJECT-TYPE
        SYNTAX          TrunkGroupIndex
        MAX-ACCESS      read-write
        STATUS          obsolete
        DESCRIPTION
            "A unique value for each trunk group."
        ::= { mpsTrunkGroupPOTSEntry 1 }

    mpsTrunkGroupPOTSDialingType OBJECT-TYPE
        SYNTAX          INTEGER {
                            none(1),
                            mfv(2),
                            iwv(3)
                        }
        MAX-ACCESS      read-write
        STATUS          obsolete
        DESCRIPTION
            "Type of dialling, DTMF and pulse dialing. "
        DEFVAL { none }
        ::= { mpsTrunkGroupPOTSEntry 2 }

    mpsTrunkGroupPOTSWait2Dial OBJECT-TYPE
        SYNTAX          INTEGER
        MAX-ACCESS      read-write
        STATUS          obsolete
        DESCRIPTION
            "Time slice in seconds, before digits
             will be send to trunk. 
             Set to 0: dial tone detection is on."
        ::= { mpsTrunkGroupPOTSEntry 3 }

    mpsTrunkGroupPOTSBusytoneDetection OBJECT-TYPE
        SYNTAX          TruthValue
        MAX-ACCESS      read-write
        STATUS          obsolete
        DESCRIPTION
            "This value determine if busystone detection is on (true) or off
             (false)."
        DEFVAL { false }
        ::= { mpsTrunkGroupPOTSEntry 4 }

    mpsTrunkGroupPOTSBusytoneTimeSlice OBJECT-TYPE
        SYNTAX          INTEGER
        MAX-ACCESS      read-write
        STATUS          obsolete
        DESCRIPTION
            "Max time slice in seconds, to detect the busytone."
        ::= { mpsTrunkGroupPOTSEntry 5 }

    mpsTrunkGroupPOTSClip OBJECT-TYPE
        SYNTAX          INTEGER {
                            none(1),
                            mfv(2),
                            dtmf(3)
                        }
        MAX-ACCESS      read-write
        STATUS          obsolete
        DESCRIPTION
            "Number display (CLIP)."
        DEFVAL { none }
        ::= { mpsTrunkGroupPOTSEntry 6 }

    mpsTrunkGroupPOTSChargeFrequency OBJECT-TYPE
        SYNTAX          INTEGER { no(1), f12khz(2), f16khz(3) }
        MAX-ACCESS      read-write
        STATUS          obsolete
        DESCRIPTION
            "This value determine the frequency of the charge pulse for 
             POTS trunk groups"
        DEFVAL { no }
        ::= { mpsTrunkGroupPOTSEntry 7 }

    mpsTrunkGroupPOTSEndOfDial OBJECT-TYPE
        SYNTAX          INTEGER
        MAX-ACCESS      read-write
        STATUS          obsolete
        DESCRIPTION
            "End of dial time slice in seconds."
        ::= { mpsTrunkGroupPOTSEntry 8 }

    mpsTrunkGroupPOTSAdminStatus OBJECT-TYPE
        SYNTAX          INTEGER { enable(1), delete(2) }
        MAX-ACCESS      read-write
        STATUS          obsolete
        DESCRIPTION
            "Just for MIB entry deletion."
        DEFVAL { enable }
        ::= { mpsTrunkGroupPOTSEntry 9 }

    mpsTrunkGroupPOTSFaxSwitchIndex OBJECT-TYPE
        SYNTAX          FaxSwitchIndexOrZero
        MAX-ACCESS      read-write
        STATUS          obsolete
        DESCRIPTION
            "A unique value for each fax switch."
        ::= { mpsTrunkGroupPOTSEntry 10 }

    mpsTrunkGroupPOTSUefs OBJECT-TYPE
        SYNTAX          TruthValue
        MAX-ACCESS      read-write
        STATUS          obsolete
        DESCRIPTION
            "This value determine if 'DDI on POTS' (UEFS) is on (true) or off
             (false)."
        DEFVAL { false }
        ::= { mpsTrunkGroupPOTSEntry 11 }

---------------------------------------------------------------------------
mpsTrunkNumberTable OBJECT-TYPE
    SYNTAX      SEQUENCE OF MpsTrunkNumberEntry
    MAX-ACCESS  not-accessible
    STATUS      current
    DESCRIPTION
        "This table contains advanced information about external numbers."
    ::= { mpsCommon 7 }

    mpsTrunkNumberEntry OBJECT-TYPE
    SYNTAX          MpsTrunkNumberEntry 
        MAX-ACCESS      not-accessible
        STATUS          current
        DESCRIPTION
            ""
        INDEX { mpsTrunkNumberIndex }
        ::= { mpsTrunkNumberTable 1 }

    MpsTrunkNumberEntry ::=
        SEQUENCE {
            mpsTrunkNumberIndex                             TrunkNumberIndex,
            mpsTrunkNumberGroup                             TrunkGroupIndexOrZero, 
            mpsTrunkNumberNumberIndex                       Unsigned32,
            mpsTrunkNumberType                              INTEGER,
            mpsTrunkNumberTarget                            INTEGER,
            mpsTrunkNumberTargetIndex                       INTEGER,
            mpsTrunkNumberNumberEntry                       DisplayString,
            mpsTrunkNumberCalendar                          CalendarIndexOrZero,
            mpsTrunkNumberDisplayName                       DisplayString,
            mpsTrunkNumberAdminStatus                       INTEGER,
            mpsTrunkNumberReRouteAppl                       ReRouteApplIndexOrZero
        }

    mpsTrunkNumberIndex OBJECT-TYPE
        SYNTAX          TrunkNumberIndex
        MAX-ACCESS      read-write
        STATUS          current
        DESCRIPTION
            "A unique value for each trunk number."
        ::= { mpsTrunkNumberEntry 1 }

    mpsTrunkNumberGroup OBJECT-TYPE
        SYNTAX          TrunkGroupIndexOrZero
        MAX-ACCESS      read-write
        STATUS          current
        DESCRIPTION
            "A unique value for each trunk group index.
             0 allowed for mpsTrunkNumberType = cnsIndividual, for all trunk
             groups"
        ::= { mpsTrunkNumberEntry 2 }

    mpsTrunkNumberNumberIndex OBJECT-TYPE
        SYNTAX          Unsigned32
        MAX-ACCESS      read-write
        STATUS          current
        DESCRIPTION
            "A unique value for each number entry of a trunk group."
        ::= { mpsTrunkNumberEntry 3 }

    mpsTrunkNumberType OBJECT-TYPE
        SYNTAX          INTEGER { msn(1), ddi(2), cnsIndividual(3), additionalMSN(4) }
        MAX-ACCESS      read-write
        STATUS          current
        DESCRIPTION
            "This variable contains the information of the type of number:
             msn           : MSN
             ddi           : DDI (direct dialling in)
             cnsIndividual : clip no screening
             additionalMSN : MSN at point-to-point device"
        DEFVAL { msn }
        ::= { mpsTrunkNumberEntry 4 }

    mpsTrunkNumberTarget OBJECT-TYPE
        SYNTAX          INTEGER { group(1),
                                  extension(2),
                                  call-through(3),
                                  re-route(4),
                                  telematicAccess(5),
                                  isdnLogin(6),
                                  webServiceLogin(7),
                                  call-center(8),
                                  isdnSysFwuServer(9)
                                }
        MAX-ACCESS      read-write
        STATUS          current
        DESCRIPTION
            "The external number can be assigned to an internal target:
             group:            a group of internal extensions.
             extension:        one internal extension.
             call-through:     use the call-through feature
             re-route:         direct routing to announcement
             telematicAccess:  telematic control
             isdnLogin:        console login
             webServiceLogin:  web access
             call-center:      group call center
             isdnSysFwuServer: ISDN SysTel Firmware Update Server"
        DEFVAL { group }
        ::= { mpsTrunkNumberEntry 5 }

    mpsTrunkNumberTargetIndex OBJECT-TYPE
        SYNTAX          INTEGER
        MAX-ACCESS      read-write
        STATUS          current
        DESCRIPTION
            "This variable contains index of the target table or zero, 
             mpsTrunkNumberTarget=group       : index = mpsGroupIndex.
             mpsTrunkNumberTarget=extension   : index = ExtensionIndex.
             mpsTrunkNumberTarget=call-center : index = mpsGroupIndex 
                                                (call-center)
             for all other set to 0."
        ::= { mpsTrunkNumberEntry 6 }

    mpsTrunkNumberNumberEntry OBJECT-TYPE
        SYNTAX          DisplayString (SIZE(0..24))
        MAX-ACCESS      read-write
        STATUS          current
        DESCRIPTION
            "This variable contains the digits of the external number
             (MSN,DDI,...)."
        ::= { mpsTrunkNumberEntry 7 }

    mpsTrunkNumberCalendar OBJECT-TYPE
        SYNTAX          CalendarIndexOrZero
        MAX-ACCESS      read-write
        STATUS          current
        DESCRIPTION
            "Select a calendar index to switch the call distribution for
             immediately rerouting automatically."
        DEFVAL { 0 }
        ::= { mpsTrunkNumberEntry 8 }

    mpsTrunkNumberDisplayName OBJECT-TYPE
        SYNTAX          DisplayString (SIZE(0..32))
        MAX-ACCESS      read-write
        STATUS          current
        DESCRIPTION
            "Display name of the trunk number."
        ::= { mpsTrunkNumberEntry 9 }

    mpsTrunkNumberAdminStatus OBJECT-TYPE
        SYNTAX          INTEGER { enable(1),
                                  delete(2) 
                                }
        MAX-ACCESS      read-write
        STATUS          current
        DESCRIPTION
            "Just for MIB entry deletion."
        DEFVAL { enable }
        ::= { mpsTrunkNumberEntry 10 }

    mpsTrunkNumberReRouteAppl OBJECT-TYPE
        SYNTAX          ReRouteApplIndexOrZero
        MAX-ACCESS      read-write
        STATUS          current
        DESCRIPTION
            "Index of ReRouting application in mpsReRouteApplTable.
             Value 0 means that ReRouting application is inactive."
        DEFVAL { 0 }
        ::= { mpsTrunkNumberEntry 11 }

---------------------------------------------------------------------------
mpsTrunkNumberUserTable OBJECT-TYPE
    SYNTAX      SEQUENCE OF MpsTrunkNumberUserEntry
    MAX-ACCESS  not-accessible
    STATUS      current
    DESCRIPTION
        "This table contains information about current mode for incoming call
         distribution to an immediately rerouting function."
    ::= { mpsCommon 8 }

    mpsTrunkNumberUserEntry OBJECT-TYPE
        SYNTAX          MpsTrunkNumberUserEntry 
        MAX-ACCESS      not-accessible
        STATUS          current
        DESCRIPTION
            ""
        INDEX { mpsTrunkNumberUserIndex }
        ::= { mpsTrunkNumberUserTable 1 }

    MpsTrunkNumberUserEntry ::=
        SEQUENCE {
            mpsTrunkNumberUserIndex             TrunkNumberIndex,
            mpsTrunkNumberUserMode              Unsigned32,
            mpsTrunkNumberUserAdminStatus       INTEGER
        }

    mpsTrunkNumberUserIndex OBJECT-TYPE
        SYNTAX          TrunkNumberIndex
        MAX-ACCESS      read-write
        STATUS          current
        DESCRIPTION
            "A unique value for each trunk number, references mpsTrunkNumberIndex
             in mpsTrunkNumberTable."
        ::= { mpsTrunkNumberUserEntry 1 }

    mpsTrunkNumberUserMode OBJECT-TYPE
        SYNTAX          Unsigned32
        MAX-ACCESS      read-write
        STATUS          current
        DESCRIPTION
            "This variable contains the actual mode for incoming call
             distribution to a reroute function."
        ::= { mpsTrunkNumberUserEntry 2 }

    mpsTrunkNumberUserAdminStatus OBJECT-TYPE
        SYNTAX          INTEGER { enable(1),
                                  delete(2) 
                                }
        MAX-ACCESS      read-write
        STATUS          current
        DESCRIPTION
            "Just for MIB entry deletion."
        DEFVAL { enable }
        ::= { mpsTrunkNumberUserEntry 3 }

---------------------------------------------------------------------------
mpsTrunkNumberModeTable OBJECT-TYPE
    SYNTAX      SEQUENCE OF MpsTrunkNumberModeEntry
    MAX-ACCESS  not-accessible
    STATUS      current
    DESCRIPTION
        "This table contains reroute information for each trunk number and mode."
    ::= { mpsCommon 9 }

    mpsTrunkNumberModeEntry OBJECT-TYPE
        SYNTAX          MpsTrunkNumberModeEntry 
        MAX-ACCESS      not-accessible
        STATUS          current
        DESCRIPTION
            ""
        INDEX { mpsTrunkNumberModeIndex }
        ::= { mpsTrunkNumberModeTable 1 }

    MpsTrunkNumberModeEntry ::=
        SEQUENCE {
            mpsTrunkNumberModeIndex             Unsigned32,
            mpsTrunkNumberModeNumberIndex       TrunkNumberIndex,
            mpsTrunkNumberModeMode              Unsigned32,
            mpsTrunkNumberModeRerouteIndex      ReRouteIndexOrZero,
            mpsTrunkNumberModeAdminStatus       INTEGER
        }

    mpsTrunkNumberModeIndex OBJECT-TYPE
        SYNTAX          Unsigned32
        MAX-ACCESS      read-write
        STATUS          current
        DESCRIPTION
            "A unique value for each entry."
        ::= { mpsTrunkNumberModeEntry 1 }

    mpsTrunkNumberModeNumberIndex OBJECT-TYPE
        SYNTAX          TrunkNumberIndex
        MAX-ACCESS      read-write
        STATUS          current
        DESCRIPTION
            "This variable contains the trunk number index. Reference to
             mpsTrunkNumberTable."
        ::= { mpsTrunkNumberModeEntry 2 }

    mpsTrunkNumberModeMode OBJECT-TYPE
        SYNTAX          Unsigned32
        MAX-ACCESS      read-write
        STATUS          current
        DESCRIPTION
            "For each trunk number index (mpsTrunkNumberModeNumberIndex), 
             several modes can exists."
        ::= { mpsTrunkNumberModeEntry 3 }

    mpsTrunkNumberModeRerouteIndex OBJECT-TYPE
        SYNTAX          ReRouteIndexOrZero
        MAX-ACCESS      read-write
        STATUS          current
        DESCRIPTION
            "Index of the ReRouting function in mpsReRouteTable.
             0 = ReRouting function deactived."
        ::= { mpsTrunkNumberModeEntry 4 }

    mpsTrunkNumberModeAdminStatus OBJECT-TYPE
        SYNTAX          INTEGER { enable(1),
                                  delete(2) 
                                }
        MAX-ACCESS      read-write
        STATUS          current
        DESCRIPTION
            "Just for MIB entry deletion."
        DEFVAL { enable }
        ::= { mpsTrunkNumberModeEntry 5 }

---------------------------------------------------------------------------
mpsTrunkBundleTable OBJECT-TYPE
    SYNTAX      SEQUENCE OF MpsTrunkBundleEntry
    MAX-ACCESS  not-accessible
    STATUS      current
    DESCRIPTION
        "This table contains information of the trunk bundle configuration."
    ::= { mpsCommon 10 }

    mpsTrunkBundleEntry OBJECT-TYPE
        SYNTAX          MpsTrunkBundleEntry 
        MAX-ACCESS      not-accessible
        STATUS          current
        DESCRIPTION
            ""
        INDEX { mpsTrunkBundleIndex }
        ::= { mpsTrunkBundleTable 1 }

    MpsTrunkBundleEntry ::=
        SEQUENCE {
            mpsTrunkBundleIndex                 TrunkBundleIndex,
            mpsTrunkBundleDescription           DisplayString,
            mpsTrunkBundleAdminStatus           INTEGER
        }

    mpsTrunkBundleIndex OBJECT-TYPE
        SYNTAX          TrunkBundleIndex
        MAX-ACCESS      read-write
        STATUS          current
        DESCRIPTION
            "A unique value for each trunk bundle."
        ::= { mpsTrunkBundleEntry 1 }

    mpsTrunkBundleDescription OBJECT-TYPE
        SYNTAX          DisplayString (SIZE(0..32))
        MAX-ACCESS      read-write
        STATUS          current
        DESCRIPTION
            "Description of the trunk bundle."
        ::= { mpsTrunkBundleEntry 2 }

    mpsTrunkBundleAdminStatus OBJECT-TYPE
        SYNTAX          INTEGER { enable(1),
                                  delete(2) 
                                }
        MAX-ACCESS      read-write
        STATUS          current
        DESCRIPTION
            "Just for MIB entry deletion."
        DEFVAL { enable }
        ::= { mpsTrunkBundleEntry 3 }

---------------------------------------------------------------------------
mpsTrunkBundleEntryTable OBJECT-TYPE
    SYNTAX      SEQUENCE OF MpsTrunkBundleEntryEntry
    MAX-ACCESS  not-accessible
    STATUS      current
    DESCRIPTION
        "This table contains information about relation of trunk group and
         bundles."
    ::= { mpsCommon 11 }

    mpsTrunkBundleEntryEntry OBJECT-TYPE
        SYNTAX          MpsTrunkBundleEntryEntry 
        MAX-ACCESS      not-accessible
        STATUS          current
        DESCRIPTION
            ""
        INDEX { mpsTrunkBundleEntryIndex }
        ::= { mpsTrunkBundleEntryTable 1 }

    MpsTrunkBundleEntryEntry ::=
        SEQUENCE {
            mpsTrunkBundleEntryIndex            TrunkBundleIndex,
            mpsTrunkBundleEntryPrio             Unsigned32,
            mpsTrunkBundleEntryTrunkGroup       TrunkGroupIndex,
            mpsTrunkBundleEntryAdminStatus      INTEGER
        }

    mpsTrunkBundleEntryIndex OBJECT-TYPE
        SYNTAX          TrunkBundleIndex
        MAX-ACCESS      read-write
        STATUS          current
        DESCRIPTION
            "This variable contains the trunk bundle index of the
             mpsTrunkBundleTable for this trunk group."
        ::= { mpsTrunkBundleEntryEntry 1 }

    mpsTrunkBundleEntryPrio OBJECT-TYPE
        SYNTAX          Unsigned32
        MAX-ACCESS      read-write
        STATUS          current
        DESCRIPTION
            "This variable contains the routing priority of the trunk group."
        ::= { mpsTrunkBundleEntryEntry 2 }

    mpsTrunkBundleEntryTrunkGroup OBJECT-TYPE
        SYNTAX          TrunkGroupIndex
        MAX-ACCESS      read-write
        STATUS          current
        DESCRIPTION
            "This variable contains the trunk group index of the
             mpsTrunkGroupTable."
        ::= { mpsTrunkBundleEntryEntry 3 }

    mpsTrunkBundleEntryAdminStatus OBJECT-TYPE
        SYNTAX          INTEGER { enable(1),
                                  delete(2) 
                                }
        MAX-ACCESS      read-write
        STATUS          current
        DESCRIPTION
            "Just for MIB entry deletion."
        DEFVAL { enable }
        ::= { mpsTrunkBundleEntryEntry 4 }

---------------------------------------------------------------------------
mpsSubscriberNumberTable OBJECT-TYPE
    SYNTAX      SEQUENCE OF MpsSubscriberNumberEntry
    MAX-ACCESS  not-accessible
    STATUS      current
    DESCRIPTION
        "This table contains information about the call distribution for 
         incoming external calls."
    ::= { mpsSubscriber 1 }

    mpsSubscriberNumberEntry OBJECT-TYPE
        SYNTAX          MpsSubscriberNumberEntry 
        MAX-ACCESS      not-accessible
        STATUS          obsolete
        DESCRIPTION
            ""
        INDEX { mpsSubscriberNumberTrunkGroup, mpsSubscriberNumberIndex }
        ::= { mpsSubscriberNumberTable 1 }

    MpsSubscriberNumberEntry ::=
        SEQUENCE {
            mpsSubscriberNumberTrunkGroup       TrunkGroupIndex, 
            mpsSubscriberNumberIndex            SubscriberNumberIndex, 
            mpsSubscriberNumberType             INTEGER, 
            mpsSubscriberNumberTarget           INTEGER, 
            mpsSubscriberNumberGroupIndex       GroupIndexOrZero, 
            mpsSubscriberNumberExtensionIndex   ExtensionIndexOrZero,
            mpsSubscriberNumberAdminStatus      INTEGER
        }

    mpsSubscriberNumberTrunkGroup OBJECT-TYPE
        SYNTAX          TrunkGroupIndex
        MAX-ACCESS      read-write
        STATUS          obsolete
        DESCRIPTION
            "A unique value for each trunk group index."
        ::= { mpsSubscriberNumberEntry 1 }

    mpsSubscriberNumberIndex OBJECT-TYPE
        SYNTAX          SubscriberNumberIndex
        MAX-ACCESS      read-write
        STATUS          obsolete
        DESCRIPTION
            "A unique value for each call distribution."
        ::= { mpsSubscriberNumberEntry 2 }

    mpsSubscriberNumberType OBJECT-TYPE
        SYNTAX          INTEGER { simple(1), composite(2) }
        MAX-ACCESS      read-write
        STATUS          obsolete
        DESCRIPTION
            "This variable contains the information of the type of number."
        DEFVAL { simple }
        ::= { mpsSubscriberNumberEntry 3 }

    mpsSubscriberNumberTarget OBJECT-TYPE
        SYNTAX          INTEGER { group(1), extension(2), call-through(3) }
        MAX-ACCESS      read-write
        STATUS          obsolete
        DESCRIPTION
            "The external number can be assigned to internal teams or 
             subscribers."
        DEFVAL { group }
        ::= { mpsSubscriberNumberEntry 4 }

    mpsSubscriberNumberGroupIndex OBJECT-TYPE
        SYNTAX          GroupIndexOrZero
        MAX-ACCESS      read-write
        STATUS          obsolete
        DESCRIPTION
            "This variable contains the group index, 
             if mpsCallDistributionTargetType=team."
        ::= { mpsSubscriberNumberEntry 5 }

    mpsSubscriberNumberExtensionIndex OBJECT-TYPE
        SYNTAX          ExtensionIndexOrZero
        MAX-ACCESS      read-write
        STATUS          obsolete
        DESCRIPTION
            "This variable contains the extension index, 
             if mpsCallDistributionTargetType=extension."
        ::= { mpsSubscriberNumberEntry 6 }

    mpsSubscriberNumberAdminStatus OBJECT-TYPE
        SYNTAX          INTEGER { enable(1),
                                  delete(2) 
                                }
        MAX-ACCESS      read-write
        STATUS          obsolete
        DESCRIPTION
            "Just for MIB entry deletion."
        DEFVAL { enable }
        ::= { mpsSubscriberNumberEntry 7 }

---------------------------------------------------------------------------
mpsSubscriberNumberSimpleTable OBJECT-TYPE
    SYNTAX      SEQUENCE OF MpsSubscriberNumberSimpleEntry
    MAX-ACCESS  not-accessible
    STATUS      current
    DESCRIPTION
        "This table contains the information of the external MSN number. "
    ::= { mpsSubscriber 2 }

    mpsSubscriberNumberSimpleEntry OBJECT-TYPE
        SYNTAX          MpsSubscriberNumberSimpleEntry 
        MAX-ACCESS      not-accessible
        STATUS          obsolete
        DESCRIPTION
            ""
        INDEX { mpsSubscriberNumberSimpleTrunkGroup, 
                mpsSubscriberNumberSimpleIndex }
        ::= { mpsSubscriberNumberSimpleTable 1 }

    MpsSubscriberNumberSimpleEntry ::=
        SEQUENCE {
            mpsSubscriberNumberSimpleTrunkGroup   TrunkGroupIndex, 
            mpsSubscriberNumberSimpleIndex        SubscriberNumberIndex, 
            mpsSubscriberNumberSimpleNumber       DisplayString, 
            mpsSubscriberNumberSimpleType         INTEGER,
            mpsSubscriberNumberSimpleAdminStatus  INTEGER
        }

    mpsSubscriberNumberSimpleTrunkGroup OBJECT-TYPE
        SYNTAX          TrunkGroupIndex
        MAX-ACCESS      read-write
        STATUS          obsolete
        DESCRIPTION
            "A unique value for each trunk group index."
        ::= { mpsSubscriberNumberSimpleEntry 1 }

    mpsSubscriberNumberSimpleIndex OBJECT-TYPE
        SYNTAX          SubscriberNumberIndex
        MAX-ACCESS      read-write
        STATUS          obsolete
        DESCRIPTION
            "A unique value for each external MSN number."
        ::= { mpsSubscriberNumberSimpleEntry 2 }

    mpsSubscriberNumberSimpleNumber OBJECT-TYPE
        SYNTAX          DisplayString (SIZE(0..24))
        MAX-ACCESS      read-write
        STATUS          obsolete
        DESCRIPTION
            "This variable contains the digits of the external MSN number."
        ::= { mpsSubscriberNumberSimpleEntry 3 }

    mpsSubscriberNumberSimpleType OBJECT-TYPE
        SYNTAX          INTEGER {
                            msn(1),
                            clipnoscreening-glob(2),
                            clipnoscreening-ind(3),
                            ddi(4)
                        }
        MAX-ACCESS      read-write
        STATUS          obsolete
        DESCRIPTION
            "This variable contains the type of the external number."
        DEFVAL { msn }
        ::= { mpsSubscriberNumberSimpleEntry 4 }

    mpsSubscriberNumberSimpleAdminStatus OBJECT-TYPE
        SYNTAX          INTEGER {
                            enable(1),
                            delete(2)
                        }
        MAX-ACCESS      read-write
        STATUS          obsolete
        DESCRIPTION
            "Just for MIB entry deletion."
        DEFVAL { enable }
        ::= { mpsSubscriberNumberSimpleEntry 5 }

---------------------------------------------------------------------------
mpsSubscriberNumberCompositePrefixTable OBJECT-TYPE
    SYNTAX      SEQUENCE OF MpsSubscriberNumberCompositePrefixEntry
    MAX-ACCESS  not-accessible
    STATUS      current
    DESCRIPTION
        "This table contains the information of the external DDI number. "
    ::= { mpsSubscriber 4 }

    mpsSubscriberNumberCompositePrefixEntry OBJECT-TYPE
        SYNTAX          MpsSubscriberNumberCompositePrefixEntry 
        MAX-ACCESS      not-accessible
        STATUS          obsolete
        DESCRIPTION
            ""
        INDEX { mpsSubscriberNumberCompositePrefixTrunkGroup }
        ::= { mpsSubscriberNumberCompositePrefixTable 1 }

    MpsSubscriberNumberCompositePrefixEntry ::=
        SEQUENCE {
            mpsSubscriberNumberCompositePrefixTrunkGroup   TrunkGroupIndex, 
            mpsSubscriberNumberCompositePrefixNumber       DisplayString, 
            mpsSubscriberNumberCompositePrefixAdminStatus  INTEGER
        }

    mpsSubscriberNumberCompositePrefixTrunkGroup OBJECT-TYPE
        SYNTAX          TrunkGroupIndex
        MAX-ACCESS      read-write
        STATUS          obsolete
        DESCRIPTION
            "A unique value for each trunk group index."
        ::= { mpsSubscriberNumberCompositePrefixEntry 1 }

    mpsSubscriberNumberCompositePrefixNumber OBJECT-TYPE
        SYNTAX          DisplayString (SIZE(0..24))
        MAX-ACCESS      read-write
        STATUS          obsolete
        DESCRIPTION
            "This variable contains the digits of the external DDI prefix
             number."
        ::= { mpsSubscriberNumberCompositePrefixEntry 2 }

    mpsSubscriberNumberCompositePrefixAdminStatus OBJECT-TYPE
        SYNTAX          INTEGER { enable(1), delete(2) }
        MAX-ACCESS      read-write
        STATUS          obsolete
        DESCRIPTION
            "Just for MIB entry deletion."
        DEFVAL { enable }
        ::= { mpsSubscriberNumberCompositePrefixEntry 3 }

---------------------------------------------------------------------------
mpsCallThroughTable OBJECT-TYPE
    SYNTAX      SEQUENCE OF MpsCallThroughEntry
    MAX-ACCESS  not-accessible
    STATUS      current
    DESCRIPTION
        "This table contains the information about call through handling."
    ::= { mpsSubscriber 5 }

    mpsCallThroughEntry OBJECT-TYPE
        SYNTAX          MpsCallThroughEntry 
        MAX-ACCESS      not-accessible
        STATUS          current
        DESCRIPTION
            ""
        INDEX { mpsCallThroughIndex }
        ::= { mpsCallThroughTable 1 }

    MpsCallThroughEntry ::=
        SEQUENCE {
            mpsCallThroughIndex                 Unsigned32,
            mpsCallThroughInTrunkGroup          TrunkGroupIndex, 
            mpsCallThroughInNumberIndex         TrunkNumberIndex, 
            mpsCallThroughOutTrunkGroup         TrunkGroupIndex,
            mpsCallThroughOutNumberIndex        TrunkNumberIndex,
            mpsCallThroughOutBundle             Unsigned32,
            mpsCallThroughFacilities            BITS,
            mpsCallThroughAdminStatus           INTEGER,
            mpsCallThroughOption                INTEGER,
            mpsCallThroughExtension             ExtensionIndexOrZero,
            mpsCallThroughPIN                   DisplayString
        }

    mpsCallThroughIndex OBJECT-TYPE
        SYNTAX          Unsigned32
        MAX-ACCESS      read-write
        STATUS          current
        DESCRIPTION
            "A unique value for each call through entry."
        ::= { mpsCallThroughEntry 1 }

    mpsCallThroughInTrunkGroup OBJECT-TYPE
        SYNTAX          TrunkGroupIndex 
        MAX-ACCESS      read-write
        STATUS          current
        DESCRIPTION
            "A unique value for the incoming trunk group. 
             Reference to mpsTrunkGroupTable."
        ::= { mpsCallThroughEntry 2 }

    mpsCallThroughInNumberIndex OBJECT-TYPE
        SYNTAX          TrunkNumberIndex 
        MAX-ACCESS      read-write
        STATUS          current
        DESCRIPTION
            "This value index of the incoming external MSN.
             Reference to mpsTrunkNumberTable."
        ::= { mpsCallThroughEntry 3 }

    mpsCallThroughOutTrunkGroup OBJECT-TYPE
        SYNTAX          TrunkGroupIndex 
        MAX-ACCESS      read-write
        STATUS          current
        DESCRIPTION
            "A unique value for the outgoing trunk group.
             Reference to mpsTrunkGroupTable."
        ::= { mpsCallThroughEntry 4 }

    mpsCallThroughOutNumberIndex OBJECT-TYPE
        SYNTAX          TrunkNumberIndex 
        MAX-ACCESS      read-write
        STATUS          current
        DESCRIPTION
            "This value index of the outgoing external MSN.
             Reference to mpsTrunkNumberTable."
        ::= { mpsCallThroughEntry 5 }

    mpsCallThroughOutBundle OBJECT-TYPE
        SYNTAX          Unsigned32
        MAX-ACCESS      read-write
        STATUS          current
        DESCRIPTION
            "A unique value for the outgoing bundle.
             Reference to mpsTrunkBundleTable."
        ::= { mpsCallThroughEntry 6 } 


    mpsCallThroughFacilities OBJECT-TYPE
        SYNTAX          BITS { clip-sreening(0),
                               ars(1) }
        MAX-ACCESS      read-only
        STATUS          obsolete
        DESCRIPTION
        "Special facilities of the call through entry.
                clip_sreening :         sreen the incoming phone number.
                ars :                   use ars (automatic route selection)
        "
        ::= { mpsCallThroughEntry 7 }

    mpsCallThroughAdminStatus OBJECT-TYPE
        SYNTAX          INTEGER { enable(1), disable(2), delete(3) }
        MAX-ACCESS      read-write
        STATUS          current
        DESCRIPTION
            "For enable, disable or delete."
        DEFVAL { enable }
        ::= { mpsCallThroughEntry 8 }

    mpsCallThroughOption  OBJECT-TYPE
        SYNTAX          INTEGER { clipscr(1), pin(2), clipscrAndPin(3), clipscrOrPin(4) }
        MAX-ACCESS      read-write
        STATUS          current
        DESCRIPTION
            "This variable contains the authorisation option for the calling
             party.
               clipscr       -> only CLIP screening
               pin           -> only PIN check
               clipscrAndPin -> CLIP screening and PIN check
               clipscrOrPin  -> CLIP screening or PIN check "
        DEFVAL { clipscrAndPin }
        ::= { mpsCallThroughEntry 9 }

             
    mpsCallThroughExtension OBJECT-TYPE
        SYNTAX          ExtensionIndexOrZero
        MAX-ACCESS      read-write
        STATUS          current
        DESCRIPTION
            "This variable contains the extension for outgoing call routing."
        ::= { mpsCallThroughEntry 10 } 

    mpsCallThroughPIN OBJECT-TYPE
        SYNTAX          DisplayString (SIZE(6))
        MAX-ACCESS      read-write
        STATUS          current
        DESCRIPTION
            "This variable contains the PIN code for call through, if set in
             mpsCallThroughOption."
        DEFVAL { "000000" }
        ::= { mpsCallThroughEntry 11 }

---------------------------------------------------------------------------
mpsGroupTable OBJECT-TYPE
    SYNTAX      SEQUENCE OF MpsGroupEntry
    MAX-ACCESS  not-accessible
    STATUS      current
    DESCRIPTION
        "This table contains the information of the global team parameter for 
         each extension group."
    ::= { mpsGroup 1 }

    mpsGroupEntry OBJECT-TYPE
        SYNTAX          MpsGroupEntry 
        MAX-ACCESS      not-accessible
        STATUS          current
        DESCRIPTION
            ""
        INDEX { mpsGroupIndex }
        ::= { mpsGroupTable 1 }

    MpsGroupEntry ::=
        SEQUENCE {
            mpsGroupIndex                       GroupIndex, 
            mpsGroupDisplayName                 DisplayString, 
            mpsGroupNumber                      DisplayString, 
            mpsGroupNoReplyTimeout              INTEGER, 
            mpsGroupMulticastTrigger            INTEGER, 
            mpsGroupCallForwardingEnable        TruthValue, 
            mpsGroupCallCalendar                Unsigned32, 
            mpsGroupAdminStatus                 INTEGER,
            mpsGroupCallForwardingExtern        TruthValue,
            mpsGroupWrapUpTime                  INTEGER,
            mpsGroupExtDescription              DisplayString,
	    mpsGroupType			INTEGER
        }

    mpsGroupIndex OBJECT-TYPE
        SYNTAX          GroupIndex
        MAX-ACCESS      read-write
        STATUS          current
        DESCRIPTION
            "A unique value for each group."
        ::= { mpsGroupEntry 1 }

    mpsGroupDisplayName OBJECT-TYPE
        SYNTAX          DisplayString (SIZE(0..20))
        MAX-ACCESS      read-write
        STATUS          current
        DESCRIPTION
            "Internal name of the group."
        ::= { mpsGroupEntry 2 }

    mpsGroupNumber OBJECT-TYPE
        SYNTAX          DisplayString (SIZE(0..4))
        MAX-ACCESS      read-write
        STATUS          current
        DESCRIPTION
            "This variable contains the extension number of the group. Allowing 
             all group members to be reached at all times for external and 
             internal calls"
        ::= { mpsGroupEntry 3 }

    mpsGroupNoReplyTimeout OBJECT-TYPE
        SYNTAX          INTEGER (1..999)
        UNITS           "s"
        MAX-ACCESS      read-write
        STATUS          current
        DESCRIPTION
            "The linear and rotating team calls allow you to configure a time 
             interval in seconds, after which the next member of the team will 
             be called."
        DEFVAL { 15 }
        ::= { mpsGroupEntry 4 }

    mpsGroupMulticastTrigger OBJECT-TYPE
        SYNTAX          INTEGER (1..999)
        UNITS           "s"
        MAX-ACCESS      read-write
        STATUS          current
        DESCRIPTION
            "The linear and rotating team calls allow you to configure a time 
             interval in seconds, after which all members of the team will be 
             called in parallel."
        DEFVAL { 60 }
        ::= { mpsGroupEntry 5 }

    mpsGroupCallForwardingEnable OBJECT-TYPE
        SYNTAX          TruthValue
        MAX-ACCESS      read-write
        STATUS          current
        DESCRIPTION
            "This value determine if call forwarding of the extension group 
             member will be done(1) or not(2)."
        DEFVAL { false }
        ::= { mpsGroupEntry 6 }

    mpsGroupCallCalendar OBJECT-TYPE
        SYNTAX          Unsigned32
        MAX-ACCESS      read-write
        STATUS          current
        DESCRIPTION
            "Select a calendar to switch the call mode automatically. After 
             you have selected a calendar you can set the active call mode. 
             0 (not active), 1 (day mode), 2 (night mode)."
        DEFVAL { 0 }
        ::= { mpsGroupEntry 7 }

    mpsGroupAdminStatus OBJECT-TYPE
        SYNTAX          INTEGER { enable(1), delete(2) }
        MAX-ACCESS      read-write
        STATUS          current
        DESCRIPTION
            "Just for MIB entry deletion."
        DEFVAL { enable }
        ::= { mpsGroupEntry 8 }

    mpsGroupCallForwardingExtern OBJECT-TYPE
        SYNTAX          TruthValue
        MAX-ACCESS      read-write
        STATUS          current
        DESCRIPTION
            "Use 2nd b-channel (false) or call deflection/partial rerouting
             (true) for call forwarding."
        DEFVAL { false }
        ::= { mpsGroupEntry 9 }

    mpsGroupWrapUpTime OBJECT-TYPE
        SYNTAX          INTEGER (0..999)
        UNITS           "s"
        MAX-ACCESS      read-write
        STATUS          current
        DESCRIPTION
            "This variable contains the length of timer in seconds for the wrap
	     up time.
             This timer value is used, if mpsGroupModeOperation is set to
	     'maxIdle'."
        DEFVAL { 0 }
        ::= { mpsGroupEntry 10 }

    mpsGroupExtDescription OBJECT-TYPE
        SYNTAX          DisplayString (SIZE(0..20))
        MAX-ACCESS      read-write
        STATUS          current
        DESCRIPTION
            "This value contains an extendend description in order to combine
             several mpsGroupTable entries in the GUI."
        ::= { mpsGroupEntry 11 }
		
	mpsGroupType OBJECT-TYPE
        SYNTAX		INTEGER { standard(1), alarmInput(2) }
        MAX-ACCESS      read-write
        STATUS          current
        DESCRIPTION
            "This variable contains the type of this group. The type is used to
	     determine mpsGroupTables for different applications."
        DEFVAL { standard }
        ::= { mpsGroupEntry 12 }

---------------------------------------------------------------------------
mpsGroupModeTable OBJECT-TYPE
    SYNTAX      SEQUENCE OF MpsGroupModeEntry
    MAX-ACCESS  not-accessible
    STATUS      current
    DESCRIPTION
        "This table contains the information about mode settings of a group."
    ::= { mpsGroup 2 }

    mpsGroupModeEntry OBJECT-TYPE
        SYNTAX          MpsGroupModeEntry 
        MAX-ACCESS      not-accessible
        STATUS          current
        DESCRIPTION
            ""
        INDEX { mpsGroupModeIndex, mpsGroupModeNumber }
        ::= { mpsGroupModeTable 1 }

    MpsGroupModeEntry ::=
        SEQUENCE {
            mpsGroupModeIndex                   GroupIndex, 
            mpsGroupModeNumber                  GroupModeIndex, 
            mpsGroupModeOperation               INTEGER, 
            mpsGroupModeRoutingType             INTEGER,
            mpsGroupModeCFUEnable               TruthValue, 
            mpsGroupModeCFUTargetNumber         DisplayString, 
            mpsGroupModeCFUSourceIndex          ExtensionIndexOrZero, 
            mpsGroupModeBusyOnBusy              INTEGER, 
            mpsGroupModeCFNRTimer               INTEGER, 
            mpsGroupModeCFNRTargetGroup         GroupIndexOrZero,
            mpsGroupModeAdminStatus             INTEGER,
            mpsGroupModeAutoCallAccept          TruthValue,
            mpsGroupModeMusicOnHold             INTEGER,
	    mpsGroupModeMOHFileDirectory	DisplayString,
	    mpsGroupModeMOHDefaultVariant	INTEGER,
            mpsGroupModeReRouteIndex            ReRouteIndexOrZero
        }

    mpsGroupModeIndex OBJECT-TYPE
        SYNTAX          GroupIndex
        MAX-ACCESS      read-write
        STATUS          current
        DESCRIPTION
            "A unique value for each group"
        ::= { mpsGroupModeEntry 1 }

    mpsGroupModeNumber OBJECT-TYPE
        SYNTAX          GroupModeIndex
        MAX-ACCESS      read-write
        STATUS          current
        DESCRIPTION
            "A unique value for each mode of a group."
        ::= { mpsGroupModeEntry 2 }

    mpsGroupModeOperation OBJECT-TYPE
        SYNTAX          INTEGER {
                            multicast(1),
                            chainNoRepeat(2),
                            chainRepeat(3),
                            growing(4),
                            chainNoRepeatWithMulticastTimer(5),
                            chainRepeatWithMulticastTimer(6),
                            maxIdle(7),
                            call-center(8)
                        }
        MAX-ACCESS      read-write
        STATUS          current
        DESCRIPTION
            "Signalling mode of the group:
             multicast                      : all assigned terminals are called
					      simultaneously
             chainNoRepeat                  : All assigned terminals are called
					      in the sequence of their entry in
					      configuration.
             chainRepeat                    : This call is a special case of the
					      linear call. 
                                              After all terminals are called,
					      call signalling begins again with
					      the first entered terminal.
             growing                        : The terminals are called in the
					      sequence of their entry in the
					      subscriber list. Every terminal
					      that has already been called is
					      called again, until all entered
					      terminals are called.
             chainNoRepeatWithMulticastTimer: chainNoRepeat + after defined
					      times have run out, all team
					      subscribers can be called in
					      parallel.
             chainRepeatWithMulticastTimer  : chainRepeat + after defined times
					      have run out, all team
					      subscribers can be called in
					      parallel.
             maxIdle                        : Even distribution corresponds to 
					      'chainRepeat' and ensures that all
					      team subscribers receive the same
					      number of calls
             call-center                    : for call-center application."

        DEFVAL { multicast }
        ::= { mpsGroupModeEntry 3 }

    mpsGroupModeRoutingType OBJECT-TYPE
        SYNTAX          INTEGER {
                            standard(1),
                            busyOnBusy(2)
                        }
        MAX-ACCESS      read-write
        STATUS          current
        DESCRIPTION
            "Additonal info for the signalling mode. 
             standard(1)  :  standard routing, busy check.
             busyOnBusy(2):  check busy conditions -> The whole team is busy,
                             if one team subscriber is busy."
         DEFVAL { standard }
        ::= { mpsGroupModeEntry 4 }

    mpsGroupModeCFUEnable OBJECT-TYPE
        SYNTAX          TruthValue
        MAX-ACCESS      read-write
        STATUS          current
        DESCRIPTION
            "Determines group members are either only extension (false) or
	     an external destination (true).

	     For further implementations this variable is obsolete while 
	     group members should uniformly defined in mpsGroupModeChainTable.
	     For more information have a look at its variable descriptions,
	     in particular variables mpsGroupModeChainExternalNumber and
	     mpsGroupModeChainExtension are of interest here."
        DEFVAL { false }
        ::= { mpsGroupModeEntry 5 }

    mpsGroupModeCFUTargetNumber OBJECT-TYPE
        SYNTAX          DisplayString (SIZE(0..20))
        MAX-ACCESS      read-write
        STATUS          current
        DESCRIPTION
            "This external number (destiantion) will be called, 
             if mpsGroupModeCFUEnable set to true.

	     For further implementations this variable is not any longer
	     necessary. The external numbers are saved in the
	     mpsGroupModeChainTable.
	     New variable mpsGroupModeChainExternalNumber will be created to
	     store external numbers."
        ::= { mpsGroupModeEntry 6 }

    mpsGroupModeCFUSourceIndex OBJECT-TYPE
        SYNTAX          ExtensionIndexOrZero
        MAX-ACCESS      read-write
        STATUS          current
        DESCRIPTION
            "The charge information will be stored for this extension."
        DEFVAL { 0 }
        ::= { mpsGroupModeEntry 7 }

    mpsGroupModeBusyOnBusy OBJECT-TYPE
        SYNTAX          INTEGER (1..16)
        MAX-ACCESS      read-write
        STATUS          current
        DESCRIPTION
             "Decides whether additional calls for this team should be signalled
              or not. This variable contains the threshold for busy signalling."
        DEFVAL { 1 }
        ::= { mpsGroupModeEntry 8 }

    mpsGroupModeCFNRTimer OBJECT-TYPE
        SYNTAX          INTEGER (1..999)
        MAX-ACCESS      read-write
        STATUS          current
        DESCRIPTION
            "This is the delay until rerouting starts."
        DEFVAL { 10 }
        ::= { mpsGroupModeEntry 9 }

    mpsGroupModeCFNRTargetGroup OBJECT-TYPE
        SYNTAX          GroupIndexOrZero
        MAX-ACCESS      read-write
        STATUS          current
        DESCRIPTION
            "Group index for rerouting."
        DEFVAL { 0 }
        ::= { mpsGroupModeEntry 10 }

    mpsGroupModeAdminStatus OBJECT-TYPE
        SYNTAX          INTEGER {
                            enable(1),
                            delete(2)
                        }
        MAX-ACCESS      read-write
        STATUS          current
        DESCRIPTION
            "Just for MIB entry deletion."
        DEFVAL { enable }
        ::= { mpsGroupModeEntry 11 }

    mpsGroupModeAutoCallAccept OBJECT-TYPE
        SYNTAX          TruthValue
        MAX-ACCESS      read-write
        STATUS          current
        DESCRIPTION
            "If true, every call will be connected immediately with MoH.
             Selected MoH contains on mpsGroupModeMusicOnHold settings."
        DEFVAL { false }
        ::= { mpsGroupModeEntry 12 }

    mpsGroupModeMusicOnHold OBJECT-TYPE
        SYNTAX          INTEGER {
                            -- file1(1),
                            -- file2(2),
                            -- file3(3),
                            -- file4(4),
                            -- file5(5),
                            -- file6(6),
                            -- file7(7),
                            -- file8(8),
                            -- default1(51),
                            -- default2(52),
			    file(54),
			    default(55),
                            external(80)
                        }
        MAX-ACCESS      read-write
        STATUS          current
        DESCRIPTION
            "This variable contains the selected music on hold (MoH) that a party
             is to hear if mpsGroupModeAutoCallAccept = true.
	     Possible values are:
		file:	  variable mpsGroupModeMOHFileDirectory specifies
			  directory to contain sound file
		default:  variable mpsGroupModeMOHDefaultVariant specifies the
			  variant whose default is to be used (default)
		external: external source is used"
        DEFVAL { default }
        ::= { mpsGroupModeEntry 13 }


    mpsGroupModeReRouteIndex OBJECT-TYPE
        SYNTAX          ReRouteIndexOrZero
        MAX-ACCESS      read-write
        STATUS          current
        DESCRIPTION
            "Index of the ReRouting function in mpsReRouteTable.
             0 = ReRouting function deactived."
        DEFVAL { 0 }
        ::= { mpsGroupModeEntry 14 }


    mpsGroupModeMOHFileDirectory OBJECT-TYPE
        SYNTAX          DisplayString
        MAX-ACCESS      read-write
        STATUS          current
        DESCRIPTION
            "Name of directory (on flash medium) which contains file to be used
	     for music on hold.
             This variable references the entry in mpsWaveFile table where
	     variable mpsWaveFileDirectory has identical content.
	     If there should be multiple entrys with the same content for some
	     reason an arbitrary entry is chosen.
	     This entry is only valid if variable mpsGroupModeMusicOnHold is set
	     to value file.

	     Default value is the empty string."
        DEFVAL { "" }
        ::= { mpsGroupModeEntry 15 }


    mpsGroupModeMOHDefaultVariant OBJECT-TYPE
        SYNTAX          INTEGER (1..2)
        MAX-ACCESS      read-write
        STATUS          current
        DESCRIPTION
            "This variable specifies the chosen default variant if variable
	     mpsGroupModeMusicOnHold is set to value default.

	     Default value for that variable is 1."
        DEFVAL { 1 }
        ::= { mpsGroupModeEntry 16 }

---------------------------------------------------------------------------
mpsGroupModeChainTable OBJECT-TYPE
    SYNTAX      SEQUENCE OF MpsGroupModeChainEntry
    MAX-ACCESS  not-accessible
    STATUS      current
    DESCRIPTION
        "This table contains the extension in each group and Mode."
    ::= { mpsGroup 3 }

    mpsGroupModeChainEntry OBJECT-TYPE
        SYNTAX          MpsGroupModeChainEntry 
        MAX-ACCESS      not-accessible
        STATUS          current
        DESCRIPTION
            ""
        INDEX { mpsGroupModeChainGroup, mpsGroupModeChainGroupMode, 
                mpsGroupModeChainPosition }
        ::= { mpsGroupModeChainTable 1 }

    MpsGroupModeChainEntry ::=
        SEQUENCE {
            mpsGroupModeChainGroup              GroupIndex, 
            mpsGroupModeChainGroupMode          GroupModeIndex, 
            mpsGroupModeChainPosition           Unsigned32, 
            mpsGroupModeChainExtension          ExtensionIndexOrZero, 
            mpsGroupModeChainAdminStatus        INTEGER,
	    mpsGroupModeChainExternalNumber	DisplayString
        }

    mpsGroupModeChainGroup OBJECT-TYPE
        SYNTAX          GroupIndex
        MAX-ACCESS      read-write
        STATUS          current
        DESCRIPTION
            "A unique value for each group, reference to mpsGroupTable and
             mpsGroupModeTable."
        ::= { mpsGroupModeChainEntry 1 }

    mpsGroupModeChainGroupMode OBJECT-TYPE
        SYNTAX          GroupModeIndex
        MAX-ACCESS      read-write
        STATUS          current
        DESCRIPTION
            "A unique value for each Mode, reference to mpsGroupModeTable
             (same as mpsGroupModeNumber)."
        ::= { mpsGroupModeChainEntry 2 }

    mpsGroupModeChainPosition OBJECT-TYPE
        SYNTAX          Unsigned32
        MAX-ACCESS      read-write
        STATUS          current
        DESCRIPTION
            "A unique value for each priority."
        ::= { mpsGroupModeChainEntry 3 }

    mpsGroupModeChainExtension OBJECT-TYPE
        SYNTAX          ExtensionIndexOrZero
        MAX-ACCESS      read-write
        STATUS          current
        DESCRIPTION
            "A unique value for each extension, reference to mpsExtensionTable.

	     For further implementations this variable contains the reference to
	     an mpsExtension entry or 0, to determine internal and external 
	     group members.
	     Different membership:
	     1.) External member
		 (mpsGroupModeChainExternalNumber = a valid external number) && 
		 (mpsGroupModeChainExtension  = 0)
	     2.) Internal member
		  (mpsGroupModeChainExternalNumber = empty string) && 
		  (mpsGroupModeChainExtension != 0)
	     3.) Internal member
		  (mpsGroupModeChainExternalNumber = a valid external number) &&
		  (mpsGroupModeChainExtension != 0)
	     4.) Invalid entry
		  (mpsGroupModeChainExternalNumber = empty string) && 
		  (mpsGroupModeChainExtension  = 0)"
        DEFVAL { 0 }
		::= { mpsGroupModeChainEntry 4 }

    mpsGroupModeChainAdminStatus OBJECT-TYPE
        SYNTAX          INTEGER { enable(1), delete(2) }
        MAX-ACCESS      read-write
        STATUS          current
        DESCRIPTION
            "Just for MIB entry deletion."
        DEFVAL { enable }
        ::= { mpsGroupModeChainEntry 5 }
		
    mpsGroupModeChainExternalNumber OBJECT-TYPE
        SYNTAX          DisplayString (SIZE(0..20))
        MAX-ACCESS      read-write
        STATUS          current
        DESCRIPTION
            "For further implementations in this variable contains external
	     numbers. To show that the mpsGroupModeChainEntry is assigned to an
	     external team member, the mpsGroupModeChainExtension must be set to
	     0."
        ::= { mpsGroupModeChainEntry 6 }

---------------------------------------------------------------------------
mpsGroupActiveTable OBJECT-TYPE
    SYNTAX      SEQUENCE OF MpsGroupActiveEntry
    MAX-ACCESS  not-accessible
    STATUS      current
    DESCRIPTION
        "This table contains information of logged in or logged out state for 
         each extension in a group."
    ::= { mpsGroup 4 }

    mpsGroupActiveEntry OBJECT-TYPE
        SYNTAX          MpsGroupActiveEntry 
        MAX-ACCESS      not-accessible
        STATUS          current
        DESCRIPTION
            ""
        INDEX { mpsGroupActiveGroup, mpsGroupActiveExtension }
        ::= { mpsGroupActiveTable 1 }

    MpsGroupActiveEntry ::=
        SEQUENCE {
            mpsGroupActiveGroup                 GroupIndex, 
            mpsGroupActiveExtension             ExtensionIndex, 
            mpsGroupActiveFlag                  TruthValue, 
            mpsGroupActiveAdminStatus           INTEGER
        }

    mpsGroupActiveGroup OBJECT-TYPE
        SYNTAX          GroupIndex
        MAX-ACCESS      read-write
        STATUS          current
        DESCRIPTION
            "A unique value for each group, reference to mpsGroupTable."
        ::= { mpsGroupActiveEntry 1 }

    mpsGroupActiveExtension OBJECT-TYPE
        SYNTAX          ExtensionIndex
        MAX-ACCESS      read-write
        STATUS          current
        DESCRIPTION
            "A unique value for each extension, reference to mpsExtensionTable."
        ::= { mpsGroupActiveEntry 2 }

    mpsGroupActiveFlag OBJECT-TYPE
        SYNTAX          TruthValue
        MAX-ACCESS      read-write
        STATUS          current
        DESCRIPTION
            "Extension group member is logged in(1) or logged out(2)."
        DEFVAL { 2 }
        ::= { mpsGroupActiveEntry 3 }

    mpsGroupActiveAdminStatus OBJECT-TYPE
        SYNTAX          INTEGER { enable(1), delete(2) }
        MAX-ACCESS      read-write
        STATUS          current
        DESCRIPTION
            "Just for MIB entry deletion."
        DEFVAL { enable }
        ::= { mpsGroupActiveEntry 4 }

---------------------------------------------------------------------------
mpsGroupUserTable OBJECT-TYPE
    SYNTAX      SEQUENCE OF MpsGroupUserEntry
    MAX-ACCESS  not-accessible
    STATUS      current
    DESCRIPTION
        "This table contains the information of the current mode for each 
         group."
    ::= { mpsGroup 5 }

    mpsGroupUserEntry OBJECT-TYPE
        SYNTAX          MpsGroupUserEntry 
        MAX-ACCESS      not-accessible
        STATUS          current
        DESCRIPTION
            ""
        INDEX { mpsGroupUserIndex }
        ::= { mpsGroupUserTable 1 }

    MpsGroupUserEntry ::=
        SEQUENCE {
            mpsGroupUserIndex                   GroupIndex, 
            mpsGroupUserModeNumber              GroupModeIndex, 
            mpsGroupUserAdminStatus             INTEGER
        }

    mpsGroupUserIndex OBJECT-TYPE
        SYNTAX          GroupIndex
        MAX-ACCESS      read-write
        STATUS          current
        DESCRIPTION
            "A unique value for each group, reference to mpsGroupTable."
        ::= { mpsGroupUserEntry 1 }

    mpsGroupUserModeNumber OBJECT-TYPE
        SYNTAX          GroupModeIndex
        MAX-ACCESS      read-write
        STATUS          current
        DESCRIPTION
            "Select the active call mode list, reference to mpsGroupModeTable
             (same as mpsGroupModeNumber)."
        ::= { mpsGroupUserEntry 2 }

    mpsGroupUserAdminStatus OBJECT-TYPE
        SYNTAX          INTEGER { enable(1), delete(2) }
        MAX-ACCESS      read-write
        STATUS          current
        DESCRIPTION
            "Just for MIB entry deletion."
        DEFVAL { enable }
        ::= { mpsGroupUserEntry 3 }

---------------------------------------------------------------------------
mpsGroupStatusTable OBJECT-TYPE
    SYNTAX      SEQUENCE OF MpsGroupStatusEntry
    MAX-ACCESS  not-accessible
    STATUS      current
    DESCRIPTION
        "This table contains status information about groups,
         used for call-center application."
    ::= { mpsGroup 6 }

    mpsGroupStatusEntry OBJECT-TYPE
        SYNTAX          MpsGroupStatusEntry 
        MAX-ACCESS      not-accessible
        STATUS          current
        DESCRIPTION
            ""
        INDEX { mpsGroupStatusIndex }
        ::= { mpsGroupStatusTable 1 }

    MpsGroupStatusEntry ::=
        SEQUENCE {
            mpsGroupStatusIndex                 GroupIndex, 
            mpsGroupStatusActiveCalls           Counter32, 
            mpsGroupStatusWaitingCalls          Counter32,
            mpsGroupStatusSumConnectedCalls     Counter32,
            mpsGroupStatusConnectedCalls        Counter32,
            mpsGroupStatusSumLostCalls          Counter32,
            mpsGroupStatusLostCalls             Counter32
        }

    mpsGroupStatusIndex OBJECT-TYPE
        SYNTAX          GroupIndex
        MAX-ACCESS      read-write
        STATUS          current
        DESCRIPTION
            "A unique value for each group."
        DEFVAL { 1 }
        ::= { mpsGroupStatusEntry 1 }

    mpsGroupStatusActiveCalls OBJECT-TYPE
        SYNTAX          Counter32
        MAX-ACCESS      read-only
        STATUS          current
        DESCRIPTION
            "This variable contains the number of currently active calls. "
        DEFVAL { 0 }
        ::= { mpsGroupStatusEntry 2 }

    mpsGroupStatusWaitingCalls OBJECT-TYPE
        SYNTAX          Counter32
        MAX-ACCESS      read-only
        STATUS          current
        DESCRIPTION
            "This variable contains the number of currently waiting calls."
        DEFVAL { 0 }
        ::= { mpsGroupStatusEntry 3 }

    mpsGroupStatusSumConnectedCalls OBJECT-TYPE
        SYNTAX          Counter32
        MAX-ACCESS      read-only
        STATUS          current
        DESCRIPTION
            "This variable contains the summary of connected calls."
        DEFVAL { 0 }
        ::= { mpsGroupStatusEntry 4 }

    mpsGroupStatusConnectedCalls OBJECT-TYPE
        SYNTAX          Counter32
        MAX-ACCESS      read-only
        STATUS          current
        DESCRIPTION
            "This value is a copy from mpsGroupStatusSumConnectedCall at 0:00h.
             To get the summary of the connected calls from a day, subtract the 
             the mpsGroupStatusConnectedCalls from 
             mpsGroupStatusSumConnectedCalls."
        DEFVAL { 0 }
        ::= { mpsGroupStatusEntry 5 }

    mpsGroupStatusSumLostCalls OBJECT-TYPE
        SYNTAX          Counter32
        MAX-ACCESS      read-only
        STATUS          current
        DESCRIPTION
            "This variable contains the summary of lost calls."
        DEFVAL { 0 }
        ::= { mpsGroupStatusEntry 6 }

    mpsGroupStatusLostCalls OBJECT-TYPE
        SYNTAX          Counter32
        MAX-ACCESS      read-only
        STATUS          current
        DESCRIPTION
            "This value is a copy from mpsGroupStatusSumLostCalls at 0:00h.
             To get the summary of the lost calls from a day, subtract the 
             the mpsGroupStatusLostCalls from mpsGroupStatusSumLostCalls."
        DEFVAL { 0 }
        ::= { mpsGroupStatusEntry 7 }

---------------------------------------------------------------------------
mpsExtensionTable OBJECT-TYPE
    SYNTAX      SEQUENCE OF MpsExtensionEntry
    MAX-ACCESS  not-accessible
    STATUS      current
    DESCRIPTION
        "This table contains all internal extensions."
    ::= { mpsExtension 1 }

    mpsExtensionEntry OBJECT-TYPE
        SYNTAX          MpsExtensionEntry
        MAX-ACCESS      not-accessible
        STATUS          current
        DESCRIPTION
            ""
        INDEX { mpsExtensionIndex }
        ::= { mpsExtensionTable 1 }

    MpsExtensionEntry ::=
        SEQUENCE {
            mpsExtensionIndex              ExtensionIndex, 
            mpsExtensionIfIndex            InterfaceIndexOrZero, 
            mpsExtensionDeviceVirtualIndex INTEGER,
            mpsExtensionNumber             DisplayString, 
            mpsExtensionDisplayName        DisplayString, 
            mpsExtensionAuthName           DisplayString, 
            mpsExtensionAdminStatus        INTEGER,
            mpsExtensionUser               UserIndexOrZero,
            mpsExtensionFacStatus          INTEGER,
            mpsExtensionFacilities         BITS,
            mpsExtensionChargeCounter      INTEGER,
            mpsExtensionReRouteAppl        ReRouteApplIndexOrZero
        }

    mpsExtensionIndex OBJECT-TYPE
        SYNTAX          ExtensionIndex
        MAX-ACCESS      read-write
        STATUS          current
        DESCRIPTION
            "A unique value for each internal extension."
        ::= { mpsExtensionEntry 1 }

    mpsExtensionIfIndex OBJECT-TYPE
        SYNTAX          InterfaceIndexOrZero
        MAX-ACCESS      read-write
        STATUS          obsolete
        DESCRIPTION
            "InterfaceIndex where the extension is placed."
        ::= { mpsExtensionEntry 2 }

    mpsExtensionDeviceVirtualIndex OBJECT-TYPE
        SYNTAX          INTEGER
        MAX-ACCESS      read-write
        STATUS          obsolete
        DESCRIPTION
            "This variable contains the virtual device index of the
             mpsDeviceVirtual table, if the mpsExtensionIfIndex is zero."
        DEFVAL { 0 }
        ::= { mpsExtensionEntry 3 }

    mpsExtensionNumber OBJECT-TYPE
        SYNTAX          DisplayString (SIZE(0..4))
        MAX-ACCESS      read-write
        STATUS          current
        DESCRIPTION
            "This variable contains the internal number for the extension."
        ::= { mpsExtensionEntry 4 }

    mpsExtensionDisplayName OBJECT-TYPE
        SYNTAX          DisplayString (SIZE(0..20))
        MAX-ACCESS      read-write
        STATUS          current
        DESCRIPTION
            "Internal name of the extension. This name will be displayed as 
             internal calling party."
        ::= { mpsExtensionEntry 5 }

    mpsExtensionAuthName OBJECT-TYPE
        SYNTAX          DisplayString (SIZE(0..20))
        MAX-ACCESS      read-write
        STATUS          current
        DESCRIPTION
            "Login name for VoIP-registration at the PBX."
        ::= { mpsExtensionEntry 6 }

    mpsExtensionAdminStatus OBJECT-TYPE
        SYNTAX          INTEGER {
                            enable(1),
                            delete(2)
                        }
        MAX-ACCESS      read-write
        STATUS          current
        DESCRIPTION
            "Just for MIB entry deletion."
        DEFVAL { enable }
        ::= { mpsExtensionEntry 7 }

    mpsExtensionUser OBJECT-TYPE
        SYNTAX      UserIndexOrZero
        MAX-ACCESS  read-write
        STATUS      current
        DESCRIPTION
            "This variable contains the reference to mpsUserIndex in
             mpsUserTable."
        DEFVAL { 0 }
        ::= { mpsExtensionEntry 8 }

    mpsExtensionFacStatus OBJECT-TYPE
        SYNTAX  INTEGER { idle(1),
                          barred(2),
                          room-supervision(3),
                          trunk-transfered(4)
                        }
        MAX-ACCESS  read-only
        STATUS      current
        DESCRIPTION
             "This variable contains the status for this extension.
              This status is set from call control to handle ccbs or ccnr
              (barred), room-supervision or temporarily trunk access for this
              extension."
        DEFVAL { idle }
        ::= { mpsExtensionEntry 9 }

    mpsExtensionFacilities OBJECT-TYPE
        SYNTAX          BITS { mwi-tone(0) }
        MAX-ACCESS      read-write
        STATUS          current
        DESCRIPTION
            "Extension facilities.
                mwi-tone : message waiting indication -> special tone.
            "
        ::= { mpsExtensionEntry 10 }

    mpsExtensionChargeCounter OBJECT-TYPE
        SYNTAX          INTEGER
        MAX-ACCESS      read-write
        STATUS          current
        DESCRIPTION
            "This variable contains current total charge counter for this
             extension.
             This value is standardized to a thousandth.
             Update via acctStoreTable.
             Cleanup this charge counter, set to '-1'."
        DEFVAL { 0 }
        ::= { mpsExtensionEntry 11 }

    mpsExtensionReRouteAppl OBJECT-TYPE
        SYNTAX          ReRouteApplIndexOrZero
        MAX-ACCESS      read-write
        STATUS          current
        DESCRIPTION
            "Index of ReRouting application in mpsReRouteApplTable.
             Value 0 means that ReRouting application is inactive."
        DEFVAL { 0 }
        ::= { mpsExtensionEntry 12 }

---------------------------------------------------------------------------
mpsExtensionAdminTable OBJECT-TYPE
    SYNTAX      SEQUENCE OF MpsExtensionAdminEntry
    MAX-ACCESS  not-accessible
    STATUS      current
    DESCRIPTION
        "This table contains extended settings for internal extension."
    ::= { mpsExtension 2 }

    mpsExtensionAdminEntry OBJECT-TYPE
        SYNTAX          MpsExtensionAdminEntry 
        MAX-ACCESS      not-accessible
        STATUS          current
        DESCRIPTION
            ""
        INDEX { mpsExtensionAdminIndex }
        ::= { mpsExtensionAdminTable 1 }

    MpsExtensionAdminEntry ::=
        SEQUENCE {
            mpsExtensionAdminIndex              ExtensionIndex, 
            mpsExtensionAdminDialAuthorisation  INTEGER, 
            mpsExtensionAdminFacilities         BITS, 
            mpsExtensionAdminPickupGroup        INTEGER, 
            mpsExtensionAdminPhonebookAccess    INTEGER, 
            mpsExtensionAdminMusicOnHold        INTEGER, 
            mpsExtensionAdminAdminStatus        INTEGER,
            mpsExtensionAdminCalendar           CalendarIndexOrZero,
            mpsExtensionAdminWrapUpTime         INTEGER
        }

    mpsExtensionAdminIndex OBJECT-TYPE
        SYNTAX          ExtensionIndex
        MAX-ACCESS      read-write
        STATUS          current
        DESCRIPTION
            "A unique value for each extension."
        ::= { mpsExtensionAdminEntry 1 }

    mpsExtensionAdminDialAuthorisation OBJECT-TYPE
        SYNTAX          INTEGER {
                            unknown(1),
                            international(2),
                            incoming(3),
                            national(4),
                            region(5),
                            internal(6),
                            onlyDoorIntercom(7),
                            local(8)
                        }
        MAX-ACCESS      read-write
        STATUS          obsolete
        DESCRIPTION
            "Dialing privileges for a extension specifies what type of calls 
             (internal, external, etc. ) this extension can place. Default is 
             international."
        DEFVAL { international }
        ::= { mpsExtensionAdminEntry 2 }

    mpsExtensionAdminFacilities OBJECT-TYPE
        SYNTAX          BITS {
                            suppress-A-Addr(0),
                            suppress-B-Addr(1),
                            store-charge(2),
                            doorIntercom-access(3),
                            auto-trunk-req(4),
                            keypad(5),
                            route-barring(6),
                            add-trunk-acc-dig(7),
                            rma-access(8),
                            extern-diversion(9),
                            extern-hold(10),
                            add-line-acc-dig(11),
                            msg-waiting(12),
                            time-lock(13),
                            sms(14),
                            rma-user-access(15),
                            tapi(16),
                            ccnr(17),
                            showInPhonebook(18),
                            statusLED(19),
                            call-center-agent(20)
                        }
        MAX-ACCESS      read-write
        STATUS          current
        DESCRIPTION
            "Special facilities of the extension.
                suppress-A-Addr:      Suppress outgoing CLIP information (CLIR).
                suppress-B-Addr:      This value determines if supression number
                                      of called party (COLR) is enabled or not.
                store-charge:         Charge information for this subscriber will
                                      be record or not.
                doorIntercom-access:  Authorizes an internal subscriber to
                                      establish a connection with the door entry
                                      phone or open the door.
                auto-trunk-req:       This setting defines whether automatic
                                      access to an outside line is to be
                                      configured for the selected subscriber.
                keypad:               Authorizes an internal subscriber to carry
                                      out KEYPAD functions.
                route-barring:        If you have configured the dialing filter
                                      (consisting of an inhibit and release
                                      filter) in the PBX system you can use these
                                      settings to define whether the selected
                                      subscriber is subject to the  constraints/
                                      privileges imposed/offered by the dialing
                                      filter.
                add-trunk-acc-dig:    The line access code is placed in front of
                                      the number automatically by the PBX system
                                      for incoming external calls.
                rma-access:           This permits a subscriber to activate the
                                      service access to the PBX system, or to
                                      establish a corresponding service
                                      connection on their own.
                extern-diversion:     You can use this setting to define whether
                                      external call forwarding for the internal
                                      subscriber is to be executed within the PBX
                                      system or at the exchange.
                extern-hold:          You can use this setting to define whether
                                      external call hold for the internal
                                      subscriber is to be executed within the PBX
                                      system or at the exchange.
                add-line-acc-dig:     The internal dialing code is places in
                                      front of the number automatically 
                                      by the PBX system for incoming internal
                                      calls.
                msg-waiting:          Message waiting indication on or off.
                time-lock:            If on, the access rights will be changed at
                                      a time specified in the calendar.
                sms:                  Authorizes an internal subscriber to
                                      receive SMS messages.
                rma-user-access:      Authorization for remote access activation
                                      is on or off.
                tapi:                 Authorizes a subscriber to use the PBX's
                                      TAPI features.
                ccnr:                 The completion of call on no answer (CCNR)
                                      feature is available to the user.
                showInPhonebook:      Show this extension number in display at
                                      access to the global phonebook.
                statusLED:            Show status of this extension number at
                                      status LED at systemphones.
                call-center-agent:    Mark this extension as call center agent.
        ."
        ::= { mpsExtensionAdminEntry 3 }

    mpsExtensionAdminPickupGroup OBJECT-TYPE
        SYNTAX          INTEGER
        MAX-ACCESS      read-write
        STATUS          obsolete
        DESCRIPTION
            "Enter the number of the group in which calls are to be taken."
        DEFVAL { 0 }
        ::= { mpsExtensionAdminEntry 4 }

    mpsExtensionAdminPhonebookAccess OBJECT-TYPE
        SYNTAX          INTEGER {
                            denied(1),
                            restricted(2),
                            unrestricted(3)
                        }
        MAX-ACCESS      read-write
        STATUS          obsolete
        DESCRIPTION
            "This value determine the access to the PBX phonebook."
        DEFVAL { restricted }
        ::= { mpsExtensionAdminEntry 5 }

    mpsExtensionAdminMusicOnHold OBJECT-TYPE
        SYNTAX          INTEGER {
                            file1(1),
                            file2(2),
                            file3(3),
                            file4(4),
                            file5(5),
                            file6(6),
                            file7(7),
                            file8(8),
                            dialtone(50),
                            default1(51),
                            default2(52),
                            external(80)
                        }
        MAX-ACCESS      read-write
        STATUS          obsolete
        DESCRIPTION
            "This variable contains the selected music on hold (MoH) that a party
             is to hear that has been transferred by the selected internal
             subscriber. "
        DEFVAL { default1 }
        ::= { mpsExtensionAdminEntry 6 }

    mpsExtensionAdminAdminStatus OBJECT-TYPE
        SYNTAX          INTEGER {
                            enable(1),
                            delete(2)
                        }
        MAX-ACCESS      read-write
        STATUS          current
        DESCRIPTION
            "Just for MIB entry deletion."
        DEFVAL { enable }
        ::= { mpsExtensionAdminEntry 7 }

    mpsExtensionAdminCalendar OBJECT-TYPE
        SYNTAX          CalendarIndexOrZero
        MAX-ACCESS      read-write
        STATUS          current
        DESCRIPTION
            "Select a calendar index to switch the call distribution for
             rerouting via calendar."
        DEFVAL { 0 }
        ::= { mpsExtensionAdminEntry 8 }

    mpsExtensionAdminWrapUpTime OBJECT-TYPE
        SYNTAX          INTEGER (0..999)
        UNITS           "s"
        MAX-ACCESS      read-write
        STATUS          current
        DESCRIPTION
            "This variable contains the length of timer in seconds for the wrap
             up time.
             This timer value is used, if mpsGroupModeOperation is set to
             'callcenter'."
        DEFVAL { 60 }
        ::= { mpsExtensionAdminEntry 9 }

---------------------------------------------------------------------------
mpsExtensionUserTable OBJECT-TYPE
    SYNTAX      SEQUENCE OF MpsExtensionUserEntry
    MAX-ACCESS  not-accessible
    STATUS      current
    DESCRIPTION
        "This table contains extended settings for internal extensions."
    ::= { mpsExtension 3 }

    mpsExtensionUserEntry OBJECT-TYPE
        SYNTAX          MpsExtensionUserEntry 
        MAX-ACCESS      not-accessible
        STATUS          current
        DESCRIPTION
            ""
        INDEX { mpsExtensionUserIndex }
        ::= { mpsExtensionUserTable 1 }

    MpsExtensionUserEntry ::=
        SEQUENCE {
            mpsExtensionUserIndex               ExtensionIndex, 
            mpsExtensionUserAuthPassword        DisplayString, 
            mpsExtensionUserChargeLimit         Unsigned32, 
            mpsExtensionUserDirectCall          DirectCallIndexOrZero, 
            mpsExtensionUserFacilities          BITS, 
            mpsExtensionUserAdminStatus         INTEGER,
            mpsExtensionUserUserMode            Unsigned32
        }

    mpsExtensionUserIndex OBJECT-TYPE
        SYNTAX          ExtensionIndex
        MAX-ACCESS      read-write
        STATUS          current
        DESCRIPTION
            "This variable references the mpsExtensionIndex."
        ::= { mpsExtensionUserEntry 1 }

    mpsExtensionUserAuthPassword OBJECT-TYPE
        SYNTAX          DisplayString (SIZE(0..8))
        MAX-ACCESS      read-write
        STATUS          current
        DESCRIPTION
            "Password for VoIP-registration at the PBX."
        ::= { mpsExtensionUserEntry 2 }

    mpsExtensionUserChargeLimit OBJECT-TYPE
        SYNTAX          Unsigned32
        MAX-ACCESS      read-write
        STATUS          current
        DESCRIPTION
            "This variable contains the maximum amounts available for calling."
        ::= { mpsExtensionUserEntry 3 }

    mpsExtensionUserDirectCall OBJECT-TYPE
        SYNTAX          DirectCallIndexOrZero
        MAX-ACCESS      read-write
        STATUS          current
        DESCRIPTION
            "This variable contains the index of the DirectCallTable.
             0 = disabled."
        DEFVAL { 0 }
        ::= { mpsExtensionUserEntry 4 }

    mpsExtensionUserFacilities OBJECT-TYPE
        SYNTAX          BITS {
                            charge-limit(0),
                            call-waiting(1),
                            announcement(2),
                            intercom(3),
                            silent-phone-intern(4),
                            silent-phone-extern(5),
                            direct-call(6),
                            parallel-ringing(7)
                        }
        MAX-ACCESS      read-write
        STATUS          current
        DESCRIPTION
            "Special facilities of the extension.
                charge-limit:         This value determines if the maximum
                                      amounts available for calling is enabled.
                call-waiting:         Call waiting signal for analog terminals.
                                      ISDN terminal devices use their own special
                                      procedures for this.
                announcement:         Enables this phone to receive announcement
                                      calls.
                intercom:             Allows intercom calls to the system
                                      telephone or to another identical ISDN
                                      telephone.
                silent-phone-intern:  Enables a silent phone for incoming
                                      internal calls.
                silent-phone-extern:  Enables a silent phone for incoming
                                      external calls.
                direct-call :         Enables a direct call.
                parallel-ringing:     Enables parallel ringing."
        ::= { mpsExtensionUserEntry 5 }

    mpsExtensionUserAdminStatus OBJECT-TYPE
        SYNTAX          INTEGER {
                            enable(1),
                            delete(2)
                        }
        MAX-ACCESS      read-write
        STATUS          current
        DESCRIPTION
            "Just for MIB entry deletion."
        DEFVAL { enable }
        ::= { mpsExtensionUserEntry 6 }

    mpsExtensionUserUserMode OBJECT-TYPE
        SYNTAX          Unsigned32
        MAX-ACCESS      read-write
        STATUS          current
        DESCRIPTION
            "This variable contains the actual mode for the incoming call
             distribution to a reroute function."
        ::= { mpsExtensionUserEntry 7 }

---------------------------------------------------------------------------
mpsExtensionSourceTable OBJECT-TYPE
    SYNTAX      SEQUENCE OF MpsExtensionSourceEntry
    MAX-ACCESS  not-accessible
    STATUS      current
    DESCRIPTION
        "This table contains the outgoing CLIP information for each subscriber,
         that will be displayed to the public exchange for external outgoing
         calls."
    ::= { mpsExtension 4 }

    mpsExtensionSourceEntry OBJECT-TYPE
        SYNTAX          MpsExtensionSourceEntry 
        MAX-ACCESS      not-accessible
        STATUS          current
        DESCRIPTION
            ""
        INDEX { mpsExtensionSourceExtension, mpsExtensionSourceTrunkGroup }
        ::= { mpsExtensionSourceTable 1 }

    MpsExtensionSourceEntry ::=
        SEQUENCE {
            mpsExtensionSourceExtension              ExtensionIndex, 
            mpsExtensionSourceTrunkGroup             TrunkGroupIndex, 
            mpsExtensionSourceSubscriberNumber       SubscriberNumberIndex, 
            mpsExtensionSourceSubscriberAdminStatus  INTEGER,
            mpsExtensionSourceTrunkNumber            TrunkNumberIndexOrZero,
            mpsExtensionSourceHideNumber             TruthValue,
            mpsExtensionSourceType                   INTEGER,
            mpsExtensionSourcePrio                   Unsigned32
        }
        
    mpsExtensionSourceExtension OBJECT-TYPE
        SYNTAX          ExtensionIndex
        MAX-ACCESS      read-write
        STATUS          current
        DESCRIPTION
            "This variable references the mpsExtensionIndex."
        ::= { mpsExtensionSourceEntry 1 }

    mpsExtensionSourceTrunkGroup OBJECT-TYPE
        SYNTAX          TrunkGroupIndex
        MAX-ACCESS      read-write
        STATUS          current
        DESCRIPTION
            "This variable references the mpsTrunkGroupIndex."
        ::= { mpsExtensionSourceEntry 2 }

    mpsExtensionSourceSubscriberNumber OBJECT-TYPE
        SYNTAX          SubscriberNumberIndex
        MAX-ACCESS      read-write
        STATUS          obsolete
        DESCRIPTION
            "A unique value for each extension and outgoing external number."
        ::= { mpsExtensionSourceEntry 3 }

    mpsExtensionSourceSubscriberAdminStatus OBJECT-TYPE
        SYNTAX          INTEGER { enable(1), delete(2) }
        MAX-ACCESS      read-write
        STATUS          current
        DESCRIPTION
            "Just for MIB entry deletion."
        DEFVAL { enable }
        ::= { mpsExtensionSourceEntry 4 }

    mpsExtensionSourceTrunkNumber OBJECT-TYPE
        SYNTAX          TrunkNumberIndexOrZero
        MAX-ACCESS      read-write
        STATUS          current
        DESCRIPTION
            "A unique value for each extension and outgoing external number.
             Index in mpsTrunkNumberTable"
        ::= { mpsExtensionSourceEntry 5 }

    mpsExtensionSourceHideNumber OBJECT-TYPE
        SYNTAX          TruthValue
        MAX-ACCESS      read-write
        STATUS          current
        DESCRIPTION
            "Always hide this number on outgoing calls from this subscriber.
            "
        DEFVAL { false }
        ::= { mpsExtensionSourceEntry 6 }

    mpsExtensionSourceType OBJECT-TYPE
        SYNTAX          INTEGER { 
                             standard(1),
                             own-ddi(2)
                        }
        MAX-ACCESS      read-write
        STATUS          current
        DESCRIPTION
            "This variable contains the actual number signaling type.
		standard:	standard number signaling ->
				use the number which is indexed via the
				mpsExtensionSourceTrunkNumber field.
				If this field is zero then no number signaling
				applies. In this case the public exchange/
				provider may insert the default assigned number.
		own-ddi:	extension number signaling ->
				use extension- + base number for DDI signaling
            "
        DEFVAL { standard }
        ::= { mpsExtensionSourceEntry 7 }

    mpsExtensionSourcePrio OBJECT-TYPE
        SYNTAX          Unsigned32
        MAX-ACCESS      read-write
        STATUS          current
        DESCRIPTION
            "Priority of the outgoing trunk number.
             Used to set the outgoing trunk line sequence individually for
             each extension (instead of globally via the ClassOfService).
            "
        ::= { mpsExtensionSourceEntry 8 }

---------------------------------------------------------------------------
mpsExtensionABTable OBJECT-TYPE
    SYNTAX      SEQUENCE OF MpsExtensionABEntry
    MAX-ACCESS  not-accessible
    STATUS      current
    DESCRIPTION
        "This table contains the additional information of the analog 
         extension."
    ::= { mpsExtension 5 }

    mpsExtensionABEntry OBJECT-TYPE
        SYNTAX          MpsExtensionABEntry 
        MAX-ACCESS      not-accessible
        STATUS          obsolete
        DESCRIPTION
            ""
        INDEX { mpsExtensionABIndex }
        ::= { mpsExtensionABTable 1 }

    MpsExtensionABEntry ::=
        SEQUENCE {
            mpsExtensionABIndex                 ExtensionIndex, 
            mpsExtensionABMode                  INTEGER, 
            mpsExtensionABGatewayNumber         INTEGER, 
            mpsExtensionABDialingType           INTEGER, 
            mpsExtensionABChargePulse           TruthValue, 
            mpsExtensionABClip                  INTEGER, 
            mpsExtensionABClipOffHook           TruthValue, 
            mpsExtensionABCnip                  TruthValue, 
            mpsExtensionABFlashTime             INTEGER, 
            mpsExtensionABDoorIntercom          DoorIntercomIndexOrZero, 
            mpsExtensionABDoorIntercomTimer     INTEGER,
            mpsExtensionABAdminStatus           INTEGER
        }

    mpsExtensionABIndex OBJECT-TYPE
        SYNTAX          ExtensionIndex
        MAX-ACCESS      read-write
        STATUS          obsolete
        DESCRIPTION
            "A unique value for additional analog extension settings."
        ::= { mpsExtensionABEntry 1 }

    mpsExtensionABMode OBJECT-TYPE
        SYNTAX          INTEGER {
                            none(1),
                            telephone(2),
                            fax(3),
                            answering-machine(4),
                            modem(5),
                            multi-port(6),
                            moh(7),
                            tfe-123d12(8),
                            tfe-other(9),
                            tfe-doorline(10),
                            announcement(11),
                            voice-mail-system(12),
                            alarm-line(13),
                            tfe-adapter(14),
                            moh-anouncement(15),
                            tfe-123d12-4bells(16),
                            tfe-others-4bells(17),
                            gateway(18)
                        }
        MAX-ACCESS      read-write
        STATUS          obsolete
        DESCRIPTION
            "You can configure each analog port to accept a different 
             terminal device. Additional settings or special functions may 
             be required depending on the type of terminal device. Terminal 
             device types which require special functions / applications can be
             set at some analog connections. Set to delete, to discard the 
             whole entry."
        DEFVAL { telephone }
        ::= { mpsExtensionABEntry 2 }

    mpsExtensionABGatewayNumber OBJECT-TYPE
        SYNTAX          INTEGER
        MAX-ACCESS      read-write
        STATUS          obsolete
        DESCRIPTION
            "This variable contains the gateway number,
             if mpsExtensionABMode=gateway."
        DEFVAL { 0 }
        ::= { mpsExtensionABEntry 3 }

    mpsExtensionABDialingType OBJECT-TYPE
        SYNTAX          INTEGER {
                            none(1),
                            mfv(2),
                            iwv(3)
                        }
        MAX-ACCESS      read-write
        STATUS          obsolete
        DESCRIPTION
            "Type of dialling, DTMF and pulse dialing."
        DEFVAL { none }
        ::= { mpsExtensionABEntry 4 }

    mpsExtensionABChargePulse OBJECT-TYPE
        SYNTAX          TruthValue
        MAX-ACCESS      read-write
        STATUS          obsolete
        DESCRIPTION
        "If your analog terminal devices support the display of cost and 
         charge information you can set the transmission of charge pulses 
         at the corresponding connections."
        DEFVAL { 2 }
        ::= { mpsExtensionABEntry 5 }

    mpsExtensionABClip OBJECT-TYPE
        SYNTAX          INTEGER {
                            none(1),
                            mfv(2),
                            dtmf(3)
                        }
        MAX-ACCESS      read-write
        STATUS          obsolete
        DESCRIPTION
            "Number display (CLIP)."
        DEFVAL { none }
        ::= { mpsExtensionABEntry 6 }

    mpsExtensionABClipOffHook OBJECT-TYPE
        SYNTAX          TruthValue
        MAX-ACCESS      read-write
        STATUS          obsolete
        DESCRIPTION
            "Number display (CLIP off Hook)."
        DEFVAL { 2 }
        ::= { mpsExtensionABEntry 7 }

    mpsExtensionABCnip OBJECT-TYPE
        SYNTAX          TruthValue
        MAX-ACCESS      read-write
        STATUS          obsolete
        DESCRIPTION
            "Name display (CNIP)."
        DEFVAL { 2 }
        ::= { mpsExtensionABEntry 8 }

    mpsExtensionABFlashTime OBJECT-TYPE
        SYNTAX          INTEGER {
                            m100(1),
                            m200(2),
                            m300(3),
                            m400(4),
                            m500(5),
                            m600(6),
                            m700(7),
                            m800(8),
                            m900(9),
                            m1000(10)
                        }
        MAX-ACCESS      read-write
        STATUS          obsolete
        DESCRIPTION
            "This variable contains the analogue flash time in milliseconds."
        DEFVAL { m200 }
        ::= { mpsExtensionABEntry 9 }

    mpsExtensionABDoorIntercom OBJECT-TYPE
        SYNTAX          DoorIntercomIndexOrZero
        MAX-ACCESS      read-write
        STATUS          obsolete
        DESCRIPTION
            "This variable contains the number of the door intercom."
        DEFVAL { 0 }
        ::= { mpsExtensionABEntry 10 }

    mpsExtensionABDoorIntercomTimer OBJECT-TYPE
        SYNTAX          INTEGER
        MAX-ACCESS      read-write
        STATUS          obsolete
        DESCRIPTION
            "This variable contains the length of timer in seconds for open 
             door."
        ::= { mpsExtensionABEntry 11 }

    mpsExtensionABAdminStatus OBJECT-TYPE
        SYNTAX          INTEGER {
                            enable(1),
                            delete(2)
                        }
        MAX-ACCESS      read-write
        STATUS          obsolete
        DESCRIPTION
            "Jsut for delete."
        DEFVAL { enable }
        ::= { mpsExtensionABEntry 12 }

---------------------------------------------------------------------------
mpsExtensionVoIPTable OBJECT-TYPE
    SYNTAX      SEQUENCE OF MpsExtensionVoIPEntry
    MAX-ACCESS  not-accessible
    STATUS      current
    DESCRIPTION
        "This table contains additional information for VoIP extension."
    ::= { mpsExtension 6 }

    mpsExtensionVoIPEntry OBJECT-TYPE
        SYNTAX          MpsExtensionVoIPEntry 
        MAX-ACCESS      not-accessible
        STATUS          current
        DESCRIPTION
            ""
        INDEX { mpsExtensionVoIPIndex }
        ::= { mpsExtensionVoIPTable 1 }

    MpsExtensionVoIPEntry ::=
        SEQUENCE {
            mpsExtensionVoIPIndex                ExtensionIndex, 
            mpsExtensionVoIPLocation             INTEGER, 
            mpsExtensionVoIPNetwork              NetworkIndex, 
            mpsExtensionVoIPAdminStatus          INTEGER,
            mpsExtensionVoIPAdminBinding         DisplayString, 
            mpsExtensionVoIPFacilities           BITS, 
            mpsExtensionVoIPIpAddressInfo        IpAddress, 
            mpsExtensionVoIPOperationBinding     DisplayString, 
            mpsExtensionVoIPOperationStatus      INTEGER,
            mpsExtensionVoIPCurrentCalls         Counter32,
            mpsExtensionVoIPCodecs               BitValue,
            mpsExtensionVoIPCodecOrder           INTEGER,
            mpsExtensionVoIPCodecProperties      CodecIndexOrZero
        }

    mpsExtensionVoIPIndex OBJECT-TYPE
        SYNTAX          ExtensionIndex
        MAX-ACCESS      read-write
        STATUS          current
        DESCRIPTION
            "This variable references the mpsExtensionIndex."
        ::= { mpsExtensionVoIPEntry 1 }

    mpsExtensionVoIPLocation OBJECT-TYPE
        SYNTAX          INTEGER {
                            none(1),
                            any(2),
                            nowan(3),
                            lan(4),
                            wan(5),
                            network(6)
                        }
        MAX-ACCESS      read-write
        STATUS          obsolete
        DESCRIPTION
            "This variable contains the registration location area from which the
             subscriber is able to setup an VoIP-register."
        DEFVAL { none }
        ::= { mpsExtensionVoIPEntry 2 }

    mpsExtensionVoIPNetwork OBJECT-TYPE
        SYNTAX          NetworkIndex
        MAX-ACCESS      read-write
        STATUS          obsolete
        DESCRIPTION
            "If mpsSubsRegistrationLocation = network (6), this value 
             contains the special location index."
        ::= { mpsExtensionVoIPEntry 3 }

    mpsExtensionVoIPAdminStatus OBJECT-TYPE
        SYNTAX          INTEGER {
                            enable(1),
                            delete(2)
                        }
        MAX-ACCESS      read-write
        STATUS          current
        DESCRIPTION
            "Just for MIB entry deletion."
        DEFVAL { enable }
        ::= { mpsExtensionVoIPEntry 4 }

    mpsExtensionVoIPAdminBinding OBJECT-TYPE
        SYNTAX          DisplayString (SIZE(0..64))
        MAX-ACCESS      read-write
        STATUS          current
        DESCRIPTION
            "This variable contains name, port and transport of a statically
             registered client.
             example: 192.0.0.1:5060;tcp  or  phone30.bintec.de:5060;upd
             Data will be used, if mpsExtensionVoIPFacilities static is set."
        ::= { mpsExtensionVoIPEntry 5 }

    mpsExtensionVoIPFacilities OBJECT-TYPE
        SYNTAX          BITS {
                            static(0),
                            g726coding(1),
                            no-auto-hold(2),
                            srtp(3),
                            no-holdretrieve(4),
                            public-registration(5),
                            t38support(6)
                        }
        MAX-ACCESS      read-write
        STATUS          current
        DESCRIPTION
        "Special facilities of the IP client.
                static:                 establish client with fix IP and port, no
                                        register possible.
                g726coding:             0 -> I.366
                                        1 -> RFC 3551/X.420
                no-auto-hold:           allow multiple connections from this
                                        extension.
                srtp:                   allow SRTP negotiation
                no_holdretrieve:        no hold and retrieve to sip phone
                public-registration:    allow client registrations from public
                                        network.
                t38support:             T.38 Fax signalling/coding allowed for this
                                        VoIP extension (disabled per default).
            "
        DEFVAL { { } }
        ::= { mpsExtensionVoIPEntry 6 }

    mpsExtensionVoIPIpAddressInfo OBJECT-TYPE
        SYNTAX          IpAddress
        MAX-ACCESS      read-only
        STATUS          current
        DESCRIPTION
            "This variable contains the IP Address of the dynamically registered
             client, to show info in UI.
            "
        ::= { mpsExtensionVoIPEntry 7 }

    mpsExtensionVoIPOperationBinding OBJECT-TYPE
        SYNTAX          DisplayString (SIZE(0..32))
        MAX-ACCESS      read-only
        STATUS          current
        DESCRIPTION
            "This variable contains name:port of the registered client, 
             to show info in UI.
            "
        ::= { mpsExtensionVoIPEntry 8 }

    mpsExtensionVoIPOperationStatus OBJECT-TYPE
        SYNTAX          INTEGER { 
                             notregistered(1), 
                             registering(2), 
                             registered(3), 
                             reregistering(4) 
                         }
        MAX-ACCESS      read-only
        STATUS          current
        DESCRIPTION
            "This variable contains the actual operation status.
                    notregistered :   client is not registered
                    registering   :   notregistered, registration pending
                    registered    :   client is registered
                    reregistering :   registered, reregistration pending
            "
        DEFVAL { notregistered }
        ::= { mpsExtensionVoIPEntry 9 }

    mpsExtensionVoIPCurrentCalls OBJECT-TYPE
        SYNTAX          Counter32
        MAX-ACCESS      read-only
        STATUS          obsolete
        DESCRIPTION
            "This variable contains the current calls."
        DEFVAL { 0 }
        ::= { mpsExtensionVoIPEntry 10 }

    mpsExtensionVoIPCodecs OBJECT-TYPE
        SYNTAX          BitValue
        MAX-ACCESS      read-write
        STATUS          obsolete
        DESCRIPTION
            "For codecs, supported for this extension:
             ulaw       (1)
             alaw       (2)
             g729       (4)
             g726       (8)
             g726_16   (16)
             g726_32   (32)
             g726_40   (64)
             g728     (128)
             g723_63  (256)
             g723_53  (512)
             g729_e  (1024)
             gsm     (2048)
             dtmf    (4096)

             Default ulaw, alaw, g.729 and dtmf"
        DEFVAL { 4103 }
        ::= { mpsExtensionVoIPEntry 11 } 

    mpsExtensionVoIPCodecOrder OBJECT-TYPE
        SYNTAX  INTEGER {
            default(1),
            quality(2),
            lowest(3),
            highest(4)
        }
        MAX-ACCESS      read-write
        STATUS          obsolete
        DESCRIPTION
            " Sorting the codecs 
              default -> system default order
              quality -> highest quality first
              lowest  -> lowest bandwith first
              highest -> highest bandwith first"
                  
        DEFVAL { default }
        ::= { mpsExtensionVoIPEntry 12 } 

    mpsExtensionVoIPCodecProperties OBJECT-TYPE
        SYNTAX          CodecIndexOrZero
        MAX-ACCESS      read-write
        STATUS          current
        DESCRIPTION
            "A reference to mpsCodecPropertyTable for codec properties.
             0 = use system default."
        DEFVAL { 0 }
        ::= { mpsExtensionVoIPEntry 13 }

---------------------------------------------------------------------------
mpsExtensionTrunkRouteTable OBJECT-TYPE
    SYNTAX      SEQUENCE OF MpsExtensionTrunkRouteEntry
    MAX-ACCESS  not-accessible
    STATUS      current
    DESCRIPTION
        "This table contains information, if an internal extension is to 
         use only certain bundles for external connections. multiple entries 
         can exists for each extension."
    ::= { mpsExtension 7 }

    mpsExtensionTrunkRouteEntry OBJECT-TYPE
        SYNTAX          MpsExtensionTrunkRouteEntry 
        MAX-ACCESS      not-accessible
        STATUS          obsolete
        DESCRIPTION
            ""
        INDEX { mpsExtensionTrunkRouteIndex, mpsExtensionTrunkRouteNumber }
        ::= { mpsExtensionTrunkRouteTable 1 }

    MpsExtensionTrunkRouteEntry ::=
        SEQUENCE {
            mpsExtensionTrunkRouteIndex                 ExtensionIndex, 
            mpsExtensionTrunkRouteNumber                INTEGER, 
            mpsExtensionTrunkRouteBundle                INTEGER, 
            mpsExtensionTrunkRouteAdminStatus           INTEGER
        }

    mpsExtensionTrunkRouteIndex OBJECT-TYPE
        SYNTAX          ExtensionIndex
        MAX-ACCESS      read-write
        STATUS          obsolete
        DESCRIPTION
            "A unique value for each extension."
        ::= { mpsExtensionTrunkRouteEntry 1 }

    mpsExtensionTrunkRouteNumber OBJECT-TYPE
        SYNTAX          INTEGER
        MAX-ACCESS      read-write
        STATUS          obsolete
        DESCRIPTION
            "Priority of the bundle."
        ::= { mpsExtensionTrunkRouteEntry 2 }

    mpsExtensionTrunkRouteBundle OBJECT-TYPE
        SYNTAX          INTEGER
        MAX-ACCESS      read-write
        STATUS          obsolete
        DESCRIPTION
            "This value contain the bundle number."
        DEFVAL { 0 }
        ::= { mpsExtensionTrunkRouteEntry 3 }

    mpsExtensionTrunkRouteAdminStatus OBJECT-TYPE
        SYNTAX          INTEGER { enable(1), delete(2) }
        MAX-ACCESS      read-write
        STATUS          obsolete
        DESCRIPTION
            "Just for MIB entry deletion."
        DEFVAL { enable }
        ::= { mpsExtensionTrunkRouteEntry 4 }

---------------------------------------------------------------------------
mpsExtensionTrunkAccessTable OBJECT-TYPE
    SYNTAX      SEQUENCE OF MpsExtensionTrunkAccessEntry
    MAX-ACCESS  not-accessible
    STATUS      current
    DESCRIPTION
        "This table contains information, if the direct access to the bundle 
         from this extension is allowed or not."
    ::= { mpsExtension 8 }

    mpsExtensionTrunkAccessEntry OBJECT-TYPE
        SYNTAX          MpsExtensionTrunkAccessEntry 
        MAX-ACCESS      not-accessible
        STATUS          obsolete
        DESCRIPTION
            ""
        INDEX { mpsExtensionTrunkAccessIndex, mpsExtensionTrunkAccessBundle }
        ::= { mpsExtensionTrunkAccessTable 1 }

    MpsExtensionTrunkAccessEntry ::=
        SEQUENCE {
            mpsExtensionTrunkAccessIndex        ExtensionIndex, 
            mpsExtensionTrunkAccessBundle       INTEGER, 
            mpsExtensionTrunkAccessGrant        TruthValue, 
            mpsExtensionTrunkAccessAdminStatus  INTEGER
        }

    mpsExtensionTrunkAccessIndex OBJECT-TYPE
        SYNTAX          ExtensionIndex
        MAX-ACCESS      read-write
        STATUS          obsolete
        DESCRIPTION
            "A unique value for each extension."
        ::= { mpsExtensionTrunkAccessEntry 1 }

    mpsExtensionTrunkAccessBundle OBJECT-TYPE
        SYNTAX          INTEGER
        MAX-ACCESS      read-write
        STATUS          obsolete
        DESCRIPTION
            "This value contain the bundle number."
        DEFVAL { 0 }
        ::= { mpsExtensionTrunkAccessEntry 2 }

    mpsExtensionTrunkAccessGrant OBJECT-TYPE
        SYNTAX          TruthValue
        MAX-ACCESS      read-write
        STATUS          obsolete
        DESCRIPTION
            "This value determine whether the direct access to the bundle 
             number is allowed(1) or not allowed(2)."
        DEFVAL { false }
        ::= { mpsExtensionTrunkAccessEntry 3 }

    mpsExtensionTrunkAccessAdminStatus OBJECT-TYPE
        SYNTAX          INTEGER { enable(1), delete(2) }
        MAX-ACCESS      read-write
        STATUS          obsolete
        DESCRIPTION
            "Just for MIB entry deletion."
        DEFVAL { enable }
        ::= { mpsExtensionTrunkAccessEntry 4 }

---------------------------------------------------------------------------
mpsExtensionDiversionTable OBJECT-TYPE
    SYNTAX      SEQUENCE OF MpsExtensionDiversionEntry
    MAX-ACCESS  not-accessible
    STATUS      current
    DESCRIPTION
        "This table contains the configured diversions."
    ::= { mpsExtension 9 }

    mpsExtensionDiversionEntry OBJECT-TYPE
        SYNTAX          MpsExtensionDiversionEntry 
        MAX-ACCESS      not-accessible
        STATUS          current
        DESCRIPTION
            ""
        INDEX { mpsExtensionDiversionIndex, mpsExtensionDiversionService }
        ::= { mpsExtensionDiversionTable 1 }

    MpsExtensionDiversionEntry ::=
        SEQUENCE {
            mpsExtensionDiversionIndex          ExtensionIndex, 
            mpsExtensionDiversionService        INTEGER, 
            mpsExtensionDiversionCFU            DisplayString, 
            mpsExtensionDiversionCFB            DisplayString, 
            mpsExtensionDiversionCFNR           DisplayString, 
            mpsExtensionDiversionCFU2           DisplayString, 
            mpsExtensionDiversionCFU3           DisplayString, 
            mpsExtensionDiversionCFU3Fixed      TruthValue, 
            mpsExtensionDiversionCFU3Active     TruthValue,
            mpsExtensionDiversionAdminStatus    INTEGER
        }

    mpsExtensionDiversionIndex OBJECT-TYPE
        SYNTAX          ExtensionIndex
        MAX-ACCESS      read-write
        STATUS          current
        DESCRIPTION
            "A unique value for the extension, who has configured this 
             diversion."
    ::= { mpsExtensionDiversionEntry 1 }

    mpsExtensionDiversionService OBJECT-TYPE
        SYNTAX          INTEGER {
                            telephone(2),
                            telephone3k1hz(3),
                            telephoneAnalog(4),
                            telephone7k1hz(5),
                            analog(6),
                            analogFaxG2(7),
                            analogFaxG3(8),
                            dataViaModem(9),
                            btxViaModem(10),
                            x21(11),
                            x21Uc4(12),
                            x21Uc5(13),
                            x21Uc6(14),
                            x21Uc19(15),
                            telefaxG4(16),
                            btx64kbit(17),
                            data64kbit(18),
                            x25(19),
                            x25Uc8(20),
                            x25Uc9(21),
                            x25Uc10(22),
                            x25Uc11(23),
                            x25Uc13(24),
                            x2519k2hz(25),
                            teletex64(26),
                            mixedMode(27),
                            telematicControl(28),
                            grafiktelefondienste(29),
                            btxNew(30),
                            videoTelephone(31),
                            videoTelephone3k1hz(32),
                            videoTelephone7khz(33),
                            videoTelephonePicture(34),
                            speech(35),
                            unrestrictedDigitalInformation(36),
                            audio3k1(37),
                            audio7k(38),
                            videotextInternational(39),
                            allServices(40)
                        }
        MAX-ACCESS      read-write
        STATUS          current
        DESCRIPTION
            "Diversion for a special service."
        DEFVAL { allServices }
        ::= { mpsExtensionDiversionEntry 2 }

    mpsExtensionDiversionCFU OBJECT-TYPE
        SYNTAX          DisplayString (SIZE(0..24))
        MAX-ACCESS      read-write
        STATUS          current
        DESCRIPTION
            "Destination number for call forwarding unconditional. "
        ::= { mpsExtensionDiversionEntry 3 }

    mpsExtensionDiversionCFB OBJECT-TYPE
        SYNTAX          DisplayString (SIZE(0..24))
        MAX-ACCESS      read-write
        STATUS          current
        DESCRIPTION
            "Destination number for call forwarding busy. "
        ::= { mpsExtensionDiversionEntry 4 }

    mpsExtensionDiversionCFNR OBJECT-TYPE
        SYNTAX          DisplayString (SIZE(0..24))
        MAX-ACCESS      read-write
        STATUS          current
        DESCRIPTION
            "Destination number for call forwarding no reply. "
        ::= { mpsExtensionDiversionEntry 5 }

    mpsExtensionDiversionCFU2 OBJECT-TYPE
        SYNTAX          DisplayString (SIZE(0..24))
        MAX-ACCESS      read-write
        STATUS          current
        DESCRIPTION
            "This variable contains the diversion target number for call 
             deflection. "
        ::= { mpsExtensionDiversionEntry 6 }

    mpsExtensionDiversionCFU3 OBJECT-TYPE
        SYNTAX          DisplayString (SIZE(0..24))
        MAX-ACCESS      read-write
        STATUS          current
        DESCRIPTION
            "This variable contains the diversion target number for follow me. "
        ::= { mpsExtensionDiversionEntry 7 }

    mpsExtensionDiversionCFU3Fixed OBJECT-TYPE
        SYNTAX          TruthValue
        MAX-ACCESS      read-write
        STATUS          current
        DESCRIPTION
            "This value determines whether the follow me diversion (CFU3) is 
             fixed(1) or variable(2)."
        DEFVAL { 2 }
        ::= { mpsExtensionDiversionEntry 8 }

    mpsExtensionDiversionCFU3Active OBJECT-TYPE
        SYNTAX          TruthValue
        MAX-ACCESS      read-write
        STATUS          current
        DESCRIPTION
            "This value determines whether the follow me diversion (CFU3) is 
             active(1) or not active(2)."
        DEFVAL { 2 }
        ::= { mpsExtensionDiversionEntry 9 }

    mpsExtensionDiversionAdminStatus OBJECT-TYPE
        SYNTAX          INTEGER {
                            enable(1),
                            delete(2)
                        }
        MAX-ACCESS      read-write
        STATUS          current
        DESCRIPTION
            "Just for MIB entry deletion."
        DEFVAL { enable }
    ::= { mpsExtensionDiversionEntry 10 }

---------------------------------------------------------------------------
mpsExtensionCAPITable OBJECT-TYPE
    SYNTAX      SEQUENCE OF MpsExtensionCAPIEntry
    MAX-ACCESS  not-accessible
    STATUS      current
    DESCRIPTION
        "This table contains the additional information of the CAPI extension."
    ::= { mpsExtension 10 }

    mpsExtensionCAPIEntry OBJECT-TYPE
        SYNTAX          MpsExtensionCAPIEntry 
        MAX-ACCESS      not-accessible
        STATUS          current
        DESCRIPTION
            ""
        INDEX { mpsExtensionCAPIIndex }
        ::= { mpsExtensionCAPITable 1 }

    MpsExtensionCAPIEntry ::=
        SEQUENCE {
            mpsExtensionCAPIIndex                ExtensionIndex, 
            mpsExtensionCAPIWakeOnLan            INTEGER, 
            mpsExtensionCAPIMacAddress           MacAddress
        }

    mpsExtensionCAPIIndex OBJECT-TYPE
        SYNTAX          ExtensionIndex
        MAX-ACCESS      read-write
        STATUS          current
        DESCRIPTION
            "A unique value for additional CAPI extension settings."
        ::= { mpsExtensionCAPIEntry 1 }

    mpsExtensionCAPIWakeOnLan OBJECT-TYPE
        SYNTAX          INTEGER {
                            off(1),
                            magic-packet(2),
                            delete(3)
                        }
        MAX-ACCESS      read-write
        STATUS          current
        DESCRIPTION
            "This value determine if Wake On LAN is off or on. Set to delete, to 
             discard the whole entry."
        DEFVAL { off }
        ::= { mpsExtensionCAPIEntry 2 }

    mpsExtensionCAPIMacAddress OBJECT-TYPE
        SYNTAX          MacAddress
        MAX-ACCESS      read-write
        STATUS          current
        DESCRIPTION
            "This variable contains the MAC address of the capi extension."
        ::= { mpsExtensionCAPIEntry 3 }

---------------------------------------------------------------------------
mpsCAPIClientTable OBJECT-TYPE
    SYNTAX      SEQUENCE OF MpsCAPIClientEntry
    MAX-ACCESS  not-accessible
    STATUS      current
    DESCRIPTION
        "This table contains all registered CAPI clients."
    ::= { mpsExtension 11 }

    mpsCAPIClientEntry OBJECT-TYPE
        SYNTAX          MpsCAPIClientEntry 
        MAX-ACCESS      not-accessible
        STATUS          current
        DESCRIPTION
            ""
        INDEX { mpsCAPIClientIndex }
        ::= { mpsCAPIClientTable 1 }

    MpsCAPIClientEntry ::=
        SEQUENCE {
            mpsCAPIClientIndex                   CAPIClientIndex, 
            mpsCAPIClientIP                      IpAddress, 
            mpsCAPIClientMac                     MacAddress,
            mpsCAPIClientName                    DisplayString,
            mpsCAPIClientAdminStatus             INTEGER
        }

    mpsCAPIClientIndex OBJECT-TYPE
        SYNTAX          CAPIClientIndex
        MAX-ACCESS      read-only
        STATUS          current
        DESCRIPTION
            "A unique value for each registerd CAPI client."
        ::= { mpsCAPIClientEntry 1 }

    mpsCAPIClientIP OBJECT-TYPE
        SYNTAX          IpAddress
        MAX-ACCESS      read-only
        STATUS          current
        DESCRIPTION
            "This variable contains the IP Address of the registered CAPI
             Client."
        ::= { mpsCAPIClientEntry 2 }

    mpsCAPIClientMac OBJECT-TYPE
        SYNTAX          MacAddress
        MAX-ACCESS      read-only
        STATUS          current
        DESCRIPTION
            "This variable contains the MAC address of the registered CAPI
             Client."
        ::= { mpsCAPIClientEntry 3 }

    mpsCAPIClientName OBJECT-TYPE
        SYNTAX          DisplayString
        MAX-ACCESS      read-only
        STATUS          current
        DESCRIPTION
            "Name (DHCP/NETBIOS) of the registered CAPI Client."
        ::= { mpsCAPIClientEntry 4 }

    mpsCAPIClientAdminStatus OBJECT-TYPE
        SYNTAX          INTEGER {
                            enable(1),
                            delete(2)
                        }
        MAX-ACCESS      read-write
        STATUS          current
        DESCRIPTION
            "Just for MIB entry deletion."
        DEFVAL { enable }
        ::= { mpsCAPIClientEntry 5 }

---------------------------------------------------------------------------
mpsExtensionModeTable OBJECT-TYPE
    SYNTAX      SEQUENCE OF MpsExtensionModeEntry
    MAX-ACCESS  not-accessible
    STATUS      current
    DESCRIPTION
        "This table contains the detailed information about extension modes."
    ::= { mpsExtension 12 }

    mpsExtensionModeEntry OBJECT-TYPE
        SYNTAX          MpsExtensionModeEntry 
        MAX-ACCESS      not-accessible
        STATUS          current
        DESCRIPTION
            ""
        INDEX { mpsExtensionModeIndex }
        ::= { mpsExtensionModeTable 1 }

    MpsExtensionModeEntry ::=
        SEQUENCE {
            mpsExtensionModeIndex                       Unsigned32,
            mpsExtensionModeExtIndex                    ExtensionIndex,
            mpsExtensionModeMode                        Unsigned32,
            mpsExtensionModeReRouteIndex                ReRouteIndexOrZero,
            mpsExtensionModeAdminStatus                 INTEGER
        }

    mpsExtensionModeIndex OBJECT-TYPE
        SYNTAX          Unsigned32
        MAX-ACCESS      read-write
        STATUS          current
        DESCRIPTION
            "A unique value for each mode for extension."
        ::= { mpsExtensionModeEntry 1 }

    mpsExtensionModeExtIndex OBJECT-TYPE
        SYNTAX          ExtensionIndex
        MAX-ACCESS      read-write
        STATUS          current
        DESCRIPTION
            "Reference to the extension for this mode entry."
        ::= { mpsExtensionModeEntry 2 }

    mpsExtensionModeMode OBJECT-TYPE
        SYNTAX          Unsigned32
        MAX-ACCESS      read-write
        STATUS          current
        DESCRIPTION
            "For each extension index can exist several mode entries.
             (One entry for each mode.)"
        ::= { mpsExtensionModeEntry 3 }

    mpsExtensionModeReRouteIndex OBJECT-TYPE
        SYNTAX          ReRouteIndexOrZero
        MAX-ACCESS      read-write
        STATUS          current
        DESCRIPTION
            "Index of the ReRouting function in mpsReRouteTable.
             0 = ReRouting function inactive."
        ::= { mpsExtensionModeEntry 4 }

    mpsExtensionModeAdminStatus OBJECT-TYPE
        SYNTAX          INTEGER {
                            enable(1),
                            delete(2)
                        }
        MAX-ACCESS      read-write
        STATUS          current
        DESCRIPTION
            "Just for MIB entry deletion."
        DEFVAL { enable }
    ::= { mpsExtensionModeEntry 5 }

---------------------------------------------------------------------------
mpsClassOfServiceTable OBJECT-TYPE
    SYNTAX      SEQUENCE OF MpsClassOfServiceEntry
    MAX-ACCESS  not-accessible
    STATUS      current
    DESCRIPTION
        "This table contains the class of service settings."
    ::= { mpsExtension 13 }

    mpsClassOfServiceEntry OBJECT-TYPE
        SYNTAX          MpsClassOfServiceEntry 
        MAX-ACCESS      not-accessible
        STATUS          current
        DESCRIPTION
            ""
        INDEX { mpsCoSIndex }
        ::= { mpsClassOfServiceTable 1 }

    MpsClassOfServiceEntry ::=
        SEQUENCE {
            mpsCoSIndex                                 CoSIndex,
            mpsCoSDescription                           DisplayString,
            mpsCoSDialAuthorisation                     INTEGER,
            mpsCoSFacilities                            BITS,
            mpsCoSPickupGroup                           INTEGER,
            mpsCoSFeatureGroup                          INTEGER,
            mpsCoSPhonebookAccess                       INTEGER,
            mpsCoSMusicOnHold                           INTEGER,
	    mpsCoSMOHFileDirectory			DisplayString,
	    mpsCoSMOHDefaultVariant			INTEGER,
            mpsCoSAdminStatus                           INTEGER,
            mpsCoSTrunkBundleAccess                     BitValue,
            mpsCoSTrunkCallDisplay                      INTEGER,
            mpsCoSSwitchContacts			BitValue
        }

    mpsCoSIndex OBJECT-TYPE
        SYNTAX          CoSIndex
        MAX-ACCESS      read-write
        STATUS          current
        DESCRIPTION
            "A unique value for each class of service."
        ::= { mpsClassOfServiceEntry 1 }

    mpsCoSDescription OBJECT-TYPE
        SYNTAX          DisplayString (SIZE(0..20))
        MAX-ACCESS      read-write
        STATUS          current
        DESCRIPTION
            "This variable contains the name of the class of service."
        ::= { mpsClassOfServiceEntry 2 }

    mpsCoSDialAuthorisation OBJECT-TYPE
        SYNTAX          INTEGER {
                            unknown(1),
                            international(2),
                            incoming(3),
                            national(4),
                            region(5),
                            internal(6),
                            onlyDoorIntercom(7),
                            local(8)
                        }
        MAX-ACCESS      read-write
        STATUS          current
        DESCRIPTION
            "Dialing privileges for a extension specifies what type of calls 
             (internal, external, etc. ) this extension can place. Default is 
             international. 'unknown' = no dialling allowed."
        DEFVAL { international }
        ::= { mpsClassOfServiceEntry 3 }

    mpsCoSFacilities OBJECT-TYPE
        SYNTAX          BITS {
                            auto-trunk-req(0),
                            man-trunk-group-req(1),
                            route-barring(2),
                            ars(3),
                            suppress-A-Addr(5),
                            suppress-B-Addr(6),
                            specific-pickup(7),
                            call-waiting(8),
                            toggle-variant(9),
                            silent-phone-intern(10),
                            silent-phone-extern(11),
                            call-through(12),
                            room-supervision(14),
                            intercom(15),
                            announcement(16),
                            msg-waiting(18),
                            uus1(19),
                            keypad(20),
                            doorIntercom-access(21),
                            tapi(22),
                            store-charge(23),
                            transmit-charge-info(24),
                            use-global-rerouting(25)
                        }
        MAX-ACCESS      read-write
        STATUS          current
        DESCRIPTION
            "Special facilities of the class of service.
                auto-trunk-req :      This setting defines whether automatic
                                      access to an outside line is to be
                                      configured.
                man-trunk-group-req:  This setting defines whether manuell access
                                      via bundle to an outside line is allowed.
                route-barring:        If you have configured the dialing filter
                                      (consisting of an inhibit and release
                                      filter) in the PBX system you can use these
                                      settings to define whether the selected
                                      subscriber is subject to the constraints/
                                      privileges imposed/offered by the dialing
                                      filter.
                ars:                  Use ars (automatic route selection).
                suppress-A-Addr:      Suppress outgoing CLIP information (CLIR).
                suppress-B-Addr:      This value determine if Suppress number of
                                      called party (COLR) is enabled or not.
                specific-pickup :     Allow specific pickup.
                call-waiting :        Call waiting signal for analog terminals.
                                      ISDN terminal devices use their own special
                                      procedures for this.
                toggle-variant:       Allow toggling of variant.
                silent-phone-intern:  Enables a silent phone for incoming
                                      internal calls.
                silent-phone-extern:  Enables a silent phone for incoming
                                      external calls.
                call-through:         Allow call through.
                extern-diversion:     You can use this setting to define whether
                                      external call forwarding for the internal
                                      subscriber is to be executed within the PBX
                                      system or at the exchange.
                room-supervision:     Allow roomsupervision.
                intercom:             Allows intercom calls to the system 
                                      telephone or to another identical ISDN
                                      telephone.
                announcement:         Enables to receive announcement calls.
                sms:                  Authorizes an internal subscriber to
                                      receive SMS messages.
                msg-waiting:          Message waiting indication on or off.
                uus1:                 Authorizes an internal subscriber to
                                      receive USS1 messages.
                keypad :              Authorizes an internal subscriber to carry
                                      out KEYPAD functions.
                doorIntercom-access:  Authorizes an internal subscriber to
                                      establish a connection with the door entry
                                      phone or open the door.
                tapi:                 Authorizes a subscriber to use the PBX's
                                      TAPI features.
                store-charge:         Charge information for this subscriber will
                                      be recorded or not.
                transmit-charge-info: Charge information will be transmitted to
                                      the subscriber or not.
                use-global-rerouting: Consider global rerouting application."
        ::= { mpsClassOfServiceEntry 4 }

    mpsCoSPickupGroup OBJECT-TYPE
        SYNTAX          PickupGroup
        MAX-ACCESS      read-write
        STATUS          current
        DESCRIPTION
            "This variable contains the pickup group.
             Only extension with the same pickup group can pickup a call from
             another extension."
        ::= { mpsClassOfServiceEntry 5 }

    mpsCoSFeatureGroup OBJECT-TYPE
        SYNTAX          FeatureGroup
        MAX-ACCESS      read-write
        STATUS          current
        DESCRIPTION
            "This variable contains the feature group."
        ::= { mpsClassOfServiceEntry 6 }

    mpsCoSPhonebookAccess OBJECT-TYPE
        SYNTAX          INTEGER {
                            dial-authorisation(1),
                            without-restrictions(2),
                            no(3)
                        }
        MAX-ACCESS      read-write
        STATUS          current
        DESCRIPTION
            "Phonebook access to the global PBX phonebook.
               dial-authorisation:   Access the global phonebook to restrictions
                                     resulting from entries in the
                                     mpsBlacklistNumberTable.
               without_restrictions: Phonebook access without any restrictions.
               no:                   No access to the global phonebook."
        DEFVAL { dial-authorisation }
        ::= { mpsClassOfServiceEntry 7 }

    mpsCoSMusicOnHold OBJECT-TYPE
        SYNTAX          INTEGER {
                            -- file1(1),
                            -- file2(2),
                            -- file3(3),
                            -- file4(4),
                            -- file5(5),
                            -- file6(6),
                            -- file7(7),
                            -- file8(8),
                            -- default1(51),
                            -- default2(52),
			    file(54),
			    default(55),
                            external(80),
                            off(100)
                        }
        MAX-ACCESS      read-write
        STATUS          current
        DESCRIPTION
            "This variable contains the file/tone the remote is provided with,
	     when call is held.
	     Possible values are:
		file:	  variable mpsCoSMOHFileDirectory specifies
			  directory to contain sound file
		default:  variable mpsCoSMOHDefaultVariant specifies the
			  variant whose default is to be used
		external: external source is used
		off:	  no music on hold active (default)"
        DEFVAL { off }
        ::= { mpsClassOfServiceEntry 8 }

    mpsCoSAdminStatus OBJECT-TYPE
        SYNTAX          INTEGER {
                            enable(1),
                            delete(2)
                        }
        MAX-ACCESS      read-write
        STATUS          current
        DESCRIPTION
            "Just for MIB entry deletion."
        DEFVAL { enable }
        ::= { mpsClassOfServiceEntry 9 }

    mpsCoSTrunkBundleAccess OBJECT-TYPE
        SYNTAX          BitValue
        MAX-ACCESS      read-write
        STATUS          current
        DESCRIPTION
            "This variable contains a bit field that allows to 
             selectively enable/disable manual trunk group selection."
        DEFVAL { 0 }
        ::= { mpsClassOfServiceEntry 10 }

    mpsCoSMOHFileDirectory OBJECT-TYPE
        SYNTAX          DisplayString
        MAX-ACCESS      read-write
        STATUS          current
        DESCRIPTION
            "Name of directory (on flash medium) which contains file to be used
	     for music on hold.
             This variable references the entry in mpsWaveFile table where
	     variable mpsWaveFileDirectory has identical content.
	     If there should be multiple entrys with the same content for some
	     reason an arbitrary entry is chosen.
	     This entry is only valid if variable mpsCoSMusicOnHold is set
	     to value file.

	     Default value is the empty string."
        DEFVAL { "" }
        ::= { mpsClassOfServiceEntry 11 }

    mpsCoSMOHDefaultVariant OBJECT-TYPE
        SYNTAX          INTEGER (1..2)
        MAX-ACCESS      read-write
        STATUS          current
        DESCRIPTION
            "This variable specifies the chosen default variant if variable
	     mpsCoSMusicOnHold is set to value default.

	     Default value for that variable is 1."
        DEFVAL { 1 }
        ::= { mpsClassOfServiceEntry 12 }

    mpsCoSTrunkCallDisplay OBJECT-TYPE
        SYNTAX          INTEGER {
                            trunk-and-number-name(1),
                            trunk-name-only(2),
                            number-name-only(3),
                            no-name(4)
                            }
        MAX-ACCESS      read-write
        STATUS          current
        DESCRIPTION
            "Defines how an external trunk call shall be displayed on
             Systemphones:
             trunk-and-number-name(1): Show descriptions of mpsTrunkGroupTable
                                       and mpsTrunkNumberTable.
             trunk-name-only(2):       Show only description of
                                       mpsTrunkGroupTable.
             number-name-only(3):      Show only description of
                                       mpsTrunkNumberTable.
             no-name(4):               Show nothing."
        DEFVAL { number-name-only }
        ::= { mpsClassOfServiceEntry 13 }

    mpsCoSSwitchContacts OBJECT-TYPE
        SYNTAX          BitValue
        MAX-ACCESS      read-write
        STATUS          current
        DESCRIPTION
            "Defines which relay contact(s) may be switched by telephone
             (access) dial codes.
             The bit position corresponds to the SwitchingContactIndex."
        DEFVAL { 0 }
        ::= { mpsClassOfServiceEntry 14 }

---------------------------------------------------------------------------
mpsUserTable OBJECT-TYPE
    SYNTAX      SEQUENCE OF MpsUserEntry
    MAX-ACCESS  not-accessible
    STATUS      current
    DESCRIPTION
        "This table contains the information about users."
    ::= { mpsExtension 14 }

    mpsUserEntry OBJECT-TYPE
        SYNTAX          MpsUserEntry 
        MAX-ACCESS      not-accessible
        STATUS          current
        DESCRIPTION
            ""
        INDEX { mpsUserIndex }
        ::= { mpsUserTable 1 }

    MpsUserEntry ::=
        SEQUENCE {
            mpsUserIndex                                UserIndex,
            mpsUserName                                 DisplayString,
            mpsUserDescription                          DisplayString,
            mpsUserLoginUser                            DisplayString,
            mpsUserMobileNumber                         DisplayString,
            mpsUserHomeNumber                           DisplayString,
            mpsUserMailAddress                          DisplayString,
            mpsUserFacilities                           BITS,
            mpsUserCallThroughOutExtIndex               ExtensionIndexOrZero,
            mpsUserStandardCoS                          CoSIndexOrZero,
            mpsUserOptionalCoS                          CoSIndexOrZero,
            mpsUserNightCoS                             CoSIndexOrZero,
            mpsUserAuthPassword                         DisplayString,
            mpsUserAdminStatus                          INTEGER
        }

    mpsUserIndex OBJECT-TYPE
        SYNTAX          UserIndex
        MAX-ACCESS      read-write
        STATUS          current
        DESCRIPTION
            "A unique value for each user."
        ::= { mpsUserEntry 1 }

       mpsUserName OBJECT-TYPE
            SYNTAX  DisplayString
            MAX-ACCESS  read-write
            STATUS  current
 
            DESCRIPTION
                "This variable contains the name of the user."
        ::= { mpsUserEntry 2 }

       mpsUserDescription OBJECT-TYPE
            SYNTAX  DisplayString
            MAX-ACCESS  read-write
            STATUS  current
 
            DESCRIPTION
                "This variable contains additional description for the user.
                 e.g. 'Hotline' or 'R&D'."
        ::= { mpsUserEntry 3 }

       mpsUserLoginUser OBJECT-TYPE
            SYNTAX  DisplayString
            MAX-ACCESS  read-write
            STATUS  current
 
            DESCRIPTION
                "This variable contains the login user string, referencing
                 variable biboAdmLoginUser in biboAdmLoginTable.
                 This string will be used in mpsExtensionLoginUser, too."
        ::= { mpsUserEntry 4 }


    mpsUserMobileNumber OBJECT-TYPE
        SYNTAX          DisplayString (SIZE(0..24))
        MAX-ACCESS      read-write
        STATUS          current
        DESCRIPTION
            "This variable contains the user's mobile number."
        ::= { mpsUserEntry 5 }

    mpsUserHomeNumber OBJECT-TYPE
        SYNTAX          DisplayString (SIZE(0..24))
        MAX-ACCESS      read-write
        STATUS          current
        DESCRIPTION
            "This variable contains the user's home number."
        ::= { mpsUserEntry 6 }

    mpsUserMailAddress OBJECT-TYPE
        SYNTAX          DisplayString (SIZE(0..64))
        MAX-ACCESS      read-write
        STATUS          current
        DESCRIPTION
            "This variable contains the user's mail address."
        ::= { mpsUserEntry 7 }

    mpsUserFacilities OBJECT-TYPE
        SYNTAX          BITS {
                            showMobilNumInPhonebook(0),
                            showHomeNumInPhonebook(1),
                            callThrough(2)
                        }
        MAX-ACCESS read-write
        STATUS current
        DESCRIPTION
            "user facilities.
                showMobilNumInPhonebook:  Select whether this number is shown
                                          during system phonebook acces.
                showHomeNumInPhonebook:   Select whether this number is shown
                                          during system phonebook acces.
                callThrough:              Select whether call through should be
                                          authorised for this user.
            "
        ::= { mpsUserEntry 8 }

    mpsUserCallThroughOutExtIndex OBJECT-TYPE
        SYNTAX          ExtensionIndexOrZero
        MAX-ACCESS      read-write
        STATUS          current
        DESCRIPTION
            "This variable contains the extension index for outgoing call
             routing, 
             if mpsUserFacilities callThrough option is enabled. Otherwise this
             value is unused."
        ::= { mpsUserEntry 9 }

    mpsUserStandardCoS OBJECT-TYPE
        SYNTAX          CoSIndexOrZero
        MAX-ACCESS      read-write
        STATUS          current
        DESCRIPTION
            "This variable contains the index of the standard class of service
             referencing mpsCoSIndex in mpsClassOfServiceTable."
        ::= { mpsUserEntry 10 }

    mpsUserOptionalCoS OBJECT-TYPE
        SYNTAX          CoSIndexOrZero
        MAX-ACCESS      read-write
        STATUS          current
        DESCRIPTION
            "This variable contains the index of the optional class of service
             referencing to mpsCoSIndex in mpsClassOfServiceTable."
        ::= { mpsUserEntry 11 }

    mpsUserNightCoS OBJECT-TYPE
        SYNTAX          CoSIndexOrZero
        MAX-ACCESS      read-write
        STATUS          current
        DESCRIPTION
            "This variable contains the index of the night class of service
             referencing to mpsCoSIndex in mpsClassOfServiceTable."
        ::= { mpsUserEntry 12 }

   mpsUserAuthPassword OBJECT-TYPE
        SYNTAX          DisplayString (SIZE(0..32))
        MAX-ACCESS      read-write
        STATUS          current
        DESCRIPTION
            "This variable contains authorisation password used for VoIP client
             registration."
        ::= { mpsUserEntry 13 }

    mpsUserAdminStatus OBJECT-TYPE
        SYNTAX          INTEGER {
                            enable(1),
                            delete(2)
                        }
        MAX-ACCESS      read-write
        STATUS          current
        DESCRIPTION
            "Just for MIB entry deletion."
        DEFVAL { enable }
        ::= { mpsUserEntry 14 }

---------------------------------------------------------------------------
mpsUserUserTable OBJECT-TYPE
    SYNTAX      SEQUENCE OF MpsUserUserEntry
    MAX-ACCESS  not-accessible
    STATUS      current
    DESCRIPTION
        "This table contains additional information for the user."
    ::= { mpsExtension 18 }

    mpsUserUserEntry OBJECT-TYPE
        SYNTAX          MpsUserUserEntry 
        MAX-ACCESS      not-accessible
        STATUS          current
        DESCRIPTION
            ""
        INDEX { mpsUserUserIndex }
        ::= { mpsUserUserTable 1 }

    MpsUserUserEntry ::=
        SEQUENCE {
            mpsUserUserIndex                         UserIndex,
            mpsUserUserPin                           DisplayString,
            mpsUserUserAdminStatus                   INTEGER,
            mpsUserUserFacilities                    BITS
        }

    mpsUserUserIndex OBJECT-TYPE
        SYNTAX          UserIndex
        MAX-ACCESS      read-write
        STATUS          current
        DESCRIPTION
            "A unique value for each user, referencing to mpsUserIndex in
             mpsUserTable."
        ::= { mpsUserUserEntry 1 }

   mpsUserUserPin OBJECT-TYPE
        SYNTAX          DisplayString (SIZE(4))
        MAX-ACCESS      read-write
        STATUS          current
        DESCRIPTION
            "This variable contains authorization PIN for telephone procedures.
             'none' = inactive (can not be dialed)."
        DEFVAL { "none" }
        ::= { mpsUserUserEntry 2 }

    mpsUserUserAdminStatus OBJECT-TYPE
        SYNTAX          INTEGER {
                            enable(1),
                            delete(2)
                        }
        MAX-ACCESS      read-write
        STATUS          current
        DESCRIPTION
            "Just for MIB entry deletion."
        DEFVAL { enable }
        ::= { mpsUserUserEntry 3 }

    mpsUserUserFacilities OBJECT-TYPE
        SYNTAX          BITS {
                            userBusyOnBusy(0)
                        }
        MAX-ACCESS read-write
        STATUS current
        DESCRIPTION
            "user facilities.
                userBusyOnBusy: if set, all incoming calls for this user are
                                rejected with user busy, if at least one number
                                of this user is busy.
            "
        ::= { mpsUserUserEntry 4 }

---------------------------------------------------------------------------
mpsCoSTrunkRouteTable OBJECT-TYPE
    SYNTAX      SEQUENCE OF MpsCoSTrunkRouteEntry
    MAX-ACCESS  not-accessible
    STATUS      current
    DESCRIPTION
        "This table contains information about the call routing oder for calls to
         external destination for the referenced class of service."
    ::= { mpsExtension 15 }

    mpsCoSTrunkRouteEntry OBJECT-TYPE
        SYNTAX          MpsCoSTrunkRouteEntry 
        MAX-ACCESS      not-accessible
        STATUS          current
        DESCRIPTION
            ""
        INDEX { mpsCoSTrunkRouteIndex }
        ::= { mpsCoSTrunkRouteTable 1 }

    MpsCoSTrunkRouteEntry ::=
        SEQUENCE {
            mpsCoSTrunkRouteIndex                       INTEGER, 
            mpsCoSTrunkRouteCoS                         CoSIndexOrZero,
            mpsCoSTrunkRoutePrio                        Unsigned32, 
            mpsCoSTrunkRouteTrunkGroup                  TrunkGroupIndexOrZero, 
            mpsCoSTrunkRouteAdminStatus                 INTEGER
        }

    mpsCoSTrunkRouteIndex OBJECT-TYPE
        SYNTAX          INTEGER
        MAX-ACCESS      read-write
        STATUS          current
        DESCRIPTION
            "A unique value for each trunk route entry."
        ::= { mpsCoSTrunkRouteEntry 1 }

    mpsCoSTrunkRouteCoS OBJECT-TYPE
        SYNTAX          CoSIndexOrZero
        MAX-ACCESS      read-write
        STATUS          current
        DESCRIPTION
            "This variable contains the class of service index for this trunk
             route entry.
             Reference to mpsCoSIndex in mpsClassOfServiceTable."
        ::= { mpsCoSTrunkRouteEntry 2 }

    mpsCoSTrunkRoutePrio OBJECT-TYPE
        SYNTAX          Unsigned32
        MAX-ACCESS      read-write
        STATUS          current
        DESCRIPTION
            "Priority of the trunk route entry."
        ::= { mpsCoSTrunkRouteEntry 3 }

    mpsCoSTrunkRouteTrunkGroup OBJECT-TYPE
        SYNTAX          TrunkGroupIndexOrZero
        MAX-ACCESS      read-write
        STATUS          current
        DESCRIPTION
            "This variable contains the trunk group index (mpsTrukGroupIndex)."
        DEFVAL { 0 }
        ::= { mpsCoSTrunkRouteEntry 4 }

    mpsCoSTrunkRouteAdminStatus OBJECT-TYPE
        SYNTAX          INTEGER { enable(1), delete(2) }
        MAX-ACCESS      read-write
        STATUS          current
        DESCRIPTION
            "Just for MIB entry deletion."
        DEFVAL { enable }
        ::= { mpsCoSTrunkRouteEntry 5 }

---------------------------------------------------------------------------
mpsParallelRingingTable OBJECT-TYPE
    SYNTAX      SEQUENCE OF MpsParallelRingingEntry
    MAX-ACCESS  not-accessible
    STATUS      current
    DESCRIPTION
        "This table contains information about parallel ringing feature.
         If the extension is called an additional parallel call we be initiated."
    ::= { mpsExtension 16 }

    mpsParallelRingingEntry OBJECT-TYPE
        SYNTAX          MpsParallelRingingEntry 
        MAX-ACCESS      not-accessible
        STATUS          current
        DESCRIPTION
            ""
        INDEX { mpsPRIndex }
        ::= { mpsParallelRingingTable 1 }

    MpsParallelRingingEntry ::=
        SEQUENCE {
            mpsPRIndex                                  Unsigned32, 
            mpsPRExtension                              ExtensionIndexOrZero,
            mpsPRFacilities                             INTEGER, 
            mpsPRNumber                                 DisplayString, 
            mpsPRAdminStatus                            INTEGER
        }

    mpsPRIndex OBJECT-TYPE
        SYNTAX          Unsigned32
        MAX-ACCESS      read-write
        STATUS          current
        DESCRIPTION
            "A unique value for each parallel ringing entry."
        ::= { mpsParallelRingingEntry 1 }

    mpsPRExtension              OBJECT-TYPE
        SYNTAX          ExtensionIndexOrZero
        MAX-ACCESS      read-write
        STATUS          current
        DESCRIPTION
            "This variable contains the extension for this parallel ringing
             entry.
             Reference to mpsExtensionIndex in mpsExtensionTable."
       DEFVAL{ 0 }
        ::= { mpsParallelRingingEntry 2 } 

    mpsPRFacilities OBJECT-TYPE
        SYNTAX          INTEGER {
                            pr-number(1),
                            mobile-number(2),
                            home-number(3)
                        }
        MAX-ACCESS read-write
        STATUS current
        DESCRIPTION
            "mpsPRFacilities: This value decides which number will be used for
                              the parallel call:
                 pr-number:       the configured number (mpsPRNumber)
                 mobile-number:   the mobile number (mpsUserMobileNumber in
                                  mpsUserTable)
                 home-number:     the home number (mpsUserHomeNumber in
                                  mpsUserTable)
            "
        DEFVAL { pr-number }
        ::= { mpsParallelRingingEntry 3 }

    mpsPRNumber OBJECT-TYPE
        SYNTAX          DisplayString (SIZE(0..24))
        MAX-ACCESS      read-write
        STATUS          current
        DESCRIPTION
            "This variable contains the digits of the parallel ringing number."
       DEFVAL{ ""}
        ::= { mpsParallelRingingEntry 4 }

    mpsPRAdminStatus OBJECT-TYPE
        SYNTAX          INTEGER { enable(1), delete(2) }
        MAX-ACCESS      read-write
        STATUS          current
        DESCRIPTION
            "Just for MIB entry deletion."
        DEFVAL { enable }
        ::= { mpsParallelRingingEntry 5 }

---------------------------------------------------------------------------
mpsExtensionStatusTable OBJECT-TYPE
    SYNTAX      SEQUENCE OF MpsExtensionStatusEntry
    MAX-ACCESS  not-accessible
    STATUS      current
    DESCRIPTION
        "This table contains status information about each extension 
         logged-in in a call-center group (mpsGroupTable)."
    ::= { mpsExtension 17 }

    mpsExtensionStatusEntry OBJECT-TYPE
        SYNTAX          MpsExtensionStatusEntry 
        MAX-ACCESS      not-accessible
        STATUS          current
        DESCRIPTION
            ""
        INDEX { mpsExtensionStatusIndex }
        ::= { mpsExtensionStatusTable 1 }

    MpsExtensionStatusEntry ::=
        SEQUENCE {
            mpsExtensionStatusIndex                 ExtensionIndex, 
            mpsExtensionStatusEndOfWrapUpTime       Date, 
            mpsExtensionStatusConnectionStatus      INTEGER,
            mpsExtensionStatusSumConnectedCalls     Counter32,
            mpsExtensionStatusConnectedCalls        Counter32,
            mpsExtensionStatusSumConnectionTime     INTEGER,
            mpsExtensionStatusConnectionTime        INTEGER

        }

    mpsExtensionStatusIndex OBJECT-TYPE
        SYNTAX          ExtensionIndex
        MAX-ACCESS      read-only
        STATUS          current
        DESCRIPTION
            "A unique value for each extension."
        DEFVAL { 1 }
        ::= { mpsExtensionStatusEntry 1 }

    mpsExtensionStatusEndOfWrapUpTime OBJECT-TYPE
        SYNTAX          Date
        MAX-ACCESS      read-only
        STATUS          current
        DESCRIPTION
            "This variable contains the end or wrap-up time for this extension,
             after termination of an incoming call for
             mpsGroupModeOperation_call_center."
        DEFVAL { 0 }
        ::= { mpsExtensionStatusEntry 2 }

    mpsExtensionStatusConnectionStatus OBJECT-TYPE
        SYNTAX          INTEGER {idle(1), connected(2), ringing(3)} 
        MAX-ACCESS      read-only
        STATUS          current
        DESCRIPTION
            "This variable contains the connection status."
        DEFVAL { idle }
        ::= { mpsExtensionStatusEntry 3 }

    mpsExtensionStatusSumConnectedCalls OBJECT-TYPE
        SYNTAX          Counter32
        MAX-ACCESS      read-only
        STATUS          current
        DESCRIPTION
            "This variable contains the summary of connected calls since system
             start."
        DEFVAL { 0 }
        ::= { mpsExtensionStatusEntry 4 }

    mpsExtensionStatusConnectedCalls OBJECT-TYPE
        SYNTAX          Counter32
        MAX-ACCESS      read-only
        STATUS          current
        DESCRIPTION
            "This value is a copy from mpsExtensionStatusSumConnectedCalls at
             0:00h.
             To get the summary of the connected calls from a day, subtract the
             mpsExtensionStatusConnectedCalls from
             mpsExtensionStatusSumConnectedCalls."
        DEFVAL { 0 }
        ::= { mpsExtensionStatusEntry 5 }

    mpsExtensionStatusSumConnectionTime OBJECT-TYPE
        SYNTAX          INTEGER
        MAX-ACCESS      read-only
        STATUS          current
        DESCRIPTION
            "This variable contains the summary of time of the connected calls."
        DEFVAL { 0 }
        ::= { mpsExtensionStatusEntry 6 }

    mpsExtensionStatusConnectionTime OBJECT-TYPE
        SYNTAX          INTEGER
        MAX-ACCESS      read-only
        STATUS          current
        DESCRIPTION
            "This value is a copy from mpsExtensionStatusSumConnnectionTime at
             0:00h.
             To get the summary of time of the connected calls from a day,
             subtract the mpsExtensionStatusConnectionTime from
             mpsExtensionStatusSumConnectionTime."
        DEFVAL { 0 }
        ::= { mpsExtensionStatusEntry 7 }

---------------------------------------------------------------------------
mpsDoorIntercomTable OBJECT-TYPE
    SYNTAX      SEQUENCE OF MpsDoorIntercomEntry
    MAX-ACCESS  not-accessible
    STATUS      current
    DESCRIPTION
        "This table contains the global information about door intercoms."
    ::= { mpsDoorIntercom 1 }

    mpsDoorIntercomEntry OBJECT-TYPE
        SYNTAX          MpsDoorIntercomEntry 
        MAX-ACCESS      not-accessible
        STATUS          current
        DESCRIPTION
            ""
        INDEX { mpsDoorIntercomIndex }
        ::= { mpsDoorIntercomTable 1 }

    MpsDoorIntercomEntry ::=
        SEQUENCE {
            mpsDoorIntercomIndex                        DoorIntercomIndex, 
            mpsDoorIntercomConnectDTMF                  DisplayString, 
            mpsDoorIntercomAdminStatus                  INTEGER
        }

    mpsDoorIntercomIndex OBJECT-TYPE
        SYNTAX          DoorIntercomIndex
        MAX-ACCESS      read-write
        STATUS          current
        DESCRIPTION
            "A unique value for each door intercom."
        ::= { mpsDoorIntercomEntry 1 }

    mpsDoorIntercomConnectDTMF OBJECT-TYPE
        SYNTAX          DisplayString (SIZE(0..24))
        MAX-ACCESS      read-write
        STATUS          current
        DESCRIPTION
        "Doorline adapter keycode for call acception."
    ::= { mpsDoorIntercomEntry 2 }

    mpsDoorIntercomAdminStatus OBJECT-TYPE
        SYNTAX          INTEGER {
                            enable(1),
                            delete(2)
                        }
        MAX-ACCESS      read-write
        STATUS          current
        DESCRIPTION
            "Just for MIB entry deletion."
        DEFVAL { enable }
    ::= { mpsDoorIntercomEntry 3 }

---------------------------------------------------------------------------
mpsDoorIntercomSourceTable OBJECT-TYPE
    SYNTAX      SEQUENCE OF MpsDoorIntercomSourceEntry
    MAX-ACCESS  not-accessible
    STATUS      current
    DESCRIPTION
        "This table contains the global information for each button of a door 
         intercom."
    ::= { mpsDoorIntercom 2 }

    mpsDoorIntercomSourceEntry OBJECT-TYPE
        SYNTAX          MpsDoorIntercomSourceEntry 
        MAX-ACCESS      not-accessible
        STATUS          current
        DESCRIPTION
            ""
        INDEX { mpsDoorIntercomSourceIndex, mpsDoorIntercomSourceButton }
    ::= { mpsDoorIntercomSourceTable 1 }

    MpsDoorIntercomSourceEntry ::=
        SEQUENCE {
            mpsDoorIntercomSourceIndex                  DoorIntercomIndex, 
            mpsDoorIntercomSourceButton                 DoorButtonIndex, 
            mpsDoorIntercomSourceSetupDTMF              DisplayString, 
            mpsDoorIntercomSourceForwardingTime         INTEGER, 
            mpsDoorIntercomSourceParallelTime           INTEGER, 
            mpsDoorIntercomSourceAlertingTimeout        INTEGER, 
            mpsDoorIntercomSourceCalendar               INTEGER, 
            mpsDoorIntercomSourceAdminStatus            INTEGER,
            mpsDoorIntercomSourceDescr                  DisplayString
        }

    mpsDoorIntercomSourceIndex OBJECT-TYPE
        SYNTAX          DoorIntercomIndex
        MAX-ACCESS      read-write
        STATUS          current
        DESCRIPTION
            "A unique value for each door intercom. 
             Reference to mpsDoorIntercomIndex."
        ::= { mpsDoorIntercomSourceEntry 1 }

    mpsDoorIntercomSourceButton OBJECT-TYPE
        SYNTAX          DoorButtonIndex
        MAX-ACCESS      read-write
        STATUS          current
        DESCRIPTION
            "A unique value for each button of a door intercom."
        ::= { mpsDoorIntercomSourceEntry 2 }

    mpsDoorIntercomSourceSetupDTMF OBJECT-TYPE
        SYNTAX          DisplayString  (SIZE(0..4))
        MAX-ACCESS      read-write
        STATUS          current
        DESCRIPTION
            "A unique value for each door intercom and bell button."
        ::= { mpsDoorIntercomSourceEntry 3 }

    mpsDoorIntercomSourceForwardingTime OBJECT-TYPE
        SYNTAX          INTEGER (1..99)
        UNITS           "s"
        MAX-ACCESS      read-write
        STATUS          current
        DESCRIPTION
            "The linear and rotating doorline team calls allow you to configure
             a time interval in seconds, after which the next member of the
             doorline team will be called."
        DEFVAL { 15 }
        ::= { mpsDoorIntercomSourceEntry 4 }

    mpsDoorIntercomSourceParallelTime OBJECT-TYPE
        SYNTAX          INTEGER (1..99)
        UNITS           "s"
        MAX-ACCESS      read-write
        STATUS          current
        DESCRIPTION
            "The linear and rotating doorline team calls allow you to configure
             a time interval in seconds, after which all members of the
             doorline team will be called at the same time."
        DEFVAL { 60 }
        ::= { mpsDoorIntercomSourceEntry 5 }

    mpsDoorIntercomSourceAlertingTimeout OBJECT-TYPE
        SYNTAX          INTEGER (0..99)
        UNITS           "s"
        MAX-ACCESS      read-write
        STATUS          current
        DESCRIPTION
            "The doorline team calls allow you to configure a time interval in
             seconds, how long the whole team will be called."
        DEFVAL { 40 }
        ::= { mpsDoorIntercomSourceEntry 6 }

    mpsDoorIntercomSourceCalendar OBJECT-TYPE
        SYNTAX          INTEGER
        MAX-ACCESS      read-write
        STATUS          current
        DESCRIPTION
            "Select a calendar to switch the call mode automatically. After you
             have selected a calendar you can set the active call mode. 0 (not
             active), 1 (day mode), 2 (night mode)."
        DEFVAL { 0 }
        ::= { mpsDoorIntercomSourceEntry 7 }

    mpsDoorIntercomSourceAdminStatus OBJECT-TYPE
        SYNTAX          INTEGER {
                            enable(1),
                            delete(2)
                        }
        MAX-ACCESS      read-write
        STATUS          current
        DESCRIPTION
            "Just for MIB entry deletion."
        DEFVAL { enable }
        ::= { mpsDoorIntercomSourceEntry 8 }

    mpsDoorIntercomSourceDescr OBJECT-TYPE
        SYNTAX          DisplayString (SIZE(0..32))
        MAX-ACCESS      read-write
        STATUS          current
        DESCRIPTION
            "Name of the button."
        ::= { mpsDoorIntercomSourceEntry 9 }

---------------------------------------------------------------------------
mpsDoorIntercomUserTable OBJECT-TYPE
    SYNTAX      SEQUENCE OF MpsDoorIntercomUserEntry
    MAX-ACCESS  not-accessible
    STATUS      current
    DESCRIPTION
        "This table contains the mode information for each button of a door 
         intercom."
    ::= { mpsDoorIntercom 3 }

    mpsDoorIntercomUserEntry OBJECT-TYPE
        SYNTAX          MpsDoorIntercomUserEntry 
        MAX-ACCESS      not-accessible
        STATUS          current
        DESCRIPTION
            ""
        INDEX { mpsDoorIntercomUserIndex, mpsDoorIntercomUserButton }
        ::= { mpsDoorIntercomUserTable 1 }

    MpsDoorIntercomUserEntry ::=
        SEQUENCE {
            mpsDoorIntercomUserIndex            DoorIntercomIndex, 
            mpsDoorIntercomUserButton           DoorButtonIndex, 
            mpsDoorIntercomUserMode             DoorIntercomModeIndex, 
            mpsDoorIntercomUserAdminStatus      INTEGER
        }

    mpsDoorIntercomUserIndex OBJECT-TYPE
        SYNTAX          DoorIntercomIndex
        MAX-ACCESS      read-write
        STATUS          current
        DESCRIPTION
            "A unique value for each door intercom.
             Reference to mpsDoorIntercomIndex."
        ::= { mpsDoorIntercomUserEntry 1 }

    mpsDoorIntercomUserButton OBJECT-TYPE
        SYNTAX          DoorButtonIndex
        MAX-ACCESS      read-write
        STATUS          current
        DESCRIPTION
            "A reference to mpsDoorIntercomSourceButton."
        ::= { mpsDoorIntercomUserEntry 2 }

    mpsDoorIntercomUserMode OBJECT-TYPE
        SYNTAX          DoorIntercomModeIndex
        MAX-ACCESS      read-write
        STATUS          current
        DESCRIPTION
            "Select the active call mode. "
        ::= { mpsDoorIntercomUserEntry 3 }

    mpsDoorIntercomUserAdminStatus OBJECT-TYPE
        SYNTAX          INTEGER {
                            enable(1),
                            delete(2)
                        }
        MAX-ACCESS      read-write
        STATUS          current
        DESCRIPTION
            "Just for MIB entry deletion."
        DEFVAL { enable }
        ::= { mpsDoorIntercomUserEntry 4 }

---------------------------------------------------------------------------
mpsDoorIntercomModeTable OBJECT-TYPE
    SYNTAX  SEQUENCE OF MpsDoorIntercomModeEntry
    MAX-ACCESS  not-accessible
    STATUS      current
    DESCRIPTION
        "This table contains information about door intercom and mode."
    ::= { mpsDoorIntercom 4 }

    mpsDoorIntercomModeEntry OBJECT-TYPE
        SYNTAX          MpsDoorIntercomModeEntry 
        MAX-ACCESS      not-accessible
        STATUS          current
        DESCRIPTION
            ""
        INDEX { mpsDoorIntercomModeIndex, mpsDoorIntercomModeButton, 
                mpsDoorIntercomModeNumber }
        ::= { mpsDoorIntercomModeTable 1 }

    MpsDoorIntercomModeEntry ::=
        SEQUENCE {
            mpsDoorIntercomModeIndex                    DoorIntercomIndex, 
            mpsDoorIntercomModeButton                   DoorButtonIndex, 
            mpsDoorIntercomModeNumber                   DoorIntercomModeIndex, 
            mpsDoorIntercomModeHandling                 INTEGER, 
            mpsDoorIntercomModeAssignment               INTEGER, 
            mpsDoorIntercomModeExtNumber                DisplayString, 
            mpsDoorIntercomModeAdminStatus              INTEGER
        }

    mpsDoorIntercomModeIndex OBJECT-TYPE
        SYNTAX          DoorIntercomIndex
        MAX-ACCESS      read-write
        STATUS          current
        DESCRIPTION
            "A unique value for each door intercom.
             Reference to mpsDoorIntercomIndex."
        ::= { mpsDoorIntercomModeEntry 1 }

    mpsDoorIntercomModeButton OBJECT-TYPE
        SYNTAX          DoorButtonIndex
        MAX-ACCESS      read-write
        STATUS          current
        DESCRIPTION
            "A unique value for each button of a door intercom.
             Reference to mpsDoorIntercomSourceButtonIndex."
        ::= { mpsDoorIntercomModeEntry 2 }

    mpsDoorIntercomModeNumber OBJECT-TYPE
        SYNTAX          DoorIntercomModeIndex
        MAX-ACCESS      read-write
        STATUS          current
        DESCRIPTION
            "For each door intercom a variant.
             Reference to mpsDoorIntercomUserMode."
        ::= { mpsDoorIntercomModeEntry 3 }

    mpsDoorIntercomModeHandling OBJECT-TYPE
        SYNTAX          INTEGER {
                            simultaneous(1),
                            linear(2),
                            rotating(3),
                            adding(4),
                            linear-ext(5),
                            rotating-ext(6)
                        }
        MAX-ACCESS      read-write
        STATUS          current
        DESCRIPTION
            "Signalling mode (internal) of the door intercom group:

             simultaneous: all assigned terminals are called simultaneously
             linear      : all assigned terminals are called in the sequence 
                           of their entry in configuration.
             rotating    : this call is a special case of the linear call. 
                           After all terminals are called, call signalling 
                           begins again with the first entered terminal.
             adding      : the terminals are called in the sequence of their
                           entry in the subscriber list. Every terminal that has
                           already been called is called again, until all entered
                           terminals are called.
             linear-ext  : linear + after defined times have run out, all 
                           team subscribers can be called in parallel.
             rotating-ext: rotating + after defined times have run out, all 
                           team subscribers can be called in parallel."
        DEFVAL { simultaneous }
        ::= { mpsDoorIntercomModeEntry 4 }

    mpsDoorIntercomModeAssignment OBJECT-TYPE
        SYNTAX          INTEGER {
                            internal(1),
                            external(2)
                        }
        MAX-ACCESS      read-write
        STATUS          current
        DESCRIPTION
            "Door intercom group member are internal or one external number."
        DEFVAL { internal }
        ::= { mpsDoorIntercomModeEntry 5 }

    mpsDoorIntercomModeExtNumber OBJECT-TYPE
        SYNTAX          DisplayString (SIZE(0..20))
        MAX-ACCESS      read-write
        STATUS  current
        DESCRIPTION
            "This external number will be called, 
             if mpsDoorIntercomModeAssignment = external."
        ::= { mpsDoorIntercomModeEntry 6 }

    mpsDoorIntercomModeAdminStatus OBJECT-TYPE
        SYNTAX          INTEGER {
                            enable(1),
                            delete(2)
                        }
        MAX-ACCESS      read-write
        STATUS          current
        DESCRIPTION
            "Just for MIB entry deletion."
        DEFVAL { enable }
        ::= { mpsDoorIntercomModeEntry 7 }

---------------------------------------------------------------------------
mpsDoorIntercomModeChainTable OBJECT-TYPE
    SYNTAX      SEQUENCE OF MpsDoorIntercomModeChainEntry
    MAX-ACCESS  not-accessible
    STATUS      current
    DESCRIPTION
        "This table contains the extension of each door intercom group and 
         variant."
    ::= { mpsDoorIntercom 5 }

    mpsDoorIntercomModeChainEntry OBJECT-TYPE
        SYNTAX          MpsDoorIntercomModeChainEntry 
        MAX-ACCESS      not-accessible
        STATUS          current
        DESCRIPTION
            ""
        INDEX { mpsDoorIntercomModeChainIndex, mpsDoorIntercomModeChainButton, 
                mpsDoorIntercomModeChainNumber,mpsDoorIntercomModeChainPosition 
              }
        ::= { mpsDoorIntercomModeChainTable 1 }

    MpsDoorIntercomModeChainEntry ::=
        SEQUENCE {
            mpsDoorIntercomModeChainIndex               DoorIntercomIndex, 
            mpsDoorIntercomModeChainButton              DoorButtonIndex, 
            mpsDoorIntercomModeChainNumber              DoorIntercomModeIndex, 
            mpsDoorIntercomModeChainPosition            Unsigned32, 
            mpsDoorIntercomModeChainExtension           ExtensionIndex, 
            mpsDoorIntercomModeChainAdminStatus         INTEGER
        }

    mpsDoorIntercomModeChainIndex OBJECT-TYPE
        SYNTAX          DoorIntercomIndex
        MAX-ACCESS      read-write
        STATUS          current
        DESCRIPTION
            "A unique value for each door intercom.
             Reference to mpsDoorIntercomIndex."
        ::= { mpsDoorIntercomModeChainEntry 1 }

    mpsDoorIntercomModeChainButton OBJECT-TYPE
        SYNTAX          DoorButtonIndex
        MAX-ACCESS      read-write
        STATUS          current
        DESCRIPTION
            "A unique value for each door intercom.
             Reference to mpsDoorIntercomSourceButtonIndex."
        ::= { mpsDoorIntercomModeChainEntry 2 }

    mpsDoorIntercomModeChainNumber OBJECT-TYPE
        SYNTAX          DoorIntercomModeIndex
        MAX-ACCESS      read-write
        STATUS          current
        DESCRIPTION
            "For each door intercom a variant.
             Reference to mpsDoorIntercomUserMode."
        ::= { mpsDoorIntercomModeChainEntry 3 }

    mpsDoorIntercomModeChainPosition OBJECT-TYPE
        SYNTAX          Unsigned32
        MAX-ACCESS      read-write
        STATUS          current
        DESCRIPTION
            "This value determine the order of the called extensions."
        ::= { mpsDoorIntercomModeChainEntry 4 }

    mpsDoorIntercomModeChainExtension OBJECT-TYPE
        SYNTAX          ExtensionIndex
        MAX-ACCESS      read-write
        STATUS          current
        DESCRIPTION
            "A unique value for each extension in the door intercom group 
             variant. Reference to mpsExtensionIndex in mpsExtensionTable."
        ::= { mpsDoorIntercomModeChainEntry 5 }

    mpsDoorIntercomModeChainAdminStatus OBJECT-TYPE
        SYNTAX          INTEGER {
                            enable(1),
                            delete(2)
                        }
        MAX-ACCESS      read-write
        STATUS          current
        DESCRIPTION
            "Just for MIB entry deletion."
        DEFVAL { enable }
        ::= { mpsDoorIntercomModeChainEntry 6 }

---------------------------------------------------------------------------
mpsNetworkTable OBJECT-TYPE
        SYNTAX          SEQUENCE OF MpsNetworkEntry
        MAX-ACCESS      not-accessible
        STATUS          current
        DESCRIPTION
            "This table contains information for each IP location. Every VoIP 
             extension and VoIP provider will be associate to an IP location."
        ::= { mpsVoIP 1 }

    mpsNetworkEntry OBJECT-TYPE
        SYNTAX          MpsNetworkEntry 
        MAX-ACCESS      not-accessible
        STATUS          obsolete
        DESCRIPTION
            ""
        INDEX { mpsNetworkIndex }
        ::= { mpsNetworkTable 1 }

    MpsNetworkEntry ::=
        SEQUENCE {
            mpsNetworkIndex                     NetworkIndex, 
            mpsNetworkRegTimer                  INTEGER, 
            mpsNetworkBwUpstream                INTEGER, 
            mpsNetworkBwDownstream              INTEGER, 
            mpsNetworkAddress                   IpAddress, 
            mpsNetworkNetMask                   IpAddress, 
            mpsNetworkDescr                     DisplayString, 
            mpsNetworkDomain                    DisplayString, 
            mpsNetworkRTPTrafficReservation     INTEGER, 
            mpsNetworkAdminStatus               INTEGER,
            mpsNetworkIfIndex                   InterfaceIndexOrZero
        }

    mpsNetworkIndex OBJECT-TYPE
        SYNTAX          NetworkIndex
        MAX-ACCESS      read-write
        STATUS          obsolete
        DESCRIPTION
            "A unique value for each location."
        ::= { mpsNetworkEntry 1 }

    mpsNetworkRegTimer OBJECT-TYPE
        SYNTAX          INTEGER
        MAX-ACCESS      read-write
        STATUS          obsolete
        DESCRIPTION
            "Registration timer in seconds for IP extension. Set to 0 to get 
             the time from the terminal."
        DEFVAL { 60 }
        ::= { mpsNetworkEntry 2 }

    mpsNetworkBwUpstream OBJECT-TYPE
        SYNTAX          INTEGER
        MAX-ACCESS      read-write
        STATUS          obsolete
        DESCRIPTION
            "Bandwidth for upstream data in kBits/s."
        ::= { mpsNetworkEntry 3 }

    mpsNetworkBwDownstream OBJECT-TYPE
        SYNTAX          INTEGER
        MAX-ACCESS      read-write
        STATUS          obsolete
        DESCRIPTION
            "Bandwidth for downstream data in kBits/s."
        ::= { mpsNetworkEntry 4 }

    mpsNetworkAddress OBJECT-TYPE
        SYNTAX          IpAddress
        MAX-ACCESS      read-write
        STATUS          obsolete
        DESCRIPTION
            "IP Address of the location."
        ::= { mpsNetworkEntry 5 }

    mpsNetworkNetMask OBJECT-TYPE
        SYNTAX          IpAddress
        MAX-ACCESS      read-write
        STATUS          obsolete
        DESCRIPTION
            "Subnet mask."
        ::= { mpsNetworkEntry 6 }

    mpsNetworkDescr OBJECT-TYPE
        SYNTAX          DisplayString (SIZE(0..32))
        MAX-ACCESS      read-write
        STATUS          obsolete
        DESCRIPTION
            "Name of the location."
        ::= { mpsNetworkEntry 7 }

    mpsNetworkDomain OBJECT-TYPE
        SYNTAX          DisplayString (SIZE(0..255))
        MAX-ACCESS      read-write
        STATUS          obsolete
        DESCRIPTION
            "DNS name of the location."
        ::= { mpsNetworkEntry 8 }

    mpsNetworkRTPTrafficReservation OBJECT-TYPE
        SYNTAX          INTEGER
        MAX-ACCESS      read-write
        STATUS          obsolete
        DESCRIPTION
            "Maximum RTP Traffic in percent."
        DEFVAL { 100 }
        ::= { mpsNetworkEntry 9 }

    mpsNetworkAdminStatus OBJECT-TYPE
        SYNTAX          INTEGER { enable(1), delete(2) }
        MAX-ACCESS      read-write
        STATUS          obsolete
        DESCRIPTION
            "Just for MIB entry deletion."
        DEFVAL { enable }
        ::= { mpsNetworkEntry 10 }
        
    mpsNetworkIfIndex OBJECT-TYPE
        SYNTAX          InterfaceIndexOrZero
        MAX-ACCESS      read-write
        STATUS          obsolete
        DESCRIPTION
            "Index of network interface from ifTable to apply the
             bandwidth settings. If the default value has been set,
             the entry is manually configured by the user otherwise
             automatic by the system."
        DEFVAL { 0 }
        ::= { mpsNetworkEntry 11 }

---------------------------------------------------------------------------
mpsCodecPropertyTable OBJECT-TYPE
        SYNTAX          SEQUENCE OF MpsCodecPropertyEntry
        MAX-ACCESS      not-accessible
        STATUS          current
        DESCRIPTION
            "This table contains information about codec properties referred by
             extensions and providers."
        ::= { mpsVoIP 2 }

    mpsCodecPropertyEntry OBJECT-TYPE
        SYNTAX          MpsCodecPropertyEntry 
        MAX-ACCESS      not-accessible
        STATUS          current
        DESCRIPTION
            ""
        INDEX { mpsCodecPropertyIndex }
        ::= { mpsCodecPropertyTable 1 }

    MpsCodecPropertyEntry ::=
        SEQUENCE {
            mpsCodecPropertyIndex               CodecIndex, 
            mpsCodecPropertyDescr               DisplayString,
            mpsCodecPropertyCodecs              BitValue,
            mpsCodecPropertyOrder               INTEGER,
            mpsCodecPropertyFacilities          BITS,
            mpsCodecPropertyAdminStatus         INTEGER
        }

    mpsCodecPropertyIndex OBJECT-TYPE
        SYNTAX          CodecIndex
        MAX-ACCESS      read-write
        STATUS          current
        DESCRIPTION
            "A unique value for each codec list."
        ::= { mpsCodecPropertyEntry 1 }

    mpsCodecPropertyDescr OBJECT-TYPE
        SYNTAX          DisplayString (SIZE(0..20))
        MAX-ACCESS      read-write
        STATUS          current
        DESCRIPTION
            "Contains the description of codec property definition."
        ::= { mpsCodecPropertyEntry 2 }

    mpsCodecPropertyCodecs OBJECT-TYPE
        SYNTAX          BitValue
        MAX-ACCESS      read-write
        STATUS          current
       
        DESCRIPTION
            "For codecs, supported by the provider or extension:
             ulaw       (1)
             alaw       (2)
             g729       (4)
             g726       (8)
             g726_16   (16)
             g726_32   (32)
             g726_40   (64)
             g728     (128)
             g723_63  (256)
             g723_53  (512)
             g729_e  (1024)
             gsm     (2048)
             dtmf    (4096)

             Default ulaw, alaw, g.729 and dtmf."
        DEFVAL { 4103 }
        ::= { mpsCodecPropertyEntry 3 } 

        
    mpsCodecPropertyOrder OBJECT-TYPE
        SYNTAX  INTEGER {
            default(1),
            quality(2),
            lowest(3),
            highest(4)
        }
        MAX-ACCESS      read-write
        STATUS          current
        DESCRIPTION
            " Sorting the codecs 
              default -> system default order
              quality -> highest quality first
              lowest  -> lowest bandwith first
              highest -> highest bandwith first"
                  
        DEFVAL { default }
        ::= { mpsCodecPropertyEntry 4 } 

    mpsCodecPropertyFacilities OBJECT-TYPE
        SYNTAX          BITS {
                              g726coding(1)
                        }
        MAX-ACCESS      read-write
        STATUS          current
        DESCRIPTION
        "Facilities for codec settings:
                 g726coding:             0 -> I.366
                                         1 -> RFC 3551/X.420
             "
        ::= { mpsCodecPropertyEntry 5 }

    mpsCodecPropertyAdminStatus OBJECT-TYPE
        SYNTAX          INTEGER { enable(1), delete(2) } 
        MAX-ACCESS      read-write
        STATUS          current
        DESCRIPTION
            "Just for MIB entry deletion."
        DEFVAL { enable }
        ::= { mpsCodecPropertyEntry 6 }

---------------------------------------------------------------------------
mpsVoIPConfig OBJECT IDENTIFIER ::= { mpsVoIP 3 }

    mpsVoIPConfigRtpPort OBJECT-TYPE
        SYNTAX          INTEGER 
        MAX-ACCESS      read-write
        STATUS          current
        DESCRIPTION
            "Start value of dynamic RTP port."
        DEFVAL { 10000 }
        ::= { mpsVoIPConfig 1 }

    mpsVoIPRegTimer OBJECT-TYPE
        SYNTAX          Unsigned32
        UNITS           "s"
        MAX-ACCESS      read-write
        STATUS          current
        DESCRIPTION
            "Registration timer in seconds for IP extension. Set to 0 to get 
             the time from the VoIP client."
        DEFVAL { 60 }
        ::= { mpsVoIPConfig 2 }

    mpsVoIPDscpSignalling OBJECT-TYPE
        SYNTAX      INTEGER (0 .. 255)
        MAX-ACCESS  read-write
        STATUS      current
        DESCRIPTION
           "The DSCP value used in IP header for signalling data."
        DEFVAL { 46 }
        ::= { mpsVoIPConfig 3 }

    mpsVoIPServerCertIndex OBJECT-TYPE
        SYNTAX          INTEGER
        MAX-ACCESS      read-write
        STATUS          current
        DESCRIPTION
            "Index of certificate entry in certTable to be used as server
             certificate for SIPS transport.
             If 0, predefined certificate of SIP stack is used."
        DEFVAL { 0 }
        ::= { mpsVoIPConfig 4 }

    mpsVoIPSubscribeTimer OBJECT-TYPE
        SYNTAX          Unsigned32
        UNITS           "s"
        MAX-ACCESS      read-write
        STATUS          current
        DESCRIPTION
            "Timer value in seconds for SIP SUBSCRIBE session."
        DEFVAL { 300 }
        ::= { mpsVoIPConfig 5 }

---------------------------------------------------------------------------
mpsPhonebookTable OBJECT-TYPE
        SYNTAX          SEQUENCE OF MpsPhonebookEntry
        MAX-ACCESS      not-accessible
        STATUS          current
        DESCRIPTION
            "This table contains information about the PBX phonebook."
        ::= { mpsPhonebook 1 }

    mpsPhonebookEntry OBJECT-TYPE
        SYNTAX          MpsPhonebookEntry 
        MAX-ACCESS      not-accessible
        STATUS          current
        DESCRIPTION
            ""
        INDEX { mpsPhonebookIndex }
        ::= { mpsPhonebookTable 1 }

    MpsPhonebookEntry ::=
        SEQUENCE {
            mpsPhonebookIndex                   INTEGER, 
            mpsPhonebookName                    DisplayString, 
            mpsPhonebookNumber                  DisplayString, 
            mpsPhonebookBundle                  INTEGER,
            mpsPhonebookCallThroughAdminStatus  INTEGER
        }

    mpsPhonebookIndex OBJECT-TYPE
        SYNTAX          INTEGER
        MAX-ACCESS      read-write
        STATUS          current
        DESCRIPTION
            "A unique value for each phonebook entry."
        ::= { mpsPhonebookEntry 1 }

    mpsPhonebookName OBJECT-TYPE
        SYNTAX          DisplayString (SIZE(0..20))
        MAX-ACCESS      read-write
        STATUS          current
        DESCRIPTION
            "This name will be displayed at the telephone."
        ::= { mpsPhonebookEntry 2 }

    mpsPhonebookNumber OBJECT-TYPE
        SYNTAX          DisplayString (SIZE(0..24))
        MAX-ACCESS      read-write
        STATUS          current
        DESCRIPTION
            "This variable contains the number."
        ::= { mpsPhonebookEntry 3 }

    mpsPhonebookBundle OBJECT-TYPE
        SYNTAX          INTEGER
        MAX-ACCESS      read-write
        STATUS          current
        DESCRIPTION
            "This variable contains the bundle number.
             Reference to mpsTrunkBundleTable."
        DEFVAL { -1 }
        ::= { mpsPhonebookEntry 4 }

    mpsPhonebookCallThroughAdminStatus OBJECT-TYPE
        SYNTAX          INTEGER { enable(1), disable(2), delete(3) }
        MAX-ACCESS      read-write
        STATUS          current
        DESCRIPTION
            "If enable the remote can use the call through feature."
        DEFVAL { disable }
        ::= { mpsPhonebookEntry 5 }

---------------------------------------------------------------------------
mpsUserPhonebookTable OBJECT-TYPE
        SYNTAX          SEQUENCE OF MpsUserPhonebookEntry
        MAX-ACCESS      not-accessible
        STATUS          current
        DESCRIPTION
            "This table contains information about the private user phonebook."
        ::= { mpsPhonebook 2 }

    mpsUserPhonebookEntry OBJECT-TYPE
        SYNTAX          MpsUserPhonebookEntry 
        MAX-ACCESS      not-accessible
        STATUS          current
        DESCRIPTION
            ""
        INDEX { mpsUserPhonebookIndex }
        ::= { mpsUserPhonebookTable 1 }

    MpsUserPhonebookEntry ::=
        SEQUENCE {
            mpsUserPhonebookIndex                   INTEGER,
            mpsUserPhonebookUserIndex               UserIndexOrZero,
            mpsUserPhonebookName                    DisplayString,
            mpsUserPhonebookNumber                  DisplayString,
            mpsUserPhonebookAdminStatus             INTEGER
        }

    mpsUserPhonebookIndex OBJECT-TYPE
        SYNTAX          INTEGER
        MAX-ACCESS      read-write
        STATUS          current
        DESCRIPTION
            "A unique value for each user phonebook entry."
        ::= { mpsUserPhonebookEntry 1 }

    mpsUserPhonebookUserIndex OBJECT-TYPE
        SYNTAX          UserIndexOrZero
        MAX-ACCESS      read-write
        STATUS          current
        DESCRIPTION
            "Reference to owner of this private phonebook entry (mpsUserIndex in
	     mpsUserTable).
             An entry is visible via phonebook access only to this user."
        ::= { mpsUserPhonebookEntry 2 }

    mpsUserPhonebookName OBJECT-TYPE
        SYNTAX          DisplayString (SIZE(0..20))
        MAX-ACCESS      read-write
        STATUS          current
        DESCRIPTION
            "This name will be displayed at the telephone."
        ::= { mpsUserPhonebookEntry 3 }

    mpsUserPhonebookNumber OBJECT-TYPE
        SYNTAX          DisplayString (SIZE(0..24))
        MAX-ACCESS      read-write
        STATUS          current
        DESCRIPTION
            "This variable contains the number."
        ::= { mpsUserPhonebookEntry 4 }

    mpsUserPhonebookAdminStatus OBJECT-TYPE
        SYNTAX          INTEGER { enable(1), delete(3) }
        MAX-ACCESS      read-write
        STATUS          current
        DESCRIPTION
            "Just for MIB entry deletion."
        DEFVAL { enable }
        ::= { mpsUserPhonebookEntry 5 }

---------------------------------------------------------------------------
mpsArsRoutingConfig OBJECT IDENTIFIER ::= { mpsArs 1 }

    mpsArsRoutingFallbackLevel OBJECT-TYPE
        SYNTAX          INTEGER(0..2)
        MAX-ACCESS      read-write
        STATUS          current
        DESCRIPTION
            "This variable contains the maximum fallback level."
        DEFVAL { 2 }
        ::= { mpsArsRoutingConfig 1 }

   mpsArsRoutingFallbackAction OBJECT-TYPE
        SYNTAX          TruthValue
        MAX-ACCESS      read-write
        STATUS          current
        DESCRIPTION
            "This value determine if fallback is enabled (true) or disabled
             (false)."
        DEFVAL { false }
        ::= { mpsArsRoutingConfig 2 }

---------------------------------------------------------------------------
mpsArsZoneDetailsTable OBJECT-TYPE
        SYNTAX          SEQUENCE OF MpsArsZoneDetailsEntry
        MAX-ACCESS      not-accessible
        STATUS          current
        DESCRIPTION
            "This table contains information about zone numbers, assigning each
             entry to a zone in the zone table."
        ::= { mpsArs 2 }

    mpsArsZoneDetailsEntry OBJECT-TYPE
        SYNTAX          MpsArsZoneDetailsEntry
        MAX-ACCESS      not-accessible
        STATUS          current
        DESCRIPTION
            ""
        INDEX { mpsArsZoneDetailsIndex }
        ::= { mpsArsZoneDetailsTable 1 }

    MpsArsZoneDetailsEntry ::=
        SEQUENCE {
            mpsArsZoneDetailsIndex              INTEGER,
            mpsArsZoneDetailsNumber             DisplayString, 
            mpsArsZoneDetailsDescription        DisplayString,
            mpsArsZoneDetailsZoneIndex          ZoneIndex,
            mpsArsZoneDetailsAdminStatus        INTEGER
        }

    mpsArsZoneDetailsIndex OBJECT-TYPE
        SYNTAX          INTEGER
        MAX-ACCESS      read-write
        STATUS          current
        DESCRIPTION
            "A unique index for each zone."
        ::= { mpsArsZoneDetailsEntry 1 }

    mpsArsZoneDetailsNumber OBJECT-TYPE
        SYNTAX          DisplayString (SIZE(0..20))
        MAX-ACCESS      read-write
        STATUS          current
        DESCRIPTION
           "This object specifies a number prefix for the Automatic Route
            Selection zone."
        ::= { mpsArsZoneDetailsEntry 2 }

    mpsArsZoneDetailsDescription OBJECT-TYPE
        SYNTAX          DisplayString 
        MAX-ACCESS      read-write
        STATUS          current
        DESCRIPTION
            "An additional name description."
        ::= { mpsArsZoneDetailsEntry 3 }

    mpsArsZoneDetailsZoneIndex OBJECT-TYPE
        SYNTAX          ZoneIndex
        MAX-ACCESS      read-write
        STATUS          current
        DESCRIPTION
            "This object references the ZoneIndex in mpsArsZoneTable assigned to
             the entry."
        ::= { mpsArsZoneDetailsEntry 4 }

    mpsArsZoneDetailsAdminStatus OBJECT-TYPE
        SYNTAX          INTEGER { enable(1), delete(2) } 
        MAX-ACCESS      read-write
        STATUS          current
        DESCRIPTION
            "Specifies whether this entry defines a mpsArsZoneDetailsEntry or
             should be deleted"
        DEFVAL { enable }
        ::= { mpsArsZoneDetailsEntry 5 }

---------------------------------------------------------------------------
mpsArsZoneTable OBJECT-TYPE
        SYNTAX          SEQUENCE OF MpsArsZoneEntry
        MAX-ACCESS      not-accessible
        STATUS          current
        DESCRIPTION
            "This table contains information about Automatic Route Selection
             zones."
        ::= { mpsArs 3 }

    mpsArsZoneEntry OBJECT-TYPE
        SYNTAX          MpsArsZoneEntry
        MAX-ACCESS      not-accessible
        STATUS          current
        DESCRIPTION
            ""
        INDEX { mpsArsZoneIndex }
        ::= { mpsArsZoneTable 1 }

    MpsArsZoneEntry ::=
        SEQUENCE {
            mpsArsZoneIndex             ZoneIndex, 
            mpsArsZoneDescription       DisplayString,
            mpsArsZoneAdminStatus       INTEGER
        }

    mpsArsZoneIndex OBJECT-TYPE
        SYNTAX          ZoneIndex
        MAX-ACCESS      read-write
        STATUS          current
        DESCRIPTION
            "A unique index for each zone definition."
        ::= { mpsArsZoneEntry 1 }

    mpsArsZoneDescription OBJECT-TYPE
        SYNTAX          DisplayString (SIZE(0..32))
        MAX-ACCESS      read-write
        STATUS          current
        DESCRIPTION
            "This object defines a zone description for the Automatic Route
             Selection functionality."
        ::= { mpsArsZoneEntry 2 }

    mpsArsZoneAdminStatus OBJECT-TYPE
        SYNTAX          INTEGER { enable(1), delete(2) } 
        MAX-ACCESS      read-write
        STATUS          current
        DESCRIPTION
            "Specifies whether this entry defines an LCR Zone or
             should be deleted"
       DEFVAL { enable }
       ::= { mpsArsZoneEntry 3 }

---------------------------------------------------------------------------
mpsArsRoutingTable OBJECT-TYPE
        SYNTAX          SEQUENCE OF MpsArsRoutingEntry
        MAX-ACCESS      not-accessible
        STATUS          current
        DESCRIPTION
            "This table contains information about routing rule of the
            LCR routing."
        ::= { mpsArs 4 }

    mpsArsRoutingEntry OBJECT-TYPE
        SYNTAX          MpsArsRoutingEntry
        MAX-ACCESS      not-accessible
        STATUS          current
        DESCRIPTION
            ""
        INDEX { mpsArsRoutingIndex }
        ::= { mpsArsRoutingTable 1 }

    MpsArsRoutingEntry ::=
        SEQUENCE {
            mpsArsRoutingIndex                  RouteIndex, 
            mpsArsRoutingPrio                   INTEGER, 
            mpsArsRoutingZone                   ZoneIndex, 
            mpsArsRoutingDays                   BITS,
            mpsArsRoutingAdminStatus            INTEGER
        }
        

    mpsArsRoutingIndex OBJECT-TYPE
        SYNTAX          RouteIndex
        MAX-ACCESS      read-write
        STATUS          current
        DESCRIPTION
            "A unique index for each ArsRouting entry."
        ::= { mpsArsRoutingEntry 1 }

    mpsArsRoutingPrio OBJECT-TYPE
        SYNTAX          INTEGER
        MAX-ACCESS      read-write
        STATUS          current
        DESCRIPTION
            "This object specifies the prio among the routing entries refering
             the same Zone,Day and Week entries."
        ::= { mpsArsRoutingEntry 2 }

    mpsArsRoutingZone OBJECT-TYPE
        SYNTAX          ZoneIndex
        MAX-ACCESS      read-write
        STATUS          current
        DESCRIPTION
            "This object specifies an index in the mpsArsZoneTable."
        ::= { mpsArsRoutingEntry 3 }

    mpsArsRoutingDays OBJECT-TYPE
        SYNTAX          BITS {
                            monday(1),
                            tuesday(2),
                            wednesday(3),
                            thursday(4),
                            friday(5),
                            saturday(6),
                            sunday(7)
                        }
        MAX-ACCESS      read-write
        STATUS          current
        DESCRIPTION
            "This object specifies the weekdays this routing shall be active."
        ::= { mpsArsRoutingEntry 4 }

    mpsArsRoutingAdminStatus OBJECT-TYPE
        SYNTAX          INTEGER { enable(1), delete(2) } 
        MAX-ACCESS      read-write
        STATUS          current
        DESCRIPTION
            "Specifies whether this entry defines a routing or should be deleted"
            DEFVAL { enable }
        ::= { mpsArsRoutingEntry 5 }

---------------------------------------------------------------------------
mpsArsRoutingDetailsTable OBJECT-TYPE
        SYNTAX          SEQUENCE OF MpsArsRoutingDetailsEntry
        MAX-ACCESS      not-accessible
        STATUS          current
        DESCRIPTION
        "This table assigns a carrier and start time selection to an entry in the
         mpsArsRoutingTable."
    ::= { mpsArs 5 }

    mpsArsRoutingDetailsEntry OBJECT-TYPE
        SYNTAX          MpsArsRoutingDetailsEntry
        MAX-ACCESS      not-accessible
        STATUS          current
        DESCRIPTION
            ""
        INDEX {mpsArsRoutingDetailsHour, mpsArsRoutingDetailsMinute , mpsArsRoutingDetailsRoutingIndex}
        ::= { mpsArsRoutingDetailsTable 1 }

    MpsArsRoutingDetailsEntry ::=
        SEQUENCE {
            mpsArsRoutingDetailsHour                    INTEGER,
            mpsArsRoutingDetailsMinute                  INTEGER,
            mpsArsRoutingDetailsRoutingIndex            RouteIndex,
            mpsArsRoutingDetailsCarrierIndex            CarrierIndex, 
            mpsArsRoutingDetailsAdminStatus             INTEGER
        }
        
    mpsArsRoutingDetailsHour OBJECT-TYPE
        SYNTAX          INTEGER (0..23)
        MAX-ACCESS      read-write
        STATUS          current
        DESCRIPTION
            "This object specifies the start hour for activity of this routing
             entry."
        ::= { mpsArsRoutingDetailsEntry 1 }

    mpsArsRoutingDetailsMinute OBJECT-TYPE
        SYNTAX          INTEGER (0..59)
        MAX-ACCESS      read-write
        STATUS          current
        DESCRIPTION
            "This object specifies the start minute for activity of this routing
             entry."
        ::= { mpsArsRoutingDetailsEntry 2 }

    mpsArsRoutingDetailsRoutingIndex OBJECT-TYPE
        SYNTAX          RouteIndex
        MAX-ACCESS      read-write
        STATUS          current
        DESCRIPTION
            "This object specifies a number for the LCR zone.
             Reference to mpsARSZoneIndex."
        ::= { mpsArsRoutingDetailsEntry 3 }
        
    mpsArsRoutingDetailsCarrierIndex OBJECT-TYPE
        SYNTAX          CarrierIndex
        MAX-ACCESS      read-write
        STATUS          current
        DESCRIPTION
            "A unique index for each carrier.
             Reference to mpsARSCarrierIndex."
        ::= { mpsArsRoutingDetailsEntry 4 }

    mpsArsRoutingDetailsAdminStatus OBJECT-TYPE
        SYNTAX          INTEGER { enable(1), delete(2) } 
        MAX-ACCESS      read-write
        STATUS          current
        DESCRIPTION
            "Specifies whether this entry defines a LCR RoutingDetails Entry or
             should be deleted"
        DEFVAL { enable }
        ::= { mpsArsRoutingDetailsEntry 5 }

---------------------------------------------------------------------------
mpsArsCarrierTable OBJECT-TYPE
        SYNTAX          SEQUENCE OF MpsArsCarrierEntry
        MAX-ACCESS      not-accessible
        STATUS          current
        DESCRIPTION
            "This table contains information about carrier used by 
             Automatic Route Selection feature."
        ::= { mpsArs 6 }

    mpsArsCarrierEntry OBJECT-TYPE
        SYNTAX          MpsArsCarrierEntry
        MAX-ACCESS      not-accessible
        STATUS          current
        DESCRIPTION
            ""
        INDEX { mpsArsCarrierIndex }
        ::= { mpsArsCarrierTable 1 }

    MpsArsCarrierEntry ::=
        SEQUENCE {
            mpsArsCarrierIndex                  CarrierIndex, 
            mpsArsCarrierDisplayName            DisplayString,
            mpsArsCarrierNumber                 DisplayString, 
            mpsArsCarrierNumberPresentation     INTEGER, 
            mpsArsCarrierRoutingMode            INTEGER,
            mpsArsCarrierRoutingModeNumber      DisplayString,
            mpsArsCarrierRoutingAdminStatus     INTEGER,
            mpsArsCarrierRoutingTargetIndex     INTEGER 
        }

    mpsArsCarrierIndex OBJECT-TYPE
        SYNTAX          CarrierIndex
        MAX-ACCESS      read-write
        STATUS          current
        DESCRIPTION
            "A unique index for each carrier."
        ::= { mpsArsCarrierEntry 1 }


    mpsArsCarrierDisplayName OBJECT-TYPE
        SYNTAX          DisplayString (SIZE(0..20))
        MAX-ACCESS      read-write
        STATUS          current
        DESCRIPTION
            "This object specifies a Carrier description for the Autom. Route
             Selection functionality. The DisplayName can be shown on the sytem
             phones."
        ::= { mpsArsCarrierEntry 2 }

    mpsArsCarrierNumber OBJECT-TYPE
        SYNTAX          DisplayString (SIZE(0..12))
        MAX-ACCESS      read-write
        STATUS          current
        DESCRIPTION
            "This object specifies the number to be inserted to select a special
             route (carrier)."
        ::= { mpsArsCarrierEntry 3 }

    mpsArsCarrierNumberPresentation      OBJECT-TYPE
        SYNTAX          INTEGER {
                            show(1),
                            hide(2)
                        }
        MAX-ACCESS      read-write
        STATUS          current
        DESCRIPTION
            "show: number presentation is active (CLIP).
             hide: number presentation is restricted (CLIR)."
        DEFVAL { show }
        ::= { mpsArsCarrierEntry 4 }

    mpsArsCarrierRoutingMode OBJECT-TYPE
        SYNTAX          INTEGER {
                            standard(1),
                            bundle(2),
                            msn(3)
                        }
        MAX-ACCESS      read-write
        STATUS          current
        DESCRIPTION
            "This object specifies the routing mode for this carrier:
             RoutingMode=standard -> Route via standard (ClassOfService)
                                     settings,
             RoutingMode=bundle   -> Route via selected trunk group/bundle table,
             RoutingMode=msn      -> Route via selected MSN (e.g. internal GSM-
                                     Gateway)."
        DEFVAL { standard }
        ::= { mpsArsCarrierEntry 5 }

    mpsArsCarrierRoutingModeNumber OBJECT-TYPE
        SYNTAX          DisplayString (SIZE(0..4))
        MAX-ACCESS      read-write
        STATUS          current
        DESCRIPTION
            "This object specifies the bundle (number as string, reference to
             mpsTrunkBundleTable) or internal MSN depending on the selected
             RoutingMode."
        ::= { mpsArsCarrierEntry 6 }

    mpsArsCarrierRoutingAdminStatus OBJECT-TYPE
        SYNTAX          INTEGER {
                            enable(1),
                            delete(2)
                        }
        MAX-ACCESS      read-write
        STATUS          current
        DESCRIPTION
            "Just for MIB entry deletion."
        DEFVAL { enable }
        ::= { mpsArsCarrierEntry 7 }

    mpsArsCarrierRoutingTargetIndex OBJECT-TYPE
        SYNTAX          INTEGER
        MAX-ACCESS      read-write
        STATUS          current
        DESCRIPTION
            "This variable contains the index (reference) of the target to be
             used for routing:
             RoutingMode=standard -> TargetIndex = 0,
             RoutingMode=bundle   -> TargetIndex = mpsTrunkBundleIndex,
             RoutingMode=msn      -> TargetIndex = mpsExtensionIndex."
        DEFVAL { 0 }
        ::= { mpsArsCarrierEntry 8 }

---------------------------------------------------------------------------
mpsFaxSwitchTable OBJECT-TYPE
    SYNTAX      SEQUENCE OF MpsFaxSwitchEntry
    MAX-ACCESS  not-accessible
    STATUS      current
    DESCRIPTION
        "This table contains the information about fax switches."
    ::= { mpsFaxSwitch 1 }

    mpsFaxSwitchEntry OBJECT-TYPE
        SYNTAX          MpsFaxSwitchEntry 
        MAX-ACCESS      not-accessible
        STATUS          current
        DESCRIPTION
            ""
        INDEX { mpsFaxSwitchIndex }
        ::= { mpsFaxSwitchTable 1 }

    MpsFaxSwitchEntry ::=
        SEQUENCE {
            mpsFaxSwitchIndex                   FaxSwitchIndex, 
            mpsFaxSwitchCallCalendar            INTEGER,
            mpsFaxSwitchAdminStatus             INTEGER
        }

    mpsFaxSwitchIndex OBJECT-TYPE
        SYNTAX          FaxSwitchIndex
        MAX-ACCESS      read-write
        STATUS          current
        DESCRIPTION
            "A unique value for each fax switch.
             Use the same value in mpsFaxSwitchModeIndex and
             mpsFaxSwitchUserIndex as reference to this entry."
        ::= { mpsFaxSwitchEntry 1 }

    mpsFaxSwitchCallCalendar OBJECT-TYPE
        SYNTAX          INTEGER
        MAX-ACCESS      read-write
        STATUS          current
        DESCRIPTION
            "Select a calendar to switch the fax mode automatically. 
             The active mode will be set in mpsFaxSwitchUserModeNumber 
             in mpsFaxSwitchUserTable."
        DEFVAL { 0 }
        ::= { mpsFaxSwitchEntry 2 }

    mpsFaxSwitchAdminStatus OBJECT-TYPE
        SYNTAX          INTEGER { enable(1), delete(2) }
        MAX-ACCESS      read-write
        STATUS          current
        DESCRIPTION
            "Just for MIB entry deletion."
        DEFVAL { enable }
        ::= { mpsFaxSwitchEntry 3 }

---------------------------------------------------------------------------
mpsFaxSwitchModeTable OBJECT-TYPE
    SYNTAX      SEQUENCE OF MpsFaxSwitchModeEntry
    MAX-ACCESS  not-accessible
    STATUS      current
    DESCRIPTION
        "This table contains the information about fax switch modes."
    ::= { mpsFaxSwitch 2 }

    mpsFaxSwitchModeEntry OBJECT-TYPE
        SYNTAX          MpsFaxSwitchModeEntry
        MAX-ACCESS      not-accessible
        STATUS          current
        DESCRIPTION
            ""
        INDEX { mpsFaxSwitchModeIndex, mpsFaxSwitchModeNumber }
        ::= { mpsFaxSwitchModeTable 1 }

    MpsFaxSwitchModeEntry ::=
        SEQUENCE {
            mpsFaxSwitchModeIndex               FaxSwitchIndex, 
            mpsFaxSwitchModeNumber              FaxSwitchModeIndex,
            mpsFaxSwitchModeExtension           ExtensionIndexOrZero,
            mpsFaxSwitchModeCNGTimeSlice        Unsigned32,
            mpsFaxSwitchModeRingingTime         Unsigned32,
            mpsFaxSwitchModeAdminStatus         INTEGER
        }

    mpsFaxSwitchModeIndex OBJECT-TYPE
        SYNTAX          FaxSwitchIndex
        MAX-ACCESS      read-write
        STATUS          current
        DESCRIPTION
            "A unique value for each fax switch.
             Use the same value in mpsFaxSwitchIndex and mpsFaxSwitchUserIndex
             as reference to this entry."
        ::= { mpsFaxSwitchModeEntry 1 }

    mpsFaxSwitchModeNumber OBJECT-TYPE
        SYNTAX          FaxSwitchModeIndex
        MAX-ACCESS      read-write
        STATUS          current
        DESCRIPTION
            "A unique value or each mode of fax switch.
             The current active fax mode is set in 
             mpsFaxSwitchUserModeNumber in mpsFaxSwitchUserTable."
        ::= { mpsFaxSwitchModeEntry 2 }

    mpsFaxSwitchModeExtension OBJECT-TYPE
        SYNTAX          ExtensionIndexOrZero
        MAX-ACCESS      read-write
        STATUS          current
        DESCRIPTION
            "This variable contains the extension index of the fax port."
        ::= { mpsFaxSwitchModeEntry 3 }

    mpsFaxSwitchModeCNGTimeSlice OBJECT-TYPE
        SYNTAX          Unsigned32
        UNITS           "s"
        MAX-ACCESS      read-write
        STATUS          current
        DESCRIPTION
            "This variable contains the time slice in seconds to
             detect the CNG tone."
        ::= { mpsFaxSwitchModeEntry 4 }

    mpsFaxSwitchModeRingingTime OBJECT-TYPE
        SYNTAX          Unsigned32
        UNITS           "s"
        MAX-ACCESS      read-write
        STATUS          current
        DESCRIPTION
            "This variable contains the time in seconds how long
             the extension will be called."
        ::= { mpsFaxSwitchModeEntry 5 }

    mpsFaxSwitchModeAdminStatus OBJECT-TYPE
        SYNTAX          INTEGER { enable(1), disable(2), delete(3) }
        MAX-ACCESS      read-write
        STATUS          current
        DESCRIPTION
            "Just for MIB entry deletion."
        DEFVAL { enable }
        ::= { mpsFaxSwitchModeEntry 6 }

---------------------------------------------------------------------------
mpsFaxSwitchUserTable OBJECT-TYPE
    SYNTAX      SEQUENCE OF MpsFaxSwitchUserEntry
    MAX-ACCESS  not-accessible
    STATUS      current
    DESCRIPTION
        "This table contains the information about current mode for fax
         switches."
    ::= { mpsFaxSwitch 3 }

    mpsFaxSwitchUserEntry OBJECT-TYPE
        SYNTAX          MpsFaxSwitchUserEntry 
        MAX-ACCESS      not-accessible
        STATUS          current
        DESCRIPTION
            ""
        INDEX { mpsFaxSwitchUserIndex }
        ::= { mpsFaxSwitchUserTable 1 }

    MpsFaxSwitchUserEntry ::=
        SEQUENCE {
            mpsFaxSwitchUserIndex                   FaxSwitchIndex, 
            mpsFaxSwitchUserModeNumber              FaxSwitchModeIndex, 
            mpsFaxSwitchUserAdminStatus             INTEGER
        }

    mpsFaxSwitchUserIndex OBJECT-TYPE
        SYNTAX          FaxSwitchIndex
        MAX-ACCESS      read-write
        STATUS          current
        DESCRIPTION
            "A unique value for each fax switch.
             Use the same value in mpsFaxSwitchIndex and mpsFaxSwitchModeIndex
             as reference to this entry."
        ::= { mpsFaxSwitchUserEntry 1 }

    mpsFaxSwitchUserModeNumber OBJECT-TYPE
        SYNTAX          FaxSwitchModeIndex
        MAX-ACCESS      read-write
        STATUS          current
        DESCRIPTION
            "Select the active fax mode number.
             If a calendar in mpsFaxSwitchTable is selected the mode is switched
             automatically."
        ::= { mpsFaxSwitchUserEntry 2 }

    mpsFaxSwitchUserAdminStatus OBJECT-TYPE
        SYNTAX          INTEGER { enable(1), delete(2) }
        MAX-ACCESS      read-write
        STATUS          current
        DESCRIPTION
            "Just for MIB entry deletion."
        DEFVAL { enable }
        ::= { mpsFaxSwitchUserEntry 3 }

---------------------------------------------------------------------------
mpsCalendarTable OBJECT-TYPE
    SYNTAX      SEQUENCE OF MpsCalendarEntry
    MAX-ACCESS  not-accessible
    STATUS      current
    DESCRIPTION
        "This table contains information about calendars."
    ::= { mpsCalendar 1 }

    mpsCalendarEntry OBJECT-TYPE
        SYNTAX          MpsCalendarEntry 
        MAX-ACCESS      not-accessible
        STATUS          current
        DESCRIPTION
            ""
        INDEX { mpsCalendarIndex }
        ::= { mpsCalendarTable 1 }

    MpsCalendarEntry ::=
        SEQUENCE {
            mpsCalendarIndex                        CalendarIndex,
            mpsCalendarDescription                  DisplayString,
            mpsCalendarType                         INTEGER,
            mpsCalendarFacilities                   BITS,
            mpsCalendarAdminStatus                  INTEGER
        }

    mpsCalendarIndex OBJECT-TYPE
        SYNTAX          CalendarIndex
        MAX-ACCESS      read-write
        STATUS          current
        DESCRIPTION
            "A unique value for each calendar.
             Use the same value in mpsCalSetting->mpsCalSetCalIndex
             as reference to this entry."
        ::= { mpsCalendarEntry 1}

    mpsCalendarDescription OBJECT-TYPE
        SYNTAX          DisplayString
        MAX-ACCESS      read-write
        STATUS          current
        DESCRIPTION
            "Description of this calendar."
        ::= { mpsCalendarEntry 2}

    mpsCalendarType      OBJECT-TYPE
        SYNTAX          INTEGER {
                            group(1),
                            dayNight(2),
                            cos(3),
                            rerouting(4),
                            doorcom(5),
                            vms(6),
                            alarmInput(7)
                        }
        MAX-ACCESS      read-write
        STATUS          current
        DESCRIPTION
            "This variable contains the type of the calendar.
             group(1)      : calendar to switch group mode.
             dayNight(2)   : calendar to switch between day and night mode of the
                             whole PBX.
             cos (3)       : calendar to switch the ClassOfService settings.
             rerouting(4)  : calendar to switch rerouting function.
             doorcom(5)    : calendar to switch doorcom mode.
             vms(6)        : calendar to switch voice mail server.
             alarmInput(7) : calendar to switch alarm input mode."
        DEFVAL { group }
        ::= { mpsCalendarEntry 3 }

    mpsCalendarFacilities OBJECT-TYPE
        SYNTAX          BITS {
                            useHoliday(1)
                        }
        MAX-ACCESS      read-write
        STATUS          current
        DESCRIPTION
            "This variable contains specific facilities of the calendar
             useHoliday (1) : consider holiday or not. "
        ::= { mpsCalendarEntry 4 }

    mpsCalendarAdminStatus OBJECT-TYPE
        SYNTAX          INTEGER { enable(1), delete(2) }
        MAX-ACCESS      read-write
        STATUS          current
        DESCRIPTION
            "Just for MIB entry deletion."
        DEFVAL { enable }
        ::= { mpsCalendarEntry 5 }

---------------------------------------------------------------------------
mpsCalSettingTable OBJECT-TYPE
    SYNTAX      SEQUENCE OF MpsCalSettingEntry
    MAX-ACCESS  not-accessible
    STATUS      current
    DESCRIPTION
        "This table contains information about day of the calendar."
    ::= { mpsCalendar 2 }

    mpsCalSettingEntry OBJECT-TYPE
        SYNTAX          MpsCalSettingEntry 
        MAX-ACCESS      not-accessible
        STATUS          current
        DESCRIPTION
            ""
        INDEX { mpsCalSetIndex }
        ::= { mpsCalSettingTable 1 }

    MpsCalSettingEntry ::=
        SEQUENCE {
            mpsCalSetIndex                          CalSetIndex,
            mpsCalSetCalIndex                       CalendarIndex,
            mpsCalSetDay                            BITS,
            mpsCalSetAdminStatus                    INTEGER
        }

    mpsCalSetIndex OBJECT-TYPE
        SYNTAX          CalSetIndex
        MAX-ACCESS      read-write
        STATUS          current
        DESCRIPTION
            "A unique value for calendar.
             Use the same value in mpsCalDetail->mpsCalDetailIndex
             as reference to this entry."
        ::= { mpsCalSettingEntry 1}

    mpsCalSetCalIndex OBJECT-TYPE
        SYNTAX          CalendarIndex
        MAX-ACCESS      read-write
        STATUS          current
        DESCRIPTION
            "Reference to mpsCalendar->mpsCalendarIndex."
        ::= { mpsCalSettingEntry 2}

    mpsCalSetDay OBJECT-TYPE
        SYNTAX          BITS {
                            monday(1),
                            tuesday(2),
                            wednesday(3),
                            thursday(4),
                            friday(5),
                            saturday(6),
                            sunday(7),
                            holiday(8)
                        }
        MAX-ACCESS      read-write
        STATUS          current
        DESCRIPTION
            "This variable contains valid days for this calendar."
        ::= { mpsCalSettingEntry 3 }

    mpsCalSetAdminStatus OBJECT-TYPE
        SYNTAX          INTEGER { enable(1), delete(2) }
        MAX-ACCESS      read-write
        STATUS          current
        DESCRIPTION
            "Just for MIB entry deletion."
        DEFVAL { enable }
        ::= { mpsCalSettingEntry 4 }

---------------------------------------------------------------------------
mpsCalDetailTable OBJECT-TYPE
    SYNTAX      SEQUENCE OF MpsCalDetailEntry
    MAX-ACCESS  not-accessible
    STATUS      current
    DESCRIPTION
        "This table contains information about hour, minute and mode of the
         calendar."
    ::= { mpsCalendar 3 }

    mpsCalDetailEntry OBJECT-TYPE
        SYNTAX          MpsCalDetailEntry 
        MAX-ACCESS      not-accessible
        STATUS          current
        DESCRIPTION
            ""
        INDEX { mpsCalDetailIndex }
        ::= { mpsCalDetailTable 1 }

    MpsCalDetailEntry ::=
        SEQUENCE {
            mpsCalDetailIndex                       CalSetIndex,
            mpsCalDetailHour                        INTEGER,
            mpsCalDetailMin                         INTEGER,
            mpsCalDetailMode                        Unsigned32,
            mpsCalDetailAdminStatus                 INTEGER
        }

    mpsCalDetailIndex OBJECT-TYPE
        SYNTAX          CalSetIndex
        MAX-ACCESS      read-write
        STATUS          current
        DESCRIPTION
            "A unique value for calendar.
             Use the same value in mpsCalSetIndex->CalSetIndex
             as reference to this entry."
        ::= { mpsCalDetailEntry 1}

    mpsCalDetailHour OBJECT-TYPE
        SYNTAX          INTEGER (0..23)
        MAX-ACCESS      read-write
        STATUS          current
        DESCRIPTION
            "This variable contains the hour for the switching time."
        ::= { mpsCalDetailEntry 2 }

    mpsCalDetailMin OBJECT-TYPE
        SYNTAX          INTEGER (0..59)
        MAX-ACCESS      read-write
        STATUS          current
        DESCRIPTION
            "This variable contains the minutes for the switching time."
        ::= { mpsCalDetailEntry 3 }

    mpsCalDetailMode OBJECT-TYPE
        SYNTAX          Unsigned32
        MAX-ACCESS      read-write
        STATUS          current
        DESCRIPTION
            "This variable contains the mode, to which the calendar will be 
             switched."
        ::= { mpsCalDetailEntry 4 }

    mpsCalDetailAdminStatus OBJECT-TYPE
        SYNTAX          INTEGER { enable(1), delete(2) }
        MAX-ACCESS      read-write
        STATUS          current
        DESCRIPTION
            "Just for MIB entry deletion."
        DEFVAL { enable }
        ::= { mpsCalDetailEntry 5 }

---------------------------------------------------------------------------
mpsPublicHolidayTable OBJECT-TYPE
    SYNTAX      SEQUENCE OF MpsPublicHolidayEntry
    MAX-ACCESS  not-accessible
    STATUS      current
    DESCRIPTION
        "This table contains dates of public holiday.
         This days will be considered, if useHoliday in mpsCalendarFacilities
         of mpsCalendarTable is set."
    ::= { mpsCalendar 4 }

    mpsPublicHolidayEntry OBJECT-TYPE
        SYNTAX          MpsPublicHolidayEntry 
        MAX-ACCESS      not-accessible
        STATUS          current
        DESCRIPTION
            ""
        INDEX { mpsPubHolIndex }
        ::= { mpsPublicHolidayTable 1 }

    MpsPublicHolidayEntry ::=
        SEQUENCE {
            mpsPubHolIndex                          Unsigned32,
            mpsPubHolDescription                    DisplayString,
            mpsPubHolDateDay                        INTEGER,
            mpsPubHolDateMonth                      INTEGER,
            mpsPubHolDateEndDay                     INTEGER,
            mpsPubHolDateEndMonth                   INTEGER,
            mpsPubHolAdminStatus                    INTEGER
        }

    mpsPubHolIndex OBJECT-TYPE
        SYNTAX          Unsigned32
        MAX-ACCESS      read-write
        STATUS          current
        DESCRIPTION
            "A unique value for public holiday."
        ::= { mpsPublicHolidayEntry 1}

    mpsPubHolDescription OBJECT-TYPE
        SYNTAX          DisplayString
        MAX-ACCESS      read-write
        STATUS          current
        DESCRIPTION
            "Description of this public holiday."
        ::= { mpsPublicHolidayEntry 2}

    mpsPubHolDateDay OBJECT-TYPE
        SYNTAX          INTEGER (1..31)
        MAX-ACCESS      read-write
        STATUS          current
        DESCRIPTION
            "This variable contains the day of the public holiday"
        ::= { mpsPublicHolidayEntry 3 }

    mpsPubHolDateMonth OBJECT-TYPE
        SYNTAX          INTEGER (1..12)
        MAX-ACCESS      read-write
        STATUS          current
        DESCRIPTION
            "This variable contains the month of the public holiday."
        ::= { mpsPublicHolidayEntry 4 }

    mpsPubHolDateEndDay OBJECT-TYPE
        SYNTAX          INTEGER (1..31)
        MAX-ACCESS      read-write
        STATUS          current
        DESCRIPTION
            "This variable contains the end day for period setting."
        ::= { mpsPublicHolidayEntry 5 }

    mpsPubHolDateEndMonth OBJECT-TYPE
        SYNTAX          INTEGER (1..12)
        MAX-ACCESS      read-write
        STATUS          current
        DESCRIPTION
            "This variable contains the end month for period setting."
        ::= { mpsPublicHolidayEntry 6 }

    mpsPubHolAdminStatus OBJECT-TYPE
        SYNTAX          INTEGER { enable(1), delete(2) }
        MAX-ACCESS      read-write
        STATUS          current
        DESCRIPTION
            "Just for MIB entry deletion."
        DEFVAL { enable }
        ::= { mpsPublicHolidayEntry 7 }

---------------------------------------------------------------------------
mpsReRouteTable OBJECT-TYPE
    SYNTAX      SEQUENCE OF MpsReRouteEntry
    MAX-ACCESS  not-accessible
    STATUS      current
    DESCRIPTION
        "This table contains settings for the reroute functionality."
    ::= { mpsReRoute 1 }

    mpsReRouteEntry OBJECT-TYPE
        SYNTAX          MpsReRouteEntry 
        MAX-ACCESS      not-accessible
        STATUS          current
        DESCRIPTION
            ""
        INDEX { mpsReRouteIndex }
        ::= { mpsReRouteTable 1 }

    MpsReRouteEntry ::=
        SEQUENCE {
            mpsReRouteIndex                          ReRouteIndex,
            mpsReRouteDescr                          DisplayString,
            mpsReRouteType                           INTEGER,
            mpsReRouteBusyQueueSize                  INTEGER,
            mpsReRouteBusyMoh                        INTEGER,
	    mpsReRouteBusyMohFileDirectory	     DisplayString,
	    mpsReRouteBusyMohDefaultVariant	     INTEGER,
            mpsReRouteBusyQueueTime                  INTEGER,
            mpsReRouteNoReplyTime                    INTEGER,
            mpsReRouteAnnouncement                   INTEGER,
	    mpsReRouteAnnFileDirectory		     DisplayString,
            mpsReRouteTargetType                     INTEGER,
            mpsReRouteTargetIndex                    Unsigned32,
            mpsReRouteTransferCond                   INTEGER,
	    mpsReRouteTransferCondFileDirectory	     DisplayString,
	    mpsReRouteTransferCondDefaultVariant     INTEGER,
            mpsReRouteAdminStatus                    INTEGER,
            mpsReRoutePlayBackCnt                    Counter32,
            mpsReRouteAutoExchange                   INTEGER

        }

    mpsReRouteIndex OBJECT-TYPE
        SYNTAX          ReRouteIndex
        MAX-ACCESS      read-write
        STATUS          current
        DESCRIPTION
            "A unique value for each reroute function."
        ::= { mpsReRouteEntry 1}

    mpsReRouteDescr OBJECT-TYPE
        SYNTAX          DisplayString (SIZE(0..32))
        MAX-ACCESS      read-write
        STATUS          current
        DESCRIPTION
            "This variable contains the name of the rerouting function."
        ::= { mpsReRouteEntry 2 }

    mpsReRouteType OBJECT-TYPE
        SYNTAX          INTEGER {
                            immediatly(1),
                            onBusy(2),
                            onNoReply(3),
                            onBusyAndOnNoReply(4)
                        }
        MAX-ACCESS      read-write
        STATUS          current
        DESCRIPTION
            "This variable contains type of the rerouting function."
        DEFVAL { immediatly }
        ::= { mpsReRouteEntry 3 }

    mpsReRouteBusyQueueSize OBJECT-TYPE
        SYNTAX          INTEGER (0..10)
        MAX-ACCESS      read-write
        STATUS          current
        DESCRIPTION
            "This variable contains the max. number of calls in the queue
             if mpsReRouteType = onBusy."
        ::= { mpsReRouteEntry 4 }

    mpsReRouteBusyMoh OBJECT-TYPE
        SYNTAX          INTEGER {
                            -- file1(1),
                            -- file2(2),
                            -- file3(3),
                            -- file4(4),
                            -- file5(5),
                            -- file6(6),
                            -- file7(7),
                            -- file8(8),
                            -- default1(51),
                            -- default2(52),
			    file(54),
			    default(55),
                            external(80),
                            off(100)
                        }
        MAX-ACCESS      read-write
        STATUS          current
        DESCRIPTION
            "Incoming call can be acctepted with MoH (!= off). 
             This variable contains the selected music on hold (MoH).
	     Possible values are:
		file:	  variable mpsReRouteBusyMohFileDirectory specifies
			  directory to contain sound file
		default:  variable mpsReRouteBusyMohDefaultVariant specifies the
			  variant whose default is to be used (default)
		external: external source is used
		off:	  no music on hold active"
        DEFVAL { default }
        ::= { mpsReRouteEntry 5 }

    mpsReRouteBusyQueueTime OBJECT-TYPE
        SYNTAX          INTEGER (0..600)
        UNITS           "s"
        MAX-ACCESS      read-write
        STATUS          current
        DESCRIPTION
            "This variable contains the max. time that a call will remain in the
             busy queue, before droped.
             '0' = 'endless'"
        ::= { mpsReRouteEntry 6 }

    mpsReRouteNoReplyTime OBJECT-TYPE
        SYNTAX          INTEGER (1..120)
        UNITS           "s"
        MAX-ACCESS      read-write
        STATUS          current
        DESCRIPTION
            "The reroute type = onNoReply allow you to configure a time interval
             in seconds, after the incoming call was connected to the
             announcement."
        DEFVAL { 30 }
        ::= { mpsReRouteEntry 7 }

    mpsReRouteAnnouncement OBJECT-TYPE
        SYNTAX          INTEGER {
                            -- file1(1),
                            -- file2(2),
                            -- file3(3),
                            -- file4(4),
                            -- file5(5),
                            -- file6(6),
                            -- file7(7),
                            -- file8(8),
			    file(54),
                            off(100)
                         }
        MAX-ACCESS      read-write
        STATUS          current
        DESCRIPTION
            "An incoming call to the rerouting function gets connected to this
             announcement, unless it's off.
	     Possible values are:
		file:	  variable mpsReRouteAnnFileDirectory specifies
			  directory to contain sound file
		off:	  no announcement active"
        DEFVAL { off }
        ::= { mpsReRouteEntry 8 }

    mpsReRouteTargetType OBJECT-TYPE
        SYNTAX          INTEGER { group(1), extension(2), off(3) }
        MAX-ACCESS      read-write
        STATUS          current
        DESCRIPTION
            "This variable contains the target type of the rerouting function,
             after the announcement finished. 'off' means the call doesn't get
             dropped to an target but disconnected."
        DEFVAL { off }
        ::= { mpsReRouteEntry 9 }

    mpsReRouteTargetIndex OBJECT-TYPE
        SYNTAX          Unsigned32
        MAX-ACCESS      read-write
        STATUS          current
        DESCRIPTION
            "This variable contains index of the target table or zero, 
             mpsTrunkNumberTarget=group       : index = mpsGroupIndex.
             mpsTrunkNumberTarget=extension   : index = ExtensionIndex."
        ::= { mpsReRouteEntry 10 }

    mpsReRouteTransferCond OBJECT-TYPE
        SYNTAX          INTEGER {
                            -- file1(1),
                            -- file2(2),
                            -- file3(3),
                            -- file4(4),
                            -- file5(5),
                            -- file6(6),
                            -- file7(7),
                            -- file8(8),
                            -- default1(51),
                            -- default2(52),
                            ringtone(53),
			    file(54),
			    default(55),
                            external(80)
                        }
        MAX-ACCESS      read-write
        STATUS          current
        DESCRIPTION
            "This variable contains the file/tone the calling party hears while 
             new target gets called.
	     Possible values are:
		ringtone: use same tone as for ringing indication (default)
		file:	  variable mpsReRouteTransferCondFileDirectory specifies
			  directory to contain sound file
		default:  variable mpsReRouteTransferCondDefaultVariant
			  specifies the variant whose default is to be used
		external: external source is used"
        DEFVAL { ringtone }
        ::= { mpsReRouteEntry 11 }

    mpsReRouteAdminStatus OBJECT-TYPE
        SYNTAX          INTEGER { enable(1), delete(2) }
        MAX-ACCESS      read-write
        STATUS          current
        DESCRIPTION
            "Just for MIB entry deletion."
        DEFVAL { enable }
        ::= { mpsReRouteEntry 12 }

    mpsReRoutePlayBackCnt OBJECT-TYPE
        SYNTAX          Counter32
        MAX-ACCESS      read-write
        STATUS          current
        DESCRIPTION
            "This variable contains the playback count.
             '0' = 'endless'."
        ::= { mpsReRouteEntry 13 }

    mpsReRouteAutoExchange OBJECT-TYPE
        SYNTAX          INTEGER { auto(1), autoWithoutDisa(2), autoWithDisa(3) }
        MAX-ACCESS      read-write
        STATUS          current
        DESCRIPTION
            "This variable contains the call switching function
             auto(1)            : automatic without direct dial-in.
             autoWithoutDisa(2) : automatic with direct dial-in.
             autoWithDisa(3)    : automatic with direct dial-in + DISA.
                                  The DISA settings in mpsAnnDisaTable.."
        DEFVAL { auto }
        ::= { mpsReRouteEntry 14 }

    mpsReRouteBusyMohFileDirectory OBJECT-TYPE
        SYNTAX          DisplayString
        MAX-ACCESS      read-write
        STATUS          current
        DESCRIPTION
            "Name of directory (on flash medium) which contains file to be used
	     for music on hold.
             This variable references the entry in mpsWaveFile table where
	     variable mpsWaveFileDirectory has identical content.
	     If there should be multiple entrys with the same content for some
	     reason an arbitrary entry is chosen.
	     This entry is only valid if variable mpsReRouteBusyMoh is set
	     to value file.

	     Default value is the empty string."
        DEFVAL { "" }
        ::= { mpsReRouteEntry 15 }

    mpsReRouteBusyMohDefaultVariant OBJECT-TYPE
        SYNTAX          INTEGER (1..2)
        MAX-ACCESS      read-write
        STATUS          current
        DESCRIPTION
            "This variable specifies the chosen default variant if variable
	     mpsReRouteBusyMoh is set to value default.

	     Default value for that variable is 1."
        DEFVAL { 1 }
        ::= { mpsReRouteEntry 16 }

    mpsReRouteAnnFileDirectory OBJECT-TYPE
        SYNTAX          DisplayString
        MAX-ACCESS      read-write
        STATUS          current
        DESCRIPTION
            "Name of directory (on flash medium) which contains file to be used
	     for music on hold.
             This variable references the entry in mpsWaveFile table where
	     variable mpsWaveFileDirectory has identical content.
	     If there should be multiple entrys with the same content for some
	     reason an arbitrary entry is chosen.
	     This entry is only valid if variable mpsReRouteAnnouncement is set
	     to value file.

	     Default value is the empty string."
        DEFVAL { "" }
        ::= { mpsReRouteEntry 17 }

    mpsReRouteTransferCondFileDirectory OBJECT-TYPE
        SYNTAX          DisplayString
        MAX-ACCESS      read-write
        STATUS          current
        DESCRIPTION
            "Name of directory (on flash medium) which contains file to be used
	     for music on hold.
             This variable references the entry in mpsWaveFile table where
	     variable mpsWaveFileDirectory has identical content.
	     If there should be multiple entrys with the same content for some
	     reason an arbitrary entry is chosen.
	     This entry is only valid if variable mpsReRouteTransferCond is set
	     to value file.

	     Default value is the empty string."
        DEFVAL { "" }
        ::= { mpsReRouteEntry 18 }

    mpsReRouteTransferCondDefaultVariant OBJECT-TYPE
        SYNTAX          INTEGER (1..2)
        MAX-ACCESS      read-write
        STATUS          current
        DESCRIPTION
            "This variable specifies the chosen default variant if variable
	     mpsReRouteTransferCond is set to value default.

	     Default value for that variable is 1."
        DEFVAL { 1 }
        ::= { mpsReRouteEntry 19 }

---------------------------------------------------------------------------
mpsAnnDisaTable OBJECT-TYPE
    SYNTAX      SEQUENCE OF MpsAnnDisaEntry
    MAX-ACCESS  not-accessible
    STATUS      current
    DESCRIPTION
        "This table contains settings for the DISA (Direct Inward System Access)
         for an announcement file."
    ::= { mpsReRoute 3 }

    mpsAnnDisaEntry OBJECT-TYPE
        SYNTAX          MpsAnnDisaEntry 
        MAX-ACCESS      not-accessible
        STATUS          current
        DESCRIPTION
            ""
        INDEX { mpsAnnDisaIndex }
        ::= { mpsAnnDisaTable 1 }

    MpsAnnDisaEntry ::=
        SEQUENCE {
            mpsAnnDisaIndex                          Unsigned32,
            mpsAnnDisaReRouteIndex                   ReRouteIndex,
            mpsAnnDisaNumber                         INTEGER,
            mpsAnnDisaTargetType                     INTEGER,
            mpsAnnDisaTargetIndex                    INTEGER,
            mpsAnnDisaAdminStatus                    INTEGER
        }

    mpsAnnDisaIndex OBJECT-TYPE
        SYNTAX          Unsigned32
        MAX-ACCESS      read-write
        STATUS          current
        DESCRIPTION
            "A unique value for each announcement DISA."
        ::= { mpsAnnDisaEntry 1}

    mpsAnnDisaReRouteIndex OBJECT-TYPE
        SYNTAX          ReRouteIndex
        MAX-ACCESS      read-write
        STATUS          current
        DESCRIPTION
            "This variable contains the reroute index.
             Reference to mpsreRouteIndex."
        ::= { mpsAnnDisaEntry 2}

    mpsAnnDisaNumber OBJECT-TYPE
        SYNTAX          INTEGER (0..9)
        MAX-ACCESS      read-write
        STATUS          current
        DESCRIPTION
            "This variable contains number of the DISA for the reroute index."
        ::= { mpsAnnDisaEntry 3}

    mpsAnnDisaTargetType OBJECT-TYPE
        SYNTAX          INTEGER { group(1), extension(2) }
        MAX-ACCESS      read-write
        STATUS          current
        DESCRIPTION
            "This variable contains the default target type for this DISA, 
             default is group."
        DEFVAL { group }
        ::= { mpsAnnDisaEntry 4 }

    mpsAnnDisaTargetIndex OBJECT-TYPE
        SYNTAX          INTEGER
        MAX-ACCESS      read-write
        STATUS          current
        DESCRIPTION
            "This variable contains index of the target table or zero, 
             mpsTrunkNumberTarget=group       : index = mpsGroupIndex.
             mpsTrunkNumberTarget=extension   : index = ExtensionIndex."
        ::= { mpsAnnDisaEntry 5 }

    mpsAnnDisaAdminStatus OBJECT-TYPE
        SYNTAX          INTEGER { enable(1), delete(2) }
        MAX-ACCESS      read-write
        STATUS          current
        DESCRIPTION
            "Just for MIB entry deletion."
        DEFVAL { enable }
        ::= { mpsAnnDisaEntry 6 }

---------------------------------------------------------------------------
mpsWaveFileTable OBJECT-TYPE
    SYNTAX      SEQUENCE OF MpsWaveFileEntry
    MAX-ACCESS  not-accessible
    STATUS      current
    DESCRIPTION
        "This table contains settings for each wave file stored on an external
         memory device (e.g. SD-Card)"
    ::= { mpsReRoute 4 }

    mpsWaveFileEntry OBJECT-TYPE
        SYNTAX          MpsWaveFileEntry
        MAX-ACCESS      not-accessible
        STATUS          current
        DESCRIPTION
            "This entry only is created by the respective device driver"
        INDEX { mpsWaveFileIndex }
        ::= { mpsWaveFileTable 1 }

    MpsWaveFileEntry ::=
        SEQUENCE {
            mpsWaveFileIndex                          INTEGER,
            mpsWaveFileDescription                    DisplayString,
            mpsWaveFileDirectory                      DisplayString,
            mpsWaveFileName                           DisplayString,
            mpsWaveFileAcousticProperties             DisplayString,
            mpsWaveFileSize                           INTEGER,
            mpsWaveFileDuration                       INTEGER,
            mpsWaveFileVolume                         INTEGER,
            mpsWaveFileStatus                         INTEGER,
            mpsWaveFileUploadResult                   INTEGER
        }

    mpsWaveFileIndex OBJECT-TYPE
        SYNTAX          INTEGER (1..255)
        MAX-ACCESS      read-only
        STATUS          current
        DESCRIPTION
            "A unique index for each wave file table entry."
        ::= { mpsWaveFileEntry 1}

    mpsWaveFileDescription OBJECT-TYPE
        SYNTAX          DisplayString (SIZE(0..32))
        MAX-ACCESS      read-write
        STATUS          current
        DESCRIPTION
            "The description can be used to assign an alias name to the wave
	     file."
        ::= { mpsWaveFileEntry 2}

    mpsWaveFileDirectory OBJECT-TYPE
        SYNTAX          DisplayString
        MAX-ACCESS      read-write
        STATUS          current
        DESCRIPTION
            "Specifies the complete path/tree where the wave file can be found
	     on the mounted device."
        ::= { mpsWaveFileEntry 3}

    mpsWaveFileName OBJECT-TYPE
        SYNTAX          DisplayString
        MAX-ACCESS      read-write
        STATUS          current
        DESCRIPTION
            "Simply contains the wave file name on the mounted device."
        ::= { mpsWaveFileEntry 4 }

    mpsWaveFileAcousticProperties OBJECT-TYPE
        SYNTAX          DisplayString
        MAX-ACCESS      read-only
        STATUS          current
        DESCRIPTION
            "Optionally contains acoustic properties of the wave file: e.g.
	     audioformat, bit-rate, sample-rate etc. "
        ::= { mpsWaveFileEntry 5 }

    mpsWaveFileSize OBJECT-TYPE
        SYNTAX          INTEGER
        MAX-ACCESS      read-write
        STATUS          current
        DESCRIPTION
            "This variable contains the wave file size in kbytes."
        DEFVAL { 0 }
        ::= { mpsWaveFileEntry 6 }

    mpsWaveFileDuration OBJECT-TYPE
        SYNTAX          INTEGER
        UNITS           "s"
        MAX-ACCESS      read-only
        STATUS          current
        DESCRIPTION
            "This variable contains the wave file (music) duration in seconds."
        DEFVAL { 0 }
        ::= { mpsWaveFileEntry 7 }

    mpsWaveFileVolume OBJECT-TYPE
        SYNTAX          INTEGER (-5..3)
        MAX-ACCESS      read-write
        STATUS          current
        DESCRIPTION
            "This variable contains the volume adjustment level for the wave
	     file to be played back with (approximately in 3 dB steps):
                 negative values -> attenuate during playback
                 0               -> playback as recorded (default)
                 positive values -> amplify during playback"
        DEFVAL { 0 }
        ::= { mpsWaveFileEntry 8 }

    mpsWaveFileStatus OBJECT-TYPE
        SYNTAX          INTEGER { create(1), remove(2), done(3) }
        MAX-ACCESS      read-write
        STATUS          current
        DESCRIPTION
            "Wave file status: 
             create(1) -> new wave file shall be stored on the device
             remove(2) -> wave file shall be deleted on the storage device
             done(3)   -> synchronization of storage device with MIB is done."
        DEFVAL { done }
        ::= { mpsWaveFileEntry 9 }

    mpsWaveFileUploadResult OBJECT-TYPE
        SYNTAX          INTEGER { success(1),
                                  no-mem-card(2),
                                  no-mem-space(3),
                                  incomp-wav-format(4),
                                  transfer-error(5),
                                  write-protection(6)
                        }
        MAX-ACCESS      read-write
        STATUS          current
        DESCRIPTION
            "Wave file upload result (error) code: 
             success(1)           -> the wave file upload was successful,
             no-mem-card(2)       -> no memory card plugged,
             no-mem-space(3)      -> no more space available on the memory card,
             incomp-wav-format(4) -> the wave file format doesn't match the
                                     requirements,
             transfer-error(5)    -> any transfer error occured during upload."
        DEFVAL { success }
        ::= { mpsWaveFileEntry 10 }

---------------------------------------------------------------------------
mpsReRouteApplTable OBJECT-TYPE
    SYNTAX      SEQUENCE OF MpsReRouteApplEntry
    MAX-ACCESS  not-accessible
    STATUS      current
    DESCRIPTION
        "This table contains settings for the reroute application."
    ::= { mpsReRoute 5 }

    mpsReRouteApplEntry OBJECT-TYPE
        SYNTAX          MpsReRouteApplEntry 
        MAX-ACCESS      not-accessible
        STATUS          current
        DESCRIPTION
            ""
        INDEX { mpsReRouteApplIndex }
        ::= { mpsReRouteApplTable 1 }

    MpsReRouteApplEntry ::=
        SEQUENCE {
            mpsReRouteApplIndex                      ReRouteApplIndex,
            mpsReRouteApplDescr                      DisplayString,
            mpsReRouteApplType                       INTEGER,
            mpsReRouteApplCalendar                   CalendarIndexOrZero,
            mpsReRouteApplAdminStatus                INTEGER
        }

    mpsReRouteApplIndex OBJECT-TYPE
        SYNTAX          ReRouteApplIndex
        MAX-ACCESS      read-write
        STATUS          current
        DESCRIPTION
            "A unique value for each reroute application."
        ::= { mpsReRouteApplEntry 1}

    mpsReRouteApplDescr OBJECT-TYPE
        SYNTAX          DisplayString (SIZE(0..32))
        MAX-ACCESS      read-write
        STATUS          current
        DESCRIPTION
            "This variable contains the name of the rerouting application."
        ::= { mpsReRouteApplEntry 2 }

    mpsReRouteApplType OBJECT-TYPE
        SYNTAX          INTEGER {
                            trunkNumber(1),
                            extension(2),
                            global(3)
                        }
        MAX-ACCESS      read-write
        STATUS          current
        DESCRIPTION
            "This variable contains type of the rerouting application.
             trunkNumber: used for external trunk numbers with call distribution
                         'reroute'.
             extension  : used for internal extension numbers and individual
                          rerouting.
             global     : used for internal extension numbers and global
                          rerouting. 
                          To use this, the flag 'use-global-rerouting' in
                          mpsCoSFacilities(mpsClassOfServiceTable) must be
                          active."
        DEFVAL { trunkNumber }
        ::= { mpsReRouteApplEntry 3 }

    mpsReRouteApplCalendar OBJECT-TYPE
        SYNTAX          CalendarIndexOrZero
        MAX-ACCESS      read-write
        STATUS          current
        DESCRIPTION
            "Select a calendar index to switch the acitve mode this rerouting
	     application automatically."
        DEFVAL { 0 }
        ::= { mpsReRouteApplEntry 4 }

    mpsReRouteApplAdminStatus OBJECT-TYPE
        SYNTAX          INTEGER { enable(1), delete(2) }
        MAX-ACCESS      read-write
        STATUS          current
        DESCRIPTION
            "Just for MIB entry deletion."
        DEFVAL { enable }
        ::= { mpsReRouteApplEntry 5 }

---------------------------------------------------------------------------
mpsReRouteApplModeTable OBJECT-TYPE
    SYNTAX      SEQUENCE OF MpsReRouteApplModeEntry
    MAX-ACCESS  not-accessible
    STATUS      current
    DESCRIPTION
        "This table contains reroute information for each rerouting application
	 and mode."
    ::= { mpsReRoute 6 }

    mpsReRouteApplModeEntry OBJECT-TYPE
        SYNTAX          MpsReRouteApplModeEntry 
        MAX-ACCESS      not-accessible
        STATUS          current
        DESCRIPTION
            ""
        INDEX { mpsReRouteApplModeIndex }
        ::= { mpsReRouteApplModeTable 1 }

    MpsReRouteApplModeEntry ::=
        SEQUENCE {
            mpsReRouteApplModeIndex             Unsigned32,
            mpsReRouteApplModeApplIndex         ReRouteApplIndex,
            mpsReRouteApplModeModeNumber        Unsigned32,
            mpsReRouteApplModeRerouteIndex      ReRouteIndexOrZero,
            mpsReRouteApplModeAdminStatus       INTEGER
        }

    mpsReRouteApplModeIndex OBJECT-TYPE
        SYNTAX          Unsigned32
        MAX-ACCESS      read-write
        STATUS          current
        DESCRIPTION
            "A unique value for each entry."
        ::= { mpsReRouteApplModeEntry 1 }

    mpsReRouteApplModeApplIndex OBJECT-TYPE
        SYNTAX          ReRouteApplIndex
        MAX-ACCESS      read-write
        STATUS          current
        DESCRIPTION
            "This variable contains the reroute application index.
	     Reference to mpsReReouteApplTable."
        ::= { mpsReRouteApplModeEntry 2 }

    mpsReRouteApplModeModeNumber OBJECT-TYPE
        SYNTAX          Unsigned32
        MAX-ACCESS      read-write
        STATUS          current
        DESCRIPTION
            "For each rerouting application index, several modes can exist."
        ::= { mpsReRouteApplModeEntry 3 }

    mpsReRouteApplModeRerouteIndex OBJECT-TYPE
        SYNTAX          ReRouteIndexOrZero
        MAX-ACCESS      read-write
        STATUS          current
        DESCRIPTION
            "Index of the ReRouting function in mpsReRouteTable.
             Value 0 means that ReRouting function is inactive."
        ::= { mpsReRouteApplModeEntry 4 }

    mpsReRouteApplModeAdminStatus OBJECT-TYPE
        SYNTAX          INTEGER { enable(1),
                                  delete(2) 
                                }
        MAX-ACCESS      read-write
        STATUS          current
        DESCRIPTION
            "Just for MIB entry deletion."
        DEFVAL { enable }
        ::= { mpsReRouteApplModeEntry 5 }

---------------------------------------------------------------------------
mpsTerminalTable OBJECT-TYPE
    SYNTAX      SEQUENCE OF MpsTerminalEntry
    MAX-ACCESS  not-accessible
    STATUS      current
    DESCRIPTION
        "This table contains information about terminal endpoints."
    ::= { mpsTerminal 1 }

    mpsTerminalEntry OBJECT-TYPE
        SYNTAX          MpsTerminalEntry 
        MAX-ACCESS      not-accessible
        STATUS          current
        DESCRIPTION
            ""
        INDEX { mpsTerminalIndex }
        ::= { mpsTerminalTable 1 }

    MpsTerminalEntry ::=
        SEQUENCE {
            mpsTerminalIndex                       TerminalIndex,
            mpsTerminalIfIndex                     InterfaceIndexOrZero,
            mpsTerminalPhoneType                   INTEGER,
            mpsTerminalType                        INTEGER,
            mpsTerminalDescr                       DisplayString,
            mpsTerminalAdminStatus                 INTEGER,
            mpsTerminalDoorIntercom                DoorIntercomIndexOrZero,
            mpsTerminalIPSystelPort                INTEGER,
            mpsTerminalInterfaceType               INTEGER,
            mpsTerminalOperStatus                  INTEGER,
            mpsTerminalMacAddress                  MacAddress,
            mpsTerminalOEMType                     OEMDeviceType
         }

    mpsTerminalIndex OBJECT-TYPE
        SYNTAX          TerminalIndex
        MAX-ACCESS      read-write
        STATUS          current
        DESCRIPTION
            "A unique value for each terminal."
        ::= { mpsTerminalEntry 1}

    mpsTerminalIfIndex OBJECT-TYPE
        SYNTAX          InterfaceIndexOrZero
        MAX-ACCESS      read-write
        STATUS          current
        DESCRIPTION
            "Reference to mpsDeviceTable.
             0 = no reference."
        ::= { mpsTerminalEntry 2 }

    mpsTerminalPhoneType OBJECT-TYPE
        SYNTAX          INTEGER {
                            standard(1),
                            systemphone(2),
                            vms(3),
                            oem-phone(4)
                        }
        MAX-ACCESS      read-write
        STATUS          current
        DESCRIPTION
            "Select the phone type of the terminal:
             standard (1)    : standard terminal
             systemphone (2) : the terminal is a system phone
             vms (3)         : internal Voice Mail Server
             oem-phone (4)   : the terminal is a OEM phone.
             "
        DEFVAL { standard }
        ::= { mpsTerminalEntry 3 }

   mpsTerminalType OBJECT-TYPE
        SYNTAX          INTEGER {
                            telephone(1),
                            answering-machine(2),
                            voice-mail(3),
                            emergency-phone(4)
                        }
        MAX-ACCESS      read-write
        STATUS          current
        DESCRIPTION
            "This varibale contains the terminal type:
             telephone(1)        : 'normal' phone
             answering-machine(2): answering machine
             voice-mail(3)       : external voice mail server
             ermergency-phone(4) : allow ermergency calls with high priority
             "
        DEFVAL { telephone }
        ::= { mpsTerminalEntry 4 }


    mpsTerminalDescr OBJECT-TYPE
        SYNTAX          DisplayString (SIZE(0..20))
        MAX-ACCESS      read-write
        STATUS          current
        DESCRIPTION
            "A textual description of the terminal endpoint."
        ::= { mpsTerminalEntry 5 }

    mpsTerminalAdminStatus OBJECT-TYPE
        SYNTAX          INTEGER { enable(1), delete(2), disable(3) }
        MAX-ACCESS      read-write
        STATUS          current
        DESCRIPTION
            "Admin status of the terminal.
             Set to 'delete' to delete the whole entry."
        DEFVAL { enable }
        ::= { mpsTerminalEntry 6 }

    mpsTerminalDoorIntercom OBJECT-TYPE
        SYNTAX          DoorIntercomIndexOrZero
        MAX-ACCESS      read-write
        STATUS          current
        DESCRIPTION
            "This variable contains the number of the door intercom, refer to 
             mpsDoorIntercomIndex in mpsDoorIntercomTable, only valid for 
             mpsTerminalPhoneType = standard and mpsTerminalType = telephone."
        DEFVAL { 0 }
        ::= { mpsTerminalEntry 7 }

    mpsTerminalIPSystelPort OBJECT-TYPE
        SYNTAX          INTEGER
        MAX-ACCESS      read-only
        STATUS          current
        DESCRIPTION
            "This variable contains the RTP port number for IP system phone."
        DEFVAL { -1 }
        ::= { mpsTerminalEntry 8 }
                                  

   mpsTerminalInterfaceType OBJECT-TYPE
        SYNTAX          INTEGER {
                            isdn(1),
                            voip(2),
                            pots(3)
                        }
        MAX-ACCESS      read-write
        STATUS          current
        DESCRIPTION
            "This variable contains the interface type, for which type of
             interface this terminal can be used."
        DEFVAL { isdn }
        ::= { mpsTerminalEntry 9 }

   mpsTerminalOperStatus OBJECT-TYPE
        SYNTAX  INTEGER { up(1), down(2), licMissing(3) }
        MAX-ACCESS  read-only
        STATUS  current
        DESCRIPTION
            "Operational status of the terminal."
        DEFVAL { down }
        ::= { mpsTerminalEntry 10 }

    mpsTerminalMacAddress OBJECT-TYPE
        SYNTAX          MacAddress
        MAX-ACCESS      read-write
        STATUS          current
        DESCRIPTION
            "This variable contains the MAC address of the IP terminal."
        ::= { mpsTerminalEntry 11 }

    mpsTerminalOEMType OBJECT-TYPE
        SYNTAX          OEMDeviceType
        MAX-ACCESS      read-write
        STATUS          current
        DESCRIPTION
            "OEM device type of the terminal e.g. Siemens OpenStage, Gigaset..."
        DEFVAL { none }
        ::= { mpsTerminalEntry 12 }

---------------------------------------------------------------------------
mpsExtensionTerminalTable OBJECT-TYPE
    SYNTAX      SEQUENCE OF MpsExtensionTerminalEntry
    MAX-ACCESS  not-accessible
    STATUS      current
    DESCRIPTION
        "This table contains the information, which extension is assigned to
         which terminal."
    ::= { mpsTerminal 2 }

    mpsExtensionTerminalEntry OBJECT-TYPE
        SYNTAX          MpsExtensionTerminalEntry 
        MAX-ACCESS      not-accessible
        STATUS          current
        DESCRIPTION
            ""
        INDEX { mpsExtTermIndex }
        ::= { mpsExtensionTerminalTable 1 }

    MpsExtensionTerminalEntry ::=
        SEQUENCE {
            mpsExtTermIndex                    INTEGER,
            mpsExtTermExt                      ExtensionIndex,
            mpsExtTermTerminal                 TerminalIndex,
            mpsExtTermPrio                     INTEGER,
            mpsExtTermAdminStatus              INTEGER
        }

    mpsExtTermIndex OBJECT-TYPE
        SYNTAX          TerminalIndex
        MAX-ACCESS      read-write
        STATUS          current
        DESCRIPTION
            "A unique value for each extension-terminal assignment."
        ::= { mpsExtensionTerminalEntry 1}

    mpsExtTermExt OBJECT-TYPE
        SYNTAX          ExtensionIndex
        MAX-ACCESS      read-write
        STATUS          current
        DESCRIPTION
            "Contains the index of the assigned extension."
        ::= { mpsExtensionTerminalEntry 2 }

    mpsExtTermTerminal OBJECT-TYPE
        SYNTAX          TerminalIndex
        MAX-ACCESS      read-write
        STATUS          current
        DESCRIPTION
            "Contains the index of the terminal for this extension."
        ::= { mpsExtensionTerminalEntry 3 }

    mpsExtTermPrio OBJECT-TYPE
        SYNTAX          INTEGER (1..100)
        MAX-ACCESS      read-write
        STATUS          current
        DESCRIPTION
            "Contains the priority of this extension for this terminal."
        ::= { mpsExtensionTerminalEntry 4 }

    mpsExtTermAdminStatus OBJECT-TYPE
        SYNTAX          INTEGER { enable(1), delete(2) }
        MAX-ACCESS      read-write
        STATUS          current
        DESCRIPTION
            "Just for MIB entry deletion."
        DEFVAL { enable }
        ::= { mpsExtensionTerminalEntry 5 }

---------------------------------------------------------------------------
mpsTerminalStatusTable OBJECT-TYPE
    SYNTAX      SEQUENCE OF MpsTerminalStatusEntry
    MAX-ACCESS  not-accessible
    STATUS      current
    DESCRIPTION
        "This table contains the status information about IP terminal 
         registered via Provisioning-Server."
    ::= { mpsTerminal 3 }

    mpsTerminalStatusEntry OBJECT-TYPE
        SYNTAX          MpsTerminalStatusEntry 
        MAX-ACCESS      not-accessible
        STATUS          current
        DESCRIPTION
            ""
        INDEX { mpsTerminalStatusMacAddress }
        ::= { mpsTerminalStatusTable 1 }

    MpsTerminalStatusEntry ::=
        SEQUENCE {
            mpsTerminalStatusMacAddress        MacAddress,
            mpsTerminalStatusDeviceType        DisplayString,
            mpsTerminalStatusContactURI        DisplayString,
            mpsTerminalStatusLastSeen          Date,
            mpsTerminalStatusSerialNr          DisplayString,
            mpsTerminalStatusSoftwareVersion   DisplayString,
            mpsTerminalStatusConfigDate        Date,
            mpsTerminalStatusOEMType           OEMDeviceType
        }

    mpsTerminalStatusMacAddress OBJECT-TYPE
        SYNTAX          MacAddress
        MAX-ACCESS      read-only
        STATUS          current
        DESCRIPTION
            "This variable contains the MAC address of the IP terminal."
        ::= { mpsTerminalStatusEntry 1 }

    mpsTerminalStatusDeviceType OBJECT-TYPE
        SYNTAX          DisplayString (SIZE(0..255))
        MAX-ACCESS      read-only
        STATUS          current
        DESCRIPTION
            "This variable contains device type of the terminal."
        ::= { mpsTerminalStatusEntry 2 }

    mpsTerminalStatusContactURI OBJECT-TYPE
        SYNTAX          DisplayString (SIZE(0..255))
        MAX-ACCESS      read-only
        STATUS          current
        DESCRIPTION
            "This variable contains contact URI of the terminal:
             e.g. 'http://192.168.0.105:8085/contact_dls.html/ContactDLS'"
        ::= { mpsTerminalStatusEntry 3 }

    mpsTerminalStatusLastSeen OBJECT-TYPE
        SYNTAX          Date
        MAX-ACCESS      read-only
        STATUS          current
        DESCRIPTION
            "The date of last register at the provisioning server."
        ::= { mpsTerminalStatusEntry 4 }

    mpsTerminalStatusSerialNr OBJECT-TYPE
        SYNTAX          DisplayString (SIZE(0..255))
        MAX-ACCESS      read-only
        STATUS          current
        DESCRIPTION
            "This variable contains serial number of the terminal."
        ::= { mpsTerminalStatusEntry 5 }

    mpsTerminalStatusSoftwareVersion OBJECT-TYPE
        SYNTAX          DisplayString(SIZE(0..20))
        MAX-ACCESS      read-only
        STATUS          current
        DESCRIPTION
           "Software version of the IP terminal."
        DEFVAL { "" }
        ::= { mpsTerminalStatusEntry 6 }

    mpsTerminalStatusConfigDate OBJECT-TYPE
        SYNTAX          Date
        MAX-ACCESS      read-only
        STATUS          current
        DESCRIPTION
            "The date of last configuration change via the provisioning server."
        ::= { mpsTerminalStatusEntry 7 }

    mpsTerminalStatusOEMType OBJECT-TYPE
        SYNTAX          OEMDeviceType
        MAX-ACCESS      read-only
        STATUS          current
        DESCRIPTION
            "OEM device type of the terminal e.g. Siemens OpenStage, Gigaset..."
        DEFVAL { none }
        ::= { mpsTerminalStatusEntry 8 }

---------------------------------------------------------------------------
mpsTerminalCmdTable OBJECT-TYPE
    SYNTAX      SEQUENCE OF MpsTerminalCmdEntry
    MAX-ACCESS  not-accessible
    STATUS      current
    DESCRIPTION
        "The mpsTerminalCmdTable is used to trigger OpenStage provisioning
         actions at OpenStage phones.

          Creating entries: Entries are added to this table by assigning a value
          of the mpsTerminalCmd and mpsTerminalCmdMacAddress.

          Deleting Entries: Entries are removed by the ost application 
          after the requested command has been performed and a new command for
          the same Teminal (same mpsTerminalCmdMacAddress) is present."
    ::= { mpsTerminal 4 }

    mpsTerminalCmdEntry OBJECT-TYPE
        SYNTAX          MpsTerminalCmdEntry 
        MAX-ACCESS      not-accessible
        STATUS          current
        DESCRIPTION
            ""
        INDEX { mpsTerminalCmdMacAddress, mpsTerminalCmdCmd }
        ::= { mpsTerminalCmdTable 1 }

    MpsTerminalCmdEntry ::=
        SEQUENCE {
            mpsTerminalCmdMacAddress     MacAddress,
            mpsTerminalCmdCmd            INTEGER,
            mpsTerminalCmdState          INTEGER
        }

    mpsTerminalCmdMacAddress OBJECT-TYPE
        SYNTAX          MacAddress
        MAX-ACCESS      read-write
        STATUS          current
        DESCRIPTION
            "The MAC Address of the OpenStage Phone.
             Reference to mpsTerminalStatusTable MacAddress."
        ::= { mpsTerminalCmdEntry 1 }


   mpsTerminalCmdCmd OBJECT-TYPE
        SYNTAX          INTEGER { none(1), fw-update(2), reset-passwd(3), reset-upasswd(4) }
        MAX-ACCESS      read-write
        STATUS          current
        DESCRIPTION
            "Command for configuration handling. Possible values are :
             none(1)           -> default value
             fw-update(2)      -> new firmware file shall be stored on the device
             reset-passwd(3)   -> set admin password to default on the device.
             reset-upasswd(4)  -> set user password to default on the device."
        DEFVAL { none }
        ::= { mpsTerminalCmdEntry 2 }

   mpsTerminalCmdState OBJECT-TYPE
        SYNTAX  INTEGER  { todo(1), running(2), done(3), error(4) }
        MAX-ACCESS      read-only
        STATUS          current
        DESCRIPTION
                "The state of this command (i.e., mpsTerminalStatusCmd).

                 todo(1)     : the command will start soon
                 running(2)  : the command is currently executing
                 done(3)     : the command has successfully completed
                 error(4)    : the command has failed
                "
        DEFVAL { todo }
        ::= { mpsTerminalCmdEntry 3 }

---------------------------------------------------------------------------
mpsHotelConfig OBJECT IDENTIFIER ::= { mpsHotel 1 }

    mpsHotelConfigActive OBJECT-TYPE
        SYNTAX          TruthValue
        MAX-ACCESS      read-write
        STATUS          current
        DESCRIPTION
            "This value determines, if system hotel functions are active or not."
        DEFVAL { false }
        ::= { mpsHotelConfig 1 }

    mpsHotelConfigReception1 OBJECT-TYPE
        SYNTAX          ExtensionIndexOrZero
        MAX-ACCESS      read-write
        STATUS          current
        DESCRIPTION
            "This variable contains the first reception phone. Reference to 
             mpsExtensionTable."
        DEFVAL { 0 }
        ::= { mpsHotelConfig 2 }

    mpsHotelConfigReception2 OBJECT-TYPE
        SYNTAX          ExtensionIndexOrZero
        MAX-ACCESS      read-write
        STATUS          current
        DESCRIPTION
            "This variable contains the second reception phone. Reference to 
             mpsExtensionTable."
        DEFVAL { 0 }
        ::= { mpsHotelConfig 3 }

    mpsHotelConfigWakeUpChoice OBJECT-TYPE
        SYNTAX          BITS {
                            reception1(0),
                            reception2(1)
                        }
        MAX-ACCESS read-write
        STATUS current
        DESCRIPTION
            "If the bit is set, the wakeUp announcement at check-in is selectable
             via menue access."
        ::= { mpsHotelConfig 4 }

    mpsHotelConfigChargeMultiplier OBJECT-TYPE
        SYNTAX          INTEGER
        MAX-ACCESS      read-write
        STATUS          current
        DESCRIPTION
            "Charge rate multiplier. 
             e.g. 1 Unit = 0,064 -> mpsHotelConfigChargeMultiplier = 64,
                                    mpsHotelConfigChargeExponent = -3.
                  1 Unit = 1,200 -> mpsHotelConfigChargeMultiplier = 12,
                                    mpsHotelConfigChargeExponent = -1"
        DEFVAL { 1 }
        ::= { mpsHotelConfig 5 }

    mpsHotelConfigChargeExponent OBJECT-TYPE
        SYNTAX          INTEGER
        MAX-ACCESS      read-write
        STATUS          current
        DESCRIPTION
            "Charge rate exponent. 
             e.g. 1 Unit = 0,064 -> mpsHotelConfigChargeMultiplier = 64,
                                    mpsHotelConfigChargeExponent = -3.
                  1 Unit = 1,200 -> mpsHotelConfigChargeMultiplier = 12,
                                    mpsHotelConfigChargeExponent = -1"
        DEFVAL { 0 }
        ::= { mpsHotelConfig 6 }

    mpsHotelConfigPrintHeader OBJECT-TYPE
        SYNTAX          DisplayString (SIZE(0..255))
        MAX-ACCESS      read-write
        STATUS          current
        DESCRIPTION
            "Definition of header for charging bill printout (at reception) at
             checkout."
        ::= { mpsHotelConfig 7 }

    mpsHotelConfigPrintFooter OBJECT-TYPE
        SYNTAX          DisplayString (SIZE(0..255))
        MAX-ACCESS      read-write
        STATUS          current
        DESCRIPTION
            "Definition of footer for charging bill printout (at reception) at
             checkout."
        ::= { mpsHotelConfig 8 }

    mpsHotelConfigFacilities OBJECT-TYPE
        SYNTAX          BITS { room-to-room-call-barring(0) }
        MAX-ACCESS      read-write
        STATUS          current
        DESCRIPTION
            "Hotel global facilities:
             room-to-room-call-barring : room to room calls are not allowed."
        ::= { mpsHotelConfig 9 }

---------------------------------------------------------------------------
mpsHotelWakeUp OBJECT IDENTIFIER ::= { mpsHotel 2 }

    mpsHotelWakeUpDuration OBJECT-TYPE
        SYNTAX          INTEGER (1..99)
        UNITS           "s"
        MAX-ACCESS      read-write
        STATUS          current
        DESCRIPTION
            "This variable contains the duration of the wakeUp announcement in
             seconds."
        DEFVAL { 30 }
        ::= { mpsHotelWakeUp 1 }

    mpsHotelWakeUpPlaybackNumber OBJECT-TYPE
        SYNTAX          INTEGER (1..5)
        MAX-ACCESS      read-write
        STATUS          current
        DESCRIPTION
            "This variable contains number of play-back loops."
        DEFVAL { 1 }
        ::= { mpsHotelWakeUp 2 }

    mpsHotelWakeUpRepeatTime OBJECT-TYPE
        SYNTAX          INTEGER (0..5)
        UNITS           "s"
        MAX-ACCESS      read-write
        STATUS          current
        DESCRIPTION
            "This variable contains the time delay in minutes before repeating
             the wakeUp call if not connected."
        DEFVAL { 3 }
        ::= { mpsHotelWakeUp 3 }

   mpsHotelWakeUpAnnDefault OBJECT-TYPE
         SYNTAX          INTEGER {
                            -- file1(1),
                            -- file2(2),
                            -- file3(3),
                            -- file4(4),
                            -- file5(5),
                            -- file6(6),
                            -- file7(7),
                            -- file8(8),
                            -- default1(51),
                            -- default2(52),
			    file(54),
			    default(55)
                        }
        MAX-ACCESS      read-write
        STATUS          current
        DESCRIPTION
            "This variable contains the selected music on hold (MoH) that the
             wakeUp party hears, if no special wakeUp announcement is selected
             for the wakeUp party (default).
	     Possible values are:
		file:	  variable mpsHotelWakeUpAnnDefaultFileDirectory
			  specifies directory to contain sound file
		default:  variable mpsHotelWakeUpAnnDefaultDefaultVariant
			  specifies the variant whose default is to be used
			  (default)"
        DEFVAL { default }
        ::= { mpsHotelWakeUp 4 }

    mpsHotelWakeUpNumberOfRepetition OBJECT-TYPE
        SYNTAX          INTEGER (0..5)
        MAX-ACCESS      read-write
        STATUS          current
        DESCRIPTION
            "This variable contains number of wake-up-call repetitions."
        DEFVAL { 0 }
        ::= { mpsHotelWakeUp 5 }

    mpsHotelWakeUpAnnDefaultFileDirectory OBJECT-TYPE
        SYNTAX          DisplayString
        MAX-ACCESS      read-write
        STATUS          current
        DESCRIPTION
            "Name of directory (on flash medium) which contains file to be used
	     for music on hold.
             This variable references the entry in mpsWaveFile table where
	     variable mpsWaveFileDirectory has identical content.
	     If there should be multiple entrys with the same content for some
	     reason an arbitrary entry is chosen.
	     This entry is only valid if variable mpsHotelWakeUpAnnDefault is set
	     to value file.

	     Default value is the empty string."
        DEFVAL { "" }
        ::= { mpsHotelWakeUp 6 }

    mpsHotelWakeUpAnnDefaultDefaultVariant OBJECT-TYPE
        SYNTAX          INTEGER (1..2)
        MAX-ACCESS      read-write
        STATUS          current
        DESCRIPTION
            "This variable specifies the chosen default variant if variable
	     mpsHotelWakeUpAnnDefault is set to value default.

	     Default value for that variable is 1."
        DEFVAL { 1 }
        ::= { mpsHotelWakeUp 7 }

---------------------------------------------------------------------------
mpsHotelTable OBJECT-TYPE
    SYNTAX      SEQUENCE OF MpsHotelEntry
    MAX-ACCESS  not-accessible
    STATUS      current
    DESCRIPTION
        "This table contains information about the status of the room telephones
         for hotel function: check-in, check-out, wakeUp settings, room status."
    ::= { mpsHotel 3 }

    mpsHotelEntry OBJECT-TYPE
        SYNTAX          MpsHotelEntry 
        MAX-ACCESS      not-accessible
        STATUS          current
        DESCRIPTION
            ""
        INDEX { mpsHotelIndex }
        ::= { mpsHotelTable 1 }

    MpsHotelEntry ::=
        SEQUENCE {
            mpsHotelIndex                    Unsigned32,
            mpsHotelDescription              DisplayString,
            mpsHotelExtension                ExtensionIndexOrZero,
            mpsHotelAdditionalInfo           DisplayString,
            mpsHotelCheckInTime              Date,
            mpsHotelCheckOutStatus           TruthValue,
            mpsHotelRoomStatus               INTEGER,
            mpsHotelWakeUpDay                INTEGER,
            mpsHotelWakeUpMonth              INTEGER,
            mpsHotelWakeUpYear               INTEGER,
            mpsHotelWakeUpHour               INTEGER,
            mpsHotelWakeUpMin                INTEGER,
            mpsHotelWakeUpType               INTEGER,
            mpsHotelWakeUpAnnouncement       INTEGER,
            mpsHotelWakeUpAnnFileDirectory   DisplayString,
            mpsHotelWakeUpAnnDefaultVariant  INTEGER,
            mpsHotelFacilities               BITS,
            mpsHotelAdminStatus              INTEGER,
            mpsHotelDialAuthorisation        INTEGER
        }

    mpsHotelIndex OBJECT-TYPE
        SYNTAX          Unsigned32
        MAX-ACCESS      read-write
        STATUS          current
        DESCRIPTION
            "A unique value for each hotel room telephone."
        ::= { mpsHotelEntry 1}

    mpsHotelDescription OBJECT-TYPE
        SYNTAX          DisplayString
        MAX-ACCESS      read-write
        STATUS          current
        DESCRIPTION
            "A description for this hotel room."
        ::= { mpsHotelEntry 2}

    mpsHotelExtension OBJECT-TYPE
        SYNTAX          ExtensionIndexOrZero
        MAX-ACCESS      read-write
        STATUS          current
        DESCRIPTION
            "This variable contains index of the room telephone. Reference to
             mpsExtensionTable."
        DEFVAL { 0 }
        ::= { mpsHotelEntry 3 }

    mpsHotelAdditionalInfo OBJECT-TYPE
        SYNTAX          DisplayString
        MAX-ACCESS      read-write
        STATUS          current
        DESCRIPTION
            "Use for additional description info for the guest e.g language."
        ::= { mpsHotelEntry 4}

    mpsHotelCheckInTime OBJECT-TYPE
        SYNTAX      Date
        MAX-ACCESS  read-write
        STATUS      current
        DESCRIPTION
            "Date and time of check-in."
        ::= { mpsHotelEntry 5 }

    mpsHotelCheckOutStatus OBJECT-TYPE
        SYNTAX          TruthValue
        MAX-ACCESS      read-write
        STATUS          current
        DESCRIPTION
            "This variable contains the check-out status of the room telephone."
        DEFVAL { true }
        ::= { mpsHotelEntry 6 }

   mpsHotelRoomStatus OBJECT-TYPE
         SYNTAX          INTEGER {
                            unknown(1),
                            notCleaned(2),
                            cleaned(3),
                            checked(4)
                        }
        MAX-ACCESS      read-write
        STATUS          current
        DESCRIPTION
            "This variable contains the room status.
             unknown(1):    room status unknown.
             notCleaned(2): room not cleaned.
             cleaned(3):    room cleaned, but not checked.
             checked(4):    room cleaned and checked."
        DEFVAL { notCleaned }
        ::= { mpsHotelEntry 7 }

    mpsHotelWakeUpDay OBJECT-TYPE
        SYNTAX      INTEGER (1..31)
        MAX-ACCESS  read-write
        STATUS      current
        DESCRIPTION
            "WakeUp day."
        DEFVAL { 1 }
        ::= { mpsHotelEntry 8 }

    mpsHotelWakeUpMonth OBJECT-TYPE
        SYNTAX      INTEGER (1..12)
        MAX-ACCESS  read-write
        STATUS      current
        DESCRIPTION
            "WakeUp month."
        DEFVAL { 1 }
        ::= { mpsHotelEntry 9 }

    mpsHotelWakeUpYear OBJECT-TYPE
        SYNTAX      INTEGER (0..99)
        MAX-ACCESS  read-write
        STATUS      current
        DESCRIPTION
            "WakeUp year."
        DEFVAL { 0 }
        ::= { mpsHotelEntry 10 }

    mpsHotelWakeUpHour OBJECT-TYPE
        SYNTAX      INTEGER (0..23)
        MAX-ACCESS  read-write
        STATUS      current
        DESCRIPTION
            "WakeUp hour."
        DEFVAL { 0 }
        ::= { mpsHotelEntry 11 }

    mpsHotelWakeUpMin OBJECT-TYPE
        SYNTAX      INTEGER (0..59)
        MAX-ACCESS  read-write
        STATUS      current
        DESCRIPTION
            "WakeUp minutes."
        DEFVAL { 0 }
        ::= { mpsHotelEntry 12 }

   mpsHotelWakeUpType OBJECT-TYPE
         SYNTAX          INTEGER {
                            once(1),
                            daily(2),
                            off(3)
                        }
        MAX-ACCESS      read-write
        STATUS          current
        DESCRIPTION
            "This variable contains type of the wakeUp call.
             once(1):    wakeUp call only one day.
             daily(2):   WakeUp call daily."
         DEFVAL { off }
        ::= { mpsHotelEntry 13 }

   mpsHotelWakeUpAnnouncement OBJECT-TYPE
         SYNTAX          INTEGER {
                            -- file1(1),
                            -- file2(2),
                            -- file3(3),
                            -- file4(4),
                            -- file5(5),
                            -- file6(6),
                            -- file7(7),
                            -- file8(8),
                            -- default1(51),
                            -- default2(52),
			    file(54),
			    default(55)
                        }
        MAX-ACCESS      read-write
        STATUS          current
        DESCRIPTION
            "This variable contains the selected music on hold (MoH) that the
             wakeUp party hears at wakeUp call.
	     Possible values are:
		file:	  variable mpsHotelWakeUpAnnFileDirectory specifies
			  directory to contain sound file
		default:  variable mpsHotelWakeUpAnnDefaultVariant specifies the
			  variant whose default is to be used (default)"
        DEFVAL { default }
        ::= { mpsHotelEntry 14 }

    mpsHotelFacilities OBJECT-TYPE
        SYNTAX          BITS { mwi-tone(0) }
        MAX-ACCESS      read-write
        STATUS          current
        DESCRIPTION
            "Hotel facilities.
                mwi-tone : message waiting indication -> special tone.
            "
        ::= { mpsHotelEntry 15 }

    mpsHotelAdminStatus OBJECT-TYPE
        SYNTAX          INTEGER { enable(1),
                                  delete(2) 
                                }
        MAX-ACCESS      read-write
        STATUS          current
        DESCRIPTION
            "Just for MIB entry deletion."
        DEFVAL { enable }
        ::= { mpsHotelEntry 16 }

    mpsHotelDialAuthorisation OBJECT-TYPE
        SYNTAX          INTEGER {
                            unknown(1),
                            international(2),
                            incoming(3),
                            national(4),
                            region(5),
                            internal(6),
                            onlyDoorIntercom(7),
                            local(8)
                        }
        MAX-ACCESS      read-write
        STATUS          current
        DESCRIPTION
            "Dialing privileges for a hotel extension specifies what type of
             calls  (internal, external, etc. ) this extension can place. Default
             is incoming. This value is necessary for check-in and check-out.
             After check-in, the dial authorisation will be set to international,
             After check-out, the dial authorisation will be set to incoming."
        DEFVAL { incoming }
        ::= { mpsHotelEntry 17 }

    mpsHotelWakeUpAnnFileDirectory OBJECT-TYPE
        SYNTAX          DisplayString
        MAX-ACCESS      read-write
        STATUS          current
        DESCRIPTION
            "Name of directory (on flash medium) which contains file to be used
	     for music on hold.
             This variable references the entry in mpsWaveFile table where
	     variable mpsWaveFileDirectory has identical content.
	     If there should be multiple entrys with the same content for some
	     reason an arbitrary entry is chosen.
	     This entry is only valid if variable mpsHotelWakeUpAnnouncement is
	     set to value file.

	     Default value is the empty string."
        DEFVAL { "" }
        ::= { mpsHotelEntry 18 }

    mpsHotelWakeUpAnnDefaultVariant OBJECT-TYPE
        SYNTAX          INTEGER (1..2)
        MAX-ACCESS      read-write
        STATUS          current
        DESCRIPTION
            "This variable specifies the chosen default variant if variable
	     mpsHotelWakeUpAnnouncement is set to value default.

	     Default value for that variable is 1."
        DEFVAL { 1 }
        ::= { mpsHotelEntry 19 }

---------------------------------------------------------------------------
mpsCallTransactionTable OBJECT-TYPE
    SYNTAX      SEQUENCE OF MpsCallTransactionEntry
    MAX-ACCESS  not-accessible
    STATUS      current
    DESCRIPTION
        "This table contains status information about each transaction."
    ::= { mpsCall 1 }

    mpsCallTransactionEntry OBJECT-TYPE
        SYNTAX          MpsCallTransactionEntry 
        MAX-ACCESS      not-accessible
        STATUS          current
        DESCRIPTION
            ""
        INDEX { mpsCallTransIndex }
        ::= { mpsCallTransactionTable 1 }

    MpsCallTransactionEntry ::=
        SEQUENCE {
            mpsCallTransIndex                   Unsigned32, 
            mpsCallTransType                    INTEGER,
            mpsCallTransLocalNumber             DisplayString,
            mpsCallTransRemoteNumber            DisplayString,
            mpsCallTransRedirectNumber          DisplayString,
            mpsCallTransDirection               INTEGER,
            mpsCallTransState                   INTEGER,
            mpsCallTransChannel                 Unsigned32,
            mpsCallTransIfIndex                 InterfaceIndex
        }

    mpsCallTransIndex OBJECT-TYPE
        SYNTAX          Unsigned32
        MAX-ACCESS      read-only
        STATUS          current
        DESCRIPTION
            "A unique ID for each transaction."
        ::= { mpsCallTransactionEntry 1}

   mpsCallTransType OBJECT-TYPE
        SYNTAX          INTEGER {
                            subscriber(1),
                            trunk(2),
                            parking(3)
                        }
        MAX-ACCESS      read-only
        STATUS          current
        DESCRIPTION
            "This variable contains the transaction type:
             subscriber: transaction to/from internal subscriber.
             trunk:      transaction to/from trunk port.
             parking:    a parked call due to open-inquiry request"
        DEFVAL { subscriber }
        ::= { mpsCallTransactionEntry 2 }

    mpsCallTransLocalNumber OBJECT-TYPE
        SYNTAX          DisplayString (SIZE(0..32))
        MAX-ACCESS      read-only
        STATUS          current
        DESCRIPTION
            "This variable contains the local number of the transaction:
             for mpsCallTransType = subscriber: the number of the internal
                                                extension
             for mpsCallTransType = trunk     : the MSN or DDI of the trunk
                                                port.
             for mpsCallTransType = parking   : the system call number of the
                                                respective parking place"
        ::= { mpsCallTransactionEntry 3 }

    mpsCallTransRemoteNumber OBJECT-TYPE
        SYNTAX          DisplayString (SIZE(0..32))
        MAX-ACCESS      read-only
        STATUS          current
        DESCRIPTION
            "This variable contains the remote number of the transaction:
             for mpsCallTransType = subscriber: the MSN or DDI of the trunk port
             for mpsCallTransType = trunk     : the calling party (for incoming
                                                calls) or the called party (for
                                                outgoing calls)."
        ::= { mpsCallTransactionEntry 4 }

    mpsCallTransRedirectNumber OBJECT-TYPE
        SYNTAX          DisplayString (SIZE(0..32))
        MAX-ACCESS      read-only
        STATUS          current
        DESCRIPTION
            "This variable contains the redirected or redirection number 
             for redirected transactions."
        ::= { mpsCallTransactionEntry 5 }

    mpsCallTransDirection OBJECT-TYPE
        SYNTAX          INTEGER {
                            initiator(1),
                            recipient(2)
                        }
        MAX-ACCESS      read-only
        STATUS          current
        DESCRIPTION
            ""
        DEFVAL { initiator }
        ::= { mpsCallTransactionEntry 6 }

   mpsCallTransState OBJECT-TYPE
        SYNTAX          INTEGER {
                            idle(1),
                            alert(2),
                            connect(3),
                            held(4),
                            release(5)
                        }
        MAX-ACCESS      read-only
        STATUS          current
        DESCRIPTION
            "This variable contains the state of the transaction."
        DEFVAL { idle }
        ::= { mpsCallTransactionEntry 7 }

    mpsCallTransChannel OBJECT-TYPE
        SYNTAX          Unsigned32
        MAX-ACCESS      read-only
        STATUS          current
        DESCRIPTION
            "The corresponding channel number for this transaction."
        ::= { mpsCallTransactionEntry 8 }

    mpsCallTransIfIndex OBJECT-TYPE
        SYNTAX          InterfaceIndex
        MAX-ACCESS      read-only
        STATUS          current
        DESCRIPTION
            "The corresponding interface used for this transaction."
        ::= { mpsCallTransactionEntry 9 }

---------------------------------------------------------------------------
mpsSwitchingContactTable OBJECT-TYPE
    SYNTAX      SEQUENCE OF MpsSwitchingContactEntry
    MAX-ACCESS  not-accessible
    STATUS      current
    DESCRIPTION
        "This table contains settings for all switching contacts (relays)."
    ::= { mpsAlarm 1 }

    mpsSwitchingContactEntry OBJECT-TYPE
        SYNTAX          MpsSwitchingContactEntry
        MAX-ACCESS      not-accessible
        STATUS          current
        DESCRIPTION
            "Settings for each switching contact"
        INDEX { mpsSwitchingContactIndex }
        ::= { mpsSwitchingContactTable 1 }

    MpsSwitchingContactEntry ::=
        SEQUENCE {
            mpsSwitchingContactIndex         SwitchingContactIndex,
            mpsSwitchingContactDescription   DisplayString,
            mpsSwitchingContactType          INTEGER,
            mpsSwitchingContactTimer         INTEGER
        }

    mpsSwitchingContactIndex OBJECT-TYPE
        SYNTAX          SwitchingContactIndex
        MAX-ACCESS      read-only
        STATUS          current
        DESCRIPTION
            "A unique value for each switching contact (relay number)."
        ::= { mpsSwitchingContactEntry 1 }

     mpsSwitchingContactDescription OBJECT-TYPE
        SYNTAX          DisplayString
        MAX-ACCESS      read-write
        STATUS          current
        DESCRIPTION
            "A description for this switching contact"
        ::= { mpsSwitchingContactEntry 2 }

    mpsSwitchingContactType OBJECT-TYPE
        SYNTAX          INTEGER {
                            dial-code(1),
                            alarm-output(2),
                            voice-announcement(3),
                            dial-code-period-only(4),
                            dial-code-toggle-only(5)
                        }
        MAX-ACCESS      read-write
        STATUS          current
        DESCRIPTION
            "This value defines the application for which the switching contact
             is used:
             dial-code(1)            : Contact is controlled according to used
                                       dial codes (on/off or closed for a period
                                       of time).
             alarm-output(2)         : Contact is actuated during an alarm call.
             voice-announcement(3)   : Contact is actuated during an ongoing
                                       voice announcement.
             dial-code-period-only(4): Contact only actuated by dial code for
                                       closing a period of time.
             dial-code-toggle-only(5): Contact only actuated by dial codes for
                                       switching on/off."
        DEFVAL { dial-code }
        ::= { mpsSwitchingContactEntry 3 }

     mpsSwitchingContactTimer OBJECT-TYPE
        SYNTAX          INTEGER (1..999)
        UNITS           "s"
        MAX-ACCESS      read-write
        STATUS          current
        DESCRIPTION
            "Switching contact signalling period in seconds."
        DEFVAL { 3 }
        ::= { mpsSwitchingContactEntry 4 }

---------------------------------------------------------------------------
mpsAlarmInputTable OBJECT-TYPE
    SYNTAX      SEQUENCE OF MpsAlarmInputEntry
    MAX-ACCESS  not-accessible
    STATUS      current
    DESCRIPTION
        "This table contains settings for all alarm inputs (all FXS ports)."
    ::= { mpsAlarm 2 }

    mpsAlarmInputEntry OBJECT-TYPE
        SYNTAX          MpsAlarmInputEntry
        MAX-ACCESS      not-accessible
        STATUS          current
        DESCRIPTION
            "Settings for each alarm input mapped to FXS ports."
        INDEX { mpsAlarmInputIfIndex }
        ::= { mpsAlarmInputTable 1 }

    MpsAlarmInputEntry ::=
        SEQUENCE {
            mpsAlarmInputIfIndex             InterfaceIndexOrZero,
            mpsAlarmInputIndicationExtension ExtensionIndexOrZero,
            mpsAlarmInputContact             SwitchingContactIndexOrZero,
            mpsAlarmInputWaveType	     INTEGER,
	    mpsAlarmInputWaveFileDir         DisplayString,
	    mpsAlarmInputWaveDefaultVariant  INTEGER,
            mpsAlarmInputWavePlayBackCnt     Unsigned32,
            mpsAlarmInputGroup               GroupIndexOrZero,
            mpsAlarmInputSignalingTimer      Unsigned32,
            mpsAlarmInputSignalingRepeat     Unsigned32,
	    mpsAlarmInputDelayTimer	     Unsigned32,
	    mpsAlarmInputExternalConnTimer   Unsigned32,
            mpsAlarmInputInfoMsg             DisplayString,
            mpsAlarmInputAdminStatus         INTEGER
        }

    mpsAlarmInputIfIndex OBJECT-TYPE
        SYNTAX          InterfaceIndexOrZero
        MAX-ACCESS      read-write
        STATUS          current
        DESCRIPTION
            "A unique reference to potsIfTable."
        ::= { mpsAlarmInputEntry 1 }

    mpsAlarmInputIndicationExtension OBJECT-TYPE
        SYNTAX          ExtensionIndexOrZero
        MAX-ACCESS      read-write
        STATUS          current
        DESCRIPTION
            "A unique reference to mpsExtensionTable. This reference assignes
	     the indication number of the alarm input."
        ::= { mpsAlarmInputEntry 2 }

    mpsAlarmInputContact OBJECT-TYPE
        SYNTAX          SwitchingContactIndexOrZero
        MAX-ACCESS      read-write
        STATUS          current
        DESCRIPTION
            "A unique reference to mpsSwitchingContactTable. This reference 
	     assignes a relay contact which have to be switched if alarm input 
	     is initiated."
        ::= { mpsAlarmInputEntry 3 }

    mpsAlarmInputWaveType OBJECT-TYPE
        SYNTAX          INTEGER{
				file(54),
				default(55),
				external(80),
				off(100)
				}
        MAX-ACCESS      read-write
        STATUS          current
        DESCRIPTION
            "This variable contains the file/tone the remote is provided with, 
	     when alarm call is answered.
	     Possible values are:
		file:	  variable mpsAlarmInputWaveDir specifies the directory 
			  that contains the sound file
		default:  variable mpsAlarmInputWaveDefaultVariant specifies 
			  the variant whose default is to be used
		external: external source is used
		off:	  no wave on alarm call active (default)"
		DEFVAL { off }
        ::= { mpsAlarmInputEntry 4 }
		
	mpsAlarmInputWaveFileDir OBJECT-TYPE
        SYNTAX          DisplayString (SIZE(0..255))
        MAX-ACCESS      read-write
        STATUS          current
        DESCRIPTION
            "Name of directory (on flash medium) which contains the file to be
	     used as alarm call wave file.
             This variable references the entry in mpsWaveFile table where 
	     mpsWaveFileDirectory has identical content.
	     the entry is only valid if variable mpsAlarmInputWaveType is set 
	     to value file. 
	     Default value is the empty string."
        DEFVAL { "" }
        ::= { mpsAlarmInputEntry 5 }

	mpsAlarmInputWaveDefaultVariant OBJECT-TYPE
        SYNTAX          INTEGER(1..2)
        MAX-ACCESS      read-write
        STATUS          current
        DESCRIPTION
            "This variable specifies the chosen default variant if variable 
	     mpsAlarmInputWaveType is set to value default.
	     Default value for that variable is 1."
		DEFVAL { 1 }
        ::= { mpsAlarmInputEntry 6 }
		
    mpsAlarmInputWavePlayBackCnt OBJECT-TYPE
        SYNTAX          Unsigned32(0..10)
        MAX-ACCESS      read-write
        STATUS          current
        DESCRIPTION
            "Value contains number of playbacks of selected wave file.
             (0 = endless)."
        ::= { mpsAlarmInputEntry 7 }

	mpsAlarmInputGroup OBJECT-TYPE
        SYNTAX          GroupIndexOrZero
        MAX-ACCESS      read-write
        STATUS          current
        DESCRIPTION
            "A unique reference to mpsGroupTable. This reference assignes a 
	     special group to the alarm input. All settings for call 
	     distribution of alarm input are outsourced in the mpsGroupTable
	     and the corresponding sub-tables."
        ::= { mpsAlarmInputEntry 8 }

    mpsAlarmInputSignalingTimer OBJECT-TYPE
        SYNTAX          Unsigned32(1..600)
        UNITS           "s"
        MAX-ACCESS      read-write
        STATUS          current
        DESCRIPTION
            "This value contains the signaling timeout of the alarm. After 
	     expiration of this timer, the alarm call will be released and
	     delayed for the value stored in mpsAlarmInputDelayTimer."
        DEFVAL { 30 }
        ::= { mpsAlarmInputEntry 9 }

    mpsAlarmInputSignalingRepeat OBJECT-TYPE
        SYNTAX          Unsigned32(0..10)
        MAX-ACCESS      read-write
        STATUS          current
        DESCRIPTION
            "This value contains the number of signaling repetition on no 
	     response (after mpsAlarmInputSignalingTimeout expires) or all
	     team-members are busy (and call waiting is restricted)."
        DEFVAL { 2 }
        ::= { mpsAlarmInputEntry 10 }
		
	mpsAlarmInputDelayTimer OBJECT-TYPE
        SYNTAX          Unsigned32(1..600)
        UNITS           "s"
        MAX-ACCESS      read-write
        STATUS          current
        DESCRIPTION
            "This value contains the delay-timer of the alarm. After expiring
	     of this timer, the alarm call will be re-established if 
	     mpsAlarmInputSignalingRepeat-counter unequals 0."
        DEFVAL { 10 }
        ::= { mpsAlarmInputEntry 11 }
		
	mpsAlarmInputExternalConnTimer OBJECT-TYPE
        SYNTAX          Unsigned32(1..600)
        UNITS           "s"
        MAX-ACCESS      read-write
        STATUS          current
        DESCRIPTION
            "This value contains the external connection timer of the alarm. 
	     After timer expiry the external alarm call will be released."
        DEFVAL { 60 }
        ::= { mpsAlarmInputEntry 12 }

	mpsAlarmInputInfoMsg OBJECT-TYPE
        SYNTAX          DisplayString (SIZE(0..32))
        MAX-ACCESS      read-write
        STATUS          current
        DESCRIPTION
            "An info message (UUS1) delivered if alarm is initiated. Terminals 
	     must support UUS1-text messages to show this info message."
        DEFVAL { "" }
        ::= { mpsAlarmInputEntry 13 }

    mpsAlarmInputAdminStatus OBJECT-TYPE
        SYNTAX          INTEGER {
                            enable(1),
                            disable(2),
			    delete(3)
                        }
        MAX-ACCESS      read-write
        STATUS          obsolete
        DESCRIPTION
            "Just for MIB entry deletion and for deactivation."
        DEFVAL { enable }
        ::= { mpsAlarmInputEntry 14 }

END

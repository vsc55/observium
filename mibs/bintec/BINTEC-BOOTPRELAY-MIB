-- This file is corresponding to Release 9.1.10.101 from 2014/08/11 00:00:00


---------------------------------------------------------------------------
-- (C)opyright 2006-2014 bintec elmeg GmbH
-- $RCSfile: mib-bootprelay,v $
-- $Revision: 1.8 $
-- $Date: 2014-02-07 10:37:49 $
---------------------------------------------------------------------------

BINTEC-BOOTPRELAY-MIB DEFINITIONS ::= BEGIN

IMPORTS
    MODULE-IDENTITY, OBJECT-TYPE, NOTIFICATION-TYPE,
    Integer32, Unsigned32, Counter32, Counter64, IpAddress, TimeTicks,
    mib-2, enterprises
        FROM SNMPv2-SMI

    DisplayString, TimeStamp, PhysAddress
        FROM SNMPv2-TC

    biboip, Date, BitValue, HexValue
	FROM BINTEC-MIB

    MODULE-COMPLIANCE, OBJECT-GROUP, NOTIFICATION-GROUP
        FROM SNMPv2-CONF;

---------------------------------------------------------------------------

bootprelayMIB MODULE-IDENTITY
    LAST-UPDATED "201111190000Z"
    ORGANIZATION "bintec elmeg GmbH"
    CONTACT-INFO
            "EMail:   info@bintec-elmeg.com
	     Web:     www.bintec-elmeg.com
	    "
    DESCRIPTION
            "The MIB module for BOOTP relay administration entities.
            "
    REVISION      "200612120000Z"
    DESCRIPTION
            "BOOTP relay administration used for: 
	        - BOOTP relay servers assignment"
    ::= { biboip 55 }

---------------------------------------------------------------------------
-- OID groups & all tables 
---------------------------------------------------------------------------
	-- ipBootpRelayTable 				bootprelayMIB 1

---------------------------------------------------------------------------
-- ipBootpRelayTable
---------------------------------------------------------------------------

ipBootpRelayTable OBJECT-TYPE
    SYNTAX      SEQUENCE OF IpBootpRelayEntry
    MAX-ACCESS  not-accessible
    STATUS      current
    DESCRIPTION
	"Interfaces that are enabled for BOOTP relay mode."
    ::= { bootprelayMIB 1 }

    ipBootpRelayEntry OBJECT-TYPE
	SYNTAX      IpBootpRelayEntry
	MAX-ACCESS  not-accessible
	STATUS      current
	DESCRIPTION
	    ""
	INDEX { ipBootpRelayIfIndex }
	::= { ipBootpRelayTable 1 }

    IpBootpRelayEntry ::= 
	SEQUENCE {
	    ipBootpRelayIfIndex			INTEGER,
	    ipBootpRelayEnabled			INTEGER,
	    ipBootpRelayServer1			IpAddress,
	    ipBootpRelayServer2			IpAddress,
	    ipBootpRelayDiscoverOptionsGroupID	INTEGER,
	    ipBootpRelayRequestOptionsGroupID	INTEGER,
	    ipBootpRelayInformOptionsGroupID	INTEGER,
	    ipBootpRelayOfferOptionsGroupID	INTEGER,
	    ipBootpRelayAckOptionsGroupID	INTEGER,
	    ipBootpRelayDnsAssign		INTEGER
	}
	
    ipBootpRelayIfIndex OBJECT-TYPE
	SYNTAX      INTEGER
	MAX-ACCESS  read-write
	STATUS      current
	DESCRIPTION
	    "Index of interface which will use BOOTP relay."
	::= { ipBootpRelayEntry 1 }
	
    ipBootpRelayEnabled OBJECT-TYPE
  	SYNTAX      INTEGER { delete(1), true(2), false(3) }
	MAX-ACCESS  read-write
	STATUS      current
	DESCRIPTION
	    "Enable, disable or delete the table entry."
	DEFVAL { true }
	::= { ipBootpRelayEntry 2 }

    ipBootpRelayServer1 OBJECT-TYPE
	SYNTAX      IpAddress
	MAX-ACCESS  read-write
	STATUS      current
	DESCRIPTION
	    "The IP address of the first BOOTP server to use."
	DEFVAL { '00000000'H }
	::= { ipBootpRelayEntry 3 }

    ipBootpRelayServer2 OBJECT-TYPE
	SYNTAX      IpAddress
	MAX-ACCESS  read-write
	STATUS      current
	DESCRIPTION
	    "The IP address of the second BOOTP server to use."
	DEFVAL { '00000000'H }
	::= { ipBootpRelayEntry 4 }

    ipBootpRelayDiscoverOptionsGroupID OBJECT-TYPE
	SYNTAX      INTEGER (0..65535)
	MAX-ACCESS  read-write
	STATUS      current
	DESCRIPTION
	    "Identifies the option or set of options which are added 
	     to the original DHCP DISCOVER message received from the 
	     client before forwarding it to the DHCP server. The 
	     options are defined in ipDhcpOptionTable. Selecting a
	     null value result in no option being added."
	::= { ipBootpRelayEntry 5 }
	
    ipBootpRelayRequestOptionsGroupID OBJECT-TYPE
	SYNTAX      INTEGER (0..65535)
	MAX-ACCESS  read-write
	STATUS      current
	DESCRIPTION
	    "Identifies the option or set of options which are added 
	     to the original DHCP REQUEST message received from the 
	     client before forwarding it to the DHCP server. The 
	     options are defined in ipDhcpOptionTable. Selecting a
	     null value result in no option being added."
	::= { ipBootpRelayEntry 6 }
	
    ipBootpRelayInformOptionsGroupID OBJECT-TYPE
	SYNTAX      INTEGER (0..65535)
	MAX-ACCESS  read-write
	STATUS      current
	DESCRIPTION
	    "Identifies the option or set of options which are added 
	     to the original DHCP INFORM message received from the 
	     client before forwarding it to the DHCP server. The 
	     options are defined in ipDhcpOptionTable. Selecting a
	     null value result in no option being added."
	::= { ipBootpRelayEntry 7 }
	
    ipBootpRelayOfferOptionsGroupID OBJECT-TYPE
	SYNTAX      INTEGER (0..65535)
	MAX-ACCESS  read-write
	STATUS      current
	DESCRIPTION
	    "Identifies the option or set of options which are added 
	     to the original DHCP OFFER message received from the 
	     DHCP server before forwarding it to the DHCP client. The 
	     options are defined in ipDhcpOptionTable. Selecting a
	     null value result in no option being added."
	::= { ipBootpRelayEntry 8 }
	
    ipBootpRelayAckOptionsGroupID OBJECT-TYPE
	SYNTAX      INTEGER (0..65535)
	MAX-ACCESS  read-write
	STATUS      current
	DESCRIPTION
	    "Identifies the option or set of options which are added 
	     to the original DHCP ACK message received from the 
	     DHCP server before forwarding it to the DHCP client. The 
	     options are defined in ipDhcpOptionTable. Selecting a
	     null value result in no option being added."
	::= { ipBootpRelayEntry 9 }
	
    ipBootpRelayDnsAssign OBJECT-TYPE
  	SYNTAX      INTEGER { passthrough(1), self(2) }
	MAX-ACCESS  read-write
	STATUS      current
	DESCRIPTION
	    "This variable determines the assignment policy, if set to
	     passthrough (1) the DHCP domain server tag(s) will be passed
	     unchanged, if set to self (2) the own IP address is provided
	     as first nameserver address."
	DEFVAL { passthrough }
	::= { ipBootpRelayEntry 10 }
	


---------------------------------------------------------------------------
END

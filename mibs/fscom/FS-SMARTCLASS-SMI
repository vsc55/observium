-- *****************************************************************
-- FS-SMARTCLASS-SMI.mib: FS Smart Class SMI File
-- 
-- Feb. 2017, panshiyong
--
-- Copyright (c) 2014 by FS.COM Inc..
-- All rights reserved.
-- 
-- *****************************************************************
--

FS-SMARTCLASS-SMI DEFINITIONS ::= BEGIN

IMPORTS
        MODULE-IDENTITY,
        OBJECT-IDENTITY
                FROM SNMPv2-SMI
        products
                FROM FS-SMI;
                
smartclass OBJECT IDENTIFIER ::= { products 8 }

smartclassMib MODULE-IDENTITY
        LAST-UPDATED "201702130000Z"
        ORGANIZATION "FS.COM Inc.."
        CONTACT-INFO
                " 
                Tel: 400-865-2852 

                E-mail: https://www.fs.com/live_chat_service_mail.html"
        DESCRIPTION
                "The Structure of Management Information for the
                 FS enterprise."
        REVISION      "201702130000Z"
        DESCRIPTION
                "Initial version of this MIB module."
        ::= { smartclass 1 }        

fsSmartClassProducts OBJECT-IDENTITY
        STATUS  current
        DESCRIPTION
                "fsSmartClassProducts is the root OBJECT IDENTIFIER from
                 which sysObjectID values are assigned for smartclass.  Actual
                 values are defined in FS-PRODUCTS-MIB."
        ::= { smartclassMib 1 }
        
END

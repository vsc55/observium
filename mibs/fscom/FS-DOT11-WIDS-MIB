-- *******************************************************************
-- FS-DOT11-WIDS-MIB.mib : FS WLAN wids MIB
--
-- Oct 2009, kangxiankun
--
-- Copyright (c) 2009 by FS.COM Inc..
-- All rights reserved.
-- *******************************************************************
--
FS-DOT11-WIDS-MIB DEFINITIONS ::= BEGIN

IMPORTS
        TruthValue,
        MacAddress,
        DisplayString
                FROM SNMPv2-TC
        MODULE-IDENTITY,
        OBJECT-TYPE,
        TimeTicks,
        Integer32
                FROM SNMPv2-SMI
        MODULE-COMPLIANCE,
        OBJECT-GROUP
                FROM SNMPv2-CONF
        fsMgmt
                FROM FS-SMI;
--********************************************************************
--*  MODULE IDENTITY
--********************************************************************
fsDot11WIDSMIB    MODULE-IDENTITY
   LAST-UPDATED    "200904150900Z"
   ORGANIZATION    "FS.COM Inc.."
   CONTACT-INFO
            "
            Tel: 400-865-2852

            E-mail: https://www.fs.com/live_chat_service_mail.html"
    DESCRIPTION
          "This MIB provides information about WIDS feature.

          GLOSSARY

          Wireless Intrusion Detection Sensor (WIDS)
          WIDS is designed to be employed in an area that is serviced
          by an existing wireless network.
          It aids in the early detection of malicious outsider attacks
          and intrusions via wireless networks.

          Rogue AP
          A rogue access point is any Wi-Fi access point connected to
          your network without authorization.
          As it is not authorized, if there is any weakness in
          the AP, the hacker will have chance to compromise your
          network.

          Rogue Station
          It is similiar to Rogue AP, while it is a station.

          Monitor AP
          An AP will scan or listen to the air, and try to detect
          wireless attack in the network.
          Some AP products will work only in monitor role, while some
          AP products could switch between normal AP role (only
          provide wireless access service)and monitor AP role.

          Ad Hoc Mode
          Station could work under Ad hoc mode, then they
          could directly do peer-to-peer communication without
          other device support."

          REVISION "200904150900Z"
          DESCRIPTION
                  "The initial revision of this MIB module."
          ::= { fsMgmt 62 }

fsDot11WIDSConfigObjects OBJECT IDENTIFIER       ::= { fsDot11WIDSMIB 1 }
fsDot11WIDSDetectObjects OBJECT IDENTIFIER       ::= { fsDot11WIDSMIB 2 }
--fsDot11WIDSTraps OBJECT IDENTIFIER       ::= { fsDot11WIDSMIB 0 }

--*****************************************************************************
--*  fsDot11WIDSPermitVendorTable Definition
--*****************************************************************************
fsDot11WIDSPermitVendorTable OBJECT-TYPE
    SYNTAX      SEQUENCE OF FSDot11WIDSPermitVendorEntry
    MAX-ACCESS  not-accessible
    STATUS      current
    DESCRIPTION
        "The table provides the permitted vendor list, and each vendor
        will be identified by MAC. The legal device should be made by the permitted vendors."
    ::= { fsDot11WIDSConfigObjects 1 }

fsDot11WIDSPermitVendorEntry OBJECT-TYPE
    SYNTAX      FSDot11WIDSPermitVendorEntry
    MAX-ACCESS  not-accessible
    STATUS      current
    DESCRIPTION
        "Each entry provides the information of permitted vendor."
    INDEX { fsDot11VendorOUI }
    ::= { fsDot11WIDSPermitVendorTable 1 }

FSDot11WIDSPermitVendorEntry ::=
    SEQUENCE {
        fsDot11VendorOUI                Integer32,
        fsDot11VendorOper               Integer32,
        fsDot11VendorName               MacAddress
    }

fsDot11VendorOUI OBJECT-TYPE
    SYNTAX      Integer32
    MAX-ACCESS  not-accessible
    STATUS      current
    DESCRIPTION
        "Represents the vendor OUI information of the wireless device."
    ::= { fsDot11WIDSPermitVendorEntry 1 }

fsDot11VendorOper OBJECT-TYPE
    SYNTAX      Integer32
    MAX-ACCESS  read-write
    STATUS      current
    DESCRIPTION
        "Represents the operation of vendor list."
    ::= { fsDot11WIDSPermitVendorEntry 2 }

fsDot11VendorName OBJECT-TYPE
    SYNTAX      MacAddress
    MAX-ACCESS  read-write
    STATUS      current
    DESCRIPTION
        "Represents the vendor mac of the wireless device."
    ::= { fsDot11WIDSPermitVendorEntry 3 }

--*****************************************************************************
--*  fsDot11WIDSPermitSSIDTable Definition
--*****************************************************************************

fsDot11WIDSPermitSSIDTable OBJECT-TYPE
    SYNTAX      SEQUENCE OF FSDot11WIDSPermitSSIDEntry
    MAX-ACCESS  not-accessible
    STATUS      current
    DESCRIPTION
        "The table represents the list of SSID could be permitted in
        the wireless network."
    ::= { fsDot11WIDSConfigObjects 2 }

fsDot11WIDSPermitSSIDEntry OBJECT-TYPE
    SYNTAX      FSDot11WIDSPermitSSIDEntry
    MAX-ACCESS  not-accessible
    STATUS      current
    DESCRIPTION
        "Each entry provides the information of permitted SSID."
    INDEX { fsDot11PermitNum }
    ::= { fsDot11WIDSPermitSSIDTable 1 }

FSDot11WIDSPermitSSIDEntry ::=
    SEQUENCE {
        fsDot11PermitNum              Integer32,
        fsDot11PermitOper             Integer32,
        fsDot11PermitSSID             DisplayString
    }

fsDot11PermitNum OBJECT-TYPE
    SYNTAX      Integer32
    MAX-ACCESS  not-accessible
    STATUS      current
    DESCRIPTION
        "Represents the permitted num in the wireless network."
    ::= { fsDot11WIDSPermitSSIDEntry 1 }

fsDot11PermitOper OBJECT-TYPE
    SYNTAX      Integer32
    MAX-ACCESS  read-write
    STATUS      current
    DESCRIPTION
        "Represents the operation of ssid list."
    ::= { fsDot11WIDSPermitSSIDEntry 2 }

fsDot11PermitSSID OBJECT-TYPE
    SYNTAX      DisplayString(SIZE (0..255))
    MAX-ACCESS  read-write
    STATUS      current
    DESCRIPTION
        "Represents the permitted SSID in the wireless network."
    ::= { fsDot11WIDSPermitSSIDEntry 3 }

--*****************************************************************************
--*  fsDot11WIDSDeviceAttackMacaddressListTable Definition
--*****************************************************************************
fsDot11WIDSDeviceAttackMacaddressListTable OBJECT-TYPE
    SYNTAX      SEQUENCE OF FSDot11WIDSDeviceAttackMacaddressListEntry
    MAX-ACCESS  not-accessible
    STATUS      current
    DESCRIPTION
        "The table provides the MAC address list of legal stations"
    ::= { fsDot11WIDSConfigObjects 3 }

fsDot11WIDSDeviceAttackMacaddressListEntry OBJECT-TYPE
    SYNTAX      FSDot11WIDSDeviceAttackMacaddressListEntry
    MAX-ACCESS  not-accessible
    STATUS      current
    DESCRIPTION
        "Each entry contains the MAC address of legal stations."
    INDEX { fsDot11AttackNum }
    ::= { fsDot11WIDSDeviceAttackMacaddressListTable 1 }

FSDot11WIDSDeviceAttackMacaddressListEntry ::=
    SEQUENCE {
        fsDot11AttackNum              Integer32,
        fsDot11AttackOper             Integer32,
        fsDot11AttackMAC              MacAddress,
        fsDot11AttackInfo             DisplayString
    }

fsDot11AttackNum OBJECT-TYPE
    SYNTAX      Integer32
    MAX-ACCESS  not-accessible
    STATUS      current
    DESCRIPTION
        "Represents the number of station or AP, and WIDS always
        take it as illegal station or AP."
    ::= { fsDot11WIDSDeviceAttackMacaddressListEntry 1 }

fsDot11AttackOper OBJECT-TYPE
    SYNTAX      Integer32
    MAX-ACCESS  read-write
    STATUS      current
    DESCRIPTION
        "Represents the operaton of attack mac address list."
    ::= { fsDot11WIDSDeviceAttackMacaddressListEntry 2 }

fsDot11AttackMAC OBJECT-TYPE
    SYNTAX      MacAddress
    MAX-ACCESS  read-write
    STATUS      current
    DESCRIPTION
        "Represents the MAC address of illegal stations."
    ::= { fsDot11WIDSDeviceAttackMacaddressListEntry 3 }

fsDot11AttackInfo OBJECT-TYPE
    SYNTAX DisplayString (SIZE (0..255))
    MAX-ACCESS read-only
    STATUS current
    DESCRIPTION
        "Represents the detail of illegal stations."
    ::= { fsDot11WIDSDeviceAttackMacaddressListEntry 4 }

--*****************************************************************************
--*  fsDot11WIDSDevicePermitMacaddressListTable Definition
--*****************************************************************************

fsDot11WIDSDevicePermitMacaddressListTable OBJECT-TYPE
    SYNTAX      SEQUENCE OF FSDot11WIDSDevicePermitMacaddressListEntry
    MAX-ACCESS  not-accessible
    STATUS      current
    DESCRIPTION
        "The table provides the MAC address list of stations or APs,
        and WIDS always take them as legal stations or APs."
    ::= { fsDot11WIDSConfigObjects 4 }

fsDot11WIDSDevicePermitMacaddressListEntry OBJECT-TYPE
    SYNTAX      FSDot11WIDSDevicePermitMacaddressListEntry
    MAX-ACCESS  not-accessible
    STATUS      current
    DESCRIPTION
        "Each entry contains the MAC address of station or AP,
        and WIDS always take it as legal station or AP."
    INDEX { fsDot11PermitMACNum }
    ::= { fsDot11WIDSDevicePermitMacaddressListTable 1 }

FSDot11WIDSDevicePermitMacaddressListEntry ::=
    SEQUENCE {
        fsDot11PermitMACNum           Integer32,
        fsDot11PermitMACOper          Integer32,
        fsDot11PermitMACAddr          MacAddress
    }

fsDot11PermitMACNum OBJECT-TYPE
    SYNTAX      Integer32
    MAX-ACCESS  not-accessible
    STATUS      current
    DESCRIPTION
        "Represents the number of station or AP, and WIDS always
        take it as legal station or AP."
    ::= { fsDot11WIDSDevicePermitMacaddressListEntry 1 }

fsDot11PermitMACOper OBJECT-TYPE
    SYNTAX      Integer32
    MAX-ACCESS  read-write
    STATUS      current
    DESCRIPTION
        "Represents the operation for mac address list."
    ::= { fsDot11WIDSDevicePermitMacaddressListEntry 2 }

fsDot11PermitMACAddr OBJECT-TYPE
    SYNTAX      MacAddress
    MAX-ACCESS  read-write
    STATUS      current
    DESCRIPTION
        "Represents the MAC address of station or AP, and WIDS always
        take it as legal station or AP."
    ::= { fsDot11WIDSDevicePermitMacaddressListEntry 3 }

-- *****************************************************************************
-- *  fsDot11WIDSDeviceagingDuration Definition
-- *****************************************************************************

fsDot11WIDSDeviceagingDuration OBJECT-TYPE
    SYNTAX Integer32
    MAX-ACCESS  read-write
    STATUS      current
    DESCRIPTION
        "Represents the scope of device aging duration."
    ::= { fsDot11WIDSConfigObjects 5 }


-- *****************************************************************************
-- *  fsDot11WIDSCountermeasuresMode Definition
-- *****************************************************************************

fsDot11WIDSCountermeasuresMode OBJECT-TYPE
    SYNTAX Integer32
    MAX-ACCESS  read-write
    STATUS      current
    DESCRIPTION
        "Represents device working countermeasures mode ."
    ::= { fsDot11WIDSConfigObjects 6 }

-- *****************************************************************************
-- *  fsDot11WIDSCountermeasureSet Definition
-- *****************************************************************************

fsDot11WIDSCountermeasureSet OBJECT-TYPE
    SYNTAX Integer32
    MAX-ACCESS  read-write
    STATUS      current
    DESCRIPTION
        "Represents enable or disable device countermeasures."
    ::= { fsDot11WIDSConfigObjects 7 }


-- *****************************************************************************
-- *  fsDot11WIDSMode Definition
-- *****************************************************************************

fsDot11WIDSModeTable OBJECT-TYPE
    SYNTAX SEQUENCE OF FSDot11WIDSModeEntry
    MAX-ACCESS not-accessible
    STATUS current
    DESCRIPTION
      "FS AP device mode"
    ::={ fsDot11WIDSConfigObjects 8 }

fsDot11WIDSModeEntry OBJECT-TYPE
    SYNTAX FSDot11WIDSModeEntry
    MAX-ACCESS not-accessible
    STATUS current
    DESCRIPTION
      "AP MAC is the index of this MIB table."
    INDEX { fsDot11WIDSAPID }
    ::={ fsDot11WIDSModeTable 1 }

FSDot11WIDSModeEntry ::=
    SEQUENCE {
        fsDot11WIDSAPID                  Integer32,
        fsDot11WIDSDeviceMode            Integer32
    }

fsDot11WIDSAPID OBJECT-TYPE
    SYNTAX Integer32
    MAX-ACCESS  not-accessible
    STATUS      current
    DESCRIPTION
        "AP ID."
    ::= { fsDot11WIDSModeEntry 1 }

fsDot11WIDSDeviceMode OBJECT-TYPE
    SYNTAX Integer32
    MAX-ACCESS  read-write
    STATUS      current
    DESCRIPTION
        "Represents WIDS device mode."
    ::= { fsDot11WIDSModeEntry 2 }

--*****************************************************************************
--*  fsDot11WIDSWhitelistMacaddressListTable Definition
--*****************************************************************************

fsDot11WIDSWhitelistMacaddressListTable OBJECT-TYPE
    SYNTAX      SEQUENCE OF FSDot11WIDSWhitelistMacaddressListEntry
    MAX-ACCESS  not-accessible
    STATUS      current
    DESCRIPTION
        "The table provides the MAC address list of stations or APs,
        and WIDS always take them as legal stations or APs."
    ::= { fsDot11WIDSConfigObjects 9 }

fsDot11WIDSWhitelistMacaddressListEntry OBJECT-TYPE
    SYNTAX      FSDot11WIDSWhitelistMacaddressListEntry
    MAX-ACCESS  not-accessible
    STATUS      current
    DESCRIPTION
        "Each entry contains the MAC address of station or AP,
        and WIDS always take it as legal station or AP."
    INDEX { fsDot11WhitelistNum }
    ::= { fsDot11WIDSWhitelistMacaddressListTable 1 }

FSDot11WIDSWhitelistMacaddressListEntry ::=
    SEQUENCE {
        fsDot11WhitelistNum              Integer32,
        fsDot11WhitelistOper             Integer32,
        fsDot11WhitelistMAC              MacAddress
    }

fsDot11WhitelistNum OBJECT-TYPE
    SYNTAX      Integer32
    MAX-ACCESS  not-accessible
    STATUS      current
    DESCRIPTION
        "Represents the Number of station or AP, and WIDS always
        take it as legal station or AP."
    ::= { fsDot11WIDSWhitelistMacaddressListEntry 1 }

fsDot11WhitelistOper OBJECT-TYPE
    SYNTAX      Integer32
    MAX-ACCESS  read-write
    STATUS      current
    DESCRIPTION
        "Represents the operation for this table."
    ::= { fsDot11WIDSWhitelistMacaddressListEntry 2 }

fsDot11WhitelistMAC OBJECT-TYPE
    SYNTAX      MacAddress
    MAX-ACCESS  read-write
    STATUS      current
    DESCRIPTION
        "Represents the MAC address of station or AP, and WIDS always
        take it as legal station or AP."
    ::= { fsDot11WIDSWhitelistMacaddressListEntry 3 }

--*****************************************************************************
--*  fsDot11WIDSStaticblacklistMacaddressListTable Definition
--*****************************************************************************

fsDot11WIDSStaticblackListTable OBJECT-TYPE
    SYNTAX      SEQUENCE OF FSDot11WIDSStaticblackListEntry
    MAX-ACCESS  not-accessible
    STATUS      current
    DESCRIPTION
        "The table provides the MAC address list of stations or APs,
        and WIDS always take them as illegal stations or APs."
    ::= { fsDot11WIDSConfigObjects 10 }

fsDot11WIDSStaticblackListEntry OBJECT-TYPE
    SYNTAX      FSDot11WIDSStaticblackListEntry
    MAX-ACCESS  not-accessible
    STATUS      current
    DESCRIPTION
        "Each entry contains the MAC address of station or AP,
        and WIDS always take it as illegal station or AP."
    INDEX { fsDot11StaticblacklistNum }
    ::= { fsDot11WIDSStaticblackListTable 1 }

FSDot11WIDSStaticblackListEntry ::=
    SEQUENCE {
        fsDot11StaticblacklistNum              Integer32,
        fsDot11StaticblacklistOper             Integer32,
        fsDot11StaticblacklistMAC              MacAddress
    }

fsDot11StaticblacklistNum OBJECT-TYPE
    SYNTAX      Integer32
    MAX-ACCESS  not-accessible
    STATUS      current
    DESCRIPTION
        "Represents the number of station or AP, and WIDS always
        take it as illegal station or AP."
    ::= { fsDot11WIDSStaticblackListEntry 1 }

fsDot11StaticblacklistOper OBJECT-TYPE
    SYNTAX      Integer32
    MAX-ACCESS  read-write
    STATUS      current
    DESCRIPTION
        "Represents the operation for this table."
    ::= { fsDot11WIDSStaticblackListEntry 2 }

fsDot11StaticblacklistMAC OBJECT-TYPE
    SYNTAX      MacAddress
    MAX-ACCESS  read-write
    STATUS      current
    DESCRIPTION
        "Represents the MAC address of station or AP, and WIDS always
        take it as illegal station or AP."
    ::= { fsDot11WIDSStaticblackListEntry 3 }


--*****************************************************************************
--*  fsDot11WIDSDynamicblacklistEnable Definition
--*****************************************************************************

fsDot11WIDSDynamicblacklistEnable OBJECT-TYPE
    SYNTAX TruthValue
    MAX-ACCESS  read-write
    STATUS      current
    DESCRIPTION
        "Represents enable or disable devic dynamic blacklist."
    ::= { fsDot11WIDSConfigObjects 11 }

-- *****************************************************************************
-- *  fsDot11WIDSDynamicblacklistLifetime Definition
-- *****************************************************************************

fsDot11WIDSDynamicblacklistLifetime OBJECT-TYPE
    SYNTAX Integer32
    MAX-ACCESS  read-write
    STATUS      current
    DESCRIPTION
        "Represents the scope of dynamic blacklist lifetime."
    ::= { fsDot11WIDSConfigObjects 12 }

--*****************************************************************************
--*  fsDot11WIDSAttackDetectionMode Definition
--*****************************************************************************

fsDot11WIDSAttackDetectionMode OBJECT-TYPE
    SYNTAX Integer32
    MAX-ACCESS  read-write
    STATUS      current
    DESCRIPTION
        "Represents enable which mode of attack-detection to work."
    ::= { fsDot11WIDSConfigObjects 13 }

--*****************************************************************************
--*  fsDot11WIDSRogueInfo Definition
--*****************************************************************************
fsDot11WIDSRogueInfoTable OBJECT-TYPE
    SYNTAX      SEQUENCE OF FSDot11WIDSRogueInfoEntry
    MAX-ACCESS  not-accessible
    STATUS      current
    DESCRIPTION
        "The table provides Rogue information."
    ::= { fsDot11WIDSConfigObjects 14 }

fsDot11WIDSRogueInfoEntry OBJECT-TYPE
    SYNTAX      FSDot11WIDSRogueInfoEntry
    MAX-ACCESS  not-accessible
    STATUS      current
    DESCRIPTION
        "Each entry contains vlan list for user-isolation."
    INDEX { fsDot11WIDSRogueInfoNUM, fsDot11WIDSRogueInfoTYPE}
    ::= { fsDot11WIDSRogueInfoTable 1 }

FSDot11WIDSRogueInfoEntry ::=
    SEQUENCE {
        fsDot11WIDSRogueInfoNUM       Integer32,
        fsDot11WIDSRogueInfoTYPE      Integer32,
        fsDot11WIDSRogueInfoOper      Integer32,
        fsDot11WIDSRogueInfoMAC       MacAddress,
        fsDot11WIDSRogueInfoString	  DisplayString
    }

fsDot11WIDSRogueInfoNUM OBJECT-TYPE
    SYNTAX      Integer32
    MAX-ACCESS  not-accessible
    STATUS      current
    DESCRIPTION
        "Each entry contains the number for rogue device."
    ::= { fsDot11WIDSRogueInfoEntry 1 }

fsDot11WIDSRogueInfoTYPE OBJECT-TYPE
    SYNTAX      Integer32
    MAX-ACCESS  not-accessible
    STATUS      current
    DESCRIPTION
        "Each entry contains the type for rogue device ."
    ::= { fsDot11WIDSRogueInfoEntry 2 }

fsDot11WIDSRogueInfoOper OBJECT-TYPE
    SYNTAX      Integer32
    MAX-ACCESS  read-write
    STATUS      current
    DESCRIPTION
        "Each entry contains the operation for rogue device ."
    ::= { fsDot11WIDSRogueInfoEntry 3 }

fsDot11WIDSRogueInfoMAC OBJECT-TYPE
    SYNTAX      MacAddress
    MAX-ACCESS  read-write
    STATUS      current
    DESCRIPTION
        "Each entry contains the mac for rogue device ."
    ::= { fsDot11WIDSRogueInfoEntry 4 }

fsDot11WIDSRogueInfoString OBJECT-TYPE
    SYNTAX      DisplayString
    MAX-ACCESS  read-write
    STATUS      current
    DESCRIPTION
        "Each entry contains the info for rogue device."
    ::= { fsDot11WIDSRogueInfoEntry 5 }

--*****************************************************************************
--*  fsDot11WIDSUserisolationPermitmaclist Definition
--*****************************************************************************

fsDot11WIDSPermitmaclistEnableTable OBJECT-TYPE
    SYNTAX      SEQUENCE OF FSDot11WIDSPermitmaclistEnableEntry
    MAX-ACCESS  not-accessible
    STATUS      current
    DESCRIPTION
        "The table provides vlan Permitmaclist for user-isolation."
    ::= { fsDot11WIDSConfigObjects 15 }

fsDot11WIDSPermitmaclistEnableEntry OBJECT-TYPE
    SYNTAX      FSDot11WIDSPermitmaclistEnableEntry
    MAX-ACCESS  not-accessible
    STATUS      current
    DESCRIPTION
        "Each entry contains vlan Permitmaclist for user-isolation."
    INDEX { fsDot11WIDSEnableVlanPermitmaclistNum }
    ::= { fsDot11WIDSPermitmaclistEnableTable 1 }

FSDot11WIDSPermitmaclistEnableEntry ::=
    SEQUENCE {
        fsDot11WIDSEnableVlanPermitmaclistNum  Integer32,
        fsDot11WIDSEnableVlanPermitmaclistOper Integer32,
        fsDot11WIDSEnableVlanPermitmaclist     MacAddress
    }

fsDot11WIDSEnableVlanPermitmaclistNum OBJECT-TYPE
    SYNTAX      Integer32
    MAX-ACCESS  not-accessible
    STATUS      current
    DESCRIPTION
        "Each entry contains vlan Permitmaclist number for user-isolation."
    ::= { fsDot11WIDSPermitmaclistEnableEntry 1 }

fsDot11WIDSEnableVlanPermitmaclistOper OBJECT-TYPE
    SYNTAX      Integer32
    MAX-ACCESS  read-write
    STATUS      current
    DESCRIPTION
        "Each entry contains vlan Permitmaclist operation for user-isolation."
    ::= { fsDot11WIDSPermitmaclistEnableEntry 2 }

fsDot11WIDSEnableVlanPermitmaclist OBJECT-TYPE
    SYNTAX      MacAddress
    MAX-ACCESS  read-write
    STATUS      current
    DESCRIPTION
        "Each entry contains vlan Permitmaclist for user-isolation."
    ::= { fsDot11WIDSPermitmaclistEnableEntry 3 }

--*****************************************************************************
--*  fsDot11WIDSResetStatistics Definition
--*****************************************************************************

fsDot11WIDSResetStatistics    OBJECT-TYPE
  SYNTAX                  TruthValue
  MAX-ACCESS              read-write
  STATUS                  current
  DESCRIPTION
  "This attribute set to clears all the statistics of attack detection information."
  ::= { fsDot11WIDSConfigObjects  18 }

--*****************************************************************************
--*  fsDot11WIDSResetRoguehistoryStatistics Definition
--*****************************************************************************

fsDot11WIDSResetRoguehistoryStatistics    OBJECT-TYPE
  SYNTAX                  Integer32
  MAX-ACCESS              read-write
  STATUS                  current
  DESCRIPTION
  "This attribute set to clears all the statistics of rogue information."
  ::= { fsDot11WIDSConfigObjects  19 }

--*****************************************************************************
--*  fsDot11WIDSResethistory Definition
--*****************************************************************************

fsDot11WIDSResethistory    OBJECT-TYPE
  SYNTAX                  Integer32
  MAX-ACCESS              read-write
  STATUS                  current
  DESCRIPTION
  "This attribute set to clears the history."
  ::= { fsDot11WIDSConfigObjects  20 }

--*****************************************************************************
--*  fsDot11WIDSResetDynamicBlacklisttable Definition
--*****************************************************************************

fsDot11WIDSResetDynamicBlacklistTable OBJECT-TYPE
    SYNTAX      SEQUENCE OF FSDot11WIDSResetDynamicBlacklistEntry
    MAX-ACCESS  not-accessible
    STATUS      current
    DESCRIPTION
        "The table descrips information about reseting wlan dynamic-blacklist."
    ::= { fsDot11WIDSConfigObjects 21 }

fsDot11WIDSResetDynamicBlacklistEntry OBJECT-TYPE
    SYNTAX      FSDot11WIDSResetDynamicBlacklistEntry
    MAX-ACCESS  not-accessible
    STATUS      current
    DESCRIPTION
        "Each entry contains information about reseting wlan dynamic-blacklist."
    INDEX { fsDot11WIDSResetDynamicBlacklistMac }
    ::= { fsDot11WIDSResetDynamicBlacklistTable 1 }

FSDot11WIDSResetDynamicBlacklistEntry ::=
    SEQUENCE {
        fsDot11WIDSResetDynamicBlacklistMac  MacAddress,
        fsDot11WIDSResetDynamicBlacklistType Integer32
    }

fsDot11WIDSResetDynamicBlacklistMac OBJECT-TYPE
    SYNTAX      MacAddress
    MAX-ACCESS  not-accessible
    STATUS      current
    DESCRIPTION
        "Each entry contains Macaddress."
    ::= { fsDot11WIDSResetDynamicBlacklistEntry 1 }

fsDot11WIDSResetDynamicBlacklistType OBJECT-TYPE
    SYNTAX      Integer32
    MAX-ACCESS  read-write
    STATUS      current
    DESCRIPTION
        "Each entry contains Macaddress."
    ::= { fsDot11WIDSResetDynamicBlacklistEntry 2 }


--*****************************************************************************
--*  fsDot11WIDResetUserisolationStatistics Definition
--*****************************************************************************

fsDot11WIDResetUserisolationStatistics OBJECT-TYPE
    SYNTAX Integer32
    MAX-ACCESS  read-write
    STATUS      current
    DESCRIPTION
        "Represents information about which vlanlist to reset user-isolation statistics."
    ::= { fsDot11WIDSConfigObjects 22 }


--*****************************************************************************
--*  fsDot11WIDSShowDot11IdsAttacklist Definition
--*****************************************************************************

fsDot11WIDSShowDot11IdsAttacklistTable OBJECT-TYPE
    SYNTAX      SEQUENCE OF FSDot11WIDSShowDot11IdsAttacklistEntry
    MAX-ACCESS  not-accessible
    STATUS      current
    DESCRIPTION
        "The table descrips information about reseting wlan dynamic-blacklist."
    ::= { fsDot11WIDSDetectObjects 1 }

fsDot11WIDSShowDot11IdsAttacklistEntry OBJECT-TYPE
    SYNTAX      FSDot11WIDSShowDot11IdsAttacklistEntry
    MAX-ACCESS  not-accessible
    STATUS      current
    DESCRIPTION
        "Each entry contains information about reseting wlan dynamic-blacklist."
    INDEX { fsDot11WIDSShowDot11IdsAttacklistNum }
    ::= { fsDot11WIDSShowDot11IdsAttacklistTable 1 }

FSDot11WIDSShowDot11IdsAttacklistEntry ::=
    SEQUENCE {
        fsDot11WIDSShowDot11IdsAttacklistNum  INTEGER,
        fsDot11WIDSShowDot11IdsAttacklistOper INTEGER,
        fsDot11WIDSShowDot11IdsAttacklistMac  MacAddress,
        fsDot11WIDSShowDot11IdsAttacklistInfo DisplayString
    }

fsDot11WIDSShowDot11IdsAttacklistNum OBJECT-TYPE
    SYNTAX      INTEGER
    MAX-ACCESS  not-accessible
    STATUS      current
    DESCRIPTION
        "Each entry contains Macaddress."
    ::= { fsDot11WIDSShowDot11IdsAttacklistEntry 1 }

fsDot11WIDSShowDot11IdsAttacklistOper OBJECT-TYPE
    SYNTAX      INTEGER
    MAX-ACCESS  read-write
    STATUS      current
    DESCRIPTION
        "Each entry contains operation."
    ::= { fsDot11WIDSShowDot11IdsAttacklistEntry 2 }

fsDot11WIDSShowDot11IdsAttacklistMac OBJECT-TYPE
    SYNTAX      MacAddress
    MAX-ACCESS  read-write
    STATUS      current
    DESCRIPTION
        "Each entry contains Macaddress."
    ::= { fsDot11WIDSShowDot11IdsAttacklistEntry 3 }

fsDot11WIDSShowDot11IdsAttacklistInfo OBJECT-TYPE
    SYNTAX      DisplayString (SIZE (0..255))
    MAX-ACCESS  read-write
    STATUS      current
    DESCRIPTION
         "Each entry contains info."
    ::= { fsDot11WIDSShowDot11IdsAttacklistEntry 4 }

--*****************************************************************************
--*  fsDot11WIDUserisolation Definition
--*****************************************************************************
fsDot11WIDUserisolationAC OBJECT-TYPE
    SYNTAX Integer32
    MAX-ACCESS  read-write
    STATUS      current
    DESCRIPTION
        "Represents information about user-isolation for AC."
    ::= { fsDot11WIDSConfigObjects 23 }

fsDot11WIDUserisolationAP OBJECT-TYPE
    SYNTAX Integer32
    MAX-ACCESS  read-write
    STATUS      current
    DESCRIPTION
        "Represents information about user-isolation for AP."
    ::= { fsDot11WIDSConfigObjects 24 }

--*****************************************************************************
--*  fsDot11WIDSShowStatics Definition
--*****************************************************************************

fsDot11WIDSShowStaticsTable OBJECT-TYPE
    SYNTAX      SEQUENCE OF FSDot11WIDSShowStaticsEntry
    MAX-ACCESS  not-accessible
    STATUS      current
    DESCRIPTION
        "The table contains statics."
    ::= { fsDot11WIDSConfigObjects 25 }

fsDot11WIDSShowStaticsEntry OBJECT-TYPE
    SYNTAX      FSDot11WIDSShowStaticsEntry
    MAX-ACCESS  not-accessible
    STATUS      current
    DESCRIPTION
        "The table contains statics."
    INDEX { fsDot11WIDSShowStaticsNum }
    ::= { fsDot11WIDSShowStaticsTable 1 }

FSDot11WIDSShowStaticsEntry ::=
    SEQUENCE {
        fsDot11WIDSShowStaticsNum  INTEGER,
        fsDot11WIDSShowStaticsOper INTEGER,
        fsDot11WIDSShowStaticsMac  MacAddress,
        fsDot11WIDSShowStaticsInfo DisplayString
    }

fsDot11WIDSShowStaticsNum OBJECT-TYPE
    SYNTAX      INTEGER
    MAX-ACCESS  not-accessible
    STATUS      current
    DESCRIPTION
        "Each entry contains Macaddress."
    ::= { fsDot11WIDSShowStaticsEntry 1 }

fsDot11WIDSShowStaticsOper OBJECT-TYPE
    SYNTAX      INTEGER
    MAX-ACCESS  read-write
    STATUS      current
    DESCRIPTION
        "Each entry contains operation."
    ::= { fsDot11WIDSShowStaticsEntry 2 }

fsDot11WIDSShowStaticsMac OBJECT-TYPE
    SYNTAX      MacAddress
    MAX-ACCESS  read-write
    STATUS      current
    DESCRIPTION
        "Each entry contains Macaddress."
    ::= { fsDot11WIDSShowStaticsEntry 3 }

fsDot11WIDSShowStaticsInfo OBJECT-TYPE
    SYNTAX      DisplayString (SIZE (0..255))
    MAX-ACCESS  read-write
    STATUS      current
    DESCRIPTION
        "Each entry contains info."
    ::= { fsDot11WIDSShowStaticsEntry 4 }
--********************************************************************
--*
--********************************************************************
fsDot11WIDSAssociationFailureTotalTimes  OBJECT-TYPE
    SYNTAX      INTEGER
    MAX-ACCESS  read-only
    STATUS      current
    DESCRIPTION
        " The total times the association fails."
    ::= { fsDot11WIDSConfigObjects 26 }
--********************************************************************
--*
--********************************************************************


--**************************************************
--* fsDot11WIDSSuspiciousAPInfoTable begins
--**************************************************
fsDot11WIDSSuspiciousAPInfoTable OBJECT-TYPE
    SYNTAX SEQUENCE OF FSDot11WIDSSuspiciousAPInfoEntry
    MAX-ACCESS not-accessible
    STATUS current
    DESCRIPTION
      "The table includes the information of the suspicious ap detected."
    ::={ fsDot11WIDSConfigObjects 27 }

fsDot11WIDSSuspiciousAPInfoEntry OBJECT-TYPE
    SYNTAX FSDot11WIDSSuspiciousAPInfoEntry
    MAX-ACCESS not-accessible
    STATUS current
    DESCRIPTION
      "The entry of the fsDot11WIDSSuspiciousAPInfoTable table."
    INDEX { fsDot11WIDSSuspiciousAPBSS }
    ::={ fsDot11WIDSSuspiciousAPInfoTable 1 }
    
FSDot11WIDSSuspiciousAPInfoEntry ::=
    SEQUENCE {
        fsDot11WIDSSuspiciousAPBSS                  MacAddress,
        fsDot11WIDSSuspiciousAPCount                INTEGER,
        fsDot11WIDSMomentFirstTimeDetectedSusAP     TimeTicks,
        fsDot11WIDSMomentLastTimeDetectedSusAP      TimeTicks,
        fsDot11WIDSSuspiciousAPSSID                 DisplayString,
        fsDot11WIDSSuspiciousAPMaxSignalStrength    INTEGER,
        fsDot11WIDSSuspiciousAPUsingChannel         INTEGER,
        fsDot11WIDSSuspiciousAPFrameEncrption       INTEGER,
        fsDot11WIDSSuspiciousAPNeedsDealingTag      TruthValue,
        fsDot11WIDSSuspiciousAPIgnoredTag           TruthValue
    }

fsDot11WIDSSuspiciousAPBSS OBJECT-TYPE
    SYNTAX  MacAddress
    MAX-ACCESS  read-only
    STATUS      current
    DESCRIPTION
        " The BSS MAC of the Suspicious AP."
    ::= { fsDot11WIDSSuspiciousAPInfoEntry 1 }

fsDot11WIDSSuspiciousAPCount OBJECT-TYPE
    SYNTAX  INTEGER
    MAX-ACCESS  read-only
    STATUS      current
    DESCRIPTION
        " The count of the Suspicious AP."
    ::= { fsDot11WIDSSuspiciousAPInfoEntry 2 }

fsDot11WIDSMomentFirstTimeDetectedSusAP OBJECT-TYPE
    SYNTAX  TimeTicks
    MAX-ACCESS  read-only
    STATUS      current
    DESCRIPTION
        " The moment when the AP is detected as the Suspicious AP at the first time."
    ::= { fsDot11WIDSSuspiciousAPInfoEntry 3 }

fsDot11WIDSMomentLastTimeDetectedSusAP OBJECT-TYPE
    SYNTAX  TimeTicks
    MAX-ACCESS  read-only
    STATUS      current
    DESCRIPTION
        " The moment when the AP is detected as the Suspicious AP at the last time."
    ::= { fsDot11WIDSSuspiciousAPInfoEntry 4 }

fsDot11WIDSSuspiciousAPSSID OBJECT-TYPE
    SYNTAX  DisplayString
    MAX-ACCESS  read-only
    STATUS      current
    DESCRIPTION
        " The SSID of the Suspicious AP."
    ::= { fsDot11WIDSSuspiciousAPInfoEntry 5 }

fsDot11WIDSSuspiciousAPMaxSignalStrength OBJECT-TYPE
    SYNTAX  INTEGER
    MAX-ACCESS  read-only
    STATUS      current
    DESCRIPTION
        " The max signal strength of the Suspicious AP."
    ::= { fsDot11WIDSSuspiciousAPInfoEntry 6 }

fsDot11WIDSSuspiciousAPUsingChannel OBJECT-TYPE
    SYNTAX  INTEGER
    MAX-ACCESS  read-only
    STATUS      current
    DESCRIPTION
        " The channel the Suspicious AP is in."
    ::= { fsDot11WIDSSuspiciousAPInfoEntry 7 }

fsDot11WIDSSuspiciousAPFrameEncrption OBJECT-TYPE
    SYNTAX  INTEGER
    MAX-ACCESS  read-only
    STATUS      current
    DESCRIPTION
        " The frame encrption of the Suspicious AP."
    ::= { fsDot11WIDSSuspiciousAPInfoEntry 8 }

fsDot11WIDSSuspiciousAPNeedsDealingTag OBJECT-TYPE
    SYNTAX  TruthValue
    MAX-ACCESS  read-only
    STATUS      current
    DESCRIPTION
        " The tag telling whether it needs to deal the Suspicious AP."
    ::= { fsDot11WIDSSuspiciousAPInfoEntry 9 }

fsDot11WIDSSuspiciousAPIgnoredTag OBJECT-TYPE
    SYNTAX  TruthValue
    MAX-ACCESS  read-only
    STATUS      current
    DESCRIPTION
        " The tag telling whether to ignore the Suspicious AP."
    ::= { fsDot11WIDSSuspiciousAPInfoEntry 10 }

--**************************************************
--* fsDot11WIDSSuspiciousAPInfoTable begins
--**************************************************    
    
--**************************************************
--* fsDot11WIDSSuspiciousSTAInfoTable begins
--**************************************************

fsDot11WIDSSuspiciousSTAInfoTable OBJECT-TYPE
    SYNTAX SEQUENCE OF FSDot11WIDSSuspiciousSTAInfoEntry
    MAX-ACCESS not-accessible
    STATUS current
    DESCRIPTION
      "The table includes the information of the suspicious STA detected."
    ::={ fsDot11WIDSConfigObjects 28 }

fsDot11WIDSSuspiciousSTAInfoEntry OBJECT-TYPE
    SYNTAX FSDot11WIDSSuspiciousSTAInfoEntry
    MAX-ACCESS not-accessible
    STATUS current
    DESCRIPTION
      "The entry of the fsDot11WIDSSuspiciousSTAInfoTable table."
    INDEX { fsDot11WIDSSuspiciousSTAMAC }
    ::={ fsDot11WIDSSuspiciousSTAInfoTable 1 }
    
FSDot11WIDSSuspiciousSTAInfoEntry ::=
    SEQUENCE {        
        fsDot11WIDSSuspiciousSTAMAC                 MacAddress,
        fsDot11WIDSAPCountDetectingSuspiciousSTA    INTEGER,
        fsDot11WIDSMomentFirstTimeDetectedSusSTA    TimeTicks,
        fsDot11WIDSMomentLastTimeDetectedSusSTA     TimeTicks,
        fsDot11WIDSBSSIDSuspiciousSTAAccessing      MacAddress,
        fsDot11WIDSSuspiciousSTAMaxSignalStrength   INTEGER,
        fsDot11WIDSSuspiciousSTAUsingChannel        INTEGER,
        fsDot11WIDSSuspiciousSTAWorksInAdhocMode    TruthValue,
        fsDot11WIDSSuspiciousSTANeedsDealingTag     TruthValue,
        fsDot11WIDSSuspiciousSTAIgnoredTag          TruthValue
    }

fsDot11WIDSSuspiciousSTAMAC OBJECT-TYPE
    SYNTAX  MacAddress
    MAX-ACCESS  read-only
    STATUS      current
    DESCRIPTION
        " The MAC of the the Suspicious STA."
    ::= { fsDot11WIDSSuspiciousSTAInfoEntry 1 }

fsDot11WIDSAPCountDetectingSuspiciousSTA OBJECT-TYPE
    SYNTAX  INTEGER
    MAX-ACCESS  read-only
    STATUS      current
    DESCRIPTION
        " The AP count which is detecting the Suspicious STA."
    ::= { fsDot11WIDSSuspiciousSTAInfoEntry 2 }

fsDot11WIDSMomentFirstTimeDetectedSusSTA OBJECT-TYPE
    SYNTAX  TimeTicks
    MAX-ACCESS  read-only
    STATUS      current
    DESCRIPTION
        " The moment when the STA is detected as the Suspicious STA at the first time."
    ::= { fsDot11WIDSSuspiciousSTAInfoEntry 3 }

fsDot11WIDSMomentLastTimeDetectedSusSTA OBJECT-TYPE
    SYNTAX  TimeTicks
    MAX-ACCESS  read-only
    STATUS      current
    DESCRIPTION
        " The moment when the AP is detected as the Suspicious AP at the last time."
    ::= { fsDot11WIDSSuspiciousSTAInfoEntry 4 }

fsDot11WIDSBSSIDSuspiciousSTAAccessing OBJECT-TYPE
    SYNTAX  MacAddress
    MAX-ACCESS  read-only
    STATUS      current
    DESCRIPTION
        " The BSSID which the the Suspicious STA is trying to access."
    ::= { fsDot11WIDSSuspiciousSTAInfoEntry 5 }

fsDot11WIDSSuspiciousSTAMaxSignalStrength OBJECT-TYPE
    SYNTAX  INTEGER
    MAX-ACCESS  read-only
    STATUS      current
    DESCRIPTION
        " The max signal strength of the Suspicious STA."
    ::= { fsDot11WIDSSuspiciousSTAInfoEntry 6 }

fsDot11WIDSSuspiciousSTAUsingChannel OBJECT-TYPE
    SYNTAX  INTEGER
    MAX-ACCESS  read-only
    STATUS      current
    DESCRIPTION
        " The channel the Suspicious sta is in."
    ::= { fsDot11WIDSSuspiciousSTAInfoEntry 7 }

fsDot11WIDSSuspiciousSTAWorksInAdhocMode OBJECT-TYPE
    SYNTAX  TruthValue
    MAX-ACCESS  read-only
    STATUS      current
    DESCRIPTION
        " The tag whether the Suspicious STA is working in the Ad hoc mode."
    ::= { fsDot11WIDSSuspiciousSTAInfoEntry 8 }


fsDot11WIDSSuspiciousSTANeedsDealingTag OBJECT-TYPE
    SYNTAX  TruthValue
    MAX-ACCESS  read-only
    STATUS      current
    DESCRIPTION
        " The tag telling whether it needs to deal the Suspicious STA."
    ::= { fsDot11WIDSSuspiciousSTAInfoEntry 9 }

fsDot11WIDSSuspiciousSTAIgnoredTag OBJECT-TYPE
    SYNTAX  TruthValue
    MAX-ACCESS  read-write
    STATUS      current
    DESCRIPTION
        " The tag telling whether to ignore the Suspicious STA."
    ::= { fsDot11WIDSSuspiciousSTAInfoEntry 10 }

--**************************************************
--* fsDot11WIDSSuspiciousSTAInfoTable ends
--**************************************************

--*******************************************************************
--* traps begin here
--*******************************************************************
--*************************************************************
--*************************************************************
fsDot11WIDSTraps OBJECT IDENTIFIER ::= { fsDot11WIDSMIB 0}
fsDot11WIDSTrapsObjects OBJECT IDENTIFIER ::= { fsDot11WIDSMIB 3 }

fsDot11WIDSWirelessUserConnect NOTIFICATION-TYPE
    OBJECTS {
        fsDot11WIDSSTAMAC,
        fsDot11WIDSAPBSSID,
        fsDot11WIDSInformation,
        fsDot11WIDSextinfo
    }
    STATUS  current
    DESCRIPTION
            "trap of 802.11 connection, tell the receiver information
             as follow: STAMAC, BSSID, Information need."
    ::= { fsDot11WIDSTraps 1 }
    
fsDot11WIDSWirelessUserDisconnect NOTIFICATION-TYPE
    OBJECTS {
        fsDot11WIDSSTAMAC,
        fsDot11WIDSAPBSSID,
        fsDot11WIDSInformation,
        fsDot11WIDSextinfo
    }
    STATUS  current
    DESCRIPTION
            "trap of 802.11 disconnection, tell the receiver information
             as follow: STAMAC, BSSID, Information need."
    ::= { fsDot11WIDSTraps 2 }

fsDot11WIDSWirelessUserReauthentication NOTIFICATION-TYPE
    OBJECTS {
        fsDot11WIDSSTAMAC,
        fsDot11WIDSAPBSSID,
        fsDot11WIDSInformation,
        fsDot11WIDSextinfo
    }
    STATUS  current
    DESCRIPTION
            "trap of 802.11 re-authentication, tell the receiver information
             as follow: STAMAC, BSSID, Information need."
    ::= { fsDot11WIDSTraps 3 }
    
fsDot11WIDSWirelessUserAuthenticationFailure NOTIFICATION-TYPE
    OBJECTS {
        fsDot11WIDSSTAMAC,
        fsDot11WIDSAPBSSID,
        fsDot11WIDSInformation,
        fsDot11WIDSextinfo
    }
    STATUS  current
    DESCRIPTION
            "trap of the failure of802.11 authentication, tell the receiver 
             information as follow: STAMAC, BSSID, Information need."
    ::= { fsDot11WIDSTraps 4 }

fsDot11WIDSWirelessUserConnectFailure NOTIFICATION-TYPE
    OBJECTS {
        fsDot11WIDSSTAMAC,
        fsDot11WIDSAPBSSID,
        fsDot11WIDSInformation,
        fsDot11WIDSextinfo
    }
    STATUS  current
    DESCRIPTION
            "trap of the failure of 802.11 connection, tell the receiver information
             as follow: STAMAC, BSSID, Information need."
    ::= { fsDot11WIDSTraps 5 }
  
--*************************************************************************
--*************************************************************************
fsDot11WIDSDevice NOTIFICATION-TYPE
    OBJECTS {
        fsDot11WIDSDeviceInfoNUM,
        fsDot11WIDSDeviceInfoTYPE,
        fsDot11WIDSDeviceInfoOper,
        fsDot11WIDSDeviceInfoMAC,
        fsDot11WIDSDeviceInfoString
    }
    STATUS  current
    DESCRIPTION
            "The information of an event of a device, which can be a rogue ap,  a debious ap,
            a friendly ap, a rogue ad hoc, a debious ad hoc, a friendly ad hoc, a rogue sta,
            a debious sta, a friendly sta or an attacking device."
    ::= { fsDot11WIDSTraps 6 } 
    
fsDot11WIDSSuspiciousDeviceTrap NOTIFICATION-TYPE
    OBJECTS {
        fsDot11WIDSSuspiciousDeviceMac,
        fsDot11WIDSSuspiciousDeviceExtensionInfo
    }
    STATUS  current
    DESCRIPTION
            " This trap will be sent at once when detecting an suspicious ap or sta."
    ::= { fsDot11WIDSTraps 7 }

fsDot11WIDSUnauthorizedSSIDTrap NOTIFICATION-TYPE
    OBJECTS {
        fsDot11WIDSUnauthorizedSSID,
        fsDot11WIDSSUnauthorizedSSIDExtensionInfo
    }
    STATUS  current
    DESCRIPTION
            " This trap will be sent at once when detecting an unauthorized SSID
            which is not in the permitted ssid list."
    ::= { fsDot11WIDSTraps 8 }

fsDot11WIDSDetectingAttackTrap NOTIFICATION-TYPE
    OBJECTS {
        fsDot11WIDSAttackingDeviceMac,
        fsDot11WIDSAttackType,
        fsDot11WIDSAttackExtensionInfo
    }
    STATUS  current
    DESCRIPTION
            " This trap will be sent at once when detecting an attack, such as flood
            attack, spoof attack, and so on."
    ::= { fsDot11WIDSTraps 9 }

fsDot11WIDSSTAMAC OBJECT-TYPE
    SYNTAX      MacAddress
    MAX-ACCESS  read-write
    STATUS      current
    DESCRIPTION
        "MAC address of the STA."
    ::= { fsDot11WIDSTrapsObjects 1 }

fsDot11WIDSAPBSSID OBJECT-TYPE
    SYNTAX      DisplayString(SIZE (0..255))
    MAX-ACCESS  read-write
    STATUS      current
    DESCRIPTION
        "BSSID of AP."
    ::= { fsDot11WIDSTrapsObjects 2 }

fsDot11WIDSInformation OBJECT-TYPE
    SYNTAX      DisplayString(SIZE (0..255))
    MAX-ACCESS  read-write
    STATUS      current
    DESCRIPTION
        "Information to be commited."
    ::= { fsDot11WIDSTrapsObjects 3 }

fsDot11WIDSextinfo OBJECT-TYPE
    SYNTAX      DisplayString(SIZE (0..255))
    MAX-ACCESS  read-write
    STATUS      current
    DESCRIPTION
        "Extensive information to be commited."
    ::= { fsDot11WIDSTrapsObjects 4 }

fsDot11WIDSDeviceInfoNUM OBJECT-TYPE
    SYNTAX      Integer32
    MAX-ACCESS  read-write
    STATUS      current
    DESCRIPTION
        "Each entry contains the number for rogue device."
    ::= { fsDot11WIDSTrapsObjects 5 }

fsDot11WIDSDeviceInfoTYPE OBJECT-TYPE
    SYNTAX      Integer32
    MAX-ACCESS  read-write
    STATUS      current
    DESCRIPTION
        "Each entry contains the type for rogue device ."
    ::= { fsDot11WIDSTrapsObjects 6 }

fsDot11WIDSDeviceInfoOper OBJECT-TYPE
    SYNTAX      Integer32
    MAX-ACCESS  read-write
    STATUS      current
    DESCRIPTION
        "Each entry contains the operation for rogue device ."
    ::= { fsDot11WIDSTrapsObjects 7 }

fsDot11WIDSDeviceInfoMAC OBJECT-TYPE
    SYNTAX      MacAddress
    MAX-ACCESS  read-write
    STATUS      current
    DESCRIPTION
        "Each entry contains the mac for rogue device ."
    ::= { fsDot11WIDSTrapsObjects 8 }

fsDot11WIDSDeviceInfoString OBJECT-TYPE
    SYNTAX      DisplayString (SIZE (0..255))
    MAX-ACCESS  read-write
    STATUS      current
    DESCRIPTION
        "Each entry contains the info for rogue device."
    ::= { fsDot11WIDSTrapsObjects 9 }     
    
fsDot11WIDSSuspiciousDeviceMac OBJECT-TYPE
    SYNTAX      MacAddress
    MAX-ACCESS  read-write
    STATUS      current
    DESCRIPTION
        " The macaddress of the suspicious device."
    ::= { fsDot11WIDSTrapsObjects 10 }

fsDot11WIDSSuspiciousDeviceExtensionInfo OBJECT-TYPE
    SYNTAX      DisplayString
    MAX-ACCESS  read-write
    STATUS      current
    DESCRIPTION
        " The information left for the future extension."
    ::= { fsDot11WIDSTrapsObjects 11 }

fsDot11WIDSUnauthorizedSSID OBJECT-TYPE
    SYNTAX      DisplayString
    MAX-ACCESS  read-write
    STATUS      current
    DESCRIPTION
        " The macaddress of the suspicious device."
    ::= { fsDot11WIDSTrapsObjects 12 }

fsDot11WIDSSUnauthorizedSSIDExtensionInfo OBJECT-TYPE
    SYNTAX      DisplayString
    MAX-ACCESS  read-write
    STATUS      current
    DESCRIPTION
        " The information left for the future extension."
    ::= { fsDot11WIDSTrapsObjects 13 }

fsDot11WIDSAttackingDeviceMac OBJECT-TYPE
    SYNTAX      MacAddress
    MAX-ACCESS  read-write
    STATUS      current
    DESCRIPTION
        " The macaddress of the suspicious device."
    ::= { fsDot11WIDSTrapsObjects 14 }

fsDot11WIDSAttackType OBJECT-TYPE
    SYNTAX      INTEGER
    MAX-ACCESS  read-write
    STATUS      current
    DESCRIPTION
        " The information left for the future extension."
    ::= { fsDot11WIDSTrapsObjects 15 }
    
fsDot11WIDSAttackExtensionInfo OBJECT-TYPE
    SYNTAX      DisplayString
    MAX-ACCESS  read-write
    STATUS      current
    DESCRIPTION
        " The information left for the future extension."
    ::= { fsDot11WIDSTrapsObjects 16 }

--*******************************************************************
--* traps end here
--*******************************************************************

--********************************************************************
--*    Compliance statements
--********************************************************************
fsDot11WIDSMIBConform OBJECT IDENTIFIER ::= { fsDot11WIDSMIB 4 }

fsDot11WIDSMIBCompliances OBJECT IDENTIFIER ::= { fsDot11WIDSMIBConform 1 }

fsDot11WIDSMIBGroups      OBJECT IDENTIFIER ::= { fsDot11WIDSMIBConform 2 }

fsDot11WIDSMIBCompliance MODULE-COMPLIANCE
    STATUS  current
    DESCRIPTION
        "The compliance statement for entities which implement
        the dot11 wids module of FS Ac device Manager"
    MODULE
    MANDATORY-GROUPS {
        fsDot11WIDSMIBGroup
    }
    ::= { fsDot11WIDSMIBCompliances 1 }

--********************************************************************
--*    Units of conformance
--********************************************************************

fsDot11WIDSMIBGroup OBJECT-GROUP
    OBJECTS {
        fsDot11VendorOper,
        fsDot11VendorName,
        fsDot11PermitOper,
        fsDot11PermitSSID,
        fsDot11AttackOper,
        fsDot11AttackMAC,
        fsDot11AttackInfo,
        fsDot11PermitMACOper,
        fsDot11PermitMACAddr,
        fsDot11WIDSDeviceagingDuration,
        fsDot11WIDSCountermeasuresMode,
        fsDot11WIDSCountermeasureSet,
        fsDot11WIDSDeviceMode,
        fsDot11WhitelistOper,
        fsDot11WhitelistMAC,
        fsDot11StaticblacklistOper,
        fsDot11StaticblacklistMAC,
        fsDot11WIDSDynamicblacklistEnable,
        fsDot11WIDSDynamicblacklistLifetime,
        fsDot11WIDSAttackDetectionMode,
        fsDot11WIDSRogueInfoOper,
        fsDot11WIDSRogueInfoMAC,
        fsDot11WIDSRogueInfoString,
        fsDot11WIDSEnableVlanPermitmaclistOper,
        fsDot11WIDSEnableVlanPermitmaclist,
        fsDot11WIDSResetStatistics,
        fsDot11WIDSResetRoguehistoryStatistics,
        fsDot11WIDSResethistory,
        fsDot11WIDSResetDynamicBlacklistType,
        fsDot11WIDResetUserisolationStatistics,
        fsDot11WIDSShowDot11IdsAttacklistOper,
        fsDot11WIDSShowDot11IdsAttacklistMac,
        fsDot11WIDSShowDot11IdsAttacklistInfo,
        fsDot11WIDUserisolationAC,
        fsDot11WIDUserisolationAP,
        fsDot11WIDSShowStaticsOper,
        fsDot11WIDSShowStaticsMac,
        fsDot11WIDSShowStaticsInfo,
        fsDot11WIDSAssociationFailureTotalTimes,
        fsDot11WIDSSuspiciousAPCount,
        fsDot11WIDSMomentFirstTimeDetectedSusAP,
        fsDot11WIDSMomentLastTimeDetectedSusAP,
        fsDot11WIDSSuspiciousAPSSID,
        fsDot11WIDSSuspiciousAPMaxSignalStrength,
        fsDot11WIDSSuspiciousAPUsingChannel,
        fsDot11WIDSSuspiciousAPFrameEncrption,
        fsDot11WIDSSuspiciousAPNeedsDealingTag,
        fsDot11WIDSSuspiciousAPIgnoredTag,
        fsDot11WIDSAPCountDetectingSuspiciousSTA,
        fsDot11WIDSMomentFirstTimeDetectedSusSTA,
        fsDot11WIDSMomentLastTimeDetectedSusSTA,
        fsDot11WIDSBSSIDSuspiciousSTAAccessing,
        fsDot11WIDSSuspiciousSTAMaxSignalStrength,
        fsDot11WIDSSuspiciousSTAUsingChannel,
        fsDot11WIDSSuspiciousSTAWorksInAdhocMode,
        fsDot11WIDSSuspiciousSTANeedsDealingTag,
        fsDot11WIDSSuspiciousSTAIgnoredTag,
        fsDot11WIDSSuspiciousDeviceMac,
        fsDot11WIDSSuspiciousDeviceExtensionInfo,
        fsDot11WIDSUnauthorizedSSID,
        fsDot11WIDSSUnauthorizedSSIDExtensionInfo,
        fsDot11WIDSAttackingDeviceMac,
        fsDot11WIDSAttackType,
        fsDot11WIDSAttackExtensionInfo,        
        fsDot11WIDSSTAMAC,
        fsDot11WIDSAPBSSID,
        fsDot11WIDSInformation,
        fsDot11WIDSextinfo,        
        fsDot11WIDSDeviceInfoNUM,
        fsDot11WIDSDeviceInfoTYPE,
        fsDot11WIDSDeviceInfoOper,
        fsDot11WIDSDeviceInfoMAC,
        fsDot11WIDSDeviceInfoString
    }
    STATUS     current
    DESCRIPTION
            "This collection of objects represents the
             dot11 wids private MIB "
    ::= { fsDot11WIDSMIBGroups 1 }



END

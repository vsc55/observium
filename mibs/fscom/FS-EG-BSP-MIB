-- *****************************************************************
-- FS-EG-BSP-MIB.mib:  FS EG Bsp MIB file
--
-- March 2016, xiahongliang
--
-- Copyright (c) 2016 by FS.COM Inc..
-- All rights reserved.
-- 
-- *****************************************************************
--

FS-EG-BSP-MIB DEFINITIONS ::= BEGIN

IMPORTS
        MODULE-IDENTITY,
        OBJECT-TYPE,
        NOTIFICATION-TYPE,
        Integer32
                FROM SNMPv2-SMI
        DisplayString,
        MacAddress
                FROM SNMPv2-TC
        MODULE-COMPLIANCE,
        OBJECT-GROUP,
        NOTIFICATION-GROUP
                FROM SNMPv2-CONF
        fsMgmt
                FROM FS-SMI;
				
fsEgBspMIB MODULE-IDENTITY
	LAST-UPDATED "201602190000Z"
	ORGANIZATION "FS.COM Inc.."
	CONTACT-INFO
        " 
		    Tel: 400-865-2852 

		    E-mail: https://www.fs.com/live_chat_service_mail.html"
	DESCRIPTION
		"This module defines fs eg bsp mibs."
	REVISION      "201602190000Z"
	DESCRIPTION
		"Initial version of this MIB module."
	::= { fsMgmt 147}

fsEgBspMIBObjects OBJECT IDENTIFIER ::= { fsEgBspMIB 1 }

fsEgBspMaxNumber OBJECT-TYPE
        SYNTAX Integer32
        MAX-ACCESS read-only
        STATUS current
        DESCRIPTION
            "Max number of the mac info of the eg bsp permitting."
        ::= { fsEgBspMIBObjects 1 }

fsEgBspInfoTable OBJECT-TYPE
        SYNTAX SEQUENCE OF FSEgBspInfoEntry
        MAX-ACCESS not-accessible
        STATUS current
        DESCRIPTION
            "Mac Info List of devices."
        ::= { fsEgBspMIBObjects 2 }

fsEgBspInfoEntry OBJECT-TYPE
        SYNTAX FSEgBspInfoEntry
        MAX-ACCESS not-accessible
        STATUS current
        DESCRIPTION
            "Entry of a device mac information."
        INDEX { fsEgBspInfoMacAddress, fsEgBspInfoVlanID, fsEgBspInfoPort }
        ::= { fsEgBspInfoTable 1 }

FSEgBspInfoEntry ::=
        SEQUENCE {
                fsEgBspInfoMacAddress MacAddress,
                fsEgBspInfoVlanID Integer32,
				fsEgBspInfoPort Integer32,
				fsEgBspInfoAge Integer32
        }

fsEgBspInfoMacAddress OBJECT-TYPE
          SYNTAX  MacAddress
          MAX-ACCESS read-only
          STATUS current
          DESCRIPTION
            "The physical address of device."
          ::= { fsEgBspInfoEntry 1 }

fsEgBspInfoVlanID OBJECT-TYPE
        SYNTAX Integer32
        MAX-ACCESS read-only
        STATUS current
        DESCRIPTION
            "The vlan ID."
        ::= { fsEgBspInfoEntry 2 }

fsEgBspInfoPort OBJECT-TYPE
        SYNTAX Integer32
        MAX-ACCESS read-only
        STATUS current
        DESCRIPTION
            "The port number."
        ::= { fsEgBspInfoEntry 3 }

fsEgBspInfoAge OBJECT-TYPE
        SYNTAX Integer32
        MAX-ACCESS read-only
        STATUS current
        DESCRIPTION
            "relearning or not."
        ::= { fsEgBspInfoEntry 4 }

fsEgBspMIBConformance OBJECT IDENTIFIER ::= { fsEgBspMIB 2 }
fsEgBspMIBCompliances OBJECT IDENTIFIER ::= { fsEgBspMIBConformance 1 }
fsEgBspMIBGroups      OBJECT IDENTIFIER ::= { fsEgBspMIBConformance 2 }


-- compliance statements

fsEgBspMIBCompliance MODULE-COMPLIANCE
        STATUS  current
        DESCRIPTION
                "The compliance statement for entities which implement the FS Eg Bsp MIB"
        MODULE  -- this module
                MANDATORY-GROUPS { fsEgBspMIBGroup
                 }
        ::= { fsEgBspMIBCompliances 1 }
                
-- units of conformance

fsEgBspMIBGroup OBJECT-GROUP
        OBJECTS {
            fsEgBspMaxNumber,
            fsEgBspInfoMacAddress,
            fsEgBspInfoVlanID,
            fsEgBspInfoPort,
            fsEgBspInfoAge
        }
        STATUS  current
        DESCRIPTION
                "A collection of objects accessing device information of the eg learning ."
        ::= { fsEgBspMIBGroups 1 }    

END

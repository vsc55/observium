-- *****************************************************************
-- FS-TRAP-FORMAT-MIB.mib:  FS TRAP FORMAT MIB file
--
-- May 2011, Panshiyong
--
-- Copyright(c) 2011 by FS.COM Inc..
-- All rights reserved.
-- 
-- *****************************************************************
--

FS-TRAP-FORMAT-MIB DEFINITIONS ::= BEGIN

IMPORTS
        MODULE-IDENTITY,
        OBJECT-TYPE,
        TimeTicks,
        Unsigned32,
        IpAddress
                FROM SNMPv2-SMI
        Counter
                FROM RFC1155-SMI
        DisplayString
                FROM SNMPv2-TC
        MODULE-COMPLIANCE,
        OBJECT-GROUP
                FROM SNMPv2-CONF
        fsMgmt
                FROM FS-SMI;

fsTrapFormatMIB MODULE-IDENTITY
        LAST-UPDATED "201105110000Z"
        ORGANIZATION "FS.COM Inc.."
        CONTACT-INFO
                " 
                Tel: 400-865-2852 

                E-mail: https://www.fs.com/live_chat_service_mail.html"
        DESCRIPTION
                "This module defines fs trap-format mibs."
        REVISION      "201105110000Z"
        DESCRIPTION
                "Initial version of this MIB module."
        ::= { fsMgmt 97 }


fsTrapFormatMIBObjects OBJECT IDENTIFIER ::= { fsTrapFormatMIB 1 }


--**********************************************************************
-- fs Trap Format MIB info 
--**********************************************************************
fsTrapFormatTrapSerialNo OBJECT-TYPE
    SYNTAX DisplayString(SIZE (1..32))
    MAX-ACCESS read-only
    STATUS current
    DESCRIPTION
        "Serial NO. of trap informations."
    ::= { fsTrapFormatMIBObjects 1 }

fsTrapFormatTrapLevel OBJECT-TYPE
    SYNTAX DisplayString(SIZE (1..32))
    MAX-ACCESS read-only
    STATUS current
    DESCRIPTION
        "Original level of trap informations:
         1 - critical,
         2 - major,
         3 - minor,
         4 - normal,
         5 - uncertain.
        "
    ::= { fsTrapFormatMIBObjects 2 }

fsTrapFormatTrapType OBJECT-TYPE
    SYNTAX DisplayString(SIZE (1..32))
    MAX-ACCESS read-only
    STATUS current
    DESCRIPTION
        "Original type of trap informations:
         1 - Communication Trap,
         2 - Environment Trap,
         3 - Device Trap,
         4 - Process Error Trap,
         5 - Quality of Service Trap.
        "
    ::= { fsTrapFormatMIBObjects 3 }

fsTrapFormatTrapReasonNo OBJECT-TYPE
    SYNTAX INTEGER
    MAX-ACCESS read-only
    STATUS current
    DESCRIPTION
        "Reason NO. of trap informations."
    ::= { fsTrapFormatMIBObjects 4 }

fsTrapFormatTrapReasons OBJECT-TYPE
    SYNTAX DisplayString(SIZE (1..64))
    MAX-ACCESS read-only
    STATUS current
    DESCRIPTION
        "Reasons of trap informations."
    ::= { fsTrapFormatMIBObjects 5 }

fsTrapFormatTrapStatus OBJECT-TYPE
    SYNTAX INTEGER
    MAX-ACCESS read-only
    STATUS current
    DESCRIPTION
        "Status of trap informations:
         1 - active,
         0 - eliminate.
        "
    ::= { fsTrapFormatMIBObjects 6 }

fsTrapFormatTrapTitle OBJECT-TYPE
    SYNTAX DisplayString(SIZE (1..64))
    MAX-ACCESS read-only
    STATUS current
    DESCRIPTION
        "Title of trap informations."
    ::= { fsTrapFormatMIBObjects 7 }

fsTrapFormatTrapContent OBJECT-TYPE
    SYNTAX DisplayString(SIZE (1..64))
    MAX-ACCESS read-only
    STATUS current
    DESCRIPTION
        "Content of trap informations."
    ::= { fsTrapFormatMIBObjects 8 }

fsTrapFormatTrapTime OBJECT-TYPE
    SYNTAX Counter
    MAX-ACCESS read-only
    STATUS current
    DESCRIPTION
        "The time (in seconds) since the trap alarm occurred 
         of the system was last re-initialized."
    ::= { fsTrapFormatMIBObjects 9 }
	
fsTrapFormatTrapSlotInfo OBJECT-TYPE
    SYNTAX DisplayString
    MAX-ACCESS read-only
    STATUS current
    DESCRIPTION
        "The slot info(1/2 or 2) of slot that send trap."
    ::= { fsTrapFormatMIBObjects 10 }
	
fsTrapFormatTrapVendorId OBJECT-TYPE
    SYNTAX INTEGER
    MAX-ACCESS read-only
    STATUS current
    DESCRIPTION
        "The vendor id of the send trap."
    ::= { fsTrapFormatMIBObjects 11 }
    
fsTrapFormatTrapSerialNum OBJECT-TYPE
    SYNTAX DisplayString(SIZE (1..64))
    MAX-ACCESS read-only
    STATUS current
    DESCRIPTION
        "The serial number of the send trap."
    ::= { fsTrapFormatMIBObjects 12 }   

fsTrapFormatTrapDateTime OBJECT-TYPE
    SYNTAX DisplayString(SIZE (1..64))
    MAX-ACCESS read-only
    STATUS current
    DESCRIPTION
        "The date time when the trap occurred ."
    ::= { fsTrapFormatMIBObjects 13 }       
    
--**********************************************************************
-- about conformance info 
--**********************************************************************
fsTrapFormatMIBConformance OBJECT IDENTIFIER ::= { fsTrapFormatMIB 2 }
fsTrapFormatMIBCompliances OBJECT IDENTIFIER ::= { fsTrapFormatMIBConformance 1 }
fsTrapFormatMIBGroups      OBJECT IDENTIFIER ::= { fsTrapFormatMIBConformance 2 }

-- compliance statements
fsTrapFormatMIBCompliance MODULE-COMPLIANCE
    STATUS  current
    DESCRIPTION
        "The compliance statement for entities which implement
         the FS Trap Format MIB"
    MODULE  
    MANDATORY-GROUPS { 
        fsTrapFormatMIBGroup
    }
    ::= { fsTrapFormatMIBCompliances 1 }
                
-- units of conformance
fsTrapFormatMIBGroup OBJECT-GROUP
        OBJECTS {
            fsTrapFormatTrapSerialNo,
            fsTrapFormatTrapLevel,
            fsTrapFormatTrapType,
            fsTrapFormatTrapReasonNo,
            fsTrapFormatTrapReasons,
            fsTrapFormatTrapStatus,
            fsTrapFormatTrapTitle,
            fsTrapFormatTrapContent,
            fsTrapFormatTrapTime,
			fsTrapFormatTrapSlotInfo,
            fsTrapFormatTrapVendorId,
            fsTrapFormatTrapSerialNum,
            fsTrapFormatTrapDateTime
        }
        STATUS  current
        DESCRIPTION
                "A collection of objects providing Capwap App configure."
        ::= { fsTrapFormatMIBGroups 1 }
        
END

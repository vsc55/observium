NSCRTV-EPON-PON-PORT-MIB DEFINITIONS ::= BEGIN

IMPORTS
    MODULE-IDENTITY, OBJECT-TYPE, Counter32, Unsigned32, TimeTicks
        FROM SNMPv2-SMI
    DateAndTime, MacAddress, TimeStamp, RowStatus, TruthValue, DisplayString, TEXTUAL-CONVENTION
        FROM SNMPv2-TC
    EponDeviceIndex, EponCardIndex, EponPortIndex, EponAlarmCode, EponAlarmInstance, EponSeverityType,
    AutoNegotiationTechAbility, TAddress, EponStats15MinRecordType, EponStats24HourRecordType, EponStatsThresholdType
		FROM NSCRTV-EPONEOC-EPON-MIB
    ponPortObjects
        FROM NSCRTV-EPONEOC-EPON-MIB;

--------------------------------------------------------------------------------
--  ponPortObjects[PON端口属性管理项](1.3.6.1.4.1.17409.2.3.3)
-------------------------------------------------------------------------------- 
    ponPortInfoTable OBJECT-TYPE
      SYNTAX SEQUENCE OF PonPortInfoEntry
      MAX-ACCESS not-accessible
      STATUS current
      DESCRIPTION
        "PON端口配置信息表"
      ::= { ponPortObjects 1 }
    
    ponPortInfoEntry OBJECT-TYPE
      SYNTAX PonPortInfoEntry
      MAX-ACCESS not-accessible
      STATUS current
      DESCRIPTION     " "
      INDEX { ponDeviceIndex, ponCardIndex, ponPortIndex}
      ::= { ponPortInfoTable 1 }
    
    PonPortInfoEntry ::=
      SEQUENCE { 
        ponDeviceIndex
          INTEGER,
        ponCardIndex
          EponCardIndex,
        ponPortIndex
          EponPortIndex,
        ponPortType
          INTEGER,
        ponOperationStatus
          INTEGER,
        ponPortAdminStatus
          INTEGER,
        ponPortMaxOnuNumSupport
          INTEGER,
        ponPortUpOnuNum
          INTEGER,
        ponPortEncryptMode
          INTEGER,
        ponPortEncryptKeyExchangeTime
          INTEGER,
        ponPortIsolationEnable
          TruthValue,
        maxDsBandwidth
          INTEGER,
        actualDsBandwidthInUse
          INTEGER,
        remainDsBandwidth
          INTEGER,
        perfStats15minuteEnable
          TruthValue,
        perfStats24hourEnable
          TruthValue,
        ponPortMacAddrLearnMaxNum
          INTEGER,
        maxUsBandwidth
          INTEGER,
        actualUsBandwidthInUse
          INTEGER,
        remainUsBandwidth
          INTEGER
       }

    ponDeviceIndex  OBJECT-TYPE
      SYNTAX INTEGER
      MAX-ACCESS not-accessible
      STATUS current
      DESCRIPTION
        "
        OLT设备索引号。        
        一个OLT节点可以由多台OLT设备组成。节点内的每台OLT设备由OLT设备索引号唯一标识"
      ::= { ponPortInfoEntry 1 }
    ponCardIndex  OBJECT-TYPE
      SYNTAX EponCardIndex
      MAX-ACCESS not-accessible
      STATUS current
      DESCRIPTION
        "
        板卡索引号"
      ::= { ponPortInfoEntry 2 }

    ponPortIndex  OBJECT-TYPE
      SYNTAX EponPortIndex
      MAX-ACCESS not-accessible
      STATUS current
      DESCRIPTION
        "
        pon端口索引号"
      ::= { ponPortInfoEntry 3 }

    ponPortType OBJECT-TYPE
      SYNTAX INTEGER
        {
        ge-epon(1),
        tenge-epon(2),
        gpon(3),
        other(4)
        }
      MAX-ACCESS read-only
      STATUS current
      DESCRIPTION
        "
        PON端口类型"
      ::= { ponPortInfoEntry 4 }

    ponOperationStatus OBJECT-TYPE
      SYNTAX INTEGER
        {
        up(1),
        down(2),
        testing(3)
        }
      MAX-ACCESS read-only
      STATUS current
      DESCRIPTION
        "
        端口操作状态        
        up(1)      - 该端口可以提供业务
        down(2)    - 该端口无法提供业务
        testing(3) - 该端口处于测试状态，该状态下可能无法正常提供业务"
      ::= { ponPortInfoEntry 5 }

    ponPortAdminStatus OBJECT-TYPE
      SYNTAX INTEGER
        {
        up(1),
        down(2),
        testing(3)
        }
      MAX-ACCESS read-write
      STATUS current
      DESCRIPTION
        "
        板卡管理状态        
        up(1)      - 该端口允许提供业务
        down(2)    - 该端口禁止提供业务
        testing(3) - 该端口处于测试状态，该状态下可能无法正常提供业务"
      ::= { ponPortInfoEntry 6 }

    ponPortMaxOnuNumSupport OBJECT-TYPE
      SYNTAX INTEGER
      MAX-ACCESS read-only
      STATUS current
      DESCRIPTION
        "
        支持最多ONU数量"
      ::= { ponPortInfoEntry 7 }

    ponPortUpOnuNum OBJECT-TYPE
      SYNTAX INTEGER
      MAX-ACCESS read-only
      STATUS current
      DESCRIPTION
        "
        在线ONU数量"
      ::= { ponPortInfoEntry 8 }

    ponPortEncryptMode OBJECT-TYPE
      SYNTAX INTEGER 
        {
           aes128(1), 
           ctcTripleChurning(2), 
           other(3)
        }
      MAX-ACCESS read-write
      STATUS current
      DESCRIPTION
        "
        加密模式"
      ::= { ponPortInfoEntry 9 }

    ponPortEncryptKeyExchangeTime OBJECT-TYPE
      SYNTAX INTEGER
      UNITS "seconds"
      MAX-ACCESS read-write
      STATUS current
      DESCRIPTION
        "
        密钥交换时间"
      ::= { ponPortInfoEntry 10 }

    ponPortIsolationEnable OBJECT-TYPE
      SYNTAX TruthValue
      MAX-ACCESS read-write
      STATUS current
      DESCRIPTION
        "
        PON端口隔离使能"
      ::= { ponPortInfoEntry 11 }

    maxDsBandwidth OBJECT-TYPE
      SYNTAX INTEGER
      UNITS "kbps"
      MAX-ACCESS read-only
      STATUS current
      DESCRIPTION
        "
        最大下行带宽"
      ::= { ponPortInfoEntry 12 }
    actualDsBandwidthInUse OBJECT-TYPE
      SYNTAX INTEGER
      UNITS "kbps"
      MAX-ACCESS read-only
      STATUS current
      DESCRIPTION
        "
        实际下行使用带宽"
      ::= { ponPortInfoEntry 13 }

    remainDsBandwidth OBJECT-TYPE
      SYNTAX INTEGER
      UNITS "kbps"
      MAX-ACCESS read-only
      STATUS current
      DESCRIPTION
        "
        剩余下行使用带宽"
      ::= { ponPortInfoEntry 14 }

    perfStats15minuteEnable OBJECT-TYPE
      SYNTAX TruthValue
      MAX-ACCESS read-write
      STATUS current
      DESCRIPTION
        "
        15分钟性能统计使能"
      ::= { ponPortInfoEntry 15 }

    perfStats24hourEnable OBJECT-TYPE
      SYNTAX TruthValue
      MAX-ACCESS read-write
      STATUS current
      DESCRIPTION
        "
        24小时性能统计使能"
      ::= { ponPortInfoEntry 16 }

    ponPortMacAddrLearnMaxNum OBJECT-TYPE
      SYNTAX INTEGER
      MAX-ACCESS read-write
      STATUS current
      DESCRIPTION
        "
        PON口mac地址学习最大数目        
        value 0 means no limit"
      ::= { ponPortInfoEntry 17 }

    maxUsBandwidth OBJECT-TYPE
      SYNTAX INTEGER
      UNITS "kbps"
      MAX-ACCESS read-only
      STATUS current
      DESCRIPTION
        "
        最大上行带宽"
      ::= { ponPortInfoEntry 18 }

    actualUsBandwidthInUse OBJECT-TYPE
      SYNTAX INTEGER
      UNITS "kbps"
      MAX-ACCESS read-only
      STATUS current
      DESCRIPTION
        "
        实际上行使用带宽"
      ::= { ponPortInfoEntry 19 }

    remainUsBandwidth OBJECT-TYPE
      SYNTAX INTEGER
      UNITS "kbps"
      MAX-ACCESS read-only
      STATUS current
      DESCRIPTION
        "
        剩余上行使用带宽"
      ::= { ponPortInfoEntry 20 }

    aclManagementGroup OBJECT-IDENTITY
      STATUS current
      DESCRIPTION 
        "
        ACL管理"
      ::= { ponPortObjects 2 }

    aclListTable OBJECT-TYPE
      SYNTAX SEQUENCE OF AclListEntry
      MAX-ACCESS not-accessible
      STATUS current
      DESCRIPTION
        "
        ACL列表"
      ::= { aclManagementGroup 1 }

    aclListEntry OBJECT-TYPE
      SYNTAX AclListEntry
      MAX-ACCESS not-accessible
      STATUS current
      DESCRIPTION     " "
      INDEX { aclListIndex }
      ::= { aclListTable 1 }

    AclListEntry ::=
      SEQUENCE { 
        aclListIndex
          INTEGER,
        aclDescription
          DisplayString,
        aclRuleList
          OCTET STRING,
        ruleRowStatus
          RowStatus
       }

    aclListIndex OBJECT-TYPE
      SYNTAX INTEGER
      MAX-ACCESS not-accessible
      STATUS current
      DESCRIPTION
        "
        ACL表索引"
      ::= { aclListEntry 1 }

    aclDescription OBJECT-TYPE
      SYNTAX DisplayString
      MAX-ACCESS read-create
      STATUS current
      DESCRIPTION
        "
        ACL描述信息"
      ::= { aclListEntry 2 }

    aclRuleList OBJECT-TYPE
      SYNTAX OCTET STRING (SIZE (0..64))
      MAX-ACCESS read-create
      STATUS current
      DESCRIPTION
        "
        ACL包括的规则列表        
        采用类似INTERNET比特顺序，从左到右的OCTET分别为OCTET 0, OCTET 1, ...
        每个OCTET的bit从左到右分别为bit0，bit1，...，bit7。
        按照bit和OCTET由小到大的顺序，每个bit对应于aclRuleTable中的
        一个aclRuleIndex。如果bit置位，表示该aclRuleIndex支持，否则不支持。        
        举例来说，如果规划了80个ACL rule，aclRuleIndex范围为1..80，用10个字节表示
        aclRuleList列表，假设该aclList只支持ACL rule列表1,15,38，对应的aclRuleList可以
        设置成0x80 02 00 00 04 00 00 00 00 00"
      ::= { aclListEntry 3 }

    ruleRowStatus OBJECT-TYPE
      SYNTAX RowStatus
      MAX-ACCESS read-create
      STATUS current
      DESCRIPTION
        "
        规则行状态"
      ::= { aclListEntry 4 }

    aclRuleTable OBJECT-TYPE
      SYNTAX SEQUENCE OF AclRuleEntry
      MAX-ACCESS not-accessible
      STATUS current
      DESCRIPTION
        "
        ACL规则表"
      ::= { aclManagementGroup 2 }

    aclRuleEntry OBJECT-TYPE
      SYNTAX AclRuleEntry
      MAX-ACCESS not-accessible
      STATUS current
      DESCRIPTION     " "
      INDEX { aclRuleIndex }
      ::= { aclRuleTable 1 }

    AclRuleEntry ::=
      SEQUENCE { 
        aclRuleIndex
          INTEGER,
        matchedSourseMac
          MacAddress,
        matchedDestinationMac
          MacAddress,
        matchedVlanId
          INTEGER,
        matchedEthernetType
          INTEGER,
        matchedSourseIP
          IpAddress,
        matchedDestinationIP
          IpAddress,
        matchedIpMessageType
          INTEGER,
        matchedDscp
          INTEGER,
        matchedSoursePort
          INTEGER,
        matchedDestinationPort
          INTEGER,
        aclRuleRowStatus
          RowStatus,
        matchedFieldSelection
          BITS,
        aclAction
          INTEGER,
        aclActionParameter
          OCTET STRING
       }

    aclRuleIndex OBJECT-TYPE
      SYNTAX INTEGER
      MAX-ACCESS not-accessible
      STATUS current
      DESCRIPTION
        "
        ACL规则索引"
      ::= { aclRuleEntry 1 }

    matchedSourseMac OBJECT-TYPE
      SYNTAX MacAddress
      MAX-ACCESS read-create
      STATUS current
      DESCRIPTION
        "
        匹配的源Mac"
      ::= { aclRuleEntry 2 }

    matchedDestinationMac OBJECT-TYPE
      SYNTAX MacAddress
      MAX-ACCESS read-create
      STATUS current
      DESCRIPTION
        "
        匹配的目的Mac"
      ::= { aclRuleEntry 3 }

    matchedVlanId OBJECT-TYPE
      SYNTAX INTEGER
      MAX-ACCESS read-create
      STATUS current
      DESCRIPTION
        "
        匹配的vlan id"
      ::= { aclRuleEntry 4 }

    matchedEthernetType OBJECT-TYPE
      SYNTAX INTEGER
      MAX-ACCESS read-create
      STATUS current
      DESCRIPTION
        "
        匹配的以太网类型
        
        It is presented in decimal value for heximal EtherType"
      ::= { aclRuleEntry 5 }

    matchedSourseIP OBJECT-TYPE
      SYNTAX IpAddress
      MAX-ACCESS read-create
      STATUS current
      DESCRIPTION
        "
        匹配的源IP"
      ::= { aclRuleEntry 6 }

    matchedDestinationIP OBJECT-TYPE
      SYNTAX IpAddress
      MAX-ACCESS read-create
      STATUS current
      DESCRIPTION
        "
        匹配的目的IP"
      ::= { aclRuleEntry 7 }
    
    matchedIpMessageType OBJECT-TYPE
      SYNTAX INTEGER (0..255)
      MAX-ACCESS read-create
      STATUS current
      DESCRIPTION
        "
        匹配的IP报文类型"
      ::= { aclRuleEntry 8 }

    matchedDscp OBJECT-TYPE
      SYNTAX INTEGER (0..63)
      MAX-ACCESS read-create
      STATUS current
      DESCRIPTION
        "
        匹配的dscp"
      ::= { aclRuleEntry 9 }    
    matchedSoursePort OBJECT-TYPE
      SYNTAX INTEGER
      MAX-ACCESS read-create
      STATUS current
      DESCRIPTION
        "
        匹配的源端口"
      ::= { aclRuleEntry 10 }
    
    matchedDestinationPort OBJECT-TYPE
      SYNTAX INTEGER
      MAX-ACCESS read-create
      STATUS current
      DESCRIPTION
        "
        匹配的目的端口"
      ::= { aclRuleEntry 11 }

    aclRuleRowStatus OBJECT-TYPE
      SYNTAX RowStatus
      MAX-ACCESS read-create
      STATUS current
      DESCRIPTION
        "
        规则状态"
      ::= { aclRuleEntry 12 }

    matchedFieldSelection OBJECT-TYPE
      SYNTAX BITS
        {
        sourceMac(0),
        destinationMac(1),
        vlanId(2),
        etherType(3),
        sourceIp(4),
        destinationIp(5),
        ipProtocolType(6),
        dscp(7),
        sourceProtocolPort(8),
        destinationProtocolPort(9)
        }
      MAX-ACCESS read-create
      STATUS current
      DESCRIPTION
        "
        选择的匹配域，可以多选"
      ::= { aclRuleEntry 13 }

    aclAction OBJECT-TYPE
      SYNTAX INTEGER
        {
        permit(1),
        deny(2),
        mark(3)
        }
      MAX-ACCESS read-create
      STATUS current
      DESCRIPTION
        "
        ACL规则动作（permit、deny、标记等）"
      ::= { aclRuleEntry 14 }

    aclActionParameter OBJECT-TYPE
      SYNTAX OCTET STRING
      MAX-ACCESS read-create
      STATUS current
      DESCRIPTION
        "
        ACL规则动作参数。只对aclAction为mark(3)有效，对于aclAction其他值，
        此对象禁止配置，get时返回NULL。        
        按照INTERNET顺序从左往右的方向排列，第一个为OCTET0，第n个为OCTET
        [n-1]。        
        OCTET 0 表示 MARK 类型。后面的OCTET 表示这种类型的MARK的目标值，这
        是否这些OCTET的长度取决于MARK类型，比如对应于改MARK类型的参数的SYNTAX
        为INTEGER，则需要4个字节，表示对应的数值。        
        MARK类型    目标值的SYNTAX        描述
        -------------------------------------------------------------------
        0                             Reserved
        1       INTEGER (0..7)      MARK 801.1p的值（外层VLAN）
        2       INTEGER (1..4094)   MARK VLAN ID（外层VLAN）
        3       INTEGER (0..7)      MARK TOS PRECEDENCE
        4       INTEGER (0..63)     MARK DSCP
        5..255                            Reserved        
        比如修改VLAN ID为100，对应的值为：02 00 00 00 64"  
      ::= { aclRuleEntry 15 }

    portACLListTable OBJECT-TYPE
      SYNTAX SEQUENCE OF PortACLListEntry
      MAX-ACCESS not-accessible
      STATUS current
      DESCRIPTION
        "
        端口ACL列表
        This table applies on OLT pon port, OLT SNI, OLT onu ID, ONU UNI.
        1. If the table is maintained in OLT device:
        Applied Obj  - Descriptions of Index
        ------------------------------------------------------------------
        OLT Pon Port - OnuNum of aclDeviceIndex shall be set to 0,
        /OLT SNI     aclCardIndex, and aclPortIndex set to 0 indicates
                 meaningless 
        OLT onu ID   - Set aclDeviceIndex to corresponding ONU ID,
                 aclCardIndex, and aclPortIndex set to 0 indicates
                 meaningless        
        ONU UNI    - Set aclDeviceIndex to corresponding ONU ID,
                 aclCardIndex, and aclPortIndex set to the corresponding 
                 value        
        2. If the table is maintained in ONU device:
        aclDeviceIndex shall be set to 0 to indicate meaningless.
        aclCardIndex shall be set to corresponding slot.
        aclPortIndex shall be set to corresponding port.        
        "
        
      ::= { aclManagementGroup 3 }
    
    portACLListEntry OBJECT-TYPE
      SYNTAX PortACLListEntry
      MAX-ACCESS not-accessible
      STATUS current
      DESCRIPTION     " "
      INDEX { aclDeviceIndex, aclCardIndex, aclPortIndex, portAclListIndex }
      ::= { portACLListTable 1 }
    
    PortACLListEntry ::=
      SEQUENCE { 
        aclDeviceIndex
          EponDeviceIndex,
        aclCardIndex
          EponCardIndex,
        aclPortIndex
          EponPortIndex,
        portAclListIndex 
          INTEGER,
        aclPortDirection
          BITS,
        aclRowStatus
          RowStatus
       }

    aclDeviceIndex OBJECT-TYPE
      SYNTAX EponDeviceIndex
      MAX-ACCESS not-accessible
      STATUS current
      DESCRIPTION
        "
        设备索引号。        
        For OLT, set to corresponding PON port, SNI, or ONU
        For ONU, set to 0
        "
      ::= { portACLListEntry 1 }

    aclCardIndex OBJECT-TYPE
      SYNTAX EponCardIndex
      MAX-ACCESS not-accessible
      STATUS current
      DESCRIPTION
        "
        板卡索引号        
        For OLT, set to 0,
        For ONU, set to corresponding slot
        "
      ::= { portACLListEntry 2 }

    aclPortIndex  OBJECT-TYPE
      SYNTAX EponPortIndex
      MAX-ACCESS not-accessible
      STATUS current
      DESCRIPTION
        "
        端口索引号        
        For OLT, set to 0,
        For ONU, set to corresponding slot
        "
      ::= { portACLListEntry 3 }

    portAclListIndex OBJECT-TYPE
      SYNTAX INTEGER
      MAX-ACCESS not-accessible
      STATUS current
      DESCRIPTION
        "
        端口ACL表索引"
      ::= { portACLListEntry 4 }

    aclPortDirection OBJECT-TYPE
      SYNTAX BITS
        {
        ingress(0),
        egress(1)
        }
      MAX-ACCESS read-create
      STATUS current
      DESCRIPTION
        "
        ACL应用到出口或入口"
      ::= { portACLListEntry 5 }

    aclRowStatus OBJECT-TYPE
      SYNTAX RowStatus
      MAX-ACCESS read-create
      STATUS current
      DESCRIPTION
        "
        ACL应用状态"
      ::= { portACLListEntry 6 }

    ponBroadcastStormSuppressionTable OBJECT-TYPE
      SYNTAX SEQUENCE OF PonBroadcastStormSuppressionEntry
      MAX-ACCESS not-accessible
      STATUS current
      DESCRIPTION
        "
        广播风暴抑制表        
        注：若不支持端口级别的配置，则配置一个端口，同一板卡的所有端口的配置均生效"
      ::= { ponPortObjects 3 }

    ponBroadcastStormSuppressionEntry OBJECT-TYPE
      SYNTAX PonBroadcastStormSuppressionEntry
      MAX-ACCESS not-accessible
      STATUS current
      DESCRIPTION     " "
      INDEX { bsDeviceIndex, bsCardIndex, bsPortIndex }
      ::= { ponBroadcastStormSuppressionTable 1 }

    PonBroadcastStormSuppressionEntry ::=
      SEQUENCE { 
        bsDeviceIndex
          INTEGER,
        bsCardIndex
          EponCardIndex,
        bsPortIndex 
          EponPortIndex,
        unicastStormEnable
          TruthValue,
        unicastStormInPacketRate
          INTEGER,
        unicastStormOutPacketRate
          INTEGER,
        multicastStormEnable
          TruthValue,
        multicastStormInPacketRate
          INTEGER,
        multicastStormOutPacketRate
          INTEGER,
        broadcastStormEnable
          TruthValue,
        broadcastStormInPacketRate
          INTEGER,
        broadcastStormOutPacketRate
          INTEGER
       }

    bsDeviceIndex OBJECT-TYPE
      SYNTAX INTEGER
      MAX-ACCESS not-accessible
      STATUS current
      DESCRIPTION
        "
        OLT设备索引号。        
        一个OLT节点可以由多台OLT设备组成。节点内的每台OLT设备由OLT设备索引号唯一标识"
      ::= { ponBroadcastStormSuppressionEntry 1 }

    bsCardIndex OBJECT-TYPE
      SYNTAX EponCardIndex
      MAX-ACCESS not-accessible
      STATUS current
      DESCRIPTION
        "
        板卡索引号"
      ::= { ponBroadcastStormSuppressionEntry 2 }

    bsPortIndex   OBJECT-TYPE
      SYNTAX EponPortIndex
      MAX-ACCESS not-accessible
      STATUS current
      DESCRIPTION
        "
        pon端口索引号"
      ::= { ponBroadcastStormSuppressionEntry 3 }

    unicastStormEnable OBJECT-TYPE
      SYNTAX TruthValue
      MAX-ACCESS read-write
      STATUS current
      DESCRIPTION
        "
        未知单播风暴抑制使能"
      ::= { ponBroadcastStormSuppressionEntry 4 }

    unicastStormInPacketRate OBJECT-TYPE
      SYNTAX INTEGER
      UNITS "pps"
      MAX-ACCESS read-write
      STATUS current
      DESCRIPTION
        "
        未知单播风暴抑制入口速率"
      ::= { ponBroadcastStormSuppressionEntry 5 }

    unicastStormOutPacketRate OBJECT-TYPE
      SYNTAX INTEGER
      UNITS "pps"
      MAX-ACCESS read-write
      STATUS current
      DESCRIPTION
        "
        未知单播风暴抑制出口速率"
      ::= { ponBroadcastStormSuppressionEntry 6 }

    multicastStormEnable OBJECT-TYPE
      SYNTAX TruthValue
      MAX-ACCESS read-write
      STATUS current
      DESCRIPTION
        "
        组播风暴抑制使能"
      ::= { ponBroadcastStormSuppressionEntry 7 }

    multicastStormInPacketRate OBJECT-TYPE
      SYNTAX INTEGER
      UNITS "pps"
      MAX-ACCESS read-write
      STATUS current
      DESCRIPTION
        "
        组播风暴抑制入口速率"
      ::= { ponBroadcastStormSuppressionEntry 8 }

    multicastStormOutPacketRate OBJECT-TYPE
      SYNTAX INTEGER
      UNITS "pps"
      MAX-ACCESS read-write
      STATUS current
      DESCRIPTION
        "
        组播风暴抑制出口速率"
      ::= { ponBroadcastStormSuppressionEntry 9 }

    broadcastStormEnable OBJECT-TYPE
      SYNTAX TruthValue
      MAX-ACCESS read-write
      STATUS current
      DESCRIPTION
        "
        广播风暴抑制使能"
      ::= { ponBroadcastStormSuppressionEntry 10 }

    broadcastStormInPacketRate OBJECT-TYPE
      SYNTAX INTEGER
      UNITS "pps"
      MAX-ACCESS read-write
      STATUS current
      DESCRIPTION
        "
        广播风暴抑制入口速率"
      ::= { ponBroadcastStormSuppressionEntry 11 }

    broadcastStormOutPacketRate OBJECT-TYPE
      SYNTAX INTEGER
      UNITS "pps"
      MAX-ACCESS read-write
      STATUS current
      DESCRIPTION
        "
        广播风暴抑制出口速率"
      ::= { ponBroadcastStormSuppressionEntry 12 }
      
-- PON OPM
    oltPonPortOpticalTransmissionPropertyTable  OBJECT-TYPE
        SYNTAX      SEQUENCE OF oltPonPortOpticalTransmissionPropertyEntry
        MAX-ACCESS  not-accessible
        STATUS      current
        DESCRIPTION
            "A list of oltPonPortOpticalTransmissionPropertyTable  entries. "
        ::= { ponPortObjects 5 }
        
    oltPonPortOpticalTransmissionPropertyEntry OBJECT-TYPE
        SYNTAX      oltPonPortOpticalTransmissionPropertyEntry
        MAX-ACCESS  not-accessible
        STATUS      current
        DESCRIPTION  
            "The oltPonPortOpticalTransmissionPropertyEntry Information"
        INDEX       { ponOpDeviceIndex,ponOpCardIndex,ponOpPortIndex }   
        ::={ oltPonPortOpticalTransmissionPropertyTable  1 }   
        
    oltPonPortOpticalTransmissionPropertyEntry ::= SEQUENCE {
            ponOpDeviceIndex            INTEGER,
            ponOpCardIndex              EponCardIndex,
            ponOpPortIndex              EponPortIndex,
            PonOpmDiagnosisVcc          INTEGER,
            PonOpmDiagnosisBias         INTEGER,
            PonOpmDiagnosisTXPower      INTEGER,
            PonOpmDiagnosisRXPower      INTEGER
        }            
       
    ponOpDeviceIndex               OBJECT-TYPE
        SYNTAX      INTEGER
        MAX-ACCESS  not-accessible
        STATUS      current
        DESCRIPTION
            "设备索引 "
        ::= { oltPonPortOpticalTransmissionPropertyEntry 1 }   
        
    ponOpCardIndex                 OBJECT-TYPE
        SYNTAX  EponCardIndex
        MAX-ACCESS  not-accessible
        STATUS      current
        DESCRIPTION
            "板卡索引"
        ::= {oltPonPortOpticalTransmissionPropertyEntry 2 }  

    ponOpPortIndex                OBJECT-TYPE
        SYNTAX      EponPortIndex
        MAX-ACCESS  not-accessible
        STATUS      current
        DESCRIPTION
            "端口索引"
        ::= { oltPonPortOpticalTransmissionPropertyEntry 3 }  

    PonOpmDiagnosisVcc            OBJECT-TYPE
        SYNTAX      INTEGER
        MAX-ACCESS  read-only
        STATUS      current
        DESCRIPTION
            "光模块电压"
        ::= { oltPonPortOpticalTransmissionPropertyEntry 4 }
        
    PonOpmDiagnosisBias           OBJECT-TYPE
        SYNTAX      INTEGER
        MAX-ACCESS  read-only
        STATUS      current
        DESCRIPTION
            "光模块偏置电流"
        ::= { oltPonPortOpticalTransmissionPropertyEntry 5 }
   
    PonOpmDiagnosisTXPower      OBJECT-TYPE
        SYNTAX      INTEGER
        MAX-ACCESS  read-only
        STATUS      current
        DESCRIPTION
            "光模块发送功率"
        ::= { oltPonPortOpticalTransmissionPropertyEntry 6 }

    PonOpmDiagnosisRXPower      OBJECT-TYPE
        SYNTAX      INTEGER
        MAX-ACCESS  read-only
        STATUS      current
        DESCRIPTION
            "光模块接收功率"
        ::= { oltPonPortOpticalTransmissionPropertyEntry 7 }
        

    onuLongEmitDetectEntryTable  OBJECT-TYPE
        SYNTAX      SEQUENCE OF onuLongEmitDetectEntry
        MAX-ACCESS  not-accessible
        STATUS      current
        DESCRIPTION
            "A list of onuLongEmitDetectEntryTable  entries. "
        ::= { ponPortObjects 6 }
        
    onuLongEmitDetectEntry    OBJECT-TYPE
        SYNTAX      onuLongEmitDetectEntry
        MAX-ACCESS  not-accessible
        STATUS      current
        DESCRIPTION  
            "The onuLongEmitDetectEntry  Information"
        INDEX       { onuLongEmitDeviceIndex,onuLongEmitCardIndex,onuLongEmitPortIndex }   
        ::={ onuLongEmitDetectEntryTable   1 }   
        
    onuLongEmitDetectEntry  ::= SEQUENCE {
       onuLongEmitDeviceIndex         INTEGER,
       onuLongEmitCardIndex           EponCardIndex,
       onuLongEmitPortIndex           EponPortIndex,
       detectEnable                   INTEGER,
       }            
       
    onuLongEmitDeviceIndex         OBJECT-TYPE
        SYNTAX      INTEGER
        MAX-ACCESS  not-accessible
        STATUS      current
        DESCRIPTION
            "设备索引 "
        ::= { onuLongEmitDetectEntry 1 }   
        
    onuLongEmitCardIndex            OBJECT-TYPE
        SYNTAX      EponCardIndex
        MAX-ACCESS  not-accessible
        STATUS      current
        DESCRIPTION
            "板卡索引"
        ::= { onuLongEmitDetectEntry 2 }  

    onuLongEmitPortIndex            OBJECT-TYPE
        SYNTAX      EponPortIndex
        MAX-ACCESS  not-accessible
        STATUS      current
        DESCRIPTION
            "端口索引"
        ::= { onuLongEmitDetectEntry 3 }  

    detectEnable                   OBJECT-TYPE
        SYNTAX      INTEGER
        MAX-ACCESS  read-write
        STATUS      current
        DESCRIPTION
            "检测开关 0：关闭   1：打开"
        ::= { onuLongEmitDetectEntry 4 }
        
--
-- END of NSCRTV-EPON-PON-PORT-MIB
--

END

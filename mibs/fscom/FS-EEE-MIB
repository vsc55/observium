-- *****************************************************************
-- FS-EEE-MIB.mib:  FS EEE MIB file
--
-- Feb 2012, linzhihong
--
-- Copyright (c) 2012 by FS.COM Inc..
-- All rights reserved.
-- 
-- *****************************************************************
--

FS-EEE-MIB DEFINITIONS ::= BEGIN

IMPORTS
        MODULE-IDENTITY,
        OBJECT-TYPE,
        NOTIFICATION-TYPE,
        Integer32,
        OBJECT-TYPE
                FROM SNMPv2-SMI
        fsMgmt
                FROM FS-SMI;

fsEEEMIB MODULE-IDENTITY
        LAST-UPDATED "201210160000Z"
        ORGANIZATION "FS.COM Inc.."
        CONTACT-INFO
                " 
                Tel: 400-865-2852 

                E-mail: https://www.fs.com/live_chat_service_mail.html"
        DESCRIPTION
                "This module defines fs EEE mibs."
        REVISION      "201210160000Z"
        DESCRIPTION
                "Add a table about EEE."
        REVISION      "201210160000Z"
        DESCRIPTION
                "Initial version of this MIB module."
        ::= { fsMgmt 119 }

fsEEEConfigMIBObjects OBJECT IDENTIFIER ::= { fsEEEMIB 1 }

fsEEETable OBJECT-TYPE
        SYNTAX 			SEQUENCE OF FSEEEEntry
        MAX-ACCESS 	not-accessible
        STATUS 			current
        DESCRIPTION
            " "
        ::= { fsEEEConfigMIBObjects 1 }

   
fsEEEEntry OBJECT-TYPE
        SYNTAX 			FSEEEEntry
        MAX-ACCESS 	not-accessible
        STATUS 			current
        DESCRIPTION
            " "
        INDEX { fsEEEifIndex }
        ::= { fsEEETable 1 }

FSEEEEntry ::=
        SEQUENCE {
            fsEEEifIndex 		 Integer32,
            fsEEEAdminEnable INTEGER,
            fsEEEOperEnable  INTEGER
        }
       
fsEEEifIndex OBJECT-TYPE
        SYNTAX 			Integer32 (1..2147483647)
        MAX-ACCESS 	read-only
        STATUS 			current
        DESCRIPTION
            " "
        ::= { fsEEEEntry 1 }
   
           
fsEEEAdminEnable OBJECT-TYPE
        SYNTAX INTEGER {
            enabled(1),
            disabled(2)
        }
        MAX-ACCESS read-write
        STATUS current
        DESCRIPTION
            " "
        ::= { fsEEEEntry 2 }
    
fsEEEOperEnable OBJECT-TYPE
        SYNTAX INTEGER {
            enabled(1),
            disabled(2)
        }
        MAX-ACCESS read-only
        STATUS current
        DESCRIPTION
            " "
        ::= { fsEEEEntry 3 }                             
        
END

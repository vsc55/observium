-- *****************************************************************
-- FS-ETHERLIKE-MIB.mib:  FS etherlike MIB file
--
-- September 2009, xiongtu
--
-- Copyright (c) 2009 by FS.COM Inc..
-- All rights reserved.
-- 
-- *****************************************************************
--

FS-ETHERLIKE-MIB DEFINITIONS ::= BEGIN

IMPORTS
        MODULE-IDENTITY,
        OBJECT-TYPE,
        Counter64
                FROM SNMPv2-SMI
        MODULE-COMPLIANCE,
        OBJECT-GROUP
                FROM SNMPv2-CONF
        IfIndex
                FROM FS-TC
        fsMgmt
                FROM FS-SMI;

fsEtherlikeMIB MODULE-IDENTITY
        LAST-UPDATED "200909170000Z"
        ORGANIZATION "FS.COM Inc.."
        CONTACT-INFO
                " 
                Tel: 400-865-2852

                E-mail: https://www.fs.com/live_chat_service_mail.html"
        DESCRIPTION
                "This module defines fs etherlike mibs."
        REVISION      "200909170000Z"
        DESCRIPTION
                "Initial version of this MIB module."
        ::= { fsMgmt 55}

fsEtherlikeMIBObjects OBJECT IDENTIFIER ::= { fsEtherlikeMIB 1 }


fsEtherlikeTable OBJECT-TYPE
        SYNTAX SEQUENCE OF FSEtherlikeEntry
        MAX-ACCESS not-accessible
        STATUS current
        DESCRIPTION
            "Access table of frames collision counter on interface." 
        ::= { fsEtherlikeMIBObjects 1 }
    
fsEtherlikeEntry OBJECT-TYPE
        SYNTAX FSEtherlikeEntry
        MAX-ACCESS not-accessible
        STATUS current
        DESCRIPTION
            "Interfac frames collision counter access." 
        INDEX { fsEtherlikeIfIndex }
        ::= { fsEtherlikeTable 1 }

FSEtherlikeEntry ::=
        SEQUENCE {
            fsEtherlikeIfIndex IfIndex,
      	    fsLocIfCollisions Counter64
        }

fsEtherlikeIfIndex OBJECT-TYPE
        SYNTAX IfIndex
        MAX-ACCESS read-only
        STATUS current
        DESCRIPTION
            "Interface number"
        ::= { fsEtherlikeEntry 1 }

fsLocIfCollisions OBJECT-TYPE
        SYNTAX Counter64
        MAX-ACCESS read-only
        STATUS current
        DESCRIPTION
            "Interfac frames collision counter."
        ::= { fsEtherlikeEntry 2 }

     
                                     
fsEtherlikeMIBConformance OBJECT IDENTIFIER ::= { fsEtherlikeMIB 3 }
fsEtherlikeMIBCompliances OBJECT IDENTIFIER ::= { fsEtherlikeMIBConformance 1 }
fsEtherlikeMIBGroups      OBJECT IDENTIFIER ::= { fsEtherlikeMIBConformance 2 }

-- compliance statements

fsEtherlikeMIBCompliance MODULE-COMPLIANCE
        STATUS  current
        DESCRIPTION
                "The compliance statement for entities which implement
                the FS Interface MIB"
        MODULE  -- this module
                MANDATORY-GROUPS { fscollisionMIBGroups
                 }
        ::= { fsEtherlikeMIBCompliances 1 }
                
-- units of conformance


fscollisionMIBGroups OBJECT-GROUP
        OBJECTS {
            fsEtherlikeIfIndex,
      	    fsLocIfCollisions
        }
        STATUS  current
        DESCRIPTION
                "Interfac frames collision counter collection." 
        ::= { fsEtherlikeMIBGroups 1 }         
                        
                
END

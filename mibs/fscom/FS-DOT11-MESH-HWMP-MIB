-- *******************************************************************
-- FS-DOT11-MESH-HWMP-MIB : FS MIB
-- May 2010, liyan
--
-- Copyright (c) 2010 by FS.COM Inc..
-- All rights reserved.
-- *******************************************************************
FS-DOT11-MESH-HWMP-MIB DEFINITIONS ::= BEGIN
    IMPORTS
        MODULE-IDENTITY,
        OBJECT-TYPE
        --INTEGER
            FROM SNMPv2-SMI
        MODULE-COMPLIANCE,
        NOTIFICATION-GROUP,
        OBJECT-GROUP
            FROM SNMPv2-CONF   
        ifIndex
            FROM RFC1213-MIB 
        fsMgmt
            FROM FS-SMI;
--*******************************************
--* module definition
--*******************************************
fsDot11MeshHWMPMIB MODULE-IDENTITY
    LAST-UPDATED    "201002260000Z"
    ORGANIZATION
        "FS.COM Inc.."
    CONTACT-INFO
        "Tel: 400-865-2852
           E-mail: https://www.fs.com/live_chat_service_mail.html "

    DESCRIPTION
       "
       Wlan software private MIB for FS SNC according to the China
       Mobile standard. This is device manage MIB.
       "
    REVISION      "201002280000Z"
    DESCRIPTION
       "Initial version of this MIB module."

    ::= { fsMgmt  92 }

-- **********************************************************************
-- * dot11MeshHWMPConfig TABLE  start *                                                  
-- **********************************************************************
apdot11MeshHWMPConfigObjects        OBJECT IDENTIFIER  ::= { fsDot11MeshHWMPMIB 1 }

dot11MeshHWMPConfigTable OBJECT-TYPE
    SYNTAX SEQUENCE OF Dot11MeshHWMPConfigEntry
    MAX-ACCESS not-accessible
    STATUS current
    DESCRIPTION
      "Mesh Station HWMP Configuration attributes. In tabular form to
      allow for multiple instances on an agent." 
    ::={ apdot11MeshHWMPConfigObjects 1 }
            
dot11MeshHWMPConfigEntry OBJECT-TYPE
    SYNTAX Dot11MeshHWMPConfigEntry
    MAX-ACCESS not-accessible
    STATUS current
    DESCRIPTION
        "An entry in the dot11MeshHWMPConfigTable. It is possible for there
        to be multiple IEEE 802.11 interfaces on one agent, each with its
        unique MAC address. The relationship between an IEEE 802.11
        interface and an interface in the context of the Internet-standard
        MIB is one-to-one. As such, the value of an ifIndex object instance
        can be directly used to identify corresponding instances of the
        objects defined herein.
        ifIndex - Each IEEE 802.11 interface is represented by an ifEntry.
        Interface tables in this MIB module are indexed by ifIndex."
    INDEX { ifIndex }
    ::= { dot11MeshHWMPConfigTable 1 }
                                                                                                                                                                                                                                                                              
Dot11MeshHWMPConfigEntry ::=                                                                                                                                   
    SEQUENCE {                                                                                                                                             
        dot11MeshHWMPmaxPREQretries                   INTEGER,                                                                                             
        dot11MeshHWMPnetDiameter                      INTEGER,                                                                                             
        dot11MeshHWMPnetDiameterTraversalTime         INTEGER,
        dot11MeshHWMPpreqMinInterval                  INTEGER,
        dot11MeshHWMPperrMinInterval                  INTEGER,                                                                                             
        dot11MeshHWMPactivePathToRootTimeout          INTEGER,                                                                                             
        dot11MeshHWMPactivePathTimeout                INTEGER,                                                                                             
        dot11MeshHWMProotMode                         INTEGER,                                                                                             
        dot11MeshHWMProotInterval                     INTEGER,                                                                                             
        dot11MeshHWMPrannInterval                     INTEGER,                                                                                             
        dot11MeshHWMPtargetOnly                       INTEGER,                                                                                             
        dot11MeshHWMPmaintenanceInterval              INTEGER,                                                                                             
        dot11MeshHWMPconfirmationInterval             INTEGER                                                                                              
    }                                                                                                                                                      
                                                                                                                                                               
dot11MeshHWMPmaxPREQretries OBJECT-TYPE                                                                                                                        
    SYNTAX INTEGER (0..255)                                                                                                                                
    MAX-ACCESS read-write                                                                                                                                  
    STATUS current                                                                                                                                         
    DESCRIPTION                                                                                                                                            
        "This is a control variable.                                                                                                                       
        It is written by an external management entity.                                                                                                    
                                                                                                                                                           
        This attribute shall specify the number of Action frames containing                                                                                
        a PREQ that an originator mesh STA can send to a particular path                                                                                   
        target for a specific path discovery."                                                                                                             
    DEFVAL { 3 }                                                                                                                                           
    ::= { dot11MeshHWMPConfigEntry 1}                                                                                                                      
                                                                                                                                                               
dot11MeshHWMPnetDiameter OBJECT-TYPE                                                                                                                           
    SYNTAX INTEGER (1..255)                                                                                                                                
    MAX-ACCESS read-write                                                                                                                                  
    STATUS current                                                                                                                                         
    DESCRIPTION                                                                                                                                            
        "This is a control variable.                                                                                                                       
        It is written by an external management entity.                                                                                                    
        This attribute shall specify the estimate of the maximum number of                                                                                 
        hops that it takes for an HWMP element to propagate across the mesh                                                                                
        BSS."                                                                                                                                              
    DEFVAL { 31 }                                                                                                                                          
    ::= { dot11MeshHWMPConfigEntry 2}                                                                                                                      
                                                                                                                                                               
dot11MeshHWMPnetDiameterTraversalTime OBJECT-TYPE                                                                                                              
    SYNTAX INTEGER (1..65535)                                                                                                                              
    MAX-ACCESS read-write                                                                                                                                  
    STATUS current                                                                                                                                         
    DESCRIPTION                                                                                                                                            
        "This is a control variable.                                                                                                                       
        It is written by an external management entity.                                                                                                    
        This attribute shall specify the estimate of the interval of time                                                                                  
        (in TUs) that it takes for an HWMP element to propagate across the                                                                                 
        mesh BSS."                                                                                                                                         
    DEFVAL { 500 }                                                                                                                                         
    ::= { dot11MeshHWMPConfigEntry 3}                                                                                                                      
                                                                                                                                                               
dot11MeshHWMPpreqMinInterval OBJECT-TYPE                                                                                                                       
    SYNTAX INTEGER (1..65535)                                                                                                                              
    MAX-ACCESS read-write                                                                                                                                  
    STATUS current                                                                                                                                         
    DESCRIPTION                                                                                                                                            
        "This is a control variable.                                                                                                                       
        It is written by an external management entity.                                                                                                    
        This attribute shall specify the minimum interval of time (in TUs)                                                                                 
        during which a mesh STA can send only one Action frame containing a                                                                                
        PREQ element."                                                                                                                                     
    DEFVAL { 100 }                                                                                                                                         
    ::= { dot11MeshHWMPConfigEntry 4}                                                                                                                      
                                                                                                                                                               
dot11MeshHWMPperrMinInterval OBJECT-TYPE                                                                                                                       
    SYNTAX INTEGER (1..65535)                                                                                                                              
    MAX-ACCESS read-write                                                                                                                                  
    STATUS current                                                                                                                                         
    DESCRIPTION                                                                                                                                            
        "This is a control variable.                                                                                                                       
        It is written by an external management entity.                                                                                                    
        This attribute shall specify the minimum interval of time (in TUs)                                                                                 
        during which a mesh STA can send only one Action frame containing a                                                                                
        PERR element."                                                                                                                                     
    DEFVAL { 100 }                                                                                                                                         
    ::= { dot11MeshHWMPConfigEntry 5}                                                                                                                      
                                                                                                                                                               
dot11MeshHWMPactivePathToRootTimeout OBJECT-TYPE                                                                                                               
    SYNTAX INTEGER (1..65535)                                                                                                                              
    MAX-ACCESS read-write                                                                                                                                  
    STATUS current                                                                                                                                         
    DESCRIPTION                                                                                                                                            
        "This is a control variable.                                                                                                                       
        It is written by an external management entity.                                                                                                    
        This object shall specify the time (in TUs) for which mesh STAs                                                                                    
        receiving a proactive PREQ shall consider the forwarding                                                                                           
        information to the root mesh STA to be valid; it must be greater                                                                                   
        than dot11MeshHWMProotInterval."                                                                                                                   
    DEFVAL { 5000 }                                                                                                                                        
    ::= { dot11MeshHWMPConfigEntry 6}                                                                                                                      
                                                                                                                                                               
dot11MeshHWMPactivePathTimeout OBJECT-TYPE                                                                                                                     
    SYNTAX INTEGER (1..65535)                                                                                                                              
    MAX-ACCESS read-write                                                                                                                                  
    STATUS current                                                                                                                                         
    DESCRIPTION                                                                                                                                            
        "This is a control variable.                                                                                                                       
        It is written by an external management entity.                                                                                                    
        This attribute shall specify the time (in TUs) for which mesh STAs                                                                                 
        receiving a PREQ to individual target(s) shall consider the                                                                                        
        forwarding information to be valid."                                                                                                               
    DEFVAL { 5000 }                                                                                                                                        
    ::= { dot11MeshHWMPConfigEntry 7}                                                                                                                      
                                                                                                                                                               
dot11MeshHWMProotMode OBJECT-TYPE                                                                                                                              
    SYNTAX INTEGER {                                                                                                                                       
        noRoot(0),                                                                                                                                             
        proactivePREQnoPREP(2),
        proactivePREQwithPREP(3),                                                                                                                 
        rann(4) 
    }                                                                                                                                              
    MAX-ACCESS read-write                                                                                                                                  
    STATUS current                                                                                                                                         
    DESCRIPTION                                                                                                                                            
        "This is a control variable.                                                                                                                       
        It is written by an external management entity.                                                                                                    
        This attribute controls the configuration of a mesh STA as root                                                                                    
        mesh STA. A mesh STA is configured as a root mesh STA if                                                                                           
        dot11MeshHWMProotMode is set to 2, 3 or 4. Different values                                                                                        
        correspond to different modes of the root mesh STA. The mesh STA is                                                                                
        not a root mesh STA when the attribute is set to 0."                                                                                               
     DEFVAL { noRoot }                                                                                                                                     
    ::= { dot11MeshHWMPConfigEntry 8}                                                                                                                      
                                                                                                                                                           
dot11MeshHWMProotInterval OBJECT-TYPE                                                                                                                          
    SYNTAX INTEGER (1..65535)                                                                                                                              
    MAX-ACCESS read-write                                                                                                                                  
    STATUS current                                                                                                                                         
    DESCRIPTION                                                                                                                                            
        "This is a control variable.                                                                                                                       
        It is written by an external management entity.                                                                                                    
        This attribute shall specify the minimum interval of time (in TUs)                                                                                 
        during which a root mesh STA can send only one Action frame                                                                                        
        containing a proactive PREQ element."                                                                                                              
    DEFVAL { 2000 }                                                                                                                                        
    ::= { dot11MeshHWMPConfigEntry 9}                                                                                                                      
                                                                                                                                                           
dot11MeshHWMPrannInterval OBJECT-TYPE                                                                                                                          
    SYNTAX INTEGER (1..65535)                                                                                                                              
    MAX-ACCESS read-write                                                                                                                                  
    STATUS current                                                                                                                                         
    DESCRIPTION                                                                                                                                            
        "This is a control variable.                                                                                                                       
        It is written by an external management entity.                                                                                                    
        This attribute shall specify the minimum interval of time (in TUs)                                                                                 
        during which a mesh STA can send only one Action frame containing a                                                                                
        RANN element."                                                                                                                                     
    DEFVAL { 1000 }                                                                                                                                        
    ::= { dot11MeshHWMPConfigEntry 10}                                                                                                                     
                                                                                                                                                               
dot11MeshHWMPtargetOnly OBJECT-TYPE                                                                                                                            
    SYNTAX INTEGER { 
        intermediateMSTA(0), 
        targetOnly(1)
    }                                                                                                  
    MAX-ACCESS read-write                                                                                                                                  
    STATUS current                                                                                                                                         
    DESCRIPTION                                                                                                                                            
        "This is a control variable.                                                                                                                       
        It is written by an external management entity.                                                                                                    
        This attribute, when set to intermediateMSTA (0), shall allow                                                                                      
        intermediate mesh STAs to respond with a PREP to a PREQ if they have                                                                               
        valid forwarding information to the requested target. When set to                                                                                  
        targetOnly (1), only the target MSTA is allowed to respond with a                                                                                  
        PREP to a PREQ."                                                                                                                                   
    DEFVAL { targetOnly }                                                                                                                                  
    ::= { dot11MeshHWMPConfigEntry 11}                                                                                                                     
                                                                                                                                                               
dot11MeshHWMPmaintenanceInterval OBJECT-TYPE                                                                                                                   
    SYNTAX INTEGER (1..65535)                                                                                                                              
    MAX-ACCESS read-write                                                                                                                                  
    STATUS current                                                                                                                                         
    DESCRIPTION                                                                                                                                            
        "This is a control variable.                                                                                                                       
        It is written by an external management entity.                                                                                                    
        This attribute shall specify the minimum interval of time (in TUs)                                                                                 
        during which a mesh STA can send only one Action frame containing a                                                                                
        PREQ element for path maintenance."                                                                                                                
        DEFVAL { 2000 }                                                                                                                                    
    ::= { dot11MeshHWMPConfigEntry 12}                                                                                                                     
                                                                                                                                                           
dot11MeshHWMPconfirmationInterval OBJECT-TYPE                                                                                                                  
    SYNTAX INTEGER (1..65535)                                                                                                                              
    MAX-ACCESS read-write                                                                                                                                  
    STATUS current                                                                                                                                         
    DESCRIPTION                                                                                                                                            
        "This is a control variable.                                                                                                                       
        It is written by an external management entity.                                                                                                    
        This attribute shall specify the minimum interval of time (in TUs)                                                                                 
        during which a mesh STA can send only one Action frame containing a                                                                                
        PREQ element for root path confirmation."                                                                                                          
    DEFVAL { 2000 }                                                                                                                                        
    ::= { dot11MeshHWMPConfigEntry 13}                                                                                                                     
                                                                                                                                                           
--**********************************************************************                                                                                         
--* End of dot11MeshHWMPConfig TABLE                                                                                                                             
--**********************************************************************  

--**********************************************************************
-- about conformance info 
--**********************************************************************
fsDot11MeshHWMPConformance OBJECT IDENTIFIER ::= { fsDot11MeshHWMPMIB 2 }
fsDot11MeshHWMPCompliances OBJECT IDENTIFIER ::= { fsDot11MeshHWMPConformance 1 }
fsDot11MeshHWMPGroups      OBJECT IDENTIFIER ::= { fsDot11MeshHWMPConformance 2 }

-- compliance statements
fsDot11MeshHWMPCompliance MODULE-COMPLIANCE
			STATUS	current
			DESCRIPTION
					"The compliance statement for entities which implement the fsDot11MeshHWMPMIB."
			MODULE
			MANDATORY-GROUPS {
					fsDot11MeshHWMPGroup
			}
			::= {fsDot11MeshHWMPCompliances 1}
-- units of conformance
fsDot11MeshHWMPGroup OBJECT-GROUP
			OBJECTS {		
					dot11MeshHWMPmaxPREQretries,			                                                                                                             
        	dot11MeshHWMPnetDiameter,                                                                                                                   
        	dot11MeshHWMPnetDiameterTraversalTime,                                                                                                    
        	dot11MeshHWMPpreqMinInterval,                                                                                                    
        	dot11MeshHWMPperrMinInterval,                                                                                                              
        	dot11MeshHWMPactivePathToRootTimeout,                                                                                                       
        	dot11MeshHWMPactivePathTimeout,                                                                                                             
        	dot11MeshHWMProotMode,                                                                                                                      
        	dot11MeshHWMProotInterval,                                                                                                                  
        	dot11MeshHWMPrannInterval,                                                                                                                  
        	dot11MeshHWMPtargetOnly,                                                                                                                    
        	dot11MeshHWMPmaintenanceInterval,                                                                                                           
        	dot11MeshHWMPconfirmationInterval               
			}
			STATUS current
			DESCRIPTION
			 		"A collection of objects which is possible for there to be 
			  	 multiple IEEE 802.11 interfaces on one agent, each with its
           unique MAC address. The relationship between an IEEE 802.11
           interface and an interface in the context of the Internet-standard
           MIB is one-to-one. As such, the value of an ifIndex object instance
           can be directly used to identify corresponding instances of the
           objects defined herein."
      ::= { fsDot11MeshHWMPGroups 1 }
END

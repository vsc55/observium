-- *****************************************************************
-- FS-POE-MIB.mib:  FS POE MIB file
--
-- Feb 2012, Hedong
--
-- Copyright (c) 2012 by FS.COM Inc..
-- All rights reserved.
-- 
-- *****************************************************************
--

FS-POE-MIB DEFINITIONS ::= BEGIN

IMPORTS
        MODULE-IDENTITY,
        OBJECT-TYPE,
        NOTIFICATION-TYPE,
        Integer32,
        OBJECT-TYPE
                FROM SNMPv2-SMI
			  TruthValue
			    			FROM SNMPv2-TC
        MODULE-COMPLIANCE,
        OBJECT-GROUP
                FROM SNMPv2-CONF
        fsMgmt
                FROM FS-SMI;

fsPoeMIB MODULE-IDENTITY
        LAST-UPDATED "201202140000Z"
        ORGANIZATION "FS.COM Inc.."
        CONTACT-INFO
                " 
                Tel: 400-865-2852 

                E-mail: https://www.fs.com/live_chat_service_mail.html"
        DESCRIPTION
                "This module defines fs poe mibs."
        REVISION      "201202140000Z"
        DESCRIPTION
                "Add a table about poe."
        REVISION      "201202140000Z"
        DESCRIPTION
                "Initial version of this MIB module."
        ::= { fsMgmt 110 }

fsPoeConfigMIBObjects OBJECT IDENTIFIER ::= { fsPoeMIB 1 }

fsIfPoeTable OBJECT-TYPE
        SYNTAX 			SEQUENCE OF FSIfPoeEntry
        MAX-ACCESS 	not-accessible
        STATUS 			current
        DESCRIPTION
            "A table of objects that display and control the power
            characteristics of power Ethernet ports on a Power Source."
        ::= { fsPoeConfigMIBObjects 1 }

-- 6.1 配置信息		6.1.2 接口配置		表A.8 接口POE配置
   
fsIfPoeEntry OBJECT-TYPE
        SYNTAX 			FSIfPoeEntry
        MAX-ACCESS 	not-accessible
        STATUS 			current
        DESCRIPTION
            "A set of objects that display and control the power
               characteristics of a power Ethernet PSE port."
        INDEX { ifPoeIndex }
        ::= { fsIfPoeTable 1 }

FSIfPoeEntry ::=
        SEQUENCE {
            ifPoeIndex 			Integer32,
            ifIsPoe 				TruthValue,
            ifPoeEnable 		INTEGER,
            ifPoePwrStatus 	INTEGER,
            ifPoeMaxPwrSet 	Integer32,
            ifPoePriority 	INTEGER,
	    ifPoeConsumingPwr	Integer32,
	    ifIsHPoe 				TruthValue
        }
       
ifPoeIndex OBJECT-TYPE
        SYNTAX 			Integer32 (1..2147483647)
        MAX-ACCESS 	read-only
        STATUS 			current
        DESCRIPTION
            "This variable uniquely identifies the power Ethernet PSE
            port."
        ::= { fsIfPoeEntry 1 }
   
ifIsPoe OBJECT-TYPE
        SYNTAX TruthValue
        MAX-ACCESS read-only
        STATUS current
        DESCRIPTION
            "The poe port is supported or not."
        ::= { fsIfPoeEntry 2 }
           
ifPoeEnable OBJECT-TYPE
        SYNTAX INTEGER {
            enabled(1),
            disabled(2)
        }
        MAX-ACCESS read-write
        STATUS current
        DESCRIPTION
            "The poe port is enabled or disabled."
        ::= { fsIfPoeEntry 3 }
    
ifPoePwrStatus OBJECT-TYPE
        SYNTAX INTEGER {
            on(1),
            off(2)
        }
        MAX-ACCESS read-only
        STATUS current
        DESCRIPTION
            "The port is powered on or off."
        ::= { fsIfPoeEntry 4 }
                     
ifPoeMaxPwrSet OBJECT-TYPE
        SYNTAX Integer32 (1..2147483647)
        MAX-ACCESS read-write
        STATUS current
        DESCRIPTION
            "The port maximum power."
        ::= { fsIfPoeEntry 5 }                      

ifPoePriority OBJECT-TYPE
				SYNTAX INTEGER   {
               critical(1),
               high(2),
               low(3)
	     	}
        MAX-ACCESS read-write
        STATUS  current
        DESCRIPTION
              "The port prirority"
        ::= { fsIfPoeEntry 6 }

-- 6.2 性能信息		6.2.2 接口性能信息		表A.16 接口性能统计

ifPoeConsumingPwr OBJECT-TYPE
				SYNTAX 			Integer32
        MAX-ACCESS 	read-only
        STATUS  		current
        DESCRIPTION
              "The port consuming power."
        ::= { fsIfPoeEntry 7 }
 
ifIsHPoe OBJECT-TYPE
        SYNTAX TruthValue
        MAX-ACCESS read-only
        STATUS current
        DESCRIPTION
            "The port HPoE is supported."
        ::= { fsIfPoeEntry 8 }
        
-- Notification
fsPoeTraps OBJECT IDENTIFIER ::= { fsPoeMIB 2 }

-- 6.3 告警及通告		表A.17 交换机系统告警及通告

ifPoePowerOffTrap NOTIFICATION-TYPE
    OBJECTS { ifPoeIndex }
    STATUS  current
    DESCRIPTION
            "This notification is generated when port is powered off." 
    ::= { fsPoeTraps 1 }  

ifPoePowerOnTrap NOTIFICATION-TYPE
    OBJECTS { ifPoeIndex }
    STATUS  current
    DESCRIPTION
            "This notification is generated when port is powered on." 
    ::= { fsPoeTraps 2 }  
 
ifPoePboxAbnormalTrap NOTIFICATION-TYPE
    OBJECTS { ifPoeIndex }
    STATUS  current
    DESCRIPTION
            "This notification is generated when an abnormal pbox is detected." 
    ::= { fsPoeTraps 3 }  

END

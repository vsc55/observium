-- *****************************************************************
-- FS-CAPWAP-MULTICAST6-MIB.mib:  FS CAPWAP MULTICAST6 MIB file
--
-- May 2010, xieweiwu
--
-- Copyright (c) 2010 by FS.COM Inc..
-- All rights reserved.
-- 
-- *****************************************************************
--

FS-CAPWAP-MULTICAST6-MIB DEFINITIONS ::= BEGIN

IMPORTS
        MODULE-IDENTITY,
        OBJECT-TYPE
                FROM SNMPv2-SMI
		    InetAddress
		            FROM INET-ADDRESS-MIB
        MODULE-COMPLIANCE,
        OBJECT-GROUP
                FROM SNMPv2-CONF
        fsMgmt
                FROM FS-SMI;

fsCapwapMulticast6MIB MODULE-IDENTITY
        LAST-UPDATED "201005200000Z"
        ORGANIZATION "FS.COM Inc.."
        CONTACT-INFO
                " 
                Tel: 400-865-2852 

                E-mail: https://www.fs.com/live_chat_service_mail.html"
        DESCRIPTION
                "This module defines fs Capwap Multicast6 mibs."
        REVISION      "201005200000Z"
        DESCRIPTION
                "Initial version of this MIB module."
        ::= { fsMgmt 85}

fsCapwapMulticast6MIBObjects OBJECT IDENTIFIER ::= { fsCapwapMulticast6MIB 1 }


--capwap multicast6 mode
fsCapwapMulticast6WorkingMode OBJECT-TYPE
        SYNTAX INTEGER {
            disabled(1),   -- Multicast6 mode disable
            unicast(2),    -- Working in capwap unicast(2),
            multicast(3)    -- Working in capwap multicast(3)
        }
        MAX-ACCESS read-write
        STATUS current
        DESCRIPTION
            "System Multicast6 working mode:
             disabled(1):
                Multicast6 mode disable, and all MLD report or leave
                message will be discard.
             unicast(2):
                Working in capwap unicast.
             multicast(3):
                Working in capwap multicast."
        DEFVAL { disabled }
        ::= { fsCapwapMulticast6MIBObjects 1 }

--show capwap multicast6 group address
fsCapwapMulticast6Group OBJECT-TYPE
        SYNTAX InetAddress
        MAX-ACCESS read-write
        STATUS current
        DESCRIPTION
            "the address of capwap multicast"
        ::= { fsCapwapMulticast6MIBObjects 2 }

fsCapwapMulticast6MIBConformance OBJECT IDENTIFIER ::= { fsCapwapMulticast6MIB 2 }
fsCapwapMulticast6MIBCompliances OBJECT IDENTIFIER ::= { fsCapwapMulticast6MIBConformance 1 }
fsCapwapMulticast6MIBGroups      OBJECT IDENTIFIER ::= { fsCapwapMulticast6MIBConformance 2 }


-- compliance statements

fsCapwapMulticast6MIBCompliance MODULE-COMPLIANCE
        STATUS  current
        DESCRIPTION
                "The compliance statement for entities which implement
                the FS Capwap Multicast6 MIB"
        MODULE  -- this module
                MANDATORY-GROUPS { fsCapwapMulticast6MIBGroup
                 }
        ::= { fsCapwapMulticast6MIBCompliances 1 }
                
-- units of conformance

fsCapwapMulticast6MIBGroup OBJECT-GROUP
        OBJECTS {
           fsCapwapMulticast6WorkingMode,
           fsCapwapMulticast6Group
        }
        STATUS  current
        DESCRIPTION
                "A collection of objects providing CapwapMulticast6 configure ."
        ::= { fsCapwapMulticast6MIBGroups 1 }
        
END

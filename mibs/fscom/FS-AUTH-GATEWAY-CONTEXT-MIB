-- *****************************************************************
-- FS-AUTH-GATEWAY-CONTEXT-MIB.mib:  FS Auth-Gateway MIB file for multiple context
--
--
-- December 2009, rendh
--
-- Copyright (c) 2009 by FS.COM Inc..
-- All rights reserved.
-- 
-- *****************************************************************
--

FS-AUTH-GATEWAY-CONTEXT-MIB DEFINITIONS ::= BEGIN

IMPORTS
    MODULE-IDENTITY,
    OBJECT-TYPE,
    IpAddress, 
    Gauge32
            FROM SNMPv2-SMI
    DisplayString,
    RowStatus
            FROM SNMPv2-TC
    MODULE-COMPLIANCE,
    OBJECT-GROUP
            FROM SNMPv2-CONF
    fsMgmt
            FROM FS-SMI;

fsWebAuthVCMIB MODULE-IDENTITY
    LAST-UPDATED "200912060000Z"
    ORGANIZATION "FS.COM Inc.."
    CONTACT-INFO
            " 
            Tel: 400-865-2852 

            E-mail: https://www.fs.com/live_chat_service_mail.html"
    DESCRIPTION
            "This module defines my authGateway mibs for multiple context."
    REVISION      "200912060000Z"
    DESCRIPTION
            "Initial version of this MIB module."
    ::= { fsMgmt 67 }

fsWebAuthVCMIBObjects OBJECT IDENTIFIER ::= { fsWebAuthVCMIB 1 }


-- Web authentication gateway user table
  
fsWebAuthUserVCTable OBJECT-TYPE
    SYNTAX  SEQUENCE OF FSWebAuthUserVCEntry
    MAX-ACCESS  not-accessible
    STATUS      current
    DESCRIPTION
            "A table that contains generic information about every user 
            that is authenticated by web authentication gateway."
    ::= { fsWebAuthVCMIBObjects 1 }

fsWebAuthUserVCEntry OBJECT-TYPE
    SYNTAX  FSWebAuthUserVCEntry
    MAX-ACCESS  not-accessible
    STATUS  current
    DESCRIPTION
         "The entry of web authentication gateway table."
    INDEX   { authUserContextNameVC,authUserIpAddrVC }
    ::= { fsWebAuthUserVCTable 1 }

FSWebAuthUserVCEntry ::=
    SEQUENCE {
        authUserContextNameVC     DisplayString, 
        authUserIpAddrVC          IpAddress,
        authUserOnlineFlagVC      Gauge32,
        authUserTimeLimitVC       Gauge32,
        authUserTimeUsedVC        Gauge32,
        authUserStatusVC          RowStatus
    }
    
authUserContextNameVC OBJECT-TYPE
        SYNTAX DisplayString(SIZE (1..31))
        MAX-ACCESS read-only
        STATUS current
        DESCRIPTION
            "context name of this entry."
        ::= { fsWebAuthUserVCEntry  1 }        

authUserIpAddrVC OBJECT-TYPE
    SYNTAX  IpAddress
    MAX-ACCESS  read-only
    STATUS  current
    DESCRIPTION
            "The IP address of the user."
    ::= { fsWebAuthUserVCEntry 2 }

authUserOnlineFlagVC OBJECT-TYPE
    SYNTAX  Gauge32
    MAX-ACCESS  read-only
    STATUS  current
    DESCRIPTION
            "The online(1)/offline(2) flag of the user."
    ::= { fsWebAuthUserVCEntry 3 }


authUserTimeLimitVC OBJECT-TYPE
    SYNTAX  Gauge32
    MAX-ACCESS  read-create
    STATUS  current
    DESCRIPTION
            "The value, in seconds, is time limit of the online user.
            If the time is unlimited, then this object has the value 0."
    ::= { fsWebAuthUserVCEntry 4 }

authUserTimeUsedVC OBJECT-TYPE
    SYNTAX  Gauge32
    MAX-ACCESS  read-only
    STATUS  current
    DESCRIPTION
            "The value, in seconds, is time used by the online user."
    ::= { fsWebAuthUserVCEntry 5 }
       
authUserStatusVC OBJECT-TYPE
    SYNTAX RowStatus
    MAX-ACCESS read-create
    STATUS current
    DESCRIPTION
            "The status of this row, by which new entries may be
            created, or old entries deleted from this table."
   ::= { fsWebAuthUserVCEntry 6 }        



-- compliance statements
         
fsWebAuthVCMIBConformance OBJECT IDENTIFIER ::= { fsWebAuthVCMIB 3 }
fsWebAuthVCMIBCompliances OBJECT IDENTIFIER ::= { fsWebAuthVCMIBConformance 1 }
fsWebAuthVCMIBGroups      OBJECT IDENTIFIER ::= { fsWebAuthVCMIBConformance 2 }

fsWebAuthVCMIBCompliance MODULE-COMPLIANCE
    STATUS  current
    DESCRIPTION
            "The compliance statement for entities which implement
            the My WebAuth MIB for multiple context"
    MODULE  -- this module
            MANDATORY-GROUPS { fsWebAuthVCMIBGroup
             }
                   
    ::= { fsWebAuthVCMIBCompliances 1 }
            
-- units of conformance

fsWebAuthVCMIBGroup OBJECT-GROUP
    OBJECTS {
         authUserContextNameVC,
         authUserIpAddrVC,
         authUserOnlineFlagVC,
         authUserTimeLimitVC,
         authUserTimeUsedVC,
         authUserStatusVC   
    }
    STATUS  current
    DESCRIPTION
            "A collection of objects providing authGateway management and
            opertion to a My agent."
    ::= { fsWebAuthVCMIBGroups 1 } 

-- 

END

HIRSCHMANN-WAN-MOBILE-2-MIB DEFINITIONS ::= BEGIN

IMPORTS
    OBJECT-TYPE, MODULE-IDENTITY, Counter32, TimeTicks, Integer32
        FROM SNMPv2-SMI -- RFC 2578
    hmWanMgmt
    	FROM HIRSCHMANN-WAN-MIB;

hmWanMobile2Mib MODULE-IDENTITY
	LAST-UPDATED "201502130000Z" -- Februar 13, 2015
    ORGANIZATION "Hirschmann Automation and Control GmbH"
    CONTACT-INFO
        "Postal:     Stuttgarter Str. 45-51
                     72654 Neckartenzlingen
                     Germany
         Phone:      +49 7127 140
         E-mail:     hac.support@belden.com"
    DESCRIPTION
        "Copyright (C) 2015. All Rights Reserved."
    REVISION     "201502130000Z" -- Februar 13, 2015
    DESCRIPTION
         "Initial version."
    ::= { hmWanMgmt 5 }

hmWanMobileToday				OBJECT IDENTIFIER ::= { hmWanMobile2Mib 1 }

hmWanMobileTodayRxPri			OBJECT-TYPE
					SYNTAX	Counter32
					MAX-ACCESS	read-only
					STATUS	current
					::= { hmWanMobileToday 1 }

hmWanMobileTodayRxSec			OBJECT-TYPE
					SYNTAX	Counter32
					MAX-ACCESS	read-only
					STATUS	current
					::= { hmWanMobileToday 2 }

hmWanMobileTodayTxPri			OBJECT-TYPE
					SYNTAX	Counter32
					MAX-ACCESS	read-only
					STATUS	current
					::= { hmWanMobileToday 3 }

hmWanMobileTodayTxSec			OBJECT-TYPE
					SYNTAX	Counter32
					MAX-ACCESS	read-only
					STATUS	current
					::= { hmWanMobileToday 4 }

hmWanMobileTodayConnectionsPri		OBJECT-TYPE
					SYNTAX	Counter32
					MAX-ACCESS	read-only
					STATUS	current
					::= { hmWanMobileToday 5 }

hmWanMobileTodayConnectionsSec		OBJECT-TYPE
					SYNTAX	Counter32
					MAX-ACCESS	read-only
					STATUS	current
					::= { hmWanMobileToday 6 }

hmWanMobileTodayOnlinePri			OBJECT-TYPE
					SYNTAX	TimeTicks
					MAX-ACCESS	read-only
					STATUS	current
					::= { hmWanMobileToday 7 }

hmWanMobileTodayOnlineSec			OBJECT-TYPE
					SYNTAX	TimeTicks
					MAX-ACCESS	read-only
					STATUS	current
					::= { hmWanMobileToday 8 }

hmWanMobileTodayOffline			OBJECT-TYPE
					SYNTAX	TimeTicks
					MAX-ACCESS	read-only
					STATUS	current
					::= { hmWanMobileToday 9 }

hmWanMobileTodayCells			OBJECT-TYPE
					SYNTAX	Counter32
					MAX-ACCESS	read-only
					STATUS	current
					::= { hmWanMobileToday 10 }

hmWanMobileTodaySignalAvg			OBJECT-TYPE
					SYNTAX	Integer32
					MAX-ACCESS	read-only
					STATUS	current
					::= { hmWanMobileToday 11 }

hmWanMobileTodaySignalMin			OBJECT-TYPE
					SYNTAX	Integer32
					MAX-ACCESS	read-only
					STATUS	current
					::= { hmWanMobileToday 12 }

hmWanMobileTodaySignalMax			OBJECT-TYPE
					SYNTAX	Integer32
					MAX-ACCESS	read-only
					STATUS	current
					::= { hmWanMobileToday 13 }

hmWanMobileTodayDateMin			OBJECT-TYPE
					SYNTAX	Counter32
					MAX-ACCESS	read-only
					STATUS	current
					::= { hmWanMobileToday 14 }

hmWanMobileTodayDateMax			OBJECT-TYPE
					SYNTAX	Counter32
					MAX-ACCESS	read-only
					STATUS	current
					::= { hmWanMobileToday 15 }

hmWanMobileYesterday				OBJECT IDENTIFIER ::= { hmWanMobile2Mib 2 }

hmWanMobileYesterdayRxPri			OBJECT-TYPE
					SYNTAX	Counter32
					MAX-ACCESS	read-only
					STATUS	current
					::= { hmWanMobileYesterday 1 }

hmWanMobileYesterdayRxSec			OBJECT-TYPE
					SYNTAX	Counter32
					MAX-ACCESS	read-only
					STATUS	current
					::= { hmWanMobileYesterday 2 }

hmWanMobileYesterdayTxPri			OBJECT-TYPE
					SYNTAX	Counter32
					MAX-ACCESS	read-only
					STATUS	current
					::= { hmWanMobileYesterday 3 }

hmWanMobileYesterdayTxSec			OBJECT-TYPE
					SYNTAX	Counter32
					MAX-ACCESS	read-only
					STATUS	current
					::= { hmWanMobileYesterday 4 }

hmWanMobileYesterdayConnectionsPri		OBJECT-TYPE
					SYNTAX	Counter32
					MAX-ACCESS	read-only
					STATUS	current
					::= { hmWanMobileYesterday 5 }

hmWanMobileYesterdayConnectionsSec		OBJECT-TYPE
					SYNTAX	Counter32
					MAX-ACCESS	read-only
					STATUS	current
					::= { hmWanMobileYesterday 6 }

hmWanMobileYesterdayOnlinePri		OBJECT-TYPE
					SYNTAX	TimeTicks
					MAX-ACCESS	read-only
					STATUS	current
					::= { hmWanMobileYesterday 7 }

hmWanMobileYesterdayOnlineSec		OBJECT-TYPE
					SYNTAX	TimeTicks
					MAX-ACCESS	read-only
					STATUS	current
					::= { hmWanMobileYesterday 8 }

hmWanMobileYesterdayOffline			OBJECT-TYPE
					SYNTAX	TimeTicks
					MAX-ACCESS	read-only
					STATUS	current
					::= { hmWanMobileYesterday 9 }

hmWanMobileYesterdayCells			OBJECT-TYPE
					SYNTAX	Counter32
					MAX-ACCESS	read-only
					STATUS	current
					::= { hmWanMobileYesterday 10 }

hmWanMobileYesterdaySignalAvg		OBJECT-TYPE
					SYNTAX	Integer32
					MAX-ACCESS	read-only
					STATUS	current
					::= { hmWanMobileYesterday 11 }

hmWanMobileYesterdaySignalMin		OBJECT-TYPE
					SYNTAX	Integer32
					MAX-ACCESS	read-only
					STATUS	current
					::= { hmWanMobileYesterday 12 }

hmWanMobileYesterdaySignalMax		OBJECT-TYPE
					SYNTAX	Integer32
					MAX-ACCESS	read-only
					STATUS	current
					::= { hmWanMobileYesterday 13 }

hmWanMobileYesterdayDateMin			OBJECT-TYPE
					SYNTAX	Counter32
					MAX-ACCESS	read-only
					STATUS	current
					::= { hmWanMobileYesterday 14 }

hmWanMobileYesterdayDateMax			OBJECT-TYPE
					SYNTAX	Counter32
					MAX-ACCESS	read-only
					STATUS	current
					::= { hmWanMobileYesterday 15 }

hmWanMobileThisWeek				OBJECT IDENTIFIER ::= { hmWanMobile2Mib 3 }

hmWanMobileThisWeekRxPri			OBJECT-TYPE
					SYNTAX	Counter32
					MAX-ACCESS	read-only
					STATUS	current
					::= { hmWanMobileThisWeek 1 }

hmWanMobileThisWeekRxSec			OBJECT-TYPE
					SYNTAX	Counter32
					MAX-ACCESS	read-only
					STATUS	current
					::= { hmWanMobileThisWeek 2 }

hmWanMobileThisWeekTxPri			OBJECT-TYPE
					SYNTAX	Counter32
					MAX-ACCESS	read-only
					STATUS	current
					::= { hmWanMobileThisWeek 3 }

hmWanMobileThisWeekTxSec			OBJECT-TYPE
					SYNTAX	Counter32
					MAX-ACCESS	read-only
					STATUS	current
					::= { hmWanMobileThisWeek 4 }

hmWanMobileThisWeekConnectionsPri		OBJECT-TYPE
					SYNTAX	Counter32
					MAX-ACCESS	read-only
					STATUS	current
					::= { hmWanMobileThisWeek 5 }

hmWanMobileThisWeekConnectionsSec		OBJECT-TYPE
					SYNTAX	Counter32
					MAX-ACCESS	read-only
					STATUS	current
					::= { hmWanMobileThisWeek 6 }

hmWanMobileThisWeekOnlinePri			OBJECT-TYPE
					SYNTAX	TimeTicks
					MAX-ACCESS	read-only
					STATUS	current
					::= { hmWanMobileThisWeek 7 }

hmWanMobileThisWeekOnlineSec			OBJECT-TYPE
					SYNTAX	TimeTicks
					MAX-ACCESS	read-only
					STATUS	current
					::= { hmWanMobileThisWeek 8 }

hmWanMobileThisWeekOffline			OBJECT-TYPE
					SYNTAX	TimeTicks
					MAX-ACCESS	read-only
					STATUS	current
					::= { hmWanMobileThisWeek 9 }

hmWanMobileThisWeekCells			OBJECT-TYPE
					SYNTAX	Counter32
					MAX-ACCESS	read-only
					STATUS	current
					::= { hmWanMobileThisWeek 10 }

hmWanMobileThisWeekSignalAvg			OBJECT-TYPE
					SYNTAX	Integer32
					MAX-ACCESS	read-only
					STATUS	current
					::= { hmWanMobileThisWeek 11 }

hmWanMobileThisWeekSignalMin			OBJECT-TYPE
					SYNTAX	Integer32
					MAX-ACCESS	read-only
					STATUS	current
					::= { hmWanMobileThisWeek 12 }

hmWanMobileThisWeekSignalMax			OBJECT-TYPE
					SYNTAX	Integer32
					MAX-ACCESS	read-only
					STATUS	current
					::= { hmWanMobileThisWeek 13 }

hmWanMobileThisWeekDateMin			OBJECT-TYPE
					SYNTAX	Counter32
					MAX-ACCESS	read-only
					STATUS	current
					::= { hmWanMobileThisWeek 14 }

hmWanMobileThisWeekDateMax			OBJECT-TYPE
					SYNTAX	Counter32
					MAX-ACCESS	read-only
					STATUS	current
					::= { hmWanMobileThisWeek 15 }

hmWanMobileLastWeek				OBJECT IDENTIFIER ::= { hmWanMobile2Mib 4 }

hmWanMobileLastWeekRxPri			OBJECT-TYPE
					SYNTAX	Counter32
					MAX-ACCESS	read-only
					STATUS	current
					::= { hmWanMobileLastWeek 1 }

hmWanMobileLastWeekRxSec			OBJECT-TYPE
					SYNTAX	Counter32
					MAX-ACCESS	read-only
					STATUS	current
					::= { hmWanMobileLastWeek 2 }

hmWanMobileLastWeekTxPri			OBJECT-TYPE
					SYNTAX	Counter32
					MAX-ACCESS	read-only
					STATUS	current
					::= { hmWanMobileLastWeek 3 }

hmWanMobileLastWeekTxSec			OBJECT-TYPE
					SYNTAX	Counter32
					MAX-ACCESS	read-only
					STATUS	current
					::= { hmWanMobileLastWeek 4 }

hmWanMobileLastWeekConnectionsPri		OBJECT-TYPE
					SYNTAX	Counter32
					MAX-ACCESS	read-only
					STATUS	current
					::= { hmWanMobileLastWeek 5 }

hmWanMobileLastWeekConnectionsSec		OBJECT-TYPE
					SYNTAX	Counter32
					MAX-ACCESS	read-only
					STATUS	current
					::= { hmWanMobileLastWeek 6 }

hmWanMobileLastWeekOnlinePri			OBJECT-TYPE
					SYNTAX	TimeTicks
					MAX-ACCESS	read-only
					STATUS	current
					::= { hmWanMobileLastWeek 7 }

hmWanMobileLastWeekOnlineSec			OBJECT-TYPE
					SYNTAX	TimeTicks
					MAX-ACCESS	read-only
					STATUS	current
					::= { hmWanMobileLastWeek 8 }

hmWanMobileLastWeekOffline			OBJECT-TYPE
					SYNTAX	TimeTicks
					MAX-ACCESS	read-only
					STATUS	current
					::= { hmWanMobileLastWeek 9 }

hmWanMobileLastWeekCells			OBJECT-TYPE
					SYNTAX	Counter32
					MAX-ACCESS	read-only
					STATUS	current
					::= { hmWanMobileLastWeek 10 }

hmWanMobileLastWeekSignalAvg			OBJECT-TYPE
					SYNTAX	Integer32
					MAX-ACCESS	read-only
					STATUS	current
					::= { hmWanMobileLastWeek 11 }

hmWanMobileLastWeekSignalMin			OBJECT-TYPE
					SYNTAX	Integer32
					MAX-ACCESS	read-only
					STATUS	current
					::= { hmWanMobileLastWeek 12 }

hmWanMobileLastWeekSignalMax			OBJECT-TYPE
					SYNTAX	Integer32
					MAX-ACCESS	read-only
					STATUS	current
					::= { hmWanMobileLastWeek 13 }

hmWanMobileLastWeekDateMin			OBJECT-TYPE
					SYNTAX	Counter32
					MAX-ACCESS	read-only
					STATUS	current
					::= { hmWanMobileLastWeek 14 }

hmWanMobileLastWeekDateMax			OBJECT-TYPE
					SYNTAX	Counter32
					MAX-ACCESS	read-only
					STATUS	current
					::= { hmWanMobileLastWeek 15 }

hmWanMobileThisPeriod			OBJECT IDENTIFIER ::= { hmWanMobile2Mib 5 }

hmWanMobileThisPeriodRxPri			OBJECT-TYPE
					SYNTAX	Counter32
					MAX-ACCESS	read-only
					STATUS	current
					::= { hmWanMobileThisPeriod 1 }

hmWanMobileThisPeriodRxSec			OBJECT-TYPE
					SYNTAX	Counter32
					MAX-ACCESS	read-only
					STATUS	current
					::= { hmWanMobileThisPeriod 2 }

hmWanMobileThisPeriodTxPri			OBJECT-TYPE
					SYNTAX	Counter32
					MAX-ACCESS	read-only
					STATUS	current
					::= { hmWanMobileThisPeriod 3 }

hmWanMobileThisPeriodTxSec			OBJECT-TYPE
					SYNTAX	Counter32
					MAX-ACCESS	read-only
					STATUS	current
					::= { hmWanMobileThisPeriod 4 }

hmWanMobileThisPeriodConnectionsPri		OBJECT-TYPE
					SYNTAX	Counter32
					MAX-ACCESS	read-only
					STATUS	current
					::= { hmWanMobileThisPeriod 5 }

hmWanMobileThisPeriodConnectionsSec		OBJECT-TYPE
					SYNTAX	Counter32
					MAX-ACCESS	read-only
					STATUS	current
					::= { hmWanMobileThisPeriod 6 }

hmWanMobileThisPeriodOnlinePri		OBJECT-TYPE
					SYNTAX	TimeTicks
					MAX-ACCESS	read-only
					STATUS	current
					::= { hmWanMobileThisPeriod 7 }

hmWanMobileThisPeriodOnlineSec		OBJECT-TYPE
					SYNTAX	TimeTicks
					MAX-ACCESS	read-only
					STATUS	current
					::= { hmWanMobileThisPeriod 8 }

hmWanMobileThisPeriodOffline			OBJECT-TYPE
					SYNTAX	TimeTicks
					MAX-ACCESS	read-only
					STATUS	current
					::= { hmWanMobileThisPeriod 9 }

hmWanMobileThisPeriodCells			OBJECT-TYPE
					SYNTAX	Counter32
					MAX-ACCESS	read-only
					STATUS	current
					::= { hmWanMobileThisPeriod 10 }

hmWanMobileThisPeriodSignalAvg		OBJECT-TYPE
					SYNTAX	Integer32
					MAX-ACCESS	read-only
					STATUS	current
					::= { hmWanMobileThisPeriod 11 }

hmWanMobileThisPeriodSignalMin		OBJECT-TYPE
					SYNTAX	Integer32
					MAX-ACCESS	read-only
					STATUS	current
					::= { hmWanMobileThisPeriod 12 }

hmWanMobileThisPeriodSignalMax		OBJECT-TYPE
					SYNTAX	Integer32
					MAX-ACCESS	read-only
					STATUS	current
					::= { hmWanMobileThisPeriod 13 }

hmWanMobileThisPeriodDateMin			OBJECT-TYPE
					SYNTAX	Counter32
					MAX-ACCESS	read-only
					STATUS	current
					::= { hmWanMobileThisPeriod 14 }

hmWanMobileThisPeriodDateMax			OBJECT-TYPE
					SYNTAX	Counter32
					MAX-ACCESS	read-only
					STATUS	current
					::= { hmWanMobileThisPeriod 15 }

hmWanMobileLastPeriod			OBJECT IDENTIFIER ::= { hmWanMobile2Mib 6 }

hmWanMobileLastPeriodRxPri			OBJECT-TYPE
					SYNTAX	Counter32
					MAX-ACCESS	read-only
					STATUS	current
					::= { hmWanMobileLastPeriod 1 }

hmWanMobileLastPeriodRxSec			OBJECT-TYPE
					SYNTAX	Counter32
					MAX-ACCESS	read-only
					STATUS	current
					::= { hmWanMobileLastPeriod 2 }

hmWanMobileLastPeriodTxPri			OBJECT-TYPE
					SYNTAX	Counter32
					MAX-ACCESS	read-only
					STATUS	current
					::= { hmWanMobileLastPeriod 3 }

hmWanMobileLastPeriodTxSec			OBJECT-TYPE
					SYNTAX	Counter32
					MAX-ACCESS	read-only
					STATUS	current
					::= { hmWanMobileLastPeriod 4 }

hmWanMobileLastPeriodConnectionsPri		OBJECT-TYPE
					SYNTAX	Counter32
					MAX-ACCESS	read-only
					STATUS	current
					::= { hmWanMobileLastPeriod 5 }

hmWanMobileLastPeriodConnectionsSec		OBJECT-TYPE
					SYNTAX	Counter32
					MAX-ACCESS	read-only
					STATUS	current
					::= { hmWanMobileLastPeriod 6 }

hmWanMobileLastPeriodOnlinePri		OBJECT-TYPE
					SYNTAX	TimeTicks
					MAX-ACCESS	read-only
					STATUS	current
					::= { hmWanMobileLastPeriod 7 }

hmWanMobileLastPeriodOnlineSec		OBJECT-TYPE
					SYNTAX	TimeTicks
					MAX-ACCESS	read-only
					STATUS	current
					::= { hmWanMobileLastPeriod 8 }

hmWanMobileLastPeriodOffline			OBJECT-TYPE
					SYNTAX	TimeTicks
					MAX-ACCESS	read-only
					STATUS	current
					::= { hmWanMobileLastPeriod 9 }

hmWanMobileLastPeriodCells			OBJECT-TYPE
					SYNTAX	Counter32
					MAX-ACCESS	read-only
					STATUS	current
					::= { hmWanMobileLastPeriod 10 }

hmWanMobileLastPeriodSignalAvg		OBJECT-TYPE
					SYNTAX	Integer32
					MAX-ACCESS	read-only
					STATUS	current
					::= { hmWanMobileLastPeriod 11 }

hmWanMobileLastPeriodSignalMin		OBJECT-TYPE
					SYNTAX	Integer32
					MAX-ACCESS	read-only
					STATUS	current
					::= { hmWanMobileLastPeriod 12 }

hmWanMobileLastPeriodSignalMax		OBJECT-TYPE
					SYNTAX	Integer32
					MAX-ACCESS	read-only
					STATUS	current
					::= { hmWanMobileLastPeriod 13 }

hmWanMobileLastPeriodDateMin			OBJECT-TYPE
					SYNTAX	Counter32
					MAX-ACCESS	read-only
					STATUS	current
					::= { hmWanMobileLastPeriod 14 }

hmWanMobileLastPeriodDateMax			OBJECT-TYPE
					SYNTAX	Counter32
					MAX-ACCESS	read-only
					STATUS	current
					::= { hmWanMobileLastPeriod 15 }

END

HIRSCHMANN-WAN-MOBILE-MIB DEFINITIONS ::= BEGIN

IMPORTS
    OBJECT-TYPE, MODULE-IDENTITY, TimeTicks, Counter32, IpAddress, Integer32
        FROM SNMPv2-SMI -- RFC 2578
    hmWanMgmt
    	FROM HIRSCHMANN-WAN-MIB;

hmWanMobileMib MODULE-IDENTITY
	LAST-UPDATED "201608090000Z" -- August 9, 2016
    ORGANIZATION "Hirschmann Automation and Control GmbH"
    CONTACT-INFO
        "Postal:     Stuttgarter Str. 45-51
                     72654 Neckartenzlingen
                     Germany
         Phone:      +49 7127 140
         E-mail:     hac.support@belden.com"
    DESCRIPTION
        "Copyright (C) 2015. All Rights Reserved."
    REVISION     "201608090000Z" -- August 9, 2016
    DESCRIPTION
         "Initial version."
    ::= { hmWanMgmt 4 }

hmWanMobileTechnology	OBJECT-TYPE
					SYNTAX	INTEGER {
						none (0),
						gprs (2),
						edge (4),
						umts (6),
						hsdpa (8),
						hsupa (10),
						hspa (12),
						lte (14),
						cdma (16),
						evdo (18),
						evdo0 (20),
						evdoA (22),
						evdoB (24)
					}
					MAX-ACCESS	read-only
					STATUS	current
					::= { hmWanMobileMib 1 }

hmWanMobilePLMN				OBJECT-TYPE
					SYNTAX	OCTET STRING
					MAX-ACCESS	read-only
					STATUS	current
					::= { hmWanMobileMib 2 }

hmWanMobileCell				OBJECT-TYPE
					SYNTAX	OCTET STRING
					MAX-ACCESS	read-only
					STATUS	current
					::= { hmWanMobileMib 3 }

hmWanMobileChannel				OBJECT-TYPE
					SYNTAX	OCTET STRING
					MAX-ACCESS	read-only
					STATUS	current
					::= { hmWanMobileMib 4 }

hmWanMobileSignalStrength			OBJECT-TYPE
					SYNTAX	Integer32
					MAX-ACCESS	read-only
					STATUS	current
					::= { hmWanMobileMib 5 }

hmWanMobileChannelN1				OBJECT-TYPE
					SYNTAX	OCTET STRING
					MAX-ACCESS	read-only
					STATUS	current
					::= { hmWanMobileMib 6 }

hmWanMobileSignalStrengthN1			OBJECT-TYPE
					SYNTAX	Integer32
					MAX-ACCESS	read-only
					STATUS	current
					::= { hmWanMobileMib 7 }

hmWanMobileChannelN2				OBJECT-TYPE
					SYNTAX	OCTET STRING
					MAX-ACCESS	read-only
					STATUS	current
					::= { hmWanMobileMib 8 }

hmWanMobileSignalStrengthN2			OBJECT-TYPE
					SYNTAX	Integer32
					MAX-ACCESS	read-only
					STATUS	current
					::= { hmWanMobileMib 9 }

hmWanMobileChannelN3				OBJECT-TYPE
					SYNTAX	OCTET STRING
					MAX-ACCESS	read-only
					STATUS	current
					::= { hmWanMobileMib 10 }

hmWanMobileSignalStrengthN3			OBJECT-TYPE
					SYNTAX	Integer32
					MAX-ACCESS	read-only
					STATUS	current
					::= { hmWanMobileMib 11 }

hmWanMobileChannelN4				OBJECT-TYPE
					SYNTAX	OCTET STRING
					MAX-ACCESS	read-only
					STATUS	current
					::= { hmWanMobileMib 12 }

hmWanMobileSignalStrengthN4			OBJECT-TYPE
					SYNTAX	Integer32
					MAX-ACCESS	read-only
					STATUS	current
					::= { hmWanMobileMib 13 }

hmWanMobileChannelN5				OBJECT-TYPE
					SYNTAX	OCTET STRING
					MAX-ACCESS	read-only
					STATUS	current
					::= { hmWanMobileMib 14 }

hmWanMobileSignalStrengthN5			OBJECT-TYPE
					SYNTAX	Integer32
					MAX-ACCESS	read-only
					STATUS	current
					::= { hmWanMobileMib 15 }

hmWanMobileUpTime				OBJECT-TYPE
					SYNTAX	TimeTicks
					MAX-ACCESS	read-only
					STATUS	current
					::= { hmWanMobileMib 16 }

hmWanMobileConnect				OBJECT-TYPE
					SYNTAX	Counter32
					MAX-ACCESS	read-only
					STATUS	current
					::= { hmWanMobileMib 17 }

hmWanMobileDisconnect			OBJECT-TYPE
					SYNTAX	Counter32
					MAX-ACCESS	read-only
					STATUS	current
					::= { hmWanMobileMib 18 }

hmWanMobileCard				OBJECT-TYPE
					SYNTAX	INTEGER {
						primary (0),
						secondary (1),
						tertiary (2)
					}
					MAX-ACCESS	read-only
					STATUS	current
					::= { hmWanMobileMib 19 }

hmWanMobileIPAddress				OBJECT-TYPE
					SYNTAX	IpAddress
					MAX-ACCESS	read-only
					STATUS	current
					::= { hmWanMobileMib 20 }

hmWanMobileLatency				OBJECT-TYPE
					SYNTAX	Integer32
					MAX-ACCESS	read-only
					STATUS	current
					::= { hmWanMobileMib 21 }

hmWanMobileReportPeriod			OBJECT-TYPE
					SYNTAX	Integer32
					MAX-ACCESS	read-only
					STATUS	current
					::= { hmWanMobileMib 22 }

hmWanMobileRegistration			OBJECT-TYPE
					SYNTAX	INTEGER {
						unknown (0),
						idle (1),
						search (2),
						denied (3),
						home (4),
						foregien (5)
					}
					MAX-ACCESS	read-only
					STATUS	current
					::= { hmWanMobileMib 23 }

hmWanMobileOperator				OBJECT-TYPE
					SYNTAX	OCTET STRING
					MAX-ACCESS	read-only
					STATUS	current
					::= { hmWanMobileMib 24 }

hmWanMobileLAC				OBJECT-TYPE
					SYNTAX	OCTET STRING
					MAX-ACCESS	read-only
					STATUS	current
					::= { hmWanMobileMib 25 }

hmWanMobileSignalQuality			OBJECT-TYPE
					SYNTAX	Integer32
					MAX-ACCESS	read-only
					STATUS	current
					::= { hmWanMobileMib 26 }

hmWanMobileCSQ  			OBJECT-TYPE
					SYNTAX	Integer32
					MAX-ACCESS	read-only
					STATUS	current
					::= { hmWanMobileMib 27 }

END

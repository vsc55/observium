HIRSCHMANN-WAN-PRODUCTS-MIB DEFINITIONS ::= BEGIN

--
-- *************************************************************
-- Hirschmann WAN MIB
-- *************************************************************
--

IMPORTS
    MODULE-IDENTITY
        FROM SNMPv2-SMI -- RFC 2578
    hmWanMgmt
    	FROM HIRSCHMANN-WAN-MIB;

hmWanProductsMib MODULE-IDENTITY
	LAST-UPDATED "201608090000Z" -- August 9, 2016
    ORGANIZATION "Hirschmann Automation and Control GmbH"
    CONTACT-INFO
        "Postal:     Stuttgarter Str. 45-51
                     72654 Neckartenzlingen
                     Germany
         Phone:      +49 7127 140
         E-mail:     hac.support@belden.com"
    DESCRIPTION
        "Copyright (C) 2015. All Rights Reserved."
    REVISION     "201608090000Z" -- August 9, 2016
    DESCRIPTION
         "Initial version."
    ::= { hmWanMgmt 1 }

owl-3g		OBJECT IDENTIFIER ::= { hmWanProductsMib 1 }
owl-LTE		OBJECT IDENTIFIER ::= { hmWanProductsMib 2 }
owl-LTE-M12	OBJECT IDENTIFIER ::= { hmWanProductsMib 3 }

END

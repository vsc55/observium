RUBYTECH-GS2108C-MIB DEFINITIONS ::= BEGIN

IMPORTS
    DisplayString FROM SNMPv2-TC
    MODULE-COMPLIANCE,OBJECT-GROUP, NOTIFICATION-GROUP       FROM SNMPv2-CONF
    enterprises,MODULE-IDENTITY,OBJECT-TYPE,NOTIFICATION-TYPE,Counter32,IpAddress        FROM SNMPv2-SMI
    ifIndex    FROM RFC1213-MIB;       


rubytech MODULE-IDENTITY
       LAST-UPDATED "200603030000Z"
       ORGANIZATION "Ruby Tech Corp."
       CONTACT-INFO
           "2F, No.7, Lane 50, Nan Kang Road, Sec.3, Taipei, Taiwan
            Email: rubytech@mail.rubytech.com.tw
            TEL: 886-2-2785-3961
            FAX: 886-2-2786-3012"
       DESCRIPTION
           "The MIB module for Ruby Tech."
       ::= { enterprises 5205 }

switch                       OBJECT IDENTIFIER ::= { rubytech 2 }

gs2108cProductID	        OBJECT IDENTIFIER ::= { switch 18 }

gs2108cProduces            OBJECT IDENTIFIER ::= { gs2108cProductID 1 }

gs2108cSystem           	OBJECT IDENTIFIER ::= { gs2108cProduces 1 }

gs2108cCommonSys           	OBJECT IDENTIFIER ::= { gs2108cSystem 1 }

gs2108cReboot OBJECT-TYPE
	SYNTAX		INTEGER(0|1|2)
	MAX-ACCESS	    read-write
	STATUS		current
	DESCRIPTION
		"reboot the system. Get this oid always return zero.
            0 - do nothing
			1 - reboot without saving start
			2 - reboot with saving start"
--	@@ACTION	ruby_common_sys
	::= { gs2108cCommonSys 1 }

gs2108cBiosVsersion	OBJECT-TYPE
	SYNTAX		DisplayString
	MAX-ACCESS	    read-only
	STATUS		current
	DESCRIPTION
		"Get the BIOS version of the system."
--	@@ACTION	ruby_common_sys
	::= { gs2108cCommonSys 2 }

gs2108cFirmwareVersion	OBJECT-TYPE
	SYNTAX		DisplayString
	MAX-ACCESS	    read-only
	STATUS		current
	DESCRIPTION
		"Get the firmware version of the system."
--	@@ACTION	ruby_common_sys
	::= { gs2108cCommonSys 3 }

gs2108cHardwareVersion	OBJECT-TYPE
	SYNTAX		DisplayString
	MAX-ACCESS	    read-only
	STATUS		current
	DESCRIPTION
		"Get the hardware version of the system."
--	@@ACTION	ruby_common_sys
	::= { gs2108cCommonSys 4 }

gs2108cMechanicalVersion OBJECT-TYPE
	SYNTAX		DisplayString
	MAX-ACCESS 	    read-only
	STATUS		current
	DESCRIPTION
		"Get the mechanical version of the system."
--	@@ACTION	ruby_common_sys
	::= { gs2108cCommonSys 5 }

gs2108cSeriesNumber	OBJECT-TYPE
	SYNTAX		DisplayString
	MAX-ACCESS	    read-only
	STATUS		current
	DESCRIPTION
		"Get the series number of the system."
--	@@ACTION	ruby_common_sys
	::= { gs2108cCommonSys 6 }

gs2108cHostMacAddress	OBJECT-TYPE
	SYNTAX		DisplayString
	MAX-ACCESS	    read-only
	STATUS		current
	DESCRIPTION
		"Get the MAC address of the system."
--	@@ACTION	ruby_common_sys
	::= { gs2108cCommonSys 7 }

gs2108cDevicePort	OBJECT-TYPE
	SYNTAX		DisplayString
	MAX-ACCESS  	read-only
	STATUS		current
	DESCRIPTION
		"Get the quantity of ports that this system owns now."
--	@@ACTION	ruby_common_sys
	::= { gs2108cCommonSys 8 }

gs2108cRamSize  OBJECT-TYPE
    SYNTAX      DisplayString
    MAX-ACCESS      read-only
    STATUS      current
    DESCRIPTION
        "Get the RAM size of the system."
--	@@ACTION	ruby_common_sys
	::= { gs2108cCommonSys 9 }        

gs2108cFlashSize  OBJECT-TYPE
    SYNTAX      DisplayString
    MAX-ACCESS      read-only
    STATUS      current
    DESCRIPTION
        "Get the flash size of the system."
--	@@ACTION	ruby_common_sys
	::= { gs2108cCommonSys 10 } 

gs2108cIP           	OBJECT IDENTIFIER ::= { gs2108cSystem 2 }

gs2108cDhcpSetting OBJECT-TYPE
	SYNTAX		    INTEGER(0|1)
	MAX-ACCESS	        read-write
	STATUS		    current
	DESCRIPTION
		"Get/Set DHCP status of the system.
			0 - DHCP disable
			1 - DHCP enable"
--	@@ACTION	ruby_sys_ip
	::= { gs2108cIP 1 }

gs2108cIPAddress OBJECT-TYPE
	SYNTAX      IpAddress
	MAX-ACCESS	    read-write
	STATUS		current
	DESCRIPTION
		"Get/Set the IP address of the system.
		 Can't Set this OID if DHCP status is enabled."
--	@@ACTION	ruby_sys_ip
	::= { gs2108cIP 2 }

gs2108cNetMask OBJECT-TYPE
	SYNTAX      IpAddress
	MAX-ACCESS	    read-write
	STATUS		current
	DESCRIPTION
		"Get/Set the netmask of the system.
		 Can't Set this OID if DHCP status is enabled."
--	@@ACTION	ruby_sys_ip
	::= { gs2108cIP 3 }

gs2108cDefaultGateway OBJECT-TYPE
	SYNTAX      IpAddress
	MAX-ACCESS	    read-write
	STATUS		current
	DESCRIPTION
		"Get/Set the default gateway of the system.
		 Can't Set this OID if DHCP status is enabled."
--	@@ACTION	ruby_sys_ip
	::= { gs2108cIP 4 }
	
gs2108cDnsSetting OBJECT-TYPE
	SYNTAX      INTEGER(0|1)
	MAX-ACCESS	    read-write
	STATUS		current
	DESCRIPTION
		"Get/Set the source of DNS server.
		 Can't Set this OID if DHCP status is disabled.
			0 - manual, the DNS server is from manaul setting
            1 - auto, the DNS server is assigned by DHCP server."
--	@@ACTION	ruby_sys_ip
	::= { gs2108cIP 5 }	
	
gs2108cDnsServer OBJECT-TYPE
	SYNTAX      IpAddress
	MAX-ACCESS	    read-write
	STATUS		current
	DESCRIPTION
		"Get/Set the DNS server of the system."
--	@@ACTION	ruby_sys_ip
	::= { gs2108cIP 6 }	
	
gs2108cTime           	OBJECT IDENTIFIER ::= { gs2108cSystem 3 }

gs2108cSystemCurrentTime OBJECT-TYPE
	SYNTAX      DisplayString
	MAX-ACCESS	    read-only
	STATUS		current
	DESCRIPTION
		"Get the current time in the system."
--	@@ACTION	ruby_sys_time
	::= { gs2108cTime 1 }

gs2108cManualTimeSetting OBJECT-TYPE
	SYNTAX      DisplayString
	MAX-ACCESS	    read-write
	STATUS		current
	DESCRIPTION
		"Get/Set the system time of the device.
        The input format is 'Year/Month/Day/Hour/Minute/Second'.
        ex: 2004/1/1/12/34/25  means 2004/1/1 - 12:24:25 .
        value range:
        Year    : 2000 - 2036,
        Mouth   : 1 - 12,
        Day     : 1 - 31,
        Hour    : 0 - 23,
        Minute  : 0 - 59,
        sec     : 0 - 59."
--	@@ACTION	ruby_sys_time
	::= { gs2108cTime 2 }

gs2108cNTPServer OBJECT-TYPE
	SYNTAX      DisplayString
	MAX-ACCESS	    read-write
	STATUS		current
	DESCRIPTION
		"Get/Set the NTP Time Server. You can use the IP address or domain name."
--	@@ACTION	ruby_sys_time
	::= { gs2108cTime 3 }

gs2108cNTPTimeZone OBJECT-TYPE
	SYNTAX      INTEGER(-12..13)
	MAX-ACCESS	    read-write
	STATUS		current
	DESCRIPTION
		"Get/Set the NTP Time Zone. 
		value range is between -12 and 13
		-12 - GMT -12:00,
		-11 - GMT -11:00,
		-10 - GMT -10:00,
		 -9 - GMT -09:00,
		 -8 - GMT -08:00,
		 -7 - GMT -07:00,
		 -6 - GMT -06:00,
		 -5 - GMT -05:00,
		 -4 - GMT -04:00,
		 -3 - GMT -03:00,
		 -2 - GMT -02:00,
		 -1 - GMT -01:00,
		  0 - GMT +00:00,
		  1 - GMT +01:00,
		  2 - GMT +02:00,
		  3 - GMT +03:00,
		  4 - GMT +04:00,
		  5 - GMT +05:00,
		  6 - GMT +06:00,
		  7 - GMT +07:00,
		  8 - GMT +08:00,
		  9 - GMT +09:00,
		 10 - GMT +10:00,
		 11 - GMT +11:00,
		 12 - GMT +12:00,
		 13 - GMT +13:00. "		
--	@@ACTION	ruby_sys_time
	::= { gs2108cTime 4 }

gs2108cNTPTimeSync OBJECT-TYPE
	SYNTAX      INTEGER(0|1)
	MAX-ACCESS	    read-write
	STATUS		current
	DESCRIPTION
		"Sync time from NTP Server. Get this oid always return zero.
		Setting the Time Server and TimeZone before doing time sync.
		Notice that time server must be correct!
		value range (1|0): 
		1 - sync. 
        0 - do nothing."
--	@@ACTION	ruby_sys_time
	::= { gs2108cTime 5 }

gs2108cDaylightSavingTime OBJECT-TYPE
	SYNTAX      INTEGER(-5..5)
	MAX-ACCESS	    read-write
	STATUS		current
	DESCRIPTION
		"Get/Set the daylight saveing time. 
		value range is between -5 and 5. unit: hour. "
--	@@ACTION	ruby_sys_time
	::= { gs2108cTime 6 }

gs2108cDaylightStartTime OBJECT-TYPE
	SYNTAX      DisplayString
	MAX-ACCESS	    read-write
	STATUS		current
	DESCRIPTION
		"Get/Set the Start time of Daylight Saving.
		The input format is 'MM/DD/HH', 
		and daylight saving start month can't equal end month.
		example: month/day/hour   10/01/00 
		month: 01~12, day: 01~31, hour: 00~23 ."
--	@@ACTION	ruby_sys_time
	::= { gs2108cTime 7 }

gs2108cDaylightEndTime OBJECT-TYPE
	SYNTAX      DisplayString
	MAX-ACCESS	    read-write
	STATUS		current
	DESCRIPTION
		"Get/Set the End time of Daylight Saving.
		The input format is 'MM/DD/HH',
		and daylight saving start month can't equal end month.
		example: month/day/hour   04/01/00 
		month: 01~12, day: 01~31, hour: 00~23 ."
--	@@ACTION	ruby_sys_time
	::= { gs2108cTime 8 }

gs2108cAccount           	OBJECT IDENTIFIER ::= { gs2108cSystem 4 }

gs2108cAccountNumber OBJECT-TYPE
	SYNTAX      INTEGER(1..5)
	MAX-ACCESS	    read-only
	STATUS		current
	DESCRIPTION
		"Get the current account number(s) of the system."
--	@@ACTION	ruby_sys_account
	::= { gs2108cAccount 1 }
	
gs2108cAccountTable	OBJECT-TYPE
	SYNTAX		SEQUENCE OF GS2108CAccountEntry
	MAX-ACCESS	not-accessible
	STATUS		current
	DESCRIPTION
		"A list of GS2108CAccountEntry. The number of entries are given by 
		the value of gs2108cAccountNumber."
	::= { gs2108cAccount 2 }	
	
GS2108CAccountEntry ::=
SEQUENCE {
    gs2108cAccountIndex		    INTEGER,
    gs2108cAccountAuthorization	DisplayString,
    gs2108cAccountName             DisplayString,
    gs2108cAccountPassword         DisplayString
}

gs2108cAccountEntry	OBJECT-TYPE
	SYNTAX		GS2108CAccountEntry
	MAX-ACCESS	    not-accessible
	STATUS		current
	DESCRIPTION
		"Entry(s) for account informaion."
	INDEX {gs2108cAccountIndex}
	::= { gs2108cAccountTable 1 }
	
gs2108cAccountIndex	OBJECT-TYPE
	SYNTAX		INTEGER(1..5)
	MAX-ACCESS	    read-only
	STATUS		current
	DESCRIPTION
		"The index of the account entry."
--	@@ACTION	ruby_sys_accountentry
	::= { gs2108cAccountEntry 1 }	

gs2108cAccountAuthorization	OBJECT-TYPE
	SYNTAX		DisplayString
	MAX-ACCESS	    read-only
	STATUS		current
	DESCRIPTION
		"The authorization of the account entry."
--	@@ACTION	ruby_sys_accountentry
	::= { gs2108cAccountEntry 2 }	

gs2108cAccountName	OBJECT-TYPE
	SYNTAX		DisplayString
	MAX-ACCESS	    read-write
	STATUS		current
	DESCRIPTION
		"The username of the account entry."
--	@@ACTION	ruby_sys_accountentry
	::= { gs2108cAccountEntry 3 }	

gs2108cAccountPassword	OBJECT-TYPE
	SYNTAX		DisplayString
	MAX-ACCESS	    read-write
	STATUS		current
	DESCRIPTION
		"The password of the account entry. The return value is always '********'."
--	@@ACTION	ruby_sys_accountentry
	::= { gs2108cAccountEntry 4 }		

gs2108cAccountAddName OBJECT-TYPE
	SYNTAX      DisplayString
	MAX-ACCESS	    read-write
	STATUS		current
	DESCRIPTION
		"The account name for adding operation."
--	@@ACTION	ruby_sys_account
	::= { gs2108cAccount 3 }

gs2108cAccountAddPassword OBJECT-TYPE
	SYNTAX      DisplayString
	MAX-ACCESS	    read-write
	STATUS		current
	DESCRIPTION
		"The account password for adding operation. The return value is aloways '********'."
--	@@ACTION	ruby_sys_account
	::= { gs2108cAccount 4 }

gs2108cDoAccountAdd OBJECT-TYPE
	SYNTAX      INTEGER(0|1)
	MAX-ACCESS	    read-write
	STATUS		current
	DESCRIPTION
		"Add account name. OID gs2108cAccountAddName and gs2108cAccountAddPassword must be 
        filled first. Get this oid always return zero.
            1 - add account.
            0 - do nothing."
--	@@ACTION	ruby_sys_account
	::= { gs2108cAccount 5 }
	
gs2108cAccountDel	OBJECT-TYPE
	SYNTAX		INTEGER(2..5)
	MAX-ACCESS	    read-write
	STATUS		current
	DESCRIPTION
		"Delete account. The value is valid gs2108cAccountIndex(Can't delete administrator)."
--	@@ACTION	ruby_sys_account
	::= { gs2108cAccount 6 }	


gs2108cSnmp           	OBJECT IDENTIFIER ::= { gs2108cProduces 2 }

gs2108cGetCommunity OBJECT-TYPE
	SYNTAX      DisplayString
	MAX-ACCESS	    read-write
	STATUS		current
	DESCRIPTION
		"Get/Set the get-community of the SNMP."
--	@@ACTION	ruby_snmp
	::= { gs2108cSnmp 1 }

gs2108cSetCommunity OBJECT-TYPE
	SYNTAX      DisplayString
	MAX-ACCESS	    read-write
	STATUS		current
	DESCRIPTION
		"Get/Set the set-community of the SNMP."
--	@@ACTION	ruby_snmp
	::= { gs2108cSnmp 2 }

gs2108cTrapHostNumber OBJECT-TYPE
	SYNTAX      INTEGER(1..6)
	MAX-ACCESS	    read-only
	STATUS		current
	DESCRIPTION
		"Get the number of trap hosts."
--	@@ACTION	ruby_snmp
	::= { gs2108cSnmp 3 }

gs2108cTrapHostTable	OBJECT-TYPE
	SYNTAX		SEQUENCE OF GS2108CTrapHostEntry
	MAX-ACCESS	not-accessible
	STATUS		current
	DESCRIPTION
		"A list of trap host entry. The number of entries are given by the value of gs2108cTrapHostNumber."
    ::= { gs2108cSnmp 4 }	
	
GS2108CTrapHostEntry ::=
SEQUENCE {
    gs2108cTrapHostIndex		    INTEGER,
    gs2108cTrapHostIP          	IpAddress,
    gs2108cTrapHostPort            INTEGER,
    gs2108cTrapHostCommunity       DisplayString
}

gs2108cTrapHostEntry	OBJECT-TYPE
	SYNTAX		GS2108CTrapHostEntry
	MAX-ACCESS	    not-accessible
	STATUS		current
	DESCRIPTION
		"Entry information for trap host."
	INDEX {gs2108cTrapHostIndex}
	::= { gs2108cTrapHostTable 1 }
	
gs2108cTrapHostIndex	OBJECT-TYPE
	SYNTAX		INTEGER(1..6)
	MAX-ACCESS	    read-only
	STATUS		current
	DESCRIPTION
		"The index of the trap host entry."
--	@@ACTION	ruby_snmp_trapentry
	::= { gs2108cTrapHostEntry 1 }

gs2108cTrapHostIP	OBJECT-TYPE
	SYNTAX		IpAddress
	MAX-ACCESS	    read-write
	STATUS		current
	DESCRIPTION
		"The IP of the trap host."
--	@@ACTION	ruby_snmp_trapentry
	::= { gs2108cTrapHostEntry 2 }


gs2108cTrapHostPort	OBJECT-TYPE
	SYNTAX		INTEGER(1..65535)
	MAX-ACCESS	    read-write
	STATUS		current
	DESCRIPTION
		"The receiving-port number of the trap host."
--	@@ACTION	ruby_snmp_trapentry
	::= { gs2108cTrapHostEntry 3 }


gs2108cTrapHostCommunity	OBJECT-TYPE
	SYNTAX		DisplayString
	MAX-ACCESS	    read-write
	STATUS		current
	DESCRIPTION
		"The community name for the trap PDU."
--	@@ACTION	ruby_snmp_trapentry
	::= { gs2108cTrapHostEntry 4 }

gs2108cAlarm           	OBJECT IDENTIFIER ::= { gs2108cProduces 3 }

gs2108cEvent           	OBJECT IDENTIFIER ::= { gs2108cAlarm 1 }

gs2108cEventNumber OBJECT-TYPE
	SYNTAX      INTEGER(1..2147483647)
	MAX-ACCESS	    read-only
	STATUS		current
	DESCRIPTION
		"Get the total number of alarm events."
--	@@ACTION	ruby_alarm_event
	::= { gs2108cEvent 1 }

gs2108cEventTable	OBJECT-TYPE
	SYNTAX		SEQUENCE OF GS2108CEventEntry
	MAX-ACCESS	not-accessible
	STATUS		current
    DESCRIPTION
        "A list of alarm event entry. The number of entries are given by the value of gs2108cEventNumber."
	::= { gs2108cEvent 2 }	
	
GS2108CEventEntry ::=
SEQUENCE {
    gs2108cEventIndex		    INTEGER,
    gs2108cEventName          	DisplayString,
    gs2108cEventSendEmail      INTEGER,
    gs2108cEventSendSMS        INTEGER,
    gs2108cEventSendTrap       INTEGER
}

gs2108cEventEntry	OBJECT-TYPE
	SYNTAX		GS2108CEventEntry
	MAX-ACCESS	    not-accessible
	STATUS		current
	DESCRIPTION
		"Entry infomation for alarm event."
	INDEX {gs2108cEventIndex}
	::= { gs2108cEventTable 1 }
	
gs2108cEventIndex	OBJECT-TYPE
	SYNTAX		INTEGER(1..2147483647)
	MAX-ACCESS	    read-only
	STATUS		current
	DESCRIPTION
		"The index of the alarm event entry."
--	@@ACTION	ruby_alarm_evententry
	::= { gs2108cEventEntry 1 }

gs2108cEventName	OBJECT-TYPE
	SYNTAX		DisplayString
	MAX-ACCESS	    read-only
	STATUS		current
	DESCRIPTION
		"The alarm event name."
--	@@ACTION	ruby_alarm_evententry
	::= { gs2108cEventEntry 2 }
	
gs2108cEventSendEmail	OBJECT-TYPE
	SYNTAX		INTEGER(0|1)
	MAX-ACCESS	    read-write
	STATUS		current
	DESCRIPTION
		"Send email when alarm event is triggered."
--	@@ACTION	ruby_alarm_evententry
	::= { gs2108cEventEntry 3 }	

gs2108cEventSendSMS	OBJECT-TYPE
	SYNTAX		INTEGER(0|1)
	MAX-ACCESS	    read-write
	STATUS		current
	DESCRIPTION
		"Send sms when alarm event is triggered."
--	@@ACTION	ruby_alarm_evententry
	::= { gs2108cEventEntry 4 }

gs2108cEventSendTrap	OBJECT-TYPE
	SYNTAX		INTEGER(0|1)
	MAX-ACCESS	    read-write
	STATUS		current
	DESCRIPTION
		"Send trap when alarm event is triggered."
--	@@ACTION	ruby_alarm_evententry
	::= { gs2108cEventEntry 5 }


gs2108cEmail           	OBJECT IDENTIFIER ::= { gs2108cAlarm 2 }

gs2108cEmailServer OBJECT-TYPE
	SYNTAX      DisplayString
	MAX-ACCESS	    read-write
	STATUS		current
	DESCRIPTION
		"SMTP server for alarm event."
--	@@ACTION	ruby_alarm_email
	::= { gs2108cEmail 1 }

gs2108cEmailUsername OBJECT-TYPE
	SYNTAX      DisplayString
	MAX-ACCESS	    read-write
	STATUS		current
	DESCRIPTION
		"Username of smtp server."
--	@@ACTION	ruby_alarm_email
	::= { gs2108cEmail 2 }

gs2108cEmailPassword OBJECT-TYPE
	SYNTAX      DisplayString
	MAX-ACCESS	    read-write
	STATUS		current
	DESCRIPTION
		"User password of smtp server."
--	@@ACTION	ruby_alarm_email
	::= { gs2108cEmail 3 }

gs2108cEmailUserNumber OBJECT-TYPE
	SYNTAX      INTEGER(1..6)
	MAX-ACCESS	    read-only
	STATUS		current
	DESCRIPTION
		"The number of the email users that you want to send the alarm notification."
--	@@ACTION	ruby_alarm_email
	::= { gs2108cEmail 4 }

gs2108cEmailUserTable	OBJECT-TYPE
	SYNTAX		SEQUENCE OF GS2108CEmailUserEntry
	MAX-ACCESS	not-accessible
	STATUS		current
    DESCRIPTION
        "A list of email user entry. The number of entries are given by the value of gs2108cEmailUserNumber."
	::= { gs2108cEmail 5 }	
	
GS2108CEmailUserEntry ::=
SEQUENCE {
    gs2108cEmailUserIndex		    INTEGER,
    gs2108cEmailUserAddress       	DisplayString
}

gs2108cEmailUserEntry	OBJECT-TYPE
	SYNTAX		GS2108CEmailUserEntry
	MAX-ACCESS	    not-accessible
	STATUS		current
	DESCRIPTION
		"Entry information for email user entry."
	INDEX {gs2108cEmailUserIndex}
	::= { gs2108cEmailUserTable 1 }
	
gs2108cEmailUserIndex	OBJECT-TYPE
	SYNTAX		INTEGER(1..6)
	MAX-ACCESS	    read-only
	STATUS		current
	DESCRIPTION
		"The index of the email user entry."
--	@@ACTION	ruby_alarm_emailentry
	::= { gs2108cEmailUserEntry 1 }

gs2108cEmailUserAddress	OBJECT-TYPE
	SYNTAX		DisplayString
	MAX-ACCESS	    read-write
	STATUS		current
	DESCRIPTION
		"The email address of the email user entry."
--	@@ACTION	ruby_alarm_emailentry
	::= { gs2108cEmailUserEntry 2 }

gs2108cSMS           	OBJECT IDENTIFIER ::= { gs2108cAlarm 3 }

gs2108cSMSServer OBJECT-TYPE
	SYNTAX      DisplayString
	MAX-ACCESS	    read-write
	STATUS		current
	DESCRIPTION
		"SMS server for alarm event."
--	@@ACTION	ruby_alarm_SMS
	::= { gs2108cSMS 1 }

gs2108cSMSUsername OBJECT-TYPE
	SYNTAX      DisplayString
	MAX-ACCESS	    read-write
	STATUS		current
	DESCRIPTION
		"Username of SMS server."
--	@@ACTION	ruby_alarm_SMS
	::= { gs2108cSMS 2 }

gs2108cSMSPassword OBJECT-TYPE
	SYNTAX      DisplayString
	MAX-ACCESS	    read-write
	STATUS		current
	DESCRIPTION
		"User password of SMS server."
--	@@ACTION	ruby_alarm_SMS
	::= { gs2108cSMS 3 }

gs2108cSMSUserNumber OBJECT-TYPE
	SYNTAX      INTEGER(1..6)
	MAX-ACCESS	    read-only
	STATUS		current
	DESCRIPTION
		"The number of the SMS users that you want to send the alarm notification."
--	@@ACTION	ruby_alarm_SMS
	::= { gs2108cSMS 4 }

gs2108cSMSUserTable	OBJECT-TYPE
	SYNTAX		SEQUENCE OF GS2108CSMSUserEntry
	MAX-ACCESS	not-accessible
	STATUS		current
    DESCRIPTION
        "A list of SMS user entry. The number of entries are given by the value of gs2108cSMSUserNumber."
    ::= { gs2108cSMS 5 }	
	
GS2108CSMSUserEntry ::=
SEQUENCE {
    gs2108cSMSUserIndex		    INTEGER,
    gs2108cSMSUserMobilePhone       	DisplayString
}

gs2108cSMSUserEntry	OBJECT-TYPE
	SYNTAX		GS2108CSMSUserEntry
	MAX-ACCESS	    not-accessible
	STATUS		current
	DESCRIPTION
		"Entry information for SMS user entry."
	INDEX {gs2108cSMSUserIndex}
	::= { gs2108cSMSUserTable 1 }
	
gs2108cSMSUserIndex	OBJECT-TYPE
	SYNTAX		INTEGER(1..6)
	MAX-ACCESS	    read-only
	STATUS		current
	DESCRIPTION
		"The index of the SMS user entry."
--	@@ACTION	ruby_alarm_SMSentry
	::= { gs2108cSMSUserEntry 1 }

gs2108cSMSUserMobilePhone	OBJECT-TYPE
	SYNTAX		DisplayString
	MAX-ACCESS	    read-write
	STATUS		current
	DESCRIPTION
		"The SMS phone number of the SMS user entry."
--	@@ACTION	ruby_alarm_SMSentry
	::= { gs2108cSMSUserEntry 2 }


gs2108cTftp           	OBJECT IDENTIFIER ::= { gs2108cProduces 4 }

gs2108cTftpServer OBJECT-TYPE
	SYNTAX      IpAddress
	MAX-ACCESS	    read-write
	STATUS		current
	DESCRIPTION
		"Get/Set the tftp server."
--	@@ACTION	ruby_tftp
	::= { gs2108cTftp 1 }


gs2108cConfiguration           	OBJECT IDENTIFIER ::= { gs2108cProduces 5 }

gs2108cSaveRestore           	OBJECT IDENTIFIER ::= { gs2108cConfiguration 1 }

gs2108cSaveStart OBJECT-TYPE
	SYNTAX      INTEGER(0|1)
	MAX-ACCESS	    read-write
	STATUS		current
	DESCRIPTION
		"Save current configuration into flash memory (start section). 
        Get this oid always return zero.
            1 - save.
            0 - do nothing. "
--	@@ACTION	ruby_config_save
	::= { gs2108cSaveRestore 1 }

gs2108cSaveUser OBJECT-TYPE
	SYNTAX      INTEGER(0|1)
	MAX-ACCESS	    read-write
	STATUS		current
	DESCRIPTION
		"Save current configuration into flash memory (user config section).
        Get this oid always return zero.
            1 - save.
            0 - do nothing. "
--	@@ACTION	ruby_config_save
	::= { gs2108cSaveRestore 2 }

gs2108cRestoreDefault OBJECT-TYPE
	SYNTAX      INTEGER(0|1|2)
	MAX-ACCESS	    read-write
	STATUS		current
	DESCRIPTION
		"Restore factory default configurtion.
        Get this oid always return zero.
            2 - restore default included default ip address.
            1 - restore default without changing current ip address.
            0 - do nothing. "
--	@@ACTION	ruby_config_save
	::= { gs2108cSaveRestore 3 }

gs2108cRestoreUser OBJECT-TYPE
	SYNTAX      INTEGER(0|1)
	MAX-ACCESS	    read-write
	STATUS		current
	DESCRIPTION
		"Restore user configurtion.
        Get this oid always return zero.
            1 - retore.
            0 - do nothing. "
--	@@ACTION	ruby_config_save
	::= { gs2108cSaveRestore 4 }


gs2108cConfigFile           	OBJECT IDENTIFIER ::= { gs2108cConfiguration 2 }

gs2108cExportConfigName OBJECT-TYPE
	SYNTAX      DisplayString
	MAX-ACCESS	    read-write
	STATUS		current
	DESCRIPTION
		"Get/Set export config file path and name."
--	@@ACTION	ruby_config_file
	::= { gs2108cConfigFile 1 }

gs2108cDoExportConfig OBJECT-TYPE
	SYNTAX      INTEGER(1|2)
	MAX-ACCESS	    read-write
	STATUS		current
	DESCRIPTION
		"Do export-config. 
        Get this oid always return zero.
			1	-	export start section.
			2	-	export user-conf section."
--	@@ACTION	ruby_config_file
	::= { gs2108cConfigFile 2 }

gs2108cImportConfigName OBJECT-TYPE
	SYNTAX      DisplayString
	MAX-ACCESS	    read-write
	STATUS		current
	DESCRIPTION
        "Get/Set export config file path and name."
--	@@ACTION	ruby_config_file
	::= { gs2108cConfigFile 3 }

gs2108cDoImportConfig OBJECT-TYPE
	SYNTAX      INTEGER(1|2)
	MAX-ACCESS	    read-write
	STATUS		current
	DESCRIPTION
		"Do import-config. 
        Get this oid always return zero.
			1	-	import start section.
			2	-	import user-conf section."									 
--	@@ACTION	ruby_config_file
	::= { gs2108cConfigFile 4 }

gs2108cDiagnostic           	OBJECT IDENTIFIER ::= { gs2108cProduces 6 }

gs2108cEEPROMTest OBJECT-TYPE
	SYNTAX      DisplayString
	MAX-ACCESS	    read-only
	STATUS		current
	DESCRIPTION
		"EEPROM access test."
--	@@ACTION	ruby_diagnostic
	::= { gs2108cDiagnostic 1 }

gs2108cUartTest OBJECT-TYPE
	SYNTAX      DisplayString
	MAX-ACCESS	    read-only
	STATUS		current
	DESCRIPTION
		"UART access test."
--	@@ACTION	ruby_diagnostic
	::= { gs2108cDiagnostic 2 }

gs2108cDramTest OBJECT-TYPE
	SYNTAX      DisplayString
	MAX-ACCESS	    read-only
	STATUS		current
	DESCRIPTION
		"DRAM access test."
--	@@ACTION	ruby_diagnostic
	::= { gs2108cDiagnostic 3 }

gs2108cFlashTest OBJECT-TYPE
	SYNTAX      DisplayString
	MAX-ACCESS	    read-only
	STATUS		current
	DESCRIPTION
		"Flash memory access test."
--	@@ACTION	ruby_diagnostic
	::= { gs2108cDiagnostic 4 }

gs2108cInternalLoopbackTest OBJECT-TYPE
	SYNTAX      DisplayString
	MAX-ACCESS	    read-only
	STATUS		current
	DESCRIPTION
		"Internel loopback test."
--	@@ACTION	ruby_diagnostic
	::= { gs2108cDiagnostic 5 }

gs2108cExternalLoopbackTest OBJECT-TYPE
	SYNTAX      DisplayString
	MAX-ACCESS	    read-only
	STATUS		current
	DESCRIPTION
		"Externel loopback test."
--	@@ACTION	ruby_diagnostic
	::= { gs2108cDiagnostic 6 }

gs2108cPingTest OBJECT-TYPE
	SYNTAX      DisplayString
	MAX-ACCESS	    read-write
	STATUS		current
	DESCRIPTION
		"Set the host address that you want to ping and the system will return the test result."
--	@@ACTION	ruby_diagnostic
	::= { gs2108cDiagnostic 7 }

gs2108cLog           	OBJECT IDENTIFIER ::= { gs2108cProduces 7 }

gs2108cClearLog OBJECT-TYPE
	SYNTAX      INTEGER(0|1)
	MAX-ACCESS	    read-write
	STATUS		current
	DESCRIPTION
		"Clear system log. 
        Get this oid always return zero.
            1 - clear log.
            0 - do nothing. "
--	@@ACTION	ruby_log
	::= { gs2108cLog 1 }

gs2108cUploadLog OBJECT-TYPE
	SYNTAX      INTEGER(0|1)
	MAX-ACCESS	    read-write
	STATUS		current
	DESCRIPTION
		"Upload current system log. Set the correct tftp server first.
        The format of log file is 'ModelName_SerialNumbuer_YYMMDD_HHMM'.
        Get this oid always return zero.
            1 - upload log
            0 - do nothing. "
--	@@ACTION	ruby_log
	::= { gs2108cLog 2 }

gs2108cAutoUploadLogState OBJECT-TYPE
	SYNTAX      INTEGER(0|1)
	MAX-ACCESS	    read-write
	STATUS		current
	DESCRIPTION
		"Enable log auto-upload function. Set the correct tftp server first.
        The format of log file is 'ModelName_SerialNumbuer_YYMMDD_HHMM'.
        Get this oid always return zero.
            1 - Enable auto-upload
            0 - do nothing. "
--	@@ACTION	ruby_log
	::= { gs2108cLog 3 }

gs2108cLogNumber OBJECT-TYPE
	SYNTAX      INTEGER(0..120)
	MAX-ACCESS	    read-only
	STATUS		current
	DESCRIPTION
		"Get the number of current system log. "
--	@@ACTION	ruby_log
	::= { gs2108cLog 4 }

gs2108cLogTable	OBJECT-TYPE
	SYNTAX		SEQUENCE OF GS2108CLogEntry
	MAX-ACCESS	not-accessible
	STATUS		current
    DESCRIPTION
        "A list of log entry. The number of entries are given by the value of gs2108cLogNumber."
	::= { gs2108cLog 5 }	
	
GS2108CLogEntry ::=
SEQUENCE {
    gs2108cLogIndex		    INTEGER,
    gs2108cLogEvent           	DisplayString
}

gs2108cLogEntry	OBJECT-TYPE
	SYNTAX		GS2108CLogEntry
	MAX-ACCESS	    not-accessible
	STATUS		current
	DESCRIPTION
		"Entry information for system log."
	INDEX {gs2108cLogIndex}
	::= { gs2108cLogTable 1 }
	
gs2108cLogIndex	OBJECT-TYPE
	SYNTAX		INTEGER(1..120)
	MAX-ACCESS	    read-only
	STATUS		current
	DESCRIPTION
		"The index of the log entry."
--	@@ACTION	ruby_logentry
	::= { gs2108cLogEntry 1 }

gs2108cLogEvent	OBJECT-TYPE
	SYNTAX		DisplayString
	MAX-ACCESS	    read-only
	STATUS		current
	DESCRIPTION
		"The detail information of the log entry."
--	@@ACTION	ruby_logentry
	::= { gs2108cLogEntry 2 }


gs2108cFirmware           	OBJECT IDENTIFIER ::= { gs2108cProduces 8 }

gs2108cFirmwareFileName OBJECT-TYPE
	SYNTAX      DisplayString
	MAX-ACCESS	    read-write
	STATUS		current
	DESCRIPTION
		"Get/Set the path and filename for firmware upgrading."
--	@@ACTION	ruby_Firmware
	::= { gs2108cFirmware 1 }

gs2108cDoFirmwareUpgrade OBJECT-TYPE
	SYNTAX      INTEGER(0|1)
	MAX-ACCESS	    read-write
	STATUS		current
	DESCRIPTION
		"Do firmware upgrade. Get this oid always return zero.
            1 - do firmware upgrade.
            0 - do nothing."
--	@@ACTION	ruby_Firmware
	::= { gs2108cFirmware 2 }


gs2108cPort           	OBJECT IDENTIFIER ::= { gs2108cProduces 9 }

gs2108cPortStatus           	OBJECT IDENTIFIER ::= { gs2108cPort 1 }

gs2108cPortStatusNumber OBJECT-TYPE
	SYNTAX      INTEGER(1..2147483647)
	MAX-ACCESS	    read-only
	STATUS		current
	DESCRIPTION
		"Get the number of port state."		
--	@@ACTION	ruby_port_status
	::= { gs2108cPortStatus 1 }

gs2108cPortStatusTable	OBJECT-TYPE
	SYNTAX		SEQUENCE OF GS2108CPortStatusEntry
	MAX-ACCESS	not-accessible
	STATUS		current
    DESCRIPTION
        "A list of port status entry. The number of entries are given by the value of gs2108cPortStatusNumber."	        
	::= { gs2108cPortStatus 2 }
	
GS2108CPortStatusEntry ::=
SEQUENCE {
    gs2108cPortStatusIndex		    INTEGER,
    gs2108cPortStatusMedia          DisplayString,
    gs2108cPortStatusLink           DisplayString,
    gs2108cPortStatusPortState      DisplayString,
    gs2108cPortStatusAutoNego       DisplayString,
    gs2108cPortStatusSpdDpx         DisplayString,
    gs2108cPortStatusFlwCtrl        DisplayString,    
    gs2108cPortStatusWaitState      DisplayString     
}

gs2108cPortStatusEntry	OBJECT-TYPE
	SYNTAX		GS2108CPortStatusEntry
	MAX-ACCESS	    not-accessible
	STATUS		current
	DESCRIPTION
		"Entry(s) for port status informaion."		
	INDEX {gs2108cPortStatusIndex}
	::= { gs2108cPortStatusTable 1 }
	
gs2108cPortStatusIndex	OBJECT-TYPE
	SYNTAX		INTEGER(1..2147483647)
	MAX-ACCESS	    read-only
	STATUS		current
	DESCRIPTION
		"The index of the port status entry."		
--	@@ACTION	ruby_port_status_entry
	::= { gs2108cPortStatusEntry 1 }

gs2108cPortStatusMedia	OBJECT-TYPE
	SYNTAX		DisplayString
	MAX-ACCESS	    read-only
	STATUS		current
	DESCRIPTION
		"The port media type of the port status entry."		
--	@@ACTION	ruby_port_status_entry
	::= { gs2108cPortStatusEntry 2 }
	
gs2108cPortStatusLink	OBJECT-TYPE
	SYNTAX		DisplayString
	MAX-ACCESS	    read-only
	STATUS		current
	DESCRIPTION
		"The port link of the port status entry."		
--	@@ACTION	ruby_port_status_entry
	::= { gs2108cPortStatusEntry 3 }

gs2108cPortStatusPortState	OBJECT-TYPE
	SYNTAX		DisplayString
	MAX-ACCESS	    read-only
	STATUS		current
	DESCRIPTION
		"The port state of the port status entry."
--	@@ACTION	ruby_port_status_entry
	::= { gs2108cPortStatusEntry 4 }
	
gs2108cPortStatusAutoNego	OBJECT-TYPE
	SYNTAX		DisplayString
	MAX-ACCESS	    read-only
	STATUS		current
	DESCRIPTION
		"The auto negotiation of the port status entry."
--	@@ACTION	ruby_port_status_entry
	::= { gs2108cPortStatusEntry 5 }
	
gs2108cPortStatusSpdDpx 	OBJECT-TYPE
	SYNTAX		DisplayString
	MAX-ACCESS	    read-only
	STATUS		current
	DESCRIPTION
		"The speed/duplex of the port status entry."
--	@@ACTION	ruby_port_status_entry
	::= { gs2108cPortStatusEntry 6 }
	
gs2108cPortStatusFlwCtrl 	OBJECT-TYPE
	SYNTAX		DisplayString
	MAX-ACCESS	    read-only
	STATUS		current
	DESCRIPTION
		"The flow control of the port status entry."
--	@@ACTION	ruby_port_status_entry
	::= { gs2108cPortStatusEntry 7 }

gs2108cPortStatusWaitState 	OBJECT-TYPE
	SYNTAX		DisplayString
	MAX-ACCESS	    read-only
	STATUS		current
	DESCRIPTION
		"The wait state of the port status entry."
--	@@ACTION	ruby_port_status_entry
	::= { gs2108cPortStatusEntry 8 }


gs2108cPortConf           	OBJECT IDENTIFIER ::= { gs2108cPort 2 }

gs2108cPortConfNumber OBJECT-TYPE
	SYNTAX      INTEGER(1..2147483647)
	MAX-ACCESS	    read-only
	STATUS		current
	DESCRIPTION
		"Get the number of port configuration."		
--	@@ACTION	ruby_port_conf
	::= { gs2108cPortConf 1 }

gs2108cPortConfTable	OBJECT-TYPE
	SYNTAX		SEQUENCE OF GS2108CPortConfEntry
	MAX-ACCESS	not-accessible
	STATUS		current
    DESCRIPTION
        "A list of port configuration entry. The number of entries are given by the value of gs2108cPortConfNumber."	        
	::= { gs2108cPortConf 2 }
	
GS2108CPortConfEntry ::=
SEQUENCE {
    gs2108cPortConfIndex		    INTEGER,
    gs2108cPortConfPortState        INTEGER,
    gs2108cPortConfSpdDpx           INTEGER,
    gs2108cPortConfFlwCtrl          INTEGER,  
    gs2108cPortConfWaitState        INTEGER      
}

gs2108cPortConfEntry	OBJECT-TYPE
	SYNTAX		GS2108CPortConfEntry
	MAX-ACCESS	    not-accessible
	STATUS		current
	DESCRIPTION
		"Entry(s) for port configuration informaion."		
	INDEX {gs2108cPortConfIndex}
	::= { gs2108cPortConfTable 1 }
	
gs2108cPortConfIndex	OBJECT-TYPE
	SYNTAX		INTEGER(1..2147483647)
	MAX-ACCESS	    read-only
	STATUS		current
	DESCRIPTION
		"The index of the port configuration entry."	
--	@@ACTION	ruby_port_conf_entry
	::= { gs2108cPortConfEntry 1 }

gs2108cPortConfPortState	OBJECT-TYPE
	SYNTAX		INTEGER(0|1)
	MAX-ACCESS	    read-write
	STATUS		current
	DESCRIPTION
		"The port state of the port configuration entry. 
		 0 - disabled. 
		 1 - enabled. "
--	@@ACTION	ruby_port_conf_entry
	::= { gs2108cPortConfEntry 2 }
	
gs2108cPortConfSpdDpx	OBJECT-TYPE
	SYNTAX		INTEGER(0..5)
	MAX-ACCESS	    read-write
	STATUS		current
	DESCRIPTION
		"The speed/duplex of the port configuration entry. 
		 0 - auto.  
		 1 - 10M/Half.  
		 2 - 10M/Full.  
		 3 - 100M/Half.  
		 4 - 100M/Full.  
		 5 - 1G/Full.  "
--	@@ACTION	ruby_port_conf_entry
	::= { gs2108cPortConfEntry 3 }		
	
gs2108cPortConfFlwCtrl	OBJECT-TYPE
	SYNTAX		INTEGER(0|1)
	MAX-ACCESS	    read-write
	STATUS		current
	DESCRIPTION
		"The flow control of the port configuration entry.
		 0 - disabled.  
		 1 - enabled.  "
--	@@ACTION	ruby_port_conf_entry
	::= { gs2108cPortConfEntry 4 }	

gs2108cPortConfWaitState	OBJECT-TYPE
	SYNTAX		INTEGER(0|1)
	MAX-ACCESS	    read-write
	STATUS		current
	DESCRIPTION
		"The wait state of the port configuration entry. 
		 0 - disabled. 
		 1 - enabled. "
--	@@ACTION	ruby_port_conf_entry
	::= { gs2108cPortConfEntry 5 }

gs2108cMirror           	OBJECT IDENTIFIER ::= { gs2108cProduces 10 }

gs2108cMirrorMode OBJECT-TYPE
	SYNTAX      INTEGER(0|1)
	MAX-ACCESS	    read-write
	STATUS		current
	DESCRIPTION
		"Get/Set the Mirror mode.  
		 0 - disabled.
		 1 - enable.  "	
--	@@ACTION	ruby_mirror
	::= { gs2108cMirror 1 }

gs2108cMirroringPort OBJECT-TYPE
	SYNTAX      INTEGER(1..2147483647)
	MAX-ACCESS	    read-write
	STATUS		current
	DESCRIPTION
		"Get/Set the mirroring port.
		 The port range from 1 to 8.  "
--	@@ACTION	ruby_mirror
	::= { gs2108cMirror 2 }

gs2108cMirroredPorts OBJECT-TYPE
	SYNTAX      DisplayString
	MAX-ACCESS	    read-write
	STATUS		current
	DESCRIPTION
		"Get/Set the monitored ports.
		 The port range from 1 to 8, and the syntax is 1,5-7.  "
--	@@ACTION	ruby_mirror
	::= { gs2108cMirror 3 }	
	

gs2108cMaxPktLen           	OBJECT IDENTIFIER ::= { gs2108cProduces 11 }

gs2108cMaxPktLen1           	OBJECT IDENTIFIER ::= { gs2108cMaxPktLen 1 }

gs2108cMaxPktLenPortNumber OBJECT-TYPE
	SYNTAX      INTEGER(1..2147483647)
	MAX-ACCESS	    read-only
	STATUS		current
	DESCRIPTION
		"Get the number of Max. packet length."		
--	@@ACTION	ruby_maxpktlen_conf
	::= { gs2108cMaxPktLen1 1 }

gs2108cMaxPktLenConfTable	OBJECT-TYPE
	SYNTAX		SEQUENCE OF GS2108CMaxPktLenConfEntry
	MAX-ACCESS	not-accessible
	STATUS		current
    DESCRIPTION
        "A list of Max. packet length entry. The number of entries are given by the value of gs2108cMaxPktLenPortNumber."	        
	::= { gs2108cMaxPktLen1 2 }
	
GS2108CMaxPktLenConfEntry ::=
SEQUENCE {
    gs2108cMaxPktLenConfIndex		    INTEGER,
    gs2108cMaxPktLenConfSetting         INTEGER   
}

gs2108cMaxPktLenConfEntry	OBJECT-TYPE
	SYNTAX		GS2108CMaxPktLenConfEntry
	MAX-ACCESS	    not-accessible
	STATUS		current
	DESCRIPTION
		"Entry(s) for Max. packet length informaion."	
	INDEX {gs2108cMaxPktLenConfIndex}
	::= { gs2108cMaxPktLenConfTable 1 }
	
gs2108cMaxPktLenConfIndex	OBJECT-TYPE
	SYNTAX		INTEGER(1..2147483647)
	MAX-ACCESS	    read-only
	STATUS		current
	DESCRIPTION
		"The index of the Max. packet length entry."	
--	@@ACTION	ruby_maxpktlen_conf_entry
	::= { gs2108cMaxPktLenConfEntry 1 }

gs2108cMaxPktLenConfSetting	OBJECT-TYPE
	SYNTAX		INTEGER(1518|1532|9216)
	MAX-ACCESS	    read-write
	STATUS		current
	DESCRIPTION
		"Get/Set the Max. packet length.  
		 The Max. packet length is 1518,1532,or 9216.  "
--	@@ACTION	ruby_maxpktlen_conf_entry
	::= { gs2108cMaxPktLenConfEntry 2 }
	

gs2108cBandwidth           	OBJECT IDENTIFIER ::= { gs2108cProduces 12 }

gs2108cBandwidth1           	OBJECT IDENTIFIER ::= { gs2108cBandwidth 1 }

gs2108cBandwidthPortNumber OBJECT-TYPE
	SYNTAX      INTEGER(1..2147483647)
	MAX-ACCESS	    read-only
	STATUS		current
	DESCRIPTION
		"Get the number of bandwidth management configuration."	
--	@@ACTION	ruby_bandwidth
	::= { gs2108cBandwidth1 1 }

gs2108cBandwidthConfTable	OBJECT-TYPE
	SYNTAX		SEQUENCE OF GS2108CBandwidthConfEntry
	MAX-ACCESS	not-accessible
	STATUS		current
    DESCRIPTION
        "A list of bandwidth management configuration entry. The number of entries are given by the value of gs2108cBandwidthPortNumber."	        
	::= { gs2108cBandwidth1 2 }
	
GS2108CBandwidthConfEntry ::=
SEQUENCE {
    gs2108cBandwidthConfIndex		     INTEGER,
    gs2108cBandwidthConfIgressState      INTEGER,
    gs2108cBandwidthConfIgressBW         INTEGER,
    gs2108cBandwidthConfStormState       INTEGER,
    gs2108cBandwidthConfStormBW          INTEGER,
    gs2108cBandwidthConfEgressState      INTEGER,
    gs2108cBandwidthConfEgressBW         INTEGER
}

gs2108cBandwidthConfEntry	OBJECT-TYPE
	SYNTAX		GS2108CBandwidthConfEntry
	MAX-ACCESS	    not-accessible
	STATUS		current
	DESCRIPTION
		"Entry(s) for bandwidth management configuration informaion."	
	INDEX {gs2108cBandwidthConfIndex}
	::= { gs2108cBandwidthConfTable 1 }
	
gs2108cBandwidthConfIndex	OBJECT-TYPE
	SYNTAX		INTEGER(1..2147483647)
	MAX-ACCESS	    read-only
	STATUS		current
	DESCRIPTION
		"The index of the bandwidth management configuration entry."	
--	@@ACTION	ruby_bandwidth_entry
	::= { gs2108cBandwidthConfEntry 1 }

gs2108cBandwidthConfIgressState	OBJECT-TYPE
	SYNTAX		INTEGER(0|1)
	MAX-ACCESS	    read-write
	STATUS		current
	DESCRIPTION
		"The igress state of the bandwidth management configurateion entry.
		 0 - disabled. 
		 1 - enabled. "
--	@@ACTION	ruby_bandwidth_entry
	::= { gs2108cBandwidthConfEntry 2 }

gs2108cBandwidthConfIgressBW	OBJECT-TYPE
	SYNTAX		INTEGER(0..1000)
	MAX-ACCESS	    read-write
	STATUS		current
	DESCRIPTION
		"Get/Set the igress rate of the bandwidth management configuration.
		 The igrees rate is from 0 to 1000.  "
--	@@ACTION	ruby_bandwidth_entry
	::= { gs2108cBandwidthConfEntry 3 }

gs2108cBandwidthConfStormState	OBJECT-TYPE
	SYNTAX		INTEGER(0|1)
	MAX-ACCESS	    read-write
	STATUS		current
	DESCRIPTION
		"The storm state of the bandwidth management configurateion entry.
		 0 - disabled. 
		 1 - enabled. "
--	@@ACTION	ruby_bandwidth_entry
	::= { gs2108cBandwidthConfEntry 4 }

gs2108cBandwidthConfStormBW	OBJECT-TYPE
	SYNTAX		INTEGER(0..1000)
	MAX-ACCESS	    read-write
	STATUS		current
	DESCRIPTION
		"Get/Set the storm rate of the bandwidth management configuration.
		 The storm rate is from 0 to 1000.  "
--	@@ACTION	ruby_bandwidth_entry
	::= { gs2108cBandwidthConfEntry 5 }

gs2108cBandwidthConfEgressState	OBJECT-TYPE
	SYNTAX		INTEGER(0|1)
	MAX-ACCESS	    read-write
	STATUS		current
	DESCRIPTION
		"The egress state of the bandwidth management configurateion entry.
		 0 - disabled. 
		 1 - enabled. "
--	@@ACTION	ruby_bandwidth_entry
	::= { gs2108cBandwidthConfEntry 6 }

gs2108cBandwidthConfEgressBW	OBJECT-TYPE
	SYNTAX		INTEGER(0..1000)
	MAX-ACCESS	    read-write
	STATUS		current
	DESCRIPTION
		"Get/Set the egress rate of the bandwidth management configuration.
		 The egress rate is from 0 to 1000.  "
--	@@ACTION	ruby_bandwidth_entry
	::= { gs2108cBandwidthConfEntry 7 }
	
gs2108cTrapEntry	       OBJECT IDENTIFIER ::= { gs2108cProduces 20 }

gs2108cModuleInserted NOTIFICATION-TYPE
    OBJECTS { ifIndex }
	STATUS    current
	DESCRIPTION
	    "Send this trap when a moudle is inserted to the system. The OID value means 
	     the port number."	
	::= { gs2108cTrapEntry 1 }

gs2108cModuleRemoved NOTIFICATION-TYPE
    OBJECTS { ifIndex }
	STATUS    current
	DESCRIPTION
	    "Send this trap when a moudule is removed from the system. The OID value means 
	     the port number."	
	::= { gs2108cTrapEntry 2 }

gs2108cDualMediaSwapped NOTIFICATION-TYPE
    OBJECTS { ifIndex }
	STATUS    current
	DESCRIPTION
	    "Send this trap when the dual media port changed. The OID value means the port number." 
	::= { gs2108cTrapEntry 3 }

gs2108cStpStateDisabled NOTIFICATION-TYPE
	STATUS		current
	DESCRIPTION
	   "Send this trap when the operational state of STP is from enabled to disabled. "
	::= { gs2108cTrapEntry 100 }

gs2108cStpStateEnabled NOTIFICATION-TYPE
	STATUS		current
	DESCRIPTION
	   "Send this trap when the operational state of STP is from disabled to enabled. "
	::= { gs2108cTrapEntry 101 }
	
gs2108cStpTopologyChanged NOTIFICATION-TYPE
    OBJECTS { ifIndex }
	STATUS		current
	DESCRIPTION
	   "Send this trap when RSTP determines a port should enter the FORWARDING state  
	    (a topology change occurs). The OID value is the ifIndex of the port that
	    produces the topology change"	     
	::= { gs2108cTrapEntry 102 }

gs2108cRmonRisingAlarm NOTIFICATION-TYPE
	STATUS		current
	DESCRIPTION		
	   "Send this trap when an RMON rising alarm happened. The OID value is the value 
	    of another OID variable sampled by the RMON Alarm Group that exceeds its
	    own RisingThreshold "
	::= { gs2108cTrapEntry 110 }

gs2108cRmonFallingAlarm NOTIFICATION-TYPE
	STATUS		current
	DESCRIPTION		
           "Send this trap when an RMON falling alarm happened. The OID value is the value 
	    of another OID variable sampled by the RMON Alarm Group that is smaller than its
	    own FallingThreshold "
	::= { gs2108cTrapEntry 111 }
	
gs2108cLacpStateDisabled NOTIFICATION-TYPE
    OBJECTS {ifIndex, groupId}
	STATUS		current
	DESCRIPTION
	   "Send this trap when the operational state of LACP is from enabled to disabled. 
	    The OID value means the disabled Group ID."
	::= { gs2108cTrapEntry 120 }

gs2108cLacpStateEnabled NOTIFICATION-TYPE
    OBJECTS {ifIndex, groupId}
	STATUS		current
	DESCRIPTION
	   "Send this trap when the operational state of LACP is from disabled to enabled. 
	    The OID value means the disabled Group ID."
	::= { gs2108cTrapEntry 121 }

gs2108cLacpPortAdded NOTIFICATION-TYPE
    OBJECTS   { ifIndex, actorkey, partnerkey }
	STATUS		current
	DESCRIPTION
	   "Send this trap when the state of port is in 'trunk ready'."
	::= { gs2108cTrapEntry 123 }

gs2108cLacpPortTrunkFailure NOTIFICATION-TYPE
    OBJECTS   { ifIndex, actorkey, partnerkey}
	STATUS		current
	DESCRIPTION
	   "Send this trap when one port is not able to be aggregated
	    due to duplex-mode of the port. "
	::= { gs2108cTrapEntry 124 }

gs2108cGvrpStateDisabled NOTIFICATION-TYPE
	STATUS		current
	DESCRIPTION
	   "Send this trap when the operational state of GVRP is from enabled to disabled. "
	::= { gs2108cTrapEntry 140 }

gs2108cGvrpStateEnabled NOTIFICATION-TYPE
	STATUS		current
	DESCRIPTION
	   "Send this trap when the operational state of LACP is from disabled to enabled. "	
	::= { gs2108cTrapEntry 141 }

gs2108cVlanStateDisabled NOTIFICATION-TYPE
	STATUS		current
	DESCRIPTION
	   "Send this trap when the operational state of vlan is from enabled to disabled. 
	    The OID value means the enabled Group ID. "
	::= { gs2108cTrapEntry 150 }

gs2108cVlanPortBaseEnabled NOTIFICATION-TYPE
	STATUS		current
	DESCRIPTION
	   "Send this trap when the operational state of vlan is changed to port-based vlan."
	::= { gs2108cTrapEntry 151 }

gs2108cVlanTagBaseEnabled NOTIFICATION-TYPE
	STATUS		current
	DESCRIPTION
	   "Send this trap when the operational state of vlan is changed to tag-based vlan."
	::= { gs2108cTrapEntry 152 }

gs2108cVlanMetroModeEnabled NOTIFICATION-TYPE
    OBJECTS   {uplink}
	STATUS		current
	DESCRIPTION
	   "Send this trap when the operational state of vlan is changed to Metro-mode vlan.
        The OID vlaue means the uplink port with this metro-mode vlan."
	::= { gs2108cTrapEntry 153 }

gs2108cVlanDoubleTagEnabled NOTIFICATION-TYPE
	STATUS		current
	DESCRIPTION
	   "Send this trap when the operational state of vlan is changed to Double-tag vlan."
	::= { gs2108cTrapEntry 154 }

gs2108cUserLogin NOTIFICATION-TYPE
    OBJECTS   {username}
	STATUS		current
	DESCRIPTION
	   "Send this trap when one user logins the system."
	::= { gs2108cTrapEntry 200 }

gs2108cUserLogout NOTIFICATION-TYPE
    OBJECTS   {username}
	STATUS		current
	DESCRIPTION
	   "Send this trap when one user logouts the system."
	::= { gs2108cTrapEntry 201 }


gs2108cTrapVariable	OBJECT IDENTIFIER ::= { gs2108cProduces 21 }

username OBJECT-TYPE
    SYNTAX      DisplayString
	MAX-ACCESS  read-only	
	STATUS      current
	DESCRIPTION
	    "System account name."
	::= { gs2108cTrapVariable 1 }

groupId OBJECT-TYPE
    SYNTAX      INTEGER(1..8)
	MAX-ACCESS  read-only	
	STATUS      current
	DESCRIPTION
	    "The Trunk group ID of LACP."
	::= { gs2108cTrapVariable 2 }

actorkey OBJECT-TYPE
    SYNTAX	INTEGER(1..2147483647)
	MAX-ACCESS  read-only	
	STATUS      current
	DESCRIPTION
	    "The actor key information for LACP."
	::= { gs2108cTrapVariable 3 }

partnerkey OBJECT-TYPE
    SYNTAX	INTEGER(1..2147483647)
	MAX-ACCESS  read-only	
	STATUS      current
	DESCRIPTION
	    "The partner key information for LACP."
	::= { gs2108cTrapVariable 4 }

uplink OBJECT-TYPE
    SYNTAX	DisplayString
	MAX-ACCESS  read-only	
	STATUS      current
	DESCRIPTION
	    "Uplink port(s) in the metro-mode vlan."
	::= { gs2108cTrapVariable 5 }

END

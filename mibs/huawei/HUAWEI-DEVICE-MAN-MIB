--
-- HUAWEI-DEVICE-MAN-MIB.mib
-- MIB generated by MG-SOFT Visual MIB Builder Version 4.0 Build 347
-- Tuesday, December 27, 2016 at 17:53:50
--

	HUAWEI-DEVICE-MAN-MIB DEFINITIONS ::= BEGIN
 
		IMPORTS
			OBJECT-GROUP, MODULE-COMPLIANCE			
				FROM SNMPv2-CONF			
			enterprises, Unsigned32, OBJECT-TYPE, MODULE-IDENTITY			
				FROM SNMPv2-SMI;
	
	
		storage MODULE-IDENTITY 
			LAST-UPDATED "201612171010Z"		-- December 17, 2016 at 10:10 GMT
			ORGANIZATION 
				"Huawei Technologies Co.,Ltd."
			CONTACT-INFO 
				"Huawei Industrial Base
				Bantian, Longgang
				Shenzhen 518129
				People's Republic of China
				Website: http://www.huawei.com
				Email: support@huawei.com"
			DESCRIPTION 
				"Description."
			::= { products 251 }

		
	
--
-- Node definitions
--
	
		huawei OBJECT IDENTIFIER ::= { enterprises 2011 }

		
		products OBJECT IDENTIFIER ::= { huawei 2 }

		
		deviceManager OBJECT IDENTIFIER ::= { storage 22 }

		
		hwInfoPortIBTable OBJECT-TYPE
			SYNTAX SEQUENCE OF HwInfoPortIBEntry
			MAX-ACCESS not-accessible
			STATUS current
			DESCRIPTION
				"ActiveAlarm Information Table
				"
			::= { deviceManager 16500 }

		
		hwInfoPortIBEntry OBJECT-TYPE
			SYNTAX HwInfoPortIBEntry
			MAX-ACCESS not-accessible
			STATUS current
			DESCRIPTION
				"Entry of Active Alarm Information Table
				"
			INDEX { hwInfoPortIBID }
			::= { hwInfoPortIBTable 1 }

		
		HwInfoPortIBEntry ::=
			SEQUENCE { 
				hwInfoPortIBID
					OCTET STRING,
				hwInfoPortIBParentType
					Unsigned32,
				hwInfoPortIBParentID
					OCTET STRING,
				hwInfoPortIBLocation
					OCTET STRING,
				hwInfoPortIBHealthStatus
					Unsigned32,
				hwInfoPortIBRunningStatus
					Unsigned32,
				hwInfoPortIBType
					Unsigned32,
				hwInfoPortIBWorkingRate
					Unsigned32,
				hwInfoPortIBWWN
					OCTET STRING,
				hwInfoPortIBRole
					Unsigned32,
				hwInfoPortIBSymbolError
					Unsigned32,
				hwInfoPortIBLinkErrorRecovery
					Unsigned32,
				hwInfoPortIBReceiveErrors
					Unsigned32,
				hwInfoPortIBRemoteReceiveErrors
					Unsigned32,
				hwInfoPortIBReceiveTransmitErrors
					Unsigned32,
				hwInfoPortIBNotSendPacakges
					Unsigned32,
				hwInfoPortIBReceiveConstraintErrors
					Unsigned32,
				hwInfoPortIBLinkErrors
					Unsigned32,
				hwInfoPortIBBufferOverrunErrors
					Unsigned32,
				hwInfoPortIBStartTime
					OCTET STRING,
				hwInfoPortIBMaxSpeed
					Unsigned32
			 }

		hwInfoPortIBID OBJECT-TYPE
			SYNTAX OCTET STRING
			MAX-ACCESS read-only
			STATUS current
			DESCRIPTION
				"Active Alarm NodeCode"
			::= { hwInfoPortIBEntry 1 }

		
		hwInfoPortIBParentType OBJECT-TYPE
			SYNTAX Unsigned32
			MAX-ACCESS read-only
			STATUS current
			DESCRIPTION
				"Active Alarm Location Information"
			::= { hwInfoPortIBEntry 2 }

		
		hwInfoPortIBParentID OBJECT-TYPE
			SYNTAX OCTET STRING
			MAX-ACCESS read-only
			STATUS current
			DESCRIPTION
				"Active Alarm Restore Advice"
			::= { hwInfoPortIBEntry 3 }

		
		hwInfoPortIBLocation OBJECT-TYPE
			SYNTAX OCTET STRING
			MAX-ACCESS read-only
			STATUS current
			DESCRIPTION
				"Active Alarm Title"
			::= { hwInfoPortIBEntry 4 }

		
		hwInfoPortIBHealthStatus OBJECT-TYPE
			SYNTAX Unsigned32
			MAX-ACCESS read-only
			STATUS current
			DESCRIPTION
				"Active Alarm Type"
			::= { hwInfoPortIBEntry 5 }

		
		hwInfoPortIBRunningStatus OBJECT-TYPE
			SYNTAX Unsigned32
			MAX-ACCESS read-only
			STATUS current
			DESCRIPTION
				"Active Alarm Level
				
				
				1-criticalAlarm 
				2-majorAlarm 
				3-minorAlarm 
				4-warningAlarm 
				
				"
			::= { hwInfoPortIBEntry 6 }

		
		hwInfoPortIBType OBJECT-TYPE
			SYNTAX Unsigned32
			MAX-ACCESS read-only
			STATUS current
			DESCRIPTION
				"Active Alarm ID"
			::= { hwInfoPortIBEntry 7 }

		
		hwInfoPortIBWorkingRate OBJECT-TYPE
			SYNTAX Unsigned32
			MAX-ACCESS read-only
			STATUS current
			DESCRIPTION
				"Occurrence Time of Alarm"
			::= { hwInfoPortIBEntry 8 }

		
		hwInfoPortIBWWN OBJECT-TYPE
			SYNTAX OCTET STRING
			MAX-ACCESS read-only
			STATUS current
			DESCRIPTION
				"Active Alarm Serial No."
			::= { hwInfoPortIBEntry 9 }

		
		hwInfoPortIBRole OBJECT-TYPE
			SYNTAX Unsigned32
			MAX-ACCESS read-only
			STATUS current
			DESCRIPTION
				"Active Alarm Addtion Information"
			::= { hwInfoPortIBEntry 10 }

		
		hwInfoPortIBSymbolError OBJECT-TYPE
			SYNTAX Unsigned32
			MAX-ACCESS read-only
			STATUS current
			DESCRIPTION
				"Active Alarm Category
				
				
				1-faultAlarm  
				2-resumeAlarm 
				3-eventAlarm  "
			::= { hwInfoPortIBEntry 11 }

		
		hwInfoPortIBLinkErrorRecovery OBJECT-TYPE
			SYNTAX Unsigned32
			MAX-ACCESS read-only
			STATUS current
			DESCRIPTION
				"Active original Alarm ID"
			::= { hwInfoPortIBEntry 12 }

		
		hwInfoPortIBReceiveErrors OBJECT-TYPE
			SYNTAX Unsigned32
			MAX-ACCESS read-only
			STATUS current
			DESCRIPTION
				"Description."
			::= { hwInfoPortIBEntry 13 }

		
		hwInfoPortIBRemoteReceiveErrors OBJECT-TYPE
			SYNTAX Unsigned32
			MAX-ACCESS read-only
			STATUS current
			DESCRIPTION
				"Description."
			::= { hwInfoPortIBEntry 14 }

		
		hwInfoPortIBReceiveTransmitErrors OBJECT-TYPE
			SYNTAX Unsigned32
			MAX-ACCESS read-only
			STATUS current
			DESCRIPTION
				"Description."
			::= { hwInfoPortIBEntry 15 }

		
		hwInfoPortIBNotSendPacakges OBJECT-TYPE
			SYNTAX Unsigned32
			MAX-ACCESS read-only
			STATUS current
			DESCRIPTION
				"Description."
			::= { hwInfoPortIBEntry 16 }

		
		hwInfoPortIBReceiveConstraintErrors OBJECT-TYPE
			SYNTAX Unsigned32
			MAX-ACCESS read-only
			STATUS current
			DESCRIPTION
				"Description."
			::= { hwInfoPortIBEntry 17 }

		
		hwInfoPortIBLinkErrors OBJECT-TYPE
			SYNTAX Unsigned32
			MAX-ACCESS read-only
			STATUS current
			DESCRIPTION
				"Description."
			::= { hwInfoPortIBEntry 18 }

		
		hwInfoPortIBBufferOverrunErrors OBJECT-TYPE
			SYNTAX Unsigned32
			MAX-ACCESS read-only
			STATUS current
			DESCRIPTION
				"Description."
			::= { hwInfoPortIBEntry 19 }

		
		hwInfoPortIBStartTime OBJECT-TYPE
			SYNTAX OCTET STRING
			MAX-ACCESS read-only
			STATUS current
			DESCRIPTION
				"Description."
			::= { hwInfoPortIBEntry 20 }

		
		hwInfoPortIBMaxSpeed OBJECT-TYPE
			SYNTAX Unsigned32
			MAX-ACCESS read-only
			STATUS current
			DESCRIPTION
				"Description."
			::= { hwInfoPortIBEntry 21 }

		
		isoConformance OBJECT IDENTIFIER ::= { iso 6 }

		
		isoGroups OBJECT IDENTIFIER ::= { isoConformance 1 }

		
		currentObjectGroup OBJECT-GROUP
			OBJECTS { hwInfoPortIBID, hwInfoPortIBParentType, hwInfoPortIBParentID, hwInfoPortIBLocation, hwInfoPortIBHealthStatus, 
				hwInfoPortIBRunningStatus, hwInfoPortIBType, hwInfoPortIBWorkingRate, hwInfoPortIBWWN, hwInfoPortIBRole, 
				hwInfoPortIBSymbolError, hwInfoPortIBLinkErrorRecovery, hwInfoPortIBReceiveErrors, hwInfoPortIBRemoteReceiveErrors, hwInfoPortIBReceiveTransmitErrors, 
				hwInfoPortIBNotSendPacakges, hwInfoPortIBReceiveConstraintErrors, hwInfoPortIBLinkErrors, hwInfoPortIBBufferOverrunErrors, hwInfoPortIBStartTime, 
				hwInfoPortIBMaxSpeed }
			STATUS current
			DESCRIPTION 
				"Enter the description of the created OBJECT-GROUP."
			::= { isoGroups 1 }

		
		isoCompliances OBJECT IDENTIFIER ::= { isoConformance 2 }

		
		basicCompliance MODULE-COMPLIANCE
			STATUS current
			DESCRIPTION 
				"Enter the description of the created MODULE-COMPLIANCE."
			MODULE -- this module
				MANDATORY-GROUPS { currentObjectGroup }
			::= { isoCompliances 1 }

		
	
	END

--
-- HUAWEI-DEVICE-MAN-MIB.mib
--

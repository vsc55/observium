--
-- OPTIX-SONET-PER-MIB.mib
-- MIB generated by MG-SOFT Visual MIB Builder Version 3.0 Build 253
-- Monday, March 06, 2006 at 10:26:16
--
            -- =================================================================
--  Copyright (C) 2006 by HUAWEI TECHNOLOGIES. All rights reserved
--  
--  Description:This MIB describes the Performance interface of Huawei SONET transmit
--  Reference:
--  Version: V1.00
--  History:
-- 	<author>,<date>,<contents>
-- =================================================================
-- 

	OPTIX-GLOBAL-PM-MIB DEFINITIONS ::= BEGIN
 
		IMPORTS
			optixCommonGlobal			
				FROM OPTIX-OID-MIB			
			PerformanceEventType, ValidflagType, ObjType,AlarmEventType, AlmDataSrvEffType, AlmDataNtfcnCdeType		
				FROM OPTIX-GLOBAL-TC-MIB			
			OBJECT-GROUP, MODULE-COMPLIANCE			
				FROM SNMPv2-CONF			
			Integer32, Unsigned32, OBJECT-TYPE, MODULE-IDENTITY			
				FROM SNMPv2-SMI			
			DateAndTime, DisplayString			
				FROM SNMPv2-TC;
	
	
		optixGlobalPM MODULE-IDENTITY 
			LAST-UPDATED "200805240000Z"
			ORGANIZATION 
				"Huawei Technologies co.,Ltd."
			CONTACT-INFO 
				"R&D Building
				Huawei Technologies Co., Ltd.
				Bantian, Longgang District 
				Shenzhen, P. R. China
				http://www.huawei.com
				Zip:518129
				E-mail:support@huawei.com"
			DESCRIPTION 
				"Description."
			REVISION "200805240000Z"
			DESCRIPTION
				"The initial revision of this MIB module."
			::= { optixCommonGlobal 10 }  
			
		optixGlobalPER MODULE-IDENTITY 
			LAST-UPDATED "200805240000Z"
			ORGANIZATION 
				"Huawei Technologies co.,Ltd."
			CONTACT-INFO 
				"R&D Building
				Huawei Technologies Co., Ltd.
				Bantian, Longgang District 
				Shenzhen, P. R. China
				http://www.huawei.com
				Zip:518129
				E-mail:support@huawei.com"
			DESCRIPTION 
				"Description."
			REVISION "200805240000Z"
			DESCRIPTION
				"The initial revision of this MIB module."
			::= { optixCommonGlobal 20 }  
			
--  Alarm data    
		-- 1.3.6.1.4.1.2011.2.25.3.20.20.10
		pmHistCtr OBJECT IDENTIFIER ::= { optixGlobalPM 10 }
		
--  *************************************************************************
-- pmHistCtr
-- -------------------------------------------------------------------------
-- Perfomance 15-MIN Current Data Table (RTRV-PM-<MOD2>)
-- ------------------------------------------------------------------------- 
		-- 1.3.6.1.4.1.2011.2.25.3.20.20.10.10
		pmHistCtrTable OBJECT-TYPE
			SYNTAX SEQUENCE OF PmHistCtrEntry
			MAX-ACCESS not-accessible
			STATUS current
			DESCRIPTION
				"HistCtr."
			::= { pmHistCtr 10 }
		
		-- 1.3.6.1.4.1.2011.2.25.3.20.20.10.10.1
		pmHistCtrEntry OBJECT-TYPE
			SYNTAX PmHistCtrEntry
			MAX-ACCESS not-accessible
			STATUS current
			DESCRIPTION
				"HistCtr."
			INDEX {pmHistCtrPeriod}
			::= { pmHistCtrTable 1 }
		
		PmHistCtrEntry ::=
			SEQUENCE { 
				pmHistCtrPeriod
					INTEGER,
				pmHistCtrRecNum
					INTEGER,
				pmHistCtrInterval
					INTEGER,
				pmHistCtrEnableFlag
					INTEGER
			 }

		-- 1.3.6.1.4.1.2011.2.25.3.20.20.10.10.1.1
		pmHistCtrPeriod OBJECT-TYPE
			SYNTAX INTEGER 
				{
					period30s(17),
					period30m(18),
					periodPrdvar(19),
					periodPrdvar2(20)
				}
			MAX-ACCESS read-only
			STATUS current
			DESCRIPTION
				"Period."
			::= { pmHistCtrEntry 1 }
		
		-- 1.3.6.1.4.1.2011.2.25.3.20.20.10.10.1.2
		pmHistCtrRecNum OBJECT-TYPE
			SYNTAX INTEGER
			MAX-ACCESS read-write
			STATUS current
			DESCRIPTION
				"RecNum."
			::= { pmHistCtrEntry 2 }
		
		-- 1.3.6.1.4.1.2011.2.25.3.20.20.10.10.1.3
		pmHistCtrInterval OBJECT-TYPE
			SYNTAX INTEGER
			MAX-ACCESS read-write
			STATUS current
			DESCRIPTION
				"Interval. "
			::= { pmHistCtrEntry 3 }
		
		-- 1.3.6.1.4.1.2011.2.25.3.20.20.10.10.1.4
		pmHistCtrEnableFlag OBJECT-TYPE
			SYNTAX INTEGER 
				{
					enable(1),
					disable(0)
				}
			MAX-ACCESS read-write
			STATUS current
			DESCRIPTION
				"EnableFlag. "
			::= { pmHistCtrEntry 4 }
	END
--
-- OPTIX-SONET-PER-MIB.mib
--

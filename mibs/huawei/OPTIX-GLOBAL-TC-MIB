--
-- OPTIX-SONET-TC-MIB.mib
-- MIB generated by MG-SOFT Visual MIB Builder Version 3.0 Build 253
-- Thursday, July 27, 2006 at 15:47:18

--

-- =================================================================
-- Copyright (C) 2006 by HUAWEI TECHNOLOGIES. All rights reserved
-- 
-- Description:This MIB describes the TC interface of Huawei SONET transmit
-- Reference:
-- Version: V1.10
-- History:
-- <yuanxiaoshu>,<2006-05-10>,<change event name from evtXXX to almXXX, because alarm attribute can be changed>
-- <liyilong>,<2006-08-18>,<Add SONET R3 alarm>
-- =================================================================

    OPTIX-GLOBAL-TC-MIB DEFINITIONS ::= BEGIN
 
        IMPORTS
            optixCommonGlobal            
                FROM OPTIX-OID-MIB            
            MODULE-IDENTITY            
                FROM SNMPv2-SMI            
            TEXTUAL-CONVENTION            
                FROM SNMPv2-TC;
    
--
-- Textual conventions
--
    
        AlarmEventType ::= TEXTUAL-CONVENTION
            STATUS current
            DESCRIPTION 
                "Alarm ID."
            SYNTAX INTEGER
                {
                    almRLos(1),
                    almTLos(2),
                    almRLoc(3), 
                    almTLoc(4),
                    almROof(5),
                    almNoBdSoft(6),
                    almRLof(8),
                    almTf(9),
                    almRsCrosstr(10),
                    almB1Exc(12),
                    almTRLOC(14),  
                    almHpCrossTr(16),
                    almCurrentLockFailed(21),
                    almInpwrfail(24),
                    almInPwrAbn(25),
                    almOutPwrAbn(26),
                    almTempOver(28),
                    almTemHa(29),
                    almTemLa(30),
                    almInPwrHigh(31),
                    almInPwrLow(32),
                    almMsAis(33),
                    almMsRdi(34),
                    almB2Exc(35),
                    almInsertionLossHigh(12584),
                    almOtsTim(12615),
                    almOtsLos(12616),
                    almOtsLosP(12617),
                    almOtsLosO(12618),
                    almOtsBdi(12619),
                    almOtsBdiP(12620),
                    almOtsBdiO(12621),
                    almOosLost(12622),
                    almOmsLosP(12623),
                    almOmsSsf(12624),
                    almOmsSsfP(12625),
                    almOmsSsfO(12626),
                    almOmsFdi(12627),
                    almOmsFdiP(12628),
                    almOmsFdiO(12629),
                    almOmsBdi(12630),
                    almOmsBdiP(12631),
                    almOmsBdiO(12632),
                    almWavelenOver(12771),
                    almOnePumpWork(12779),
                    almPumpLinkUllageHigh(12780),
                    almPumpOffline(12784),
                    almPumpMisMatch(12840),
                    almApdTemHigh(12878),
                    almApdTemLow(12879),
                    almApdCoolAlm(12880),
                    almOaHighGain(12995),
                    almLockpowMis(13052),
                    almMcapsApsidMismatch(13103),
                    almMcapsDnipwMismatch(13104),
                    almWaveAddAbn(13197),
                    almWaveDropAbn(13198),
                    almApeAdjustPend(13199),
                    almApeAdjustFail(13200),
                    almRlCriticalHi(13414),
                    almRlCriticalLow(13415),
                    almFibertypeMis(13483),
                    almAlsTriggered(13504),
                    almAseNotCalibrate(13534),
                    almDerivedPwrError(13541),
                    almLaserOpenFail(13715),
                    almOtsPmi(13720),
                    almOmsPmi(13721),
                    almLsrKeyUnlock(13965),
                    almMcsSwitchBlocked(13966),
                    almOrpCriticalHi(14001),
                    almFiberBreakPos(14009),
                    almFiberAbnPos(14010),
                    almFiberLossChg(14011),
                    almWavelenRepeated(14025),
                    almSubcardComFail(14037),
                    almSubcardMismatch(14038),
                    almSubcardOffline(14039),
                    almSubcardUpgradeFail(14040),
                    almSubcardTempOver(14050),
                    almOtuWaveMismatch(14203),
                    almIntraOtuWeak(14270),
                    almChanPowerDiffOver(14320),
                    almOpaVoaMismatch(14326),
                    almOsnrDeg(14339),
                    almOmsRouteStatusAbn(14340),
                    almRmRlos(42184),
                    almB2Sd(36),
                    almMsRei(37),
                    almMsCrossTr(38), 
                    almRAps(40),
                    almApsIndi(41),
                    almApsFail(42),
                    almRSlip(46),
                    almTSlip(47),  
                    almLpRfi(48), 
                    almLpCrossTr(49), 
                    almLpUatEvent(50),
                    almLpSizeErr(51),
                    almCRC4CrossTr(53),
                    almOscRdi(54),
                    almLsrWillDie(56),
                    almLsrNoFited(57),
                    almLsrBcmAlm(58),
                    almLsrCoolAlm(60),
                    almOutPwrHigh(63),
                    almOutPwrLow(64),
                    almAuLop(66), 
                    almMsadCrossTr(67),
                    almPumTemAlm(68),
                    almPumBcmAlm(69),
                    almB3Sd(70),
                    almB3Exc(71),
                    almAuAis(72),  
                    almCesApsManualStop(13173),
                    almHpRFifo(73),
                    almHpTFifo(74),
                    almHpUneq(75),
                    almHpTIM(76),
                    almHpSlm(77),
                    almHpRdi(78),
                    almHpRei(79),
                    almMailError(80),       
                    almHpLom(81), 
                    almTuLop(82),
                    almTuAis(83), 
                    almHpadCrossTr(84),
                    almJ0Mm(87), 
                    almLpRFifo(88),
                    almLpTFifo(89),
                    almLpUneq(90),
                    almLpTim(91),
                    almLpSlm(92),
                    almLpRdi(93),
                    almLpRei(94),
                    almLossTimIn(100),
                    almSyncDegrade(101),   
                    almTAlos(107),
                    
                    almFanFail(115), 
                    almBusLoc(116),
                    almE1Los(117),
                    almUpE1Ais(118),
                    almBdOffline(119),
                    almWrgBdType(121),
                    almPwrFail(125), 
                    almUpT1Ais(130), 
                    almPLos(134),
                    almPLoc(135),
                    almPAis(137),
                    almALoc(139),  
                    almRSErr(141),  
                    almTFifoE(156),
                    almTempAlm(166),
                    almPwrMajAlarm(169),
                    almB1Sd(175),
                    almK1K2M(180),
                    almK2M(181),  
                    almBipSd(182),
                    almBipExc(183),
                    almExtSyncLos(184),
                    almDBErr(185),
                    almMutLos(186),
                    almChanLos(187),
                    almChanAdd(188),
                    almTd(189),
                    almNoBdPara(190),
                    almPumpCoolExc(192),
                    almS1SynChange(193),
                    almFpgaAbn(194),
                    almNeStateInstall(197),
                    almNesfLost(215),
                    almSncpFail(234),
                    almModuleCoolcurOver(270),
                    almSccLoc(342),
                    almAlmHangup(420),
                    almSccChange(422),
                    almHscUnavail(440),
                    almNodeidMm(578),
                    almMsApsIndiEx(600),
                    almDbRestoreFail(12644),
                    almAlcWaitAdjust(13133),
                    almAlcAdjustFail(13134),
                    almEthMisconnect(13272),
                    almMplsSectLocv(13403),
                    almMplsSectOamfail(13404),
                    almMplsSectUnexpmeg(13405),
                    almMplsSectUnexpmep(13406),
                    almMplsSectUnexpper(13407),
                    almMplsSectRdi(13408),
                    almMplsSectSd(13409),
                    almMplsSectSf(13410),
                    almEfiTypeMismatch(13437),
                    almNeipConfusion(13513),
                    almLcsShortageShelf(13664),
                    almShelfPowerUnconfig(13763),
                    almSubrackExceed(13947),
                    almRmtDevPowerOff(13489),
                    almSubrackRingConnectWeak(14401),
                    almRackConflictScreen(13952),
                    almBdSessionFail(13982),
                    almWclaAbnormal(14204),
                    almWclaAdjustFail(14205),
                    almXcsUpgradeInproc(14327),
                    almXcsUpgradeFail(14328),
                    almXcsUpgradeUncommit(14329),
                    almXcsDngradeInproc(14330),
                    almXcsDngradeFail(14331),
                    almXcsRollbackInproc(14332),
                    almXcsRollbackFail(14333),
                    almNeidConflict(63625),
                    almProtectMode(198),
                    almCommFail(199),
                    almSecuAlm(200), 
                    almDnE1Ais(201),
                    almPowerDiffOver(211),
                    almFecLof(212),
                    almFecOof(213),
                    almFuseAlarm(221),
                    almMdlAlarm(222),
                    almRateOver(223),
                    almEthLos(235),
                    
                    almLoopAlm(240),
                    almFanCommFail(256),
                    
                    almAuCmm(260),
                    almLinkErr(261),  
                    almWOffline(262),
                    almPllOutofLock(263), 
                    almE1Loc(266),
                    almNoLsrParaFile(268),
                    almAdCheckFail(269),
                    almOtuLof(272),
                    almOtuLom(273),
                    almSmTim(274),
                    almPmTim(275),
                    almSmBdi(276),
                    almPmBdi(277),
                    almSmBei(278),
                    almPmBei(279),
                    almSmIae(280),
                    almSmBip8Over(282),
                    almPmBip8Over(283),
                    almSmBip8Sd(284),
                    almPmBip8Sd(285),
                    almOtuAis(286),
                    almOduAis(287),
                    almOduOci(288),
                    almOduLck(289),
                    almDspLoadFail(292),
                    almAls(296),
                    almRmonAlmInbadoctsOver(299),
                    almSumInpwrHi(323),
                    almSumInpwrLow(324),
                    almSumOutpwrHigh(325),
                    almSumOutpwrLow(326),
                    almOaLowGain(327),
                    almClkNontracing(333),
                    almBeffecExc(335),
                    almApsManuStop(336),
                    almEdfaTempOver(337),
                    almInPwrFail(343), 
                    almOutPwrFail(344), 
                    almPwrTmpHigh(345),              
                    almPwrTmpOverTh(346),           
                    almBdVerNmat(351),
                    almTcLtc(352),
                    almTcUneq(353),
                    almTcIncais(354),
                    almTcRdi(355),
                    almTcOdi(356),
                    almTcTim(357),
                    almTcRei(358),
                    almTcOei(359),
                    almTcExc(360),
                    almTcDeg(361), 
                    almLaserClosed(364),
                    almTLosex(365),
                    almC2Vcais(366),
                    almC2Pdi(368),
                    almOhLoop(369),
                    almFSelectStg(373),
                    almTestStatus(374),
                    almBusErr(377),
                    almXcUnswitch(388),
                    almSyncLockoff(390),
                    almSyncForceManualSwch(391),
                    almLaserModErr(393),
                    almBdidError(406),
                    almPowerAbnormal(412),
                    almSlaveWorking(424),
                    almBiosStatus(449),
                    almMSSWDifferent(571),
                    almActiveTimeout(573),
                    almSwdlNepkgcheck(574),
                    almSwdlChgmngMismatch(575),
                    almBootRomBad(584),
                    almCfdbMisMatch(587),
                    almDbsyncFail(591),
                    almChipAbn(597),
                    almBip8Ecc(598),
                    almLaserModuleMismatch(606),  
                    almLpsUniBiM(619),
                    almPatchFileNotExist(620),
                    almPatchErr(621),
                    almPatchNotConfirm(622),
                    almRtcFault(624),
                    almBDNotInstalled(625),
                    almRlLow(652),
                    almRlShut(653),
                    almSWDLPkgNoBDSoft(2569),
                    almRollBackFail(2570),
                    almCommitFail(2571),
                    almSWDLInProcess(2572),
                    almPkgverMisMatch(2573),
                    almAutoMatchInh(2574),
                    almDlagProtectFail(12288),
                    almRemEthLoop(12291),
                    almRemEthSd(12292),
                    almRemEthSf(12293),
                    almEthOamFail(12294),  
                    almDownT1Ais(12295),
                    almCCLos(12298),
                    almMpidCnflct(12299),
                    almLptRfi(12300),
                    almFlowOver(12301),
                    almShelfIdConflict(12302),
                    almShelfIdMismatch(12303),
                    almShelfLoop(12304),
                    almRelayAlmCritical(12305),
                    almRelayAlmMajor(12306),
                    almRelayAlmMinor(12307),
                    almRelayAlmIgnore(12308),
                    almSingleFanFail(12309),
                    almCfgDataOutRange(12310),
                    almOtu1Lof(12311),
                    almOtu1Ais(12312),
                    almOtu1Lom(12313),
                    almOtu1Tim(12314),
                    almOtu1Deg(12315),
                    almOtu1Bdi(12316),
                    almOtu5gLof(12317),
                    almOtu5gAis(12318),
                    almOtu5gLom(12319),
                    almOtu5gTim(12320),
                    almOtu5gDeg(12321),
                    almOtu5gBdi(12322),
                    almOtu2Lof(12323),
                    almOtu2Ais(12324),
                    almOtu2Lom(12325),
                    almOtu2Tim(12326),
                    almOtu2Deg(12327),
                    almOtu2Bdi(12328),
                    almOtu3Lof(12329),
                    almOtu3Ais(12330),
                    almOtu3Lom(12331),
                    almOtu3Tim(12332),
                    almOtu3Deg(12333),
                    almOtu3Bdi(12334),
                    almOdu1PmTim(12335),
                    almOdu1PmDeg(12336),
                    almOdu1PmBdi(12337),
                    almOdu1PmLck(12338),
                    almOdu1PmOci(12339),
                    almOdu1PmAis(12340),
                    almOdu1Loflom(12341),
                    almOdu5gPMTim(12342),
                    almOdu5gPMDeg(12343),
                    almOdu5gPMBdi(12344),
                    almOdu5gPMLck(12345),
                    almOdu5gPMOci(12346),
                    almOdu5gPMAis(12347),
                    almOdu5gLoflom(12348),
                    almOdu2PmTim(12349),
                    almOdu2PmDeg(12350),
                    almOdu2PmBdi(12351),
                    almOdu2PmLck(12352),
                    almOdu2PmOci(12353),
                    almOdu2PmAis(12354),
                    almOdu2Loflom(12355),
                    almOdu3PmTim(12356),
                    almOdu3PmDeg(12357),
                    almOdu3PmBdi(12358),
                    almOdu3PmLck(12359),
                    almOdu3PmOci(12360),
                    almOdu3PmAis(12361),
                    almV5Vcais(607),
                    almCesLospktExc(12796),
                    almCesMisorderpktExc(12797),
                    almCesStraypktExc(12798),
                    almCesMalpktExc(12799),
                    almCesJtrudrExc(12800),
                    almCesJtrovrExc(12801),
                    almCesRdi(12802),
                    almMplsTunnelLocv(12814),
                    almMplsTunnelSd(12821),
                    almMplsTunnelSf(12822),
                    almEthApsTypeMismatch(12831),
                    almEthApsPathMismatch(12832),
                    almEthApsSwitchFail(12833),
                    almEthApsLost(12834),
                    almEthPwrSupplyFail(12923),
                    almEthAutoLinkDown(12928),
                    almArpMacMismatch(13008),
                    almCespwOppositeRai(13080),
                    almCespwOppositeAcfault(13081),
                    almMplsPwLocv(13091),
                    almMplsPwSd(13097),
                    almMplsPwSf(13098),
                    almPwapsTypeMismatch(13099),
                    almPwapsPathMismatch(13100),
                    almPwapsSwitchFail(13101),
                    almPwapsLost(13102),
                    almPwNoTraffic(13107),
                    almMplsPwOamfail(13135),
                    almCesK1K2M(13147),
                    almCesK2M(13148),
                    almCesApsIndi(13149),
                    almCesLpsUniBiM(13152),
                    almCesAcrLockAbn(13277),
                    almTunnelApsDegraded(13377),
                    almMplsTunnelUnexpmeg(13393),
                    almMplsTunnelUnexpmep(13394),
                    almMplsTunnelUnexpper(13395),
                    almMplsTunnelRdi(13396),
                    almMplsPwUnexpmeg(13398),
                    almMplsPwUnexpmep(13399),
                    almMplsPwUnexpper(13400),
                    almMplsPwRdi(13401),
                    almArpFail(13689),
                    almFlowExcLcs(13907),
                    almDeviceAuthFail(14007),
                    almGpsmodLockFail(14077),
                    almGpsmodInvalid(14078),
                    almSepPortFault(14084),
                    almFpOffline(14190),
                    almLfa(63554),
                    almLmfa(63558),
                    almLpRdiVc12(63590),
                    almLpReiVc12(63592),
                    almLpSlmVc12(63594),
                    almLpTimVc12(63596),
                    almAlmE1rai(63622),
                    almOdu3Loflom(12362),
                    almOdu1Tcm1Tim(12363),
                    almOdu1Tcm2Tim(12364),
                    almOdu1Tcm3Tim(12365),
                    almOdu1Tcm4Tim(12366),
                    almOdu1Tcm5Tim(12367),
                    almOdu1Tcm6Tim(12368),
                    almOdu1Tcm1Deg(12369),
                    almOdu1Tcm2Deg(12370),
                    almOdu1Tcm3Deg(12371),
                    almOdu1Tcm4Deg(12372),
                    almOdu1Tcm5Deg(12373),
                    almOdu1Tcm6Deg(12374),
                    almOdu1Tcm1Bdi(12375),
                    almOdu1Tcm2Bdi(12376),
                    almOdu1Tcm3Bdi(12377),
                    almOdu1Tcm4Bdi(12378),
                    almOdu1Tcm5Bdi(12379),
                    almOdu1Tcm6Bdi(12380),
                    almOdu1Tcm1Ais(12381),
                    almOdu1Tcm2Ais(12382),
                    almOdu1Tcm3Ais(12383),
                    almOdu1Tcm4Ais(12384),
                    almOdu1Tcm5Ais(12385),
                    almOdu1Tcm6Ais(12386),
                    almOdu1Tcm1Oci(12387),
                    almOdu1Tcm2Oci(12388),
                    almOdu1Tcm3Oci(12389),
                    almOdu1Tcm4Oci(12390),
                    almOdu1Tcm5Oci(12391),
                    almOdu1Tcm6Oci(12392),
                    almOdu1Tcm1Lck(12393),
                    almOdu1Tcm2Lck(12394),
                    almOdu1Tcm3Lck(12395),
                    almOdu1Tcm4Lck(12396),
                    almOdu1Tcm5Lck(12397),
                    almOdu1Tcm6Lck(12398),
                    almOdu1Tcm1Ltc(12399),
                    almOdu1Tcm2Ltc(12400),
                    almOdu1Tcm3Ltc(12401),
                    almOdu1Tcm4Ltc(12402),
                    almOdu1Tcm5Ltc(12403),
                    almOdu1Tcm6Ltc(12404),
                    almOdu5gTcm1Tim(12405),
                    almOdu5gTcm2Tim(12406),
                    almOdu5gTcm3Tim(12407),
                    almOdu5gTcm4Tim(12408),
                    almOdu5gTcm5Tim(12409),
                    almOdu5gTcm6Tim(12410),
                    almOdu5gTcm1Deg(12411),
                    almOdu5gTcm2Deg(12412),
                    almOdu5gTcm3Deg(12413),
                    almOdu5gTcm4Deg(12414),
                    almOdu5gTcm5Deg(12415),
                    almOdu5gTcm6Deg(12416),
                    almOdu5gTcm1Bdi(12417),
                    almOdu5gTcm2Bdi(12418),
                    almOdu5gTcm3Bdi(12419),
                    almOdu5gTcm4Bdi(12420),
                    almOdu5gTcm5Bdi(12421),
                    almOdu5gTcm6Bdi(12422),
                    almOdu5gTcm1Ais(12423),
                    almOdu5gTcm2Ais(12424),
                    almOdu5gTcm3Ais(12425),
                    almOdu5gTcm4Ais(12426),
                    almOdu5gTcm5Ais(12427),
                    almOdu5gTcm6Ais(12428),
                    almOdu5gTcm1Oci(12429),
                    almOdu5gTcm2Oci(12430),
                    almOdu5gTcm3Oci(12431),
                    almOdu5gTcm4Oci(12432),
                    almOdu5gTcm5Oci(12433),
                    almOdu5gTcm6Oci(12434),
                    almOdu5gTcm1Lck(12435),
                    almOdu5gTcm2Lck(12436),
                    almOdu5gTcm3Lck(12437),
                    almOdu5gTcm4Lck(12438),
                    almOdu5gTcm5Lck(12439),
                    almOdu5gTcm6Lck(12440),
                    almOdu5gTcm1Ltc(12441),
                    almOdu5gTcm2Ltc(12442),
                    almOdu5gTcm3Ltc(12443),
                    almOdu5gTcm4Ltc(12444),
                    almOdu5gTcm5Ltc(12445),
                    almOdu5gTcm6Ltc(12446),
                    almOdu2Tcm1Tim(12447),
                    almOdu2Tcm2Tim(12448),
                    almOdu2Tcm3Tim(12449),
                    almOdu2Tcm4Tim(12450),
                    almOdu2Tcm5Tim(12451),
                    almOdu2Tcm6Tim(12452),
                    almOdu2Tcm1Deg(12453),
                    almOdu2Tcm2Deg(12454),
                    almOdu2Tcm3Deg(12455),
                    almOdu2Tcm4Deg(12456),
                    almOdu2Tcm5Deg(12457),
                    almOdu2Tcm6Deg(12458),
                    almOdu2Tcm1Bdi(12459),
                    almOdu2Tcm2Bdi(12460),
                    almOdu2Tcm3Bdi(12461),
                    almOdu2Tcm4Bdi(12462),
                    almOdu2Tcm5Bdi(12463),
                    almOdu2Tcm6Bdi(12464),
                    almOdu2Tcm1Ais(12465),
                    almOdu2Tcm2Ais(12466),
                    almOdu2Tcm3Ais(12467),
                    almOdu2Tcm4Ais(12468),
                    almOdu2Tcm5Ais(12469),
                    almOdu2Tcm6Ais(12470),
                    almOdu2Tcm1Oci(12471),
                    almOdu2Tcm2Oci(12472),
                    almOdu2Tcm3Oci(12473),
                    almOdu2Tcm4Oci(12474),
                    almOdu2Tcm5Oci(12475),
                    almOdu2Tcm6Oci(12476),
                    almOdu2Tcm1Lck(12477),
                    almOdu2Tcm2Lck(12478),
                    almOdu2Tcm3Lck(12479),
                    almOdu2Tcm4Lck(12480),
                    almOdu2Tcm5Lck(12481),
                    almOdu2Tcm6Lck(12482),
                    almOdu2Tcm1Ltc(12483),
                    almOdu2Tcm2Ltc(12484),
                    almOdu2Tcm3Ltc(12485),
                    almOdu2Tcm4Ltc(12486),
                    almOdu2Tcm5Ltc(12487),
                    almOdu2Tcm6Ltc(12488),
                    almOdu3Tcm1Tim(12489),
                    almOdu3Tcm2Tim(12490),
                    almOdu3Tcm3Tim(12491),
                    almOdu3Tcm4Tim(12492),
                    almOdu3Tcm5Tim(12493),
                    almOdu3Tcm6Tim(12494),
                    almOdu3Tcm1Deg(12495),
                    almOdu3Tcm2Deg(12496),
                    almOdu3Tcm3Deg(12497),
                    almOdu3Tcm4Deg(12498),
                    almOdu3Tcm5Deg(12499),
                    almOdu3Tcm6Deg(12500),
                    almOdu3Tcm1Bdi(12501),
                    almOdu3Tcm2Bdi(12502),
                    almOdu3Tcm3Bdi(12503),
                    almOdu3Tcm4Bdi(12504),
                    almOdu3Tcm5Bdi(12505),
                    almOdu3Tcm6Bdi(12506),
                    almOdu3Tcm1Ais(12507),
                    almOdu3Tcm2Ais(12508),
                    almOdu3Tcm3Ais(12509),
                    almOdu3Tcm4Ais(12510),
                    almOdu3Tcm5Ais(12511),
                    almOdu3Tcm6Ais(12512),
                    almOdu3Tcm1Oci(12513),
                    almOdu3Tcm2Oci(12514),
                    almOdu3Tcm3Oci(12515),
                    almOdu3Tcm4Oci(12516),
                    almOdu3Tcm5Oci(12517),
                    almOdu3Tcm6Oci(12518),
                    almOdu3Tcm1Lck(12519),
                    almOdu3Tcm2Lck(12520),
                    almOdu3Tcm3Lck(12521),
                    almOdu3Tcm4Lck(12522),
                    almOdu3Tcm5Lck(12523),
                    almOdu3Tcm6Lck(12524),
                    almOdu3Tcm1Ltc(12525),
                    almOdu3Tcm2Ltc(12526),
                    almOdu3Tcm3Ltc(12527),
                    almOdu3Tcm4Ltc(12528),
                    almOdu3Tcm5Ltc(12529),
                    almOdu3Tcm6Ltc(12530),
                    almOpu1Plm(12531),
                    almOpu5gPlm(12532),
                    almOpu2Plm(12533),
                    almOpu2Msim(12534),
                    almOpu3Plm(12535),
                    almOpu3Msim(12536),
                    almOlpPs(12537),
                    almIntraOtuPs(12539),
                    almClientPortPs(12540),
                    almOduSncpPs(12541),
                    almSWSncpPs(12542),
                    almVlanSncpPs(12543),
                    almRemoteFault(12544),
                    almLocalFault(12545),
                    almOtu1Exc(12548),
                    almOdu1PMExc(12549),
                    almOdu1Tcm1Exc(12550),
                    almOdu1Tcm2Exc(12551),
                    almOdu1Tcm3Exc(12552),
                    almOdu1Tcm4Exc(12553),
                    almOdu1Tcm5Exc(12554),
                    almOdu1Tcm6Exc(12555),
                    almOtu5gExc(12556),
                    almOdu5gPMExc(12557),
                    almOdu5gTcm1Exc(12558),
                    almOdu5gTcm2Exc(12559),
                    almOdu5gTcm3Exc(12560),
                    almOdu5gTcm4Exc(12561),
                    almOdu5gTcm5Exc(12562),
                    almOdu5gTcm6Exc(12563),
                    almOtu2Exc(12564),
                    almOdu2PMExc(12565),
                    almOdu2Tcm1Exc(12566),
                    almOdu2Tcm2Exc(12567),
                    almOdu2Tcm3Exc(12568),
                    almOdu2Tcm4Exc(12569),
                    almOdu2Tcm5Exc(12570),
                    almOdu2Tcm6Exc(12571),
                    almOtu3Exc(12572),
                    almOdu3PMExc(12573),
                    almOdu3Tcm1Exc(12574),
                    almOdu3Tcm2Exc(12575),
                    almOdu3Tcm3Exc(12576),
                    almOdu3Tcm4Exc(12577),
                    almOdu3Tcm5Exc(12578),
                    almOdu3Tcm6Exc(12579),
                    almHardErr(12580),
                    almElabelLost(12581),
                    almLptActive(12582),
                    almCvEth(12583),
                    almInsertLossHigh(13882),
                    almInsertLossMid(13883),
                    almGneConnectFull(14303),
                    almsyslogcommfail(12586),
                    almClientPortNotStart(12595),
                    almOpaFailIndi(12596),
                    almLsrForceOpen(12597), 
                    almNePowerOver(12601),
                    almLosyncFc(12603),
                    almLinkErrFc(12604),
                    almCvFc(12605),
                    almSoSkMismatch(12614),
                    almOchLosP(12633),
                    almOchOci(12634),
                    almOchSsf(12635),
                    almOchSsfP(12636),
                    almOchSsfO(12637),
                    almOchFdi(12638),
                    almOchFdiP(12639),
                    almOchFdiO(12640),
                    almOdukspPs(12641),
                    almOwspPs(12642),
                    almPrbsLss(12643),
                    almOtu1Ssf(12711),
                    almOdu1PmSsf(12712),
                    almOdu1Tcm1Ssf(12713),
                    almOdu1Tcm2Ssf(12714),
                    almOdu1Tcm3Ssf(12715),
                    almOdu1Tcm4Ssf(12716),
                    almOdu1Tcm5Ssf(12717),
                    almOdu1Tcm6Ssf(12718),
                    almOtu5gSsf(12719),
                    almOdu5gPMSsf(12720),
                    almOdu5gTcm1Ssf(12721),
                    almOdu5gTcm2Ssf(12722),
                    almOdu5gTcm3Ssf(12723),
                    almOdu5gTcm4Ssf(12724),
                    almOdu5gTcm5Ssf(12725),
                    almOdu5gTcm6Ssf(12726),
                    almOtu2Ssf(12727),
                    almOdu2PmSsf(12728),
                    almOdu2Tcm1Ssf(12729),
                    almOdu2Tcm2Ssf(12730),
                    almOdu2Tcm3Ssf(12731),
                    almOdu2Tcm4Ssf(12732),
                    almOdu2Tcm5Ssf(12733),
                    almOdu2Tcm6Ssf(12734),
                    almOtu3Ssf(12735),
                    almOdu3PmSsf(12736),
                    almOdu3Tcm1Ssf(12737),
                    almOdu3Tcm2Ssf(12738),
                    almOdu3Tcm3Ssf(12739),
                    almOdu3Tcm4Ssf(12740),
                    almOdu3Tcm5Ssf(12741),
                    almOdu3Tcm6Ssf(12742),
                    almOpu1VcatVcplm(12743),
                    almOpu1VcatSqm(12744),
                    almDcmInsuff(12745),
                    almEthoamVcgSelfLoop(12768),
                    almLagPortFail(12769),
                    almLagVcPortFail(12770),
                    almLsrInvalid(12773),
                    almPatchDeactTimeout(12775),
                    almPatchActTimeout(12776),
                    almQValueExc(12778),
                    almVctrunkNoFlow(12787),
                    almDccChanLack(12789),
                    almPatchPkgErr(12790),
                    almSyncDisable(12792),
                    almEthLinkDown(12793),
                    almMacFcsExc(12794),
                    almEthCfmMismerge(12823),
                    almEthCfmUnexperi(12824),
                    almEthCfmLoc(12825),
                    almEthCfmRdi(12826),
                    almEthEfmDf(12827),
                    almEthEfmRemfault(12828),
                    almEthEfmEvent(12829),
                    almEthEfmLoopBack(12830),
                    almDbpsAbnormal(12835),
                    almLagMemberDown(12836),
                    almLagDown(12837),
                    almMuttlos(12842),
                    almOscLos(12843),
                    almTsCfgMismatch(12856),
                    almModTypeMismatch(12868), 
                    almPatchChgSccNotMatch(12872), 
                    almStormCurQuenumOver(12884),
                    almCpwOdu2TelDown(12911),
                    almSsmQlFailed(12914),
                    almSsmLos(12917),
                    almElpsBCfgMismatch(12921),
                    
                    almNullSend(12929),
                    almCpwOtu2TelDown(12934),
                    almCpwOdu3TelDown(12937), 
                    almMsSncpPs(12955),
                    almLSync(12956),
                    almTimeNotrace(12963),
                    almTimeLos(12964),
                    almLaserHazardWarning(12969),
                    almExtClkLost(12972),
                    almShelfTypeMismatch(12973),
                    almEthCfmMacstatus(12975),  
                    almE1Ais(13006),
                    almE1Lof(13007),  
                    almCpwLmsTelOvpnMm(13014),  
                    almCpcOspfClDown(13037),
                    almcpcnodeiderr(13044),
                    almPasswordneedchange(13047),
                    almErpsinprotection(13048),
                    almComexteccfull(13049),
                    almWavedataMis(13051),
                    almVoadataMis(13053),
                    almOdu0PmTim(13055),
                    almOdu0PmDeg(13056),
                    almOdu0PmBdi(13057),
                    almOdu0PmLck(13058),
                    almOdu0PmOci(13059),
                    almOdu0PmAis(13060),
                    almOdu0Loflom(13061),
                    almOdu0PmSsf(13062),
                    almOpu1Msim(13063),
                    almMultiRplOwner(13064),
                    almFwdPktLoss(13065),
                    almOpu0Plm(13066),
                    almodu0pmexc(13068),
                    almSvcTypeExceedLic(13070),
                    almSvcCapExceedLic(13071),  
                    almShelfAreaPowerOver(13079),
                    almOpu0Csf(13082),
                    almOpu1Csf(13083),
                    almMplsTunnelOamFail(13087),
                    almDcnsizeOver(13110),
                    almMemOver(13112),
                    almMcspPathLocv(13113),
                    almMclagCfgMismatch(13114),
                    almLptCfgClosePort(13115),
                    almntpsyncfail(13125),
                    almOdukspStaIndi(13136),
                    almOlpStaIndi(13137),
                    almOwspStaIndi(13138),
                    almClientPortStaIndi(13139),
                    almIntraOtuStaIndi(13140),
                    almMsSncpStaIndi(13141),
                    almOduSncpStaIndi(13142),
                    almSwSncpStaIndi(13143),
                    almlcsfilenotexist(13144), 
                    almlcsexpired(13145),
                    almlcsdaysofgrace(13146),
                    almSecradiusfail(13169),
                    almFeaturewithoutlicense(13170),
                    almPowerModuleOffline(13184),     
                    almOscDeg(13185),
                    almOscBdi(13186),
                    almPtptimestampabn(13188),
                    almSwdlbdexclude(13190),
                    almPtpsourceswitch(13194),
                    almClklockfail(13195),
                    almTimelockfail(13196),
                    almOtu4Ssf(13201),
                    almOtu4Ais(13202),
                    almOtu4Lof(13203),
                    almOtu4Lom(13204),
                    almOtu4Tim(13205),
                    almOtu4Deg(13206),
                    almOtu4Bdi(13207),
                    almOdu4PmSsf(13208),
                    almOdu4Tcm1Ssf(13209),
                    almOdu4Tcm2Ssf(13210),
                    almOdu4Tcm3Ssf(13211),
                    almOdu4Tcm4Ssf(13212),
                    almOdu4Tcm5Ssf(13213),
                    almOdu4Tcm6Ssf(13214),
                    almOdu4PmAis(13215),
                    almOdu4Tcm1Ais(13216),
                    almOdu4Tcm2Ais(13217),
                    almOdu4Tcm3Ais(13218),
                    almOdu4Tcm4Ais(13219),
                    almOdu4Tcm5Ais(13220),
                    almOdu4Tcm6Ais(13221),
                    almOdu4PmOci(13222),
                    almOdu4Tcm1Oci(13223),
                    almOdu4Tcm2Oci(13224),
                    almOdu4Tcm3Oci(13225),
                    almOdu4Tcm4Oci(13226),
                    almOdu4Tcm5Oci(13227),
                    almOdu4Tcm6Oci(13228),
                    almOdu4PmLck(13229),
                    almOdu4Tcm1Lck(13230),
                    almOdu4Tcm2Lck(13231),
                    almOdu4Tcm3Lck(13232),
                    almOdu4Tcm4Lck(13233),
                    almOdu4Tcm5Lck(13234),
                    almOdu4Tcm6Lck(13235),
                    almOdu4Tcm1Ltc(13236),
                    almOdu4Tcm2Ltc(13237),
                    almOdu4Tcm3Ltc(13238),
                    almOdu4Tcm4Ltc(13239),
                    almOdu4Tcm5Ltc(13240),
                    almOdu4Tcm6Ltc(13241),
                    almOdu4PmTim(13242),
                    almOdu4Tcm1Tim(13243),
                    almOdu4Tcm2Tim(13244),
                    almOdu4Tcm3Tim(13245),
                    almOdu4Tcm4Tim(13246),
                    almOdu4Tcm5Tim(13247),
                    almOdu4Tcm6Tim(13248),
                    almOdu4PmDeg(13249),
                    almOdu4Tcm1Deg(13250),
                    almOdu4Tcm2Deg(13251),
                    almOdu4Tcm3Deg(13252),
                    almOdu4Tcm4Deg(13253),
                    almOdu4Tcm5Deg(13254),
                    almOdu4Tcm6Deg(13255),
                    almOdu4PMExc(13256),
                    almOdu4Tcm1Exc(13257),
                    almOdu4Tcm2Exc(13258),
                    almOdu4Tcm3Exc(13259),
                    almOdu4Tcm4Exc(13260),
                    almOdu4Tcm5Exc(13261),
                    almOdu4Tcm6Exc(13262),
                    almOdu4PmBdi(13263),
                    almOdu4Tcm1Bdi(13264),
                    almOdu4Tcm2Bdi(13265),
                    almOdu4Tcm3Bdi(13266),
                    almOdu4Tcm4Bdi(13267),
                    almOdu4Tcm5Bdi(13268),
                    almOdu4Tcm6Bdi(13269),
                    almOpu4Plm(13270),
                    almOpu4Msim(13271),
                    almSubrackCommPS(13273),
                    almotu4exc(13274),
                    almOdu4Loflom(13275),
                    almEthserviceconfigfail(13276),
                    almOpu2Csf(13309),
                    almOpuflexPlm(13310),
                    almOduflexPmSsf(13311),
                    almOduflexPmTim(13312),
                    almOduflexPmDeg(13313),
                    almOduflexPmBdi(13314),
                    almOduflexPmLck(13315),
                    almOduflexPmOci(13316),
                    almOduflexLoa(14379),
                    almOduflexPmAis(13317),
                    almOduflexLoflom(13318),
                    almOduflexPmExc(13319),
                    almOdu0Tcm1Tim(13320),
                    almOdu0Tcm1Bdi(13321),
                    almOdu0Tcm1Ais(13322),
                    almOdu0Tcm1Lck(13323),
                    almOdu0Tcm1Oci(13324),
                    almOdu0Tcm1Ltc(13325),
                    almOdu0Tcm1Deg(13326),
                    almOdu0Tcm1Exc(13327),
                    almOdu0Tcm1Ssf(13328),
                    almOdu0Tcm2Tim(13329),
                    almOdu0Tcm2Bdi(13330),
                    almOdu0Tcm2Ais(13331),
                    almOdu0Tcm2Lck(13332),
                    almOdu0Tcm2Oci(13333),
                    almOdu0Tcm2Ltc(13334),
                    almOdu0Tcm2Deg(13335),
                    almOdu0Tcm2Exc(13336),
                    almOdu0Tcm2Ssf(13337),
                    almOdu0Tcm3Tim(13338),
                    almOdu0Tcm3Bdi(13339),
                    almOdu0Tcm3Ais(13340),
                    almOdu0Tcm3Lck(13341),
                    almOdu0Tcm3Oci(13342),
                    almOdu0Tcm3Ltc(13343),
                    almOdu0Tcm3Deg(13344),
                    almOdu0Tcm3Exc(13345),
                    almOdu0Tcm3Ssf(13346),
                    almOdu0Tcm4Tim(13347),
                    almOdu0Tcm4Bdi(13348),
                    almOdu0Tcm4Ais(13349),
                    almOdu0Tcm4Lck(13350),
                    almOdu0Tcm4Oci(13351),
                    almOdu0Tcm4Ltc(13352),
                    almOdu0Tcm4Deg(13353),
                    almOdu0Tcm4Exc(13354),
                    almOdu0Tcm4Ssf(13355),
                    almOdu0Tcm5Tim(13356),
                    almOdu0Tcm5Bdi(13357),
                    almOdu0Tcm5Ais(13358),
                    almOdu0Tcm5Lck(13359),
                    almOdu0Tcm5Oci(13360),
                    almOdu0Tcm5Ltc(13361),
                    almOdu0Tcm5Deg(13362),
                    almOdu0Tcm5Exc(13363),
                    almOdu0Tcm5Ssf(13364),
                    almOdu0Tcm6Tim(13365),
                    almOdu0Tcm6Bdi(13366),
                    almOdu0Tcm6Ais(13367),
                    almOdu0Tcm6Lck(13368),
                    almOdu0Tcm6Oci(13369),
                    almOdu0Tcm6Ltc(13370),
                    almOdu0Tcm6Deg(13371),
                    almOdu0Tcm6Exc(13372),
                    almOdu0Tcm6Ssf(13373),
                    almRxWavelenMismatch(13380),
                    almDbmsabnormal(13381),
                    almMplsPwLck(13389),
                    almMplsPwAis(13390),
                    almMplsTunnelLock(13391),
                    almMplsPwLock(13392),
                    almMPlsPwCsf(13402),
                    almAlsActive(13412),
                    almSrvShutDownLd(13416),
                    almPortExcTraffic(13417),
                    almDropratioOver(13418),
                    almBdLedTest(13419),
                    almRxPowerAbnormal(13423),
                    almOpuflexCsf(13434),
                    almEthHiBer(13622),
                    almEthBip8Sd(13623),
                    
                    almOpu3Csf(13435),
                    almOpu4Csf(13436),
                    almModuleRateMismatch(13443),
                    almEthCfmAis(13478),
                    almBwUtilizationOver(13486),
                    almFopNr(13487), 
                    almFopPr(13488),                
                    almDbmsDelete(13502),
                    almLaserCheckErr(13506),
                    almTunnelApsOutAge(13507),
                    almPwApsDegraded(13508),
                    almPwApsOutAge(13509),
                    almSslcertnoenc(13514),
                    almCpwOduTelOdurMis(13528),
                    almCpwOtuTelOvpnMm(13529),
                    almCpwOduTelOvpnMm(13530),
                    almCpwOtuTelMm(13531),
                    almCpwOtuTelOudrMis(13532),
                    almNoBdPower(13542),
                    almElanSmacFlapping(13552),
                    almPatchBdExclude(13557),
                    almPatchBdMatchFail(13558),
                    almRLol(13640),
                    almSwdlBdMatchFail(13673),
                    almCfpLos(13690),
                    almWorkBackLatenDiff(13725),
                    almSwdlBDNotMatch(13735),
                    almCpri_Los(13756),
                    almCpri_Lof(13757),
                    almUpdn_Laten_Diff(13758),
                    almOdux5PmSsf(13793),
                    almOdux5PmTim(13794),
                    almOdux5PmDeg(13795),
                    almOdux5PmBdi(13796),
                    almOdux5PmLck(13797),
                    almOdux5PmOci(13798),
                    almOdux5PmAis(13799),
                    almOdux5Loflom(13800),
                    almOtux5Ssf(13801),
                    almOpux5plm(13802),
                    almOtux5Ais(13803),
                    almOtux5Lof(13804),
                    almOtux5Lom(13805),
                    almOtux5Tim(13806),
                    almOtux5Deg(13807),
                    almOtux5Bdi(13808),
                    almServSelfadaptIndi(13910),
                    almXcpDegrade(13964),   
                    almSwdlBdWeakmatch(13714),
                    almFcAis(13967),
                    almPatchInitFail(14042),
                    almPatchMatchNoStart(14088),
                    almNebdXcDif(259),
                    almNebdOxcDif(14385),
                    almCpldNeedUpdate(14089),
                    almCpldUpdating(14090),
                    almPortModuleOffline(63629),
                    almHardBad(236),
                    almLanLoc(12926),
                    almSyncCLos(111),
                    almSplitInstFail(14081),
                    almRlminorhi(16130),
                    almRlminorlow(16131),
                    almLaserShut(63509),
                    almHardNonsupport(63537),
                    almOduVcatLoa(63538),
                    almBeffecSd(63540),
                    almRfa(63556),
                    almFcsErr(63575),
                    almB3ExCvc3(63577),
                    almB3ExCvc4(63578),
                    almB3SdVc3(63579),
                    almB3SdVc4(63580),
                    almVcatLomVc12(63584),
                    almVcatLomVc3(63585),
                    almVcatLomVc4(63586),
                    almVcatSqmVc12(63587),
                    almVcatSqmvc3(63588),
                    almVcatSqmVc4(63589),
                    almLpRdiVc3(63591),
                    almLpReiVc3(63593),
                    almLpSlmVc3(63595),
                    almLpTimVc3(63597),
                    almLpUneqVc12(63598),
                    almLpUneQvc3(63599),
                    almTuAisVc12(63600),
                    almTuAisVc3(63601),
                    almTuLopVc12(63602),
                    almTuLopVc3(63603),
                    almRemSf(63604),
                    almRemSd(63605),
                
                    almThundFail(63635),
                    almGfpDlfd(63638),
                    almGfpDcsf(63639),
                    almLaserModErrEx(63644),
                    almSlaveWorkingEx(63645),
                    almLcasPlct(63647),
                    almLcasTlct(63648),
                    almLcasPlcr(63649),
                    almLcasTlcr(63650),
                    almLcasFopt(63651),
                    almLcasFopr(63652),
                    almGfpUpm(63657),
                    almOduflexTcm4Ssf(13565),
                    almOduflexTcm4Exc(13566),
                    almOduflexTcm4Ltc(13567),
                    almOduflexTcm4Deg(13568),
                    almOduflexTcm4Lck(13569),
                    almOduflexTcm4Oci(13570),
                    almOduflexTcm4Bdi(13571),
                    almOduflexTcm4Ais(13572),
                    almOduflexTcm4Tim(13573),
                    almOduflexTcm5Exc(13574),
                    almOduflexTcm5Ssf(13575),
                    almOduflexTcm5Lck(13576),
                    almOduflexTcm5Oci(13577),
                    almOduflexTcm5Ltc(13578),
                    almOduflexTcm5Deg(13579),
                    almOduflexTcm5Tim(13580),
                    almOduflexTcm5Bdi(13581),
                    almOduflexTcm5Ais(13582),
                    almOduflexTcm6Tim(13583),
                    almOduflexTcm6Lck(13584),
                    almOduflexTcm6Oci(13585),
                    almOduflexTcm6Bdi(13586),
                    almOduflexTcm6Ais(13587),
                    almOduflexTcm6Exc(13588),
                    almOduflexTcm6Ssf(13589),
                    almOduflexTcm6Ltc(13590),
                    almOduflexTcm6Deg(13591),
                    almOduflexTcm3Tim(13592),
                    almOduflexTcm3Bdi(13593),
                    almOduflexTcm3Ais(13594),
                    almOduflexTcm3Deg(13595),
                    almOduflexTcm3Ltc(13596),
                    almOduflexTcm3Oci(13597),
                    almOduflexTcm3Lck(13598),
                    almOduflexTcm3Ssf(13599),
                    almOduflexTcm3Exc(13600),
                    almOduflexTcm2Tim(13601),
                    almOduflexTcm2Bdi(13602),
                    almOduflexTcm2Ais(13603),
                    almOduflexTcm2Lck(13604),
                    almOduflexTcm2Oci(13605),
                    almOduflexTcm2Ltc(13606),
                    almOduflexTcm2Deg(13607),
                    almOduflexTcm2Exc(13608),
                    almOduflexTcm2Ssf(13609),
                    almOduflexTcm1Tim(13610),
                    almOduflexTcm1Bdi(13611),
                    almOduflexTcm1Ais(13612),
                    almOduflexTcm1Lck(13613),
                    almOduflexTcm1Oci(13614),
                    almOduflexTcm1Ltc(13615),
                    almOduflexTcm1Deg(13616),
                    almOduflexTcm1Exc(13617),
                    almOduflexTcm1Ssf(13618),
                    almFopPm(13621),
                    almBdBpxcMismatch(13657),
                    almOpu0Msim(13671),
                    almOpuflexMsim(13672),
                    almOtucnBdi(13674),
                    almOtucnDeg(13675),
                    almOtucnTim(13676),
                    almOtucnLom(13677),
                    almOtucnLof(13678),
                    almOtucnSsf(13679),
                    almOducnPmAis(13680),
                    almOducnPmSsf(13681),
                    almOducnPmBdi(13682),
                    almOducnPmDeg(13683),
                    almOducnPmTim(13684),
                    almOpucnPlm(13685),
                    almOpucnMsim(13686),
                    almEncAuthFail(13687), 
                    almCfgDataSaveFial(13726), 
                    almCfgDataCheckFial(13727),
                    almPtpAnnounceLos(13693),
                    almPtpSyncLos(13694),
                    almPtpDelayRespLos(13695),
                    almPtpPdelayRespLos(13696),
                    almPwdEncriptRisk(13744),
                    almOchmLosP(13706),
                    almOchmOci(13707),
                    almOchmSsf(13708),
                    almOchmSsfP(13709),
                    almOchmSsfO(13710),
                    almOchmFdi(13711),
                    almOchmFdiP(13712),
                    almOchmFdiO(13713),
                    almProPktFlooding(13746),
                    almArpSpoof(13762),
                    almSubrackForceMaster(13785),
                    almLocEthNotDisabled(13877),
                    almSubrackPortCfgErr(13880),
                    almObsai_Los(13893),
                    almDcnLinkOver(13111),
                    almPatchErr(13876),
                    almSslCertDamaged(13759),
                    almSubRackOffline(13074),
                    almSslCertToExpire(13779),
                    almOmsLossAccumAbn(13631),
                    almSpanLossLowerGain(13650),
                    almSpanLossUpperGain(13649),
                    almRxcfgWavedataMis(13892),
                    almOducnPmLck(13923),
                    almChanPwrHigh(13931),   
                    almInnerCommunmisCon(13543),
                    almOaOutPwrAbn(13632),
                    almpwrUnbalanced(13633),
                    almOmsLossMonFail(13636),
                    almOmsPwrAdjFail(13630),
                    almOdcSurgeProtectionFail(13155),
                    almOdcSmokeOver(13156),
                    almOdcWaterAlm(13157),
                    almOdcLoadPwrdown(13158),
                    almOdcBatteryPwrdown(13159),
                    almOdcBatteryCurrentAbn(13160),
                    almOdcPowerFail(13163),
                    almOdcHumiAbn(13164),
                    almOdcMdlAbn(13165),
                    almOdcTempAbn(13166),
                    almBat1tempSensorFail(13289),
                    almEnvhumSensorFail(13290),
                    almEnvtemp1SensorFail(13291),
                    almEnvtemp2SensorFail(13292),
                    almBat2TempSensorFail(13293),
                    almDoorOpen(13890),
                    almOdcDoorOpen(13154),
                    almBatteryRemoved(13894),
                    almOdcTcuAbn(13755),
                    almOdcBatteDischarge(13754),
                    almUsbFileUnsec(13745),
                    almFlashCapacityDif(13928),
                    almLaserTypeMismatch(13951),
                    almOduSncpWeak(13953),
                    almUsbProcessFail(13484),
                    almLaserParaErr(13978),
                    almKmcKeySyncFail(13960),
                    almMpnApsIndi(13961),
                    almMpnOppositeCfgErr(13962),
                    almMpnApsStop(13963),
                    almInsuffcntMemSpac(13983),
                    almInsuffcntFlshSpace(13984),
                    almStorageFail(13985),
                    almlaneoutpwrhigh(13993),
                    almlaneoutpwrlow(13994),
                    almlaneinpwrhigh(13995),
                    almlaneinpwrlow(13996),
                    almlanelos(13997),
                    almSdcardOffline(14020),
                    almSdcardFailed(14021),
                    almSubnetRTConflict(13545),
                    almOPU4LOOMFI(13716),
                    almEncEmkInit(13981),
                    almPatchOPTimeout(14041),
                    almSoftError(14181),
                    almMacFcsSd(12795),
                    almPortWllcfgRepeated(14028),
                    almBdFileNotActive(14029),
                    almClntSrvExceedLcs(14096),
                    almMacFcsNumSd(14097),
                    almMacFcsNumExc(14098),
                    almLsrModFail(14179),
                    almLsrSubmodOffline(14178),
                    almFiberMisconnect(14144),
                    almServAutoCrtFail(14435),
                    almCrcExc(224),
                    almPortswitchFail(295),
                    almModComFail(432),
                    almAlmDataRlos(441),
                    almAlmDataTlos(442),
                    almEthoamSelfLoop(12767),
                    almEthNoFlow(12786),
                    almPortmodeMismatch(12788),
                    almFdbsizealmElan(12807),
                    almCpcCcDown(13042),
                    almGaindataMis(13054),
                    almLagBwmm(13108),
                    almSpanLossHigh(13132),
                    almSpanLossLow(13280),
                    almMacExtExc(13444),
                    almSpanLossExceedEol(13629),
                    almOsnrLossUnbalanced(13634),
                    almBrdcastratioOver(13933),
                    almErpsBlock(14035),
                    almSpectraAnalyseFail(14036),
                    almErpsCfmFail(14085),
                    almWorkparaMis(14087),
                    almInterBdwidthMism(14145),
                    almInterBdwidthInsuf(14146),
                    almDcncfgNotCommit(14147),
                    almSrvLoopLd(14149),
                    almPingLos(14150),
                    almPingArpMismatch(14151),
                    almErpsNotComplete(14164),
                    almApsStatusIndi(14174),
                    almSrvTypeMismatch(14180),
                    almXcSrvErr(14183),
                    almSwdlIncpkgFail(14188),
                    almWaveBlocked(14191),
                    almTsSyncFail(14198),
                    almClusterFiberlenDif(14206),
                    almDpsStaIndi(14209),
                    almOducnTcm1Ssf(14212),
                    almOducnTcm2Ssf(14213),
                    almOducnTcm3Ssf(14214),
                    almOducnTcm4Ssf(14215),
                    almOducnTcm5Ssf(14216),
                    almOducnTcm6Ssf(14217),
                    almOducnTcm1Ais(14218),
                    almOducnTcm2Ais(14219),
                    almOducnTcm3Ais(14220),
                    almOducnTcm4Ais(14221),
                    almOducnTcm5Ais(14222),
                    almOducnTcm6Ais(14223),
                    almOducnTcm1Lck(14224),
                    almOducnTcm2Lck(14225),
                    almOducnTcm3Lck(14226),
                    almOducnTcm4Lck(14227),
                    almOducnTcm5Lck(14228),
                    almOducnTcm6Lck(14229),
                    almOducnTcm1Ltc(14230),
                    almOducnTcm2Ltc(14231),
                    almOducnTcm3Ltc(14232),
                    almOducnTcm4Ltc(14233),
                    almOducnTcm5Ltc(14234),
                    almOducnTcm6Ltc(14235),
                    almOducnTcm1Tim(14236),
                    almOducnTcm2Tim(14237),
                    almOducnTcm3Tim(14238),
                    almOducnTcm4Tim(14239),
                    almOducnTcm5Tim(14240),
                    almOducnTcm6Tim(14241),
                    almOducnTcm1Deg(14242),
                    almOducnTcm2Deg(14243),
                    almOducnTcm3Deg(14244),
                    almOducnTcm4Deg(14245),
                    almOducnTcm5Deg(14246),
                    almOducnTcm6Deg(14247),
                    almOducnTcm1Bdi(14248),
                    almOducnTcm2Bdi(14249),
                    almOducnTcm3Bdi(14250),
                    almOducnTcm4Bdi(14251),
                    almOducnTcm5Bdi(14252),
                    almOducnTcm6Bdi(14253),
                    almDbUnsave(14255),
                    almBpOduLoflom(14271),
                    almModuleAdjustFail(12585),
                    
                    almModulefileUpdateFail(12606),
                    almIpaFault(13635),
                    almIpaAbnormal(14152),
                    almModuleTempOver(271),
                    almBdDcnLack(14288),
                    
                    almOscClkMismatch(13986),
                    almSysbusErr(14306),
                    almBdTempFluct(14334),
                    almFanSpeedFluct(14335),
                    almDcnSubnetMixedUp(14373),
                    almStdPtpOffsetOver(13724),
                    almServOverFwdCapa(13891),
                    
                    almPwDroppktExc(12853),
                    almGspTnnlDown(12994),
                    almGspRsvpNbDown(12997),
                    almGspRsvpNbAuthErr(12998),
                    almLdpPeerDown(13283),
                    almIsisadjacencychange(13560),
                    almBgpbacktransition(13561),
                    almL3vTrapThreExceed(13562),
                    almL3vTrapVrfDown(13563),
                    almRtTblLack(13619),
                    almOspfnbrstatechange(13663),
                    almMplsldpsessiondown(13700),
                    almMplslspTblLack(13701),
                    almIsisLspSeqExceed(14002),
                    almIsisSeqReachMax(14003),

                    almClusterShelfIsolate(14395),
                    almTelemetryCommFail(14388),
                    almSerialLogin(14322),
                    almSecuLogfailed(14323),
                    almWRFail(99),
                    almDcnChannelBiterror(14102),
                    almAlienWavelengthAccess(14392),
                    almTbFail(14412),
                    almOxcLicenseOwe(14429),
                    almOscPlm(14430),
                    almFlexeRpf(14445),
                    almFlexeLof(14446),
                    almFlexeLom(14447),
                    almFlexeGidm(14448),
                    almFlexeFmm(14449),
                    almFlexeLol(14450),
                    almModuleNotAuthenticated(14451),
                    almEnhanceSwitchFar(14457),
                    almFibertypeNotConfig(14210),
                    almCpuBusy(13090),
                    almIpaAuxiliaryMis(14464),
                    almVersionFail(14384),
                    almSdiCrcExc(14092),
                    almOduSncpNotHitless(14093),
                    almPwrCurrentNoEqual(14142),
                    almBdInMaintenance(14143),
                    almShelfWrongConnect(41987),
                    almBdRateMismatch(13925),
                    almTpmSelfTestFail(13926),
                    almTpmStmMismatch(13927),
                    almAmbientTempOver(13670),
                    almPtpClkclassFailed(13697),

                }

        AlmDataNtfcnCdeType ::= TEXTUAL-CONVENTION
            STATUS current
            DESCRIPTION 
                "The notification code of alarm."
            SYNTAX INTEGER
                {
                    cr(1),
                    mj(2),
                    mn(3),
                    ig(4),
                    nr(5)
                }
            
        AlmDataSrvEffType ::= TEXTUAL-CONVENTION
            STATUS current
            DESCRIPTION 
                "The effect on service caused by alarm."
            SYNTAX INTEGER
                {
                    nsa(1),
                    sa(2)
                }
            
        DirectionType ::= TEXTUAL-CONVENTION
            STATUS current
            DESCRIPTION 
                "Direction parameters,sorted by ID."
            SYNTAX INTEGER
                {
                    all(0),
                    rcv(1),
                    trmt(2)
                }
            
        LocationType ::= TEXTUAL-CONVENTION
            STATUS current
            DESCRIPTION 
                "Location parameters,sorted by ID."
            SYNTAX INTEGER
                {
                    all(0),
                    nend(1),
                    fend(2)
                }
            
        MOD2Type ::= TEXTUAL-CONVENTION
            STATUS current
            DESCRIPTION 
                "MOD2 parameters,sorted by ID."
            SYNTAX INTEGER
                {
                    mod2All(0),
                    mod2Ds1(1),
                    mod2E100(2),
                    mod2E1000(3),
                    mod2Ec1(4),
                    mod2Oc3(5),
                    mod2Oc12(6),
                    mod2Oc48(7),
                    mod2Oc192(8),
                    mod2Sts1(9),
                    mod2Sts3c(10),
                    mod2Sts6c(11),
                    mod2Sts9c(12),
                    mod2Sts12c(13),
                    mod2Sts15c(14),
                    mod2Sts24c(15),
                    mod2Sts48c(16),
                    mod2Sts192c(17),
                    mod2T1(18),
                    mod2T3(19),
                    mod2M13(20),
                    mod2Vt1(21),
                    mod2Vt2(22),
                    mod2Env(23),
                    mod2Sync(24),
                    mod2Bits(25),
                    mod2Eqpt(26),
                    mod2Ds3(27),
                    mod2Stm1(28),
                    mod2Stm4(29),
                    mod2Stm16(30),
                    mod2Stm64(31),
                    mod2Vc3(32),
                    mod2Vc4(33),
                    mod2Vc12(34),
                    mod2Vc16c(35),
                    mod2Vc4c(36),
                    mod2E1(37),
                    mod2E3(38),
                    mod2E1t1(39),
                    mod2E3t3(40),
                    mod2Hardware(41),
                    mod2Syncall(42),
                    mod2Syncne(43),
                    mod2Syncfac(44),
                    mod2Cont(45),
                    mod2Ochl(46),
                    mod2Pg(47),
                    mod2Feth(48),
                    mod2Geth(49),
                    mod2Fe(50),
                    mod2Ge(51),
                    mod2Vctrunk(52),
                    mod2Och(53),
                    mod2Wdm(54),
                    mod2Client(55),
                    mod2Eth(56),
                    mod2Osc(57),
                    mod2Mca(58),
                    mod2Variable(59),
                    mod2Xgeth(60),
                    mod2Fc(61),
                    mod2Dcc(62),
                    mod2Lan(63),
                    mod2EQPT(64),
                    mod2Otdr(65),
                    mod2Clk(66),
                    mod2Flow(67),
                    mod2Otu2(68),
                    mod2Butt(69)
                }
            
        PerformanceEventType ::= TEXTUAL-CONVENTION
            STATUS current
            DESCRIPTION 
                "Performance ID."
            SYNTAX INTEGER
                {
                    rsBackgroundBlockError(1),
                    rsErroredSecond(2),
                    rsSeverelyErroredSecond(3),
                    rsOutofframe(4),
                    rsOutOfFrameSecond(5),
                    rsUnavailableSecond(6),
                    rsConsecutiveSeverelyErroredSecond(7),
                    e1LcvSdh(12),
                    e1LesSdh(13),
                    e1LsesSdh(14),  
                    e1LlossSdh(15),
                    msBackgroundBlockError(16),
                    msErroredSecond(17),
                    msSeverelyErroredSecond(18),
                    msFarEndBackgroundBlockError(19),
                    msFarEndErroredSecond(20),
                    msFarEndSeverelyErroredSecond(21),
                    msUnavailableSecond(22),
                    msConsecutiveSeverelyErroredSecond(23),
                    msFarEndConsecutiveSeverelyErroredSecond(24),
                    msFarEndUnavailableSecond(33),
                    administrativeUnitPointerJustificationCountHIGH(42),
                    administrativeUnitPointerJustificationCountLOW(43),
                    administrativeUnitPointerJustificationCountNEW(44),
                    tandemConnectionBackgroundBlockError(45),
                    tandemConnectionFarEndBackgroundBlockError(46),
                    tandemConnectionOutgoingBackgroundBlockError(47),
                    higherorderPathBackgroundBlockError(48),
                    higherorderPathErroredSecond(49),
                    higherorderPathSeverelyErroredSecond(50),
                    higherorderPathFarendBackgroundBlockError(51),
                    higherorderPathFarendErroredSecond(52),
                    higherorderPathFarendSeverelyErroredSecond(53),
                    higherorderPathUnavaliableSeconds(54),
                    higherorderPathConsecutiveSeverelyErroredSeconds(55),
                    higherorderPathFarendConsecutiveSeverelyErroredSeconds(56),
                    eDFAFiberBoxTemperatureTheMaximumValue(65),
                    eDFAFiberBoxTemperatureTheMinimumValue(66),
                    eDFAFiberBoxTemperatureTheCurrentValue(67),
                    higherorderPathFarendUnavaliableSeconds(76),
                    vc3BackgroundBlockError(80),
                    vc3ErroredSecond(81),
                    vc3ServerlyErroredSecond(82),
                    vc3FARENDBackgroundBlockError(83),
                    vc3FARENDErroredSecond(84),
                    vc3farend(85),
                    vc3UnavailableSecond(86),
                    vc3ConsecutivServerlyEeeoredSecond(87),
                    vc3farendConsecutivServerlyEeeoredSecond(88),
                    vc3FarEndUnavailableSecond(89),
                    maximumvalueoflasertransmittingbiascurrent(96),
                    minimumvalueoflasertransmittingbiascurrent(97),
                    currentvalueoflasertransmittingbiascurrent(98),
                    maximumvalueoflasercoolingCurrent(99),
                    minimumvalueoflasercoolingCurrent(100),
                    currentvalueoflasercoolingcurrent(101),
                    maximumvalueoflasertransmittingpower(102),
                    minimumvalueoflasertransmittingpower(103),
                    currentvalueoflasertransmittingpower(104),
                    maximumvalueoflaserreceivingpower(105),
                    minimumvalueoflaserreceivingpower(106),
                    currentvalueoflaserreceivingpower(107),
                    maximumvalueoflasertemperature(108),
                    minimumvalueoflasertemperature(109),
                    currentvalueoflasertemperature(110),
                    workingCurrentValueMaximum(112),
                    workingCurrentValueMinimum(113),
                    workingCurrentValueValueCurrent(114),
                    coolingCurrentValueMaximum(115),
                    coolingCurrentValueMinimum(116),
                    coolingCurrentValueCurrent(117),
                    backCurrentValueMaximum(118),
                    backCurrentValueMinimum(119),
                    backCurrentValueCurrent(120),
                    edfaTransmissionPowerLevelMaximum(121),
                    edfaTransmissionPowerLevelMinimum(122),
                    edfaTransmissionPowerLevelCurrent(123),
                    edrplmax(124),
                    edrplmin(125),
                    edrplcur(126),
                    edwcsmax(127),
                    edwcsmin(128),
                    edwcscur(129),
                    edfaTemperatureMaximum(130),
                    edfaTemperatureMinimum(131),
                    edfaTemperatureCurrent(132),
                    fecCorrected0BitCount(133),
                    fecCorrected1BitCount(134),
                    fecCorrectedByteCount(135),
                    fecUnCorrectedBlockCount(136),
                    loworderPathFar-endUnavailablesecond(142),
                    loworderPathBackgroundBlockError(144),
                    loworderPatherroredseconds(145),
                    loworderPathseverelyerroredseconds(146),
                    loworderPathFar-endBackgroundBlockError(147),
                    loworderPathFar-enderroredseconds(148),
                    loworderPathFar-endseverelyerroredseconds(149),
                    loworderPathUnavailablesecond(150),
                    loworderPathConsecutiveseverelyerroredseconds(151),
                    loworderPathFar-endConsecutiveseverelyerroredseconds(152),
                    t1LcvSdh(164),
                    t1LesSdh(165),
                    t1LsesSdh(166),
                    t1LlossSdh(167),
                    tupJcHigh(170),
                    tupJcLow(171),
                    tupJcNew(172),
                    xcstmpmax(188),
                    xcstmpmin(189),
                    xcstmpcur(190),
                    
                    ambtempmax(15623),
                    ambtempmin(15624),
                    ambtempcur(15625),
                    
                    xcstmpcur(191),
                    lsoopmax(198),
                    lsoopmin(199),
                    lsoopcur(200),
                    lsiopmax(201),
                    lsiopmin(202),
                    lsiopcur(203),
                    sumiopmax(210),
                    sumiopmin(211),
                    sumiopcur(212),
                    sumoopmax(213),
                    sumoopmin(214),
                    sumoopcur(215),
                    envtmpmax(222),
                    envtmpmin(223),
                    envtmpcur(224),
                    lsclcmax(225),
                    lsclcmin(226),
                    lsclccur(227),
                    lstmpmax(204),
                    lstmpmin(205),
                    lstmpcur(206),
                    lsbiasmax(207),
                    lsbiasmin(208),
                    lsbiascur(209),
                    ictmpmax(249),
                    ictmpmin(250),
                    ictmpcur(251),
                    pclswlmax(228),
                    pclswlmin(229),
                    pclswlcur(230),
                    pclswlomax(231),
                    pclswlomax(232),
                    pclswlocur(233),
                    pclsopmax(234),
                    pclsopmin(235),
                    pclsopcur(236),
                    pclssnmax(237),
                    pclssnmin(238),
                    pclssncur(239),
                    crc4bbe(240),
                    crc4es(241),
                    crc4ses(242),
                    crc4febbe(243),
                    crc4fees(244),
                    crc4feses(245),
                    crc4uas(246),
                    crc4cses(247),
                    crc4fecses(248),
                    
                    fecBefCorEr(252),
                    fecAftCorEr(253),
                    crc4feuas(254),
                    opticaltransportsectionerror(4170),
                    opticaldatasectionerror(4171),
                    maxModuleCoolCurrent(4172),
                    minModuleCoolCurrent(4173),
                    currentModuleCoolCurrent(4174),
                    odu4tcm1iae(4395),
                    odu4tcm2iae(4396),
                    odu4tcm3iae(4397),
                    odu4tcm4iae(4398),
                    odu4tcm5iae(4399),
                    odu4tcm6iae(4400),
                    odu4tcm1biae(4401),
                    odu4tcm2biae(4402),
                    odu4tcm3biae(4403),
                    odu4tcm4biae(4404),
                    odu4tcm5biae(4405),
                    odu4tcm6biae(4406),
                    odu4tcm1bip8(4407),
                    odu4tcm2bip8(4408),
                    odu4tcm3bip8(4409),
                    odu4tcm4bip8(4410),
                    odu4tcm5bip8(4411),
                    odu4tcm6bip8(4412),
                    odu4tcm1bei(4413),
                    odu4tcm2bei(4414),
                    odu4tcm3bei(4415),
                    odu4tcm4bei(4416),
                    odu4tcm5bei(4417),
                    odu4tcm6bei(4418),
                    odu4pmbip8(4419),
                    odu4pmbei(4420),
                    otu4bip8(4421),
                    otu4bei(4422),
                    otu4iae(4423),
                    otu4biae(4424),
                    opticalOutputPowerReturnLossMaximum(8612),
                    opticalOutputPowerReturnLossMinimum(8613),
                    opticalOutputPowerReturnLossCurrent(8614),
                    otu1Iaes(14336),
                    otu1Biaes(14337),
                    otu1Bbe(14338),
                    otu1Es(14339),
                    otu1Ses(14340),
                    otu1Uas(14341),
                    otu1Febbe(14344),
                    otu1Fees(14345),
                    otu1Feses(14346),
                    otu1Feuas(14347),
                    otu1Fesesr(14348),
                    otu1Febber(14349),
                    otu5giaes(14350),
                    otu5gbiaes(14351),
                    otu5gbbe(14352),
                    otu5ges(14353),
                    otu5gses(14354),
                    otu5guas(14355),
                    otu5gsesr(14356),
                    otu5gbber(14357),
                    otu5gfebbe(14358),
                    otu5gfees(14359),
                    otu5gfeses(14360),
                    otu5gfeuas(14361),
                    otu5gfesesr(14362),
                    otu5gfebber(14363),
                    otu2Iaes(14364),
                    otu2Biaes(14365),
                    otu2Bbe(14366),
                    otu2Es(14367),
                    otu2Ses(14368),
                    otu2Uas(14369),
                    otu2Sesr(14370),
                    otu2Bber(14371),
                    otu2Febbe(14372),
                    otu2Fees(14373),
                    otu2Feses(14374),
                    otu2Feuas(14375),
                    otu2Fesesr(14376),
                    otu2Febber(14377),
                    otu3Iaes(14378),
                    odu1PmFebbe(14398),
                    odu1PmFees(14399),
                    odu1PmFeses(14400),
                    odu1PmFeuas(14401),
                    odu1PmFesesr(14402),
                    odu1PmFebber(14403),
                    odu5gpmbbe(14404),
                    odu5gpmes(14405),
                    odu5gpmses(14406),
                    odu5gpmuas(14407),
                    odu5gpmsesr(14408),
                    odu5gpmbber(14409),
                    odu5gpmfebbe(14410),
                    odu5gpmfees(14411),
                    odu5gpmfeses(14412),
                    odu5gpmfeuas(14413),
                    odu5gpmfesesr(14414),
                    odu5gpmfebber(14415),
                    odu2PmBbe(14416),
                    odu2PmEs(14417),
                    odu2PmSes(14418),
                    odu2PmUas(14419),
                    odu2PmSesr(14420),
                    odu2PmBber(14421),
                    odu2pmfebbe(14422),
                    odu2pmfees(14423),
                    odu2pmfeses(14424),
                    odu2pmfeuas(14425),
                    odu2pmfesesr(14426),
                    odu2pmfebber(14427),
                    odu3pmbbe(14428),
                    odu3pmes(14429),
                    odu3pmses(14430),
                    odu3pmuas(14431),
                    odu3pmsesr(14432),
                    odu3pmbber(14433),
                    odu3pmfebbe(14434),
                    odu3pmfees(14435),
                    odu3pmfeses(14436),
                    odu3pmfeuas(14437),
                    odu3pmfesesr(14438),
                    odu3pmfebber(14439),
                    odu1Tcm6Febbe(14518),
                    odu1Tcm6Fees(14519),
                    odu1Tcm6Feses(14520),
                    odu1Tcm6Feuas(14521),
                    odu1Tcm6Fesesr(14522),
                    odu1Tcm6Febber(14523),
                    odu5gtcm1iaes(14524),
                    odu5gtcm2iaes(14525),
                    odu5gtcm3iaes(14526),
                    odu5gtcm4iaes(14527),
                    odu5gtcm5iaes(14528),
                    odu5gtcm6iaes(14529),
                    odu5gtcm1biaes(14530),
                    odu5gtcm2biaes(14531),
                    odu5gtcm3biaes(14532),
                    odu5gtcm4biaes(14533),
                    odu5gtcm5biaes(14534),
                    odu5gtcm6biaes(14535),
                    odu5gtcm1bbe(14536),
                    odu5gtcm1es(14537),
                    odu5gtcm1ses(14538),
                    odu5gtcm1uas(14539),
                    odu5gtcm1sesr(14540),
                    odu5gtcm1bber(14541),
                    odu5gtcm2bbe(14542),
                    odu5gtcm2es(14543),
                    odu5gtcm2ses(14544),
                    odu5gtcm2uas(14545),
                    odu5gtcm2sesr(14546),
                    odu5gtcm2bber(14547),
                    odu5gtcm3bbe(14548),
                    odu5gtcm3es(14549),
                    odu5gtcm3ses(14550),
                    odu5gtcm3uas(14551),
                    odu5gtcm3sesr(14552),
                    odu5gtcm3bber(14553),
                    odu5gtcm4bbe(14554),
                    odu5gtcm4es(14555),
                    odu5gtcm4ses(14556),
                    odu5gtcm4uas(14557),
                    odu5gtcm4sesr(14558),
                    odu5gtcm4bber(14559),
                    odu5gtcm5bbe(14560),
                    odu5gtcm5es(14561),
                    odu5gtcm5ses(14562),
                    odu5gtcm5uas(14563),
                    odu5gtcm5sesr(14564),
                    odu5gtcm5bber(14565),
                    odu5gtcm6bbe(14566),
                    odu5gtcm6es(14567),
                    odu5gtcm6ses(14568),
                    odu5gtcm6uas(14569),
                    odu5gtcm6sesr(14570),
                    odu5gtcm6bber(14571),
                    odu5gtcm1febbe(14572),
                    odu5gtcm1fees(14573),
                    odu5gtcm1feses(14574),
                    odu5gtcm1feuas(14575),
                    odu5gtcm1fesesr(14576),
                    odu5gtcm1febber(14577),
                    odu5gtcm2febbe(14578),
                    odu5gtcm2fees(14579),
                    odu5gtcm2feses(14580),
                    odu5gtcm2feuas(14581),
                    odu5gtcm2fesesr(14582),
                    odu5gtcm2febber(14583),
                    odu5gtcm3febbe(14584),
                    odu5gtcm3fees(14585),
                    odu5gtcm3feses(14586),
                    odu5gtcm3feuas(14587),
                    odu5gtcm3fesesr(14588),
                    odu5gtcm3febber(14589),
                    odu5gtcm4febbe(14590),
                    odu5gtcm4fees(14591),
                    odu5gtcm4feses(14592),
                    odu5gtcm4feuas(14593),
                    odu5gtcm4fesesr(14594),
                    odu5gtcm4febber(14595),
                    odu5gtcm5febbe(14596),
                    odu5gtcm5fees(14597),
                    odu5gtcm5feses(14598),
                    odu5gtcm5feuas(14599),
                    odu5gtcm5fesesr(14600),
                    odu5gtcm5febber(14601),
                    odu5gtcm6febbe(14602),
                    odu5gtcm6fees(14603),
                    odu5gtcm6feses(14604),
                    odu5gtcm6feuas(14605),
                    odu5gtcm6fesesr(14606),
                    odu5gtcm6febber(14607),
                    odu2Tcm1Iaes(14608),
                    odu2Tcm2Iaes(14609),
                    odu2Tcm3Iaes(14610),
                    odu2Tcm4Iaes(14611),
                    odu2Tcm5Iaes(14612),
                    odu2Tcm6Iaes(14613),
                    odu2Tcm1Biaes(14614),
                    odu2Tcm2Biaes(14615),
                    odu2Tcm3Biaes(14616),
                    odu2Tcm4Biaes(14617),
                    odu2Tcm5Biaes(14618),
                    odu2Tcm6Biaes(14619),
                    odu2Tcm1Bbe(14620),
                    odu2Tcm1Es(14621),
                    odu2Tcm1Ses(14622),
                    odu2Tcm1Uas(14623),
                    odu2Tcm1Sesr(14624),
                    odu2Tcm1Bber(14625),
                    odu2Tcm2Bbe(14626),
                    odu2Tcm2Es(14627),
                    odu2Tcm2Ses(14628),
                    odu2Tcm2Uas(14629),
                    odu2Tcm2Sesr(14630),
                    odu2Tcm2Bber(14631),
                    odu2Tcm3Bbe(14632),
                    odu2Tcm3Es(14633),
                    odu2Tcm3Ses(14634),
                    odu2Tcm3Uas(14635),
                    odu2Tcm3Sesr(14636),
                    odu2Tcm3Bber(14637),
                    odu2Tcm4Bbe(14638),
                    odu2Tcm4Es(14639),
                    odu2Tcm4Ses(14640),
                    odu2Tcm4Sesr(14642),
                    odu2Tcm4Uas(14641),
                    odu2Tcm4Bber(14643),
                    odu2Tcm5Bbe(14644),
                    odu2Tcm5Es(14645),
                    odu2Tcm5Ses(14646),
                    odu2Tcm5Uas(14647),
                    odu2Tcm5Sesr(14648),
                    odu2Tcm5Bber(14649),
                    odu2Tcm6Bbe(14650),
                    odu2Tcm6Es(14651),
                    odu2Tcm6Ses(14652),
                    odu2Tcm6Uas(14653),
                    odu2Tcm6Sesr(14654),
                    odu2Tcm6Bber(14655),
                    odu2Tcm1Febbe(14656),
                    odu2Tcm1Fees(14657),
                    odu2Tcm1Feses(14658),
                    odu2Tcm1Feuas(14659),
                    odu2Tcm1Fesesr(14660),
                    odu2Tcm1Febber(14661),
                    odu2Tcm2Febbe(14662),
                    odu2Tcm2Fees(14663),
                    odu2Tcm2Feses(14664),
                    odu2Tcm2Feuas(14665),
                    odu2Tcm2Fesesr(14666),
                    odu2Tcm2Febber(14667),
                    odu2Tcm3Febbe(14668),
                    odu2Tcm3Fees(14669),
                    odu2Tcm3Feses(14670),
                    odu2Tcm3Feuas(14671),
                    odu2Tcm3Fesesr(14672),
                    odu2Tcm3Febber(14673),
                    odu2Tcm4Febbe(14674),
                    odu2Tcm4Fees(14675),
                    odu2Tcm4Feses(14676),
                    odu2Tcm4Feuas(14677),
                    odu2Tcm4Fesesr(14678),
                    odu2Tcm4Febber(14679),
                    odu2Tcm5Febbe(14680),
                    odu2Tcm5Fees(14681),
                    odu2Tcm5Feses(14682),
                    odu2Tcm5Feuas(14683),
                    odu2Tcm5Fesesr(14684),
                    odu2Tcm5Febber(14685),
                    odu2Tcm6Febbe(14686),
                    odu2Tcm6Fees(14687),
                    odu2Tcm6Feses(14688),
                    odu2Tcm6Feuas(14689),
                    odu2Tcm6Fesesr(14690),
                    odu2Tcm6Febber(14691),
                    odu3Tcm1Iaes(14692),
                    odu3Tcm2Iaes(14693),
                    odu3Tcm3Iaes(14694),
                    odu3Tcm4Iaes(14695),
                    odu3Tcm5Iaes(14696),
                    odu3Tcm6Iaes(14697),
                    odu3Tcm1Biaes(14698),
                    odu3Tcm2Biaes(14699),
                    odu3Tcm3Biaes(14700),
                    odu3Tcm4Biaes(14701),
                    odu3Tcm5Biaes(14702),
                    odu3Tcm6Biaes(14703),
                    odu3Tcm1Bbe(14704),
                    odu3Tcm1Es(14705),
                    odu3Tcm1Ses(14706),
                    odu3Tcm1Uas(14707),
                    odu3Tcm1Sesr(14708),
                    odu3Tcm1Bber(14709),
                    odu3Tcm2Bbe(14710),
                    odu3Tcm2Es(14711),
                    odu3Tcm2Ses(14712),
                    odu3Tcm2Uas(14713),
                    odu3Tcm2Sesr(14714),
                    odu3Tcm2Bber(14715),
                    odu3Tcm3Bbe(14716),
                    odu3Tcm3Es(14717),
                    odu3Tcm3Ses(14718),
                    odu3Tcm3Uas(14719),
                    odu3Tcm3Sesr(14720),
                    odu3Tcm3Bber(14721),
                    odu3Tcm4Bbe(14722),
                    odu3Tcm4Es(14723),
                    odu3Tcm4Ses(14724),
                    odu3Tcm4Uas(14725),
                    odu3Tcm4Sesr(14726),
                    odu3Tcm4Bber(14727),
                    odu3Tcm5Bbe(14728),
                    odu3Tcm5Es(14729),
                    odu3Tcm5Ses(14730),
                    odu3Tcm5Uas(14731),
                    odu3Tcm5Sesr(14732),
                    odu3Tcm5Bber(14733),
                    odu3Tcm6Bbe(14734),
                    odu3Tcm6Es(14735),
                    odu3Tcm6Ses(14736),
                    odu3Tcm6Uas(14737),
                    odu3Tcm6Sesr(14738),
                    odu3Tcm6Bber(14739),
                    odu3Tcm1Febbe(14740),
                    odu3Tcm1Fees(14741),
                    odu3Tcm1Feses(14742),
                    odu3Tcm1Feuas(14743),
                    odu3Tcm1Fesesr(14744),
                    odu3Tcm1Febber(14745),
                    odu3Tcm2Febbe(14746),
                    odu3Tcm2Fees(14747),
                    odu3Tcm2Feses(14748),
                    odu3Tcm2Feuas(14749),
                    odu3Tcm2Fesesr(14750),
                    odu3Tcm2Febber(14751),
                    odu3Tcm3Febbe(14752),
                    odu3Tcm3Fees(14753),
                    odu3Tcm3Feses(14754),
                    odu3Tcm3Feuas(14755),
                    odu3Tcm3Fesesr(14756),
                    odu3Tcm3Febber(14757),
                    odu3Tcm4Febbe(14758),
                    odu3Tcm4Fees(14759),
                    odu3Tcm4Feses(14760),
                    odu3Tcm4Feuas(14761),
                    odu3Tcm4Fesesr(14762),
                    odu3Tcm4Febber(14763),
                    odu3Tcm5Febbe(14764),
                    odu3Tcm5Fees(14765),
                    odu3Tcm5Feses(14766),
                    odu3Tcm5Feuas(14767),
                    odu3Tcm5Fesesr(14768),
                    odu3Tcm5Febber(14769),
                    odu3Tcm6Febbe(14770),
                    odu3Tcm6Fees(14771),
                    odu3Tcm6Feses(14772),
                    odu3Tcm6Feuas(14773),
                    odu3Tcm6Fesesr(14774),
                    odu3Tcm6Febber(14775),
                    tdcmax(14902),
                    tdcmin(14903),
                    tdccur(14904),  
                    cpTelDownCount(14915),
                    cpTelDownTime(14916),
                    cpCcDownCount(14917),
                    cpCcDownTime(14918),
                    qValueEer(14925),
                    fecBefCorerFloat(14926),
                    fecAftCorerFloat(14927),
                    mplsTunnelLs(14933),
                    mplsTunnelSls(14934),
                    mplsTunnelCsls(14935),
                    mplsTunnelUas(14936),
                    perEvtethcfmlosssencond(14937),
                    perEvtethcfmseverelosssencond(14938),
                    perEvtethcfmcontinualseverelylosssencond(14939),
                    perEvtethcfmunavailablesencond(14940),
                    perEvtbdtempmax(14991),
                    perEvtbdtempmin(14992),
                    perEvtbdtempcur(14993),
                    fecAftCorEravr(15009),
                    fecBefCorEravr(15010),
                    odu0PmBbe(15054),
                    odu0PmEs(15055),
                    odu0PmSes(15056),
                    odu0PmUas(15057),
                    odu0PmSesr(15058),
                    odu0PmBber(15059),
                    odu0PmFebbe(15060),
                    odu0PmFees(15061),
                    odu0PmFeses(15062),
                    odu0PmFeuas(15063),
                    odu0PmFesesr(15064),
                    odu0PmFebber(15065),
                    perEvtmplspwlosssencond(15066),
                    perEvtmplspwseverelosssencond(15067),
                    perEvtmplspwcontinualseverelylosssencond(15068),
                    perEvtmplspwunavailablesencond(15069),
                    oscbbe(15074),
                    osces(15075),
                    oscses(15076),
                    oscuas(15077),
                    oscsesr(15078),
                    oscbber(15079),
                    oscfebbe(15080),
                    oscfees(15081),
                    oscfeses(15082),
                    oscfeuas(15083),
                    oscfesesr(15084),
                    oscfebber(15085),
                    osciaes(15086),
                    oscbiaes(15087),
                    maxfreqdev(15088),
                    minfreqdev(15089),
                    avgfreqdev(15090),
                    maxphaseoffset(15091),
                    minphaseoffset(15092),
                    avgphaseoffset(15093),
                    maxmeanpathdelay(15094),
                    minmeanpathdelay(15095),
                    avgmeanpathdelay(15096),
                    otu4Iaes(15109),
                    otu4Biaes(15110),
                    otu4Bbe(15111),
                    otu4Es(15112),
                    otu4Ses(15113),
                    otu4Uas(15114),
                    otu4Sesr(15115),
                    otu4Bber(15116),
                    otu4Febbe(15117),
                    otu4Fees(15118),
                    otu4Feses(15119),
                    otu4Feuas(15120),
                    otu4Fesesr(15121),
                    otu4Febber(15122),
                    odu4Pmbbe(15123),
                    odu4Pmes(15124),
                    odu4Pmses(15125),
                    odu4Pmuas(15126),
                    odu4Pmsesr(15127),
                    odu4Pmbber(15128),
                    odu4Pmfebbe(15129),
                    odu4Pmfees(15130),
                    odu4Pmfeses(15131),
                    odu4Pmfeuas(15132),
                    odu4Pmfesesr(15133),
                    odu4Pmfebber(15134),
                    odu4Tcm1Iaes(15135),
                    odu4Tcm2Iaes(15136),
                    odu4Tcm3Iaes(15137),
                    odu4Tcm4Iaes(15138),
                    odu4Tcm5Iaes(15139),
                    odu4Tcm6Iaes(15140),
                    odu4Tcm1Biaes(15141),
                    odu4Tcm2Biaes(15142),
                    odu4Tcm3Biaes(15143),
                    odu4Tcm4Biaes(15144),
                    odu4Tcm5Biaes(15145),
                    odu4Tcm6Biaes(15146),
                    odu4Tcm1Bbe(15147),
                    odu4Tcm1Es(15148),
                    odu4Tcm1Ses(15149),
                    odu4Tcm1Uas(15150),
                    odu4Tcm1Sesr(15151),
                    odu4Tcm1Bber(15152),
                    odu4Tcm2Bbe(15153),
                    odu4Tcm2Es(15154),
                    odu4Tcm2Ses(15155),
                    odu4Tcm2Uas(15156),
                    odu4Tcm2Sesr(15157),
                    odu4Tcm2Bber(15158),
                    odu4Tcm3Bbe(15159),
                    odu4Tcm3Es(15160),
                    odu4Tcm3Ses(15161),
                    odu4Tcm3Uas(15162),
                    odu4Tcm3Sesr(15163),
                    odu4Tcm3Bber(15164),
                    odu4Tcm4Bbe(15165),
                    odu4Tcm4Es(15166),
                    odu4Tcm4Ses(15167),
                    odu4Tcm4Uas(15168),
                    odu4Tcm4Sesr(15169),
                    odu4Tcm4Bber(15170),
                    odu4Tcm5Bbe(15171),
                    odu4Tcm5Es(15172),
                    odu4Tcm5Ses(15173),
                    odu4Tcm5Uas(15174),
                    odu4Tcm5Sesr(15175),
                    odu4Tcm5Bber(15176),
                    odu4Tcm6Bbe(15177),
                    odu4Tcm6Es(15178),
                    odu4Tcm6Ses(15179),
                    odu4Tcm6Uas(15180),
                    odu4Tcm6Sesr(15181),
                    odu4Tcm6Bber(15182),
                    odu4Tcm1Febbe(15183),
                    odu4Tcm1Fees(15184),
                    odu4Tcm1Feses(15185),
                    odu4Tcm1Feuas(15186),
                    odu4Tcm1Fesesr(15187),
                    odu4Tcm1Febber(15188),
                    odu4Tcm2Febbe(15189),
                    odu4Tcm2Fees(15190),
                    odu4Tcm2Feses(15191),
                    odu4Tcm2Feuas(15192),
                    odu4Tcm2Fesesr(15193),
                    odu4Tcm2Febber(15194),
                    odu4Tcm3Febbe(15195),
                    odu4Tcm3Fees(15196),
                    odu4Tcm3Feses(15197),
                    odu4Tcm3Feuas(15198),
                    odu4Tcm3Fesesr(15199),
                    odu4Tcm3Febber(15200),
                    odu4Tcm4Febbe(15201),
                    odu4Tcm4Fees(15202),
                    odu4Tcm4Feses(15203),
                    odu4Tcm4Feuas(15204),
                    odu4Tcm4Fesesr(15205),
                    odu4Tcm4Febber(15206),
                    odu4Tcm5Febbe(15207),
                    odu4Tcm5Fees(15208),
                    odu4Tcm5Feses(15209),
                    odu4Tcm5Feuas(15210),
                    odu4Tcm5Fesesr(15211),
                    odu4Tcm5Febber(15212),
                    odu4Tcm6Febbe(15213),
                    odu4Tcm6Fees(15214),
                    odu4Tcm6Feses(15215),
                    odu4Tcm6Feuas(15216),
                    odu4Tcm6Fesesr(15217),
                    odu4Tcm6Febber(15218),

                    odu0Tcm6Febber(15360),
                    odu0Tcm6Iaes(15361),
                    odu0Tcm6Biaes(15362),
                    dgdmax(15378),
                    dgdmin(15379),
                    dgdcur(15380),
                    peakInpowerMax(15381),
                    peakInpowerCur(15382),
                    peakInpowerMin(15383),
                    valleyInpowerMax(15384),
                    valleyInpowerCur(15385),
                    valleyInpowerMin(15386),
                    peakOutpowerMax(15387),
                    peakOutpowerCur(15388),
                    peakOutpowerMin(15389),
                    valleyOutpowerMax(15390),
                    valleyOutpowerCur(15391),
                    valleyOutpowerMin(15392),
                    peakLstmpMax(15393),
                    peakLstmpCur(15394),
                    peakLstmpMin(15395),
                    valleyLstmpMax(15396),
                    valleyLstmpCur(15397),
                    valleyLstmpMin(15398),
                    peakLsbiasMax(15399),
                    peakLsbiasCur(15400),
                    peakLsbiasMin(15401),
                    valleyLsbiasMax(15402),
                    valleyLsbiasCur(15403),
                    valleyLsbiasMin(15404),
                    peakLsclcMax(15405),
                    peakLsclcCur(15406),
                    peakLsclcMin(15407),
                    valleyLsclcMax(15408),
                    valleyLsclcCur(15409),
                    valleyLsclcMin(15410),    
                    dgdavg(15416),
                    odu0PmTmp(15423),
                    odu0Tcm1Tmp(15424),  
                    odu0Tcm2Tmp(15425),   
                    odu0Tcm3Tmp(15426),     
                    odu0Tcm4Tmp(15427),  
                    odu0Tcm5Tmp(15428),    
                    odu0Tcm6Tmp(15429),   
                    otu1Tmp(15430),   
                    odu1PmTmp(15431),
                    odu1Tcm1Tmp(15432),  
                    odu1Tcm2Tmp(15433),        
                    odu1Tcm3Tmp(15434),  
                    odu1Tcm4Tmp(15435), 
                    odu1Tcm5Tmp(15436), 
                    odu1Tcm6Tmp(15437), 
                    otu2Tmp(15438), 
                    odu2PmTmp(15439),
                    odu2Tcm1Tmp(15440),
                    odu2Tcm2Tmp(15441),  
                    odu2Tcm3Tmp(15442), 
                    odu2Tcm4Tmp(15443), 
                    odu2Tcm5Tmp(15444), 
                    odu2Tcm6Tmp(15445), 
                    otu3Tmp(15446), 
                    odu3PmTmp(15447),
                    odu3Tcm1Tmp(15448),
                    odu3Tcm2Tmp(15449),  
                    odu3Tcm3Tmp(15450), 
                    odu3Tcm4Tmp(15451), 
                    odu3Tcm5Tmp(15452), 
                    odu3Tcm6Tmp(15453), 
                    otu4Tmp(15454), 
                    odu4PmTmp(15455),
                    odu4Tcm1Tmp(15456),
                    odu4Tcm2Tmp(15457),  
                    odu4Tcm3Tmp(15458), 
                    odu4Tcm4Tmp(15459), 
                    odu4Tcm5Tmp(15460), 
                    odu4Tcm6Tmp(15461), 
                    otu5gTmp(15462), 
                    odu5gPmtmp(15463), 
                    odu5gTcm1Tmp(15464),
                    odu5gTcm2Tmp(15465),  
                    odu5gTcm3Tmp(15466), 
                    odu5gTcm4Tmp(15467), 
                    odu5gTcm5Tmp(15468), 
                    odu5gTcm6Tmp(15469), 
                    oduflexPmTmp(15470),
                    fecTmp(15471),
                    rsTmp(15472),
                    rmIopmax(15476),
                    rmIopmin(15477),
                    rmIopcur(15478),
                    aswIopmax(15483),
                    aswIopmin(15484),
                    aswIopcur(15485),
                    aaOspcur(15486),
                    aswOopmax(15487),
                    aswOopmin(15488),
                    aswOopcur(15489),
                    aswSnrmax(15490),
                    aswSnrmin(15491),
                    aswSnrcur(15492),
                    aswSnlmax(15493),
                    aswSnlmin(15494),
                    aswSnlcur(15495),
                    aaInpmax(15496),
                    aaInpmin(15497),
                    aaInpcur(15498),
                    aaIspmax(15499),
                    aaIspmin(15500),
                    aaIspcur(15501),
                    aaOnpmax(15502),
                    aaOnpmin(15503),
                    aaOnpcur(15504),
                    aaOspmax(15505),
                    aaOspmin(15506),
                    ethBbe(15601),
                    ethBber(15602),
                    ethSesr(15603),
                    ethUas(15604),
                    ethEs(15605),
                    ethSes(15606),
                    mplsPwLsN(15607),
                    mplsPwUasN(15608),
                    mplsPwCslsN(15609),
                    mplsPwSlsN(15610),
                    mplsTunnelSlsN(15611),
                    mplsTunnelLsN(15612),
                    mplsTunnelCslsN(15613),
                    mplsTunnelUasN(15614),
                    ethEsr(15626),
                    otucnBbe(15627),
                    otucnFees(15628),
                    otucnFebbe(15629),
                    otucnBber(15630),
                    otucnSesr(15631),
                    otucnFeses(15632),
                    otucnBiaes(15633),
                    otucnUas(15634),
                    otucnSes(15635),
                    otucnEs(15636),
                    otucnIaes(15637),
                    otucnFebber(15638),
                    otucnFeuas(15639),
                    otucnTmp(15640),
                    otucnFesesr(15641),
                    oducnPmFesesr(15642),
                    oducnPmFebber(15643),
                    oducnPmFees(15644),
                    oducnPmFeses(15645),
                    oducnPmFeuas(15646),
                    oducnPmEs(15647),
                    oducnPmSes(15648),
                    oducnPmBbe(15649),
                    oducnPmBber(15650),
                    oducnPmFebbe(15651),
                    oducnPmUas(15652),
                    oducnPmSesr(15653),
                    oducnPmTmp(15654),
                    cfpLsoopmax(15660),
                    cfpLsoopmin(15661),
                    cfpLsoopcur(15662),
                    cfpLsiopmax(15656),
                    cfpLsiopmin(15657),
                    cfpLsiopcur(15658),
                    cfpLstmpmax(15664),
                    cfpLstmpmin(15665),
                    cfpLstmpcur(15666),
                    cfpLsbiasmax(15668),
                    cfpLsbiasmin(15669),
                    cfpLsbiascur(15670),
                    oduflexPmBbe(15267),
                    oduflexPmEs(15268),
                    oduflexPmSes(15269),
                    oduflexPmUas(15270),
                    oduflexPmSesr(15271),
                    oduflexPmBber(15272),
                    oduflexPmFebbe(15273),
                    oduflexPmFees(15274),
                    oduflexPmFeses(15275),
                    oduflexPmFeuas(15276),
                    oduflexPmFesesr(15277),
                    oduflexPmFebber(15278),
                    odu0Tcm1Bbe(15279),
                    odu0Tcm1Es(15280),
                    odu0Tcm1Ses(15281),
                    odu0Tcm1Uas(15282),
                    odu0Tcm1Sesr(15283),
                    odu0Tcm1Bber(15284),
                    odu0Tcm1Febbe(15285),
                    odu0Tcm1Fees(15286),
                    odu0Tcm1Feses(15287),
                    odu0Tcm1Fesesr(15288),
                    odu0Tcm1Fesesr(15289),
                    odu0Tcm1Febber(15290),
                    odu0Tcm1Iaes(15291),
                    odu0Tcm1Biaes(15292),
                    odu0Tcm2Bbe(15293),
                    odu0Tcm2Es(15294),
                    odu0Tcm2Ses(15295),
                    odu0Tcm2Uas(15296),
                    odu0Tcm2Sesr(15297),
                    odu0Tcm2Bber(15298),
                    odu0Tcm2FeBbe(15299),
                    odu0Tcm2Fees(15300),
                    odu0Tcm2Feses(15301),
                    odu0Tcm2Feuas(15302),
                    odu0Tcm2Fesesr(15303),
                    odu0Tcm2Febber(15304),
                    odu0Tcm2Iaes(15305),
                    odu0Tcm2Biaes(15306),
                    odu0Tcm3Bbe(15307),
                    odu0Tcm3Es(15308),
                    odu0Tcm3Ses(15309),
                    odu0Tcm3Uas(15310),
                    odu0Tcm3sesr(15311),
                    odu0Tcm3Bber(15312),
                    odu0Tcm3Febbe(15313),
                    odu0Tcm3Fees(15314),
                    odu0Tcm3Feses(15315),
                    odu0Tcm3Feuas(15316),
                    odu0Tcm3Fesesr(15317),
                    odu0Tcm3Febber(15318),
                    odu0Tcm3Iaes(15319),
                    odu0Tcm3Biaes(15320),
                    odu0Tcm4Bbe(15321),
                    odu0Tcm4Es(15322),
                    odu0Tcm4Ses(15323),
                    odu0Tcm4Uas(15324),
                    odu0Tcm4sesr(15325),
                    odu0Tcm4Bber(15326),
                    odu0Tcm4Febbe(15327),
                    odu0Tcm4Fees(15328),
                    odu0Tcm4Feses(15329),
                    odu0Tcm4Feuas(15330),
                    odu0Tcm4Fesesr(15331),
                    odu0Tcm4Febber(15332),
                    odu0Tcm4Iaes(15333),
                    odu0Tcm4Biaes(15334),
                    odu0Tcm5Bbe(15335),
                    odu0Tcm5Es(15336),
                    odu0Tcm5Ses(15337),
                    odu0Tcm5Uas(15338),
                    odu0Tcm5sesr(15339),
                    odu0Tcm5Bber(15340),
                    odu0Tcm5Febbe(15341),
                    odu0Tcm5Fees(15342),
                    odu0Tcm5Feses(15343),
                    odu0Tcm5Feuas(15344),
                    odu0Tcm5Fesesr(15345),
                    odu0Tcm5Febber(15346),
                    odu0Tcm5Iaes(15347),
                    odu0Tcm5Biaes(15348),
                    odu0Tcm6Bbe(15349),
                    odu0Tcm6Es(15350),
                    odu0Tcm6Ses(15351),
                    odu0Tcm6Uas(15352),
                    odu0Tcm6sesr(15353),
                    odu0Tcm6Bber(15354),
                    odu0Tcm6Febbe(15355),
                    odu0Tcm6Fees(15356),
                    odu0Tcm6Feses(15357),
                    odu0Tcm6Feuas(15358),
                    odu0Tcm6Fesesr(15359),
                    odu0Tcm6Febber(15360),
                    odu0Tcm6Iaes(15361),
                    odu0Tcm6Biaes(15362),
                    oduflexTcm6Fesesr(15511),
                    oduflexTcm5Tmp(15512),
                    oduflexTcm6Feuas(15513),
                    oduflexTcm6Feses(15514),
                    oduflexTcm6Ses(15515),
                    oduflexTcm6Fees(15516),
                    oduflexTcm6Es(15517),
                    oduflexTcm6Bbe(15518),
                    oduflexTcm6Bber(15519),
                    oduflexTcm6Febbe(15520),
                    oduflexTcm6Sesr(15521),
                    oduflexTcm6Uas(15522),
                    oduflexTcm6Iaes(15523),
                    oduflexTcm6Biaes(15524),
                    oduflexTcm6Febber(15525),
                    oduflexTcm6Tmp(15526),
                    oduflexTcm2Uas(15527),
                    oduflexTcm1Febbe(15528),
                    oduflexTcm5Febber(15529),
                    oduflexTcm5Fesesr(15530),
                    oduflexTcm5Bber(15531),
                    oduflexTcm5Sesr(15532),
                    oduflexTcm5Fees(15533),
                    oduflexTcm5Febbe(15534),
                    oduflexTcm5Feuas(15535),
                    oduflexTcm5Feses(15536),
                    oduflexTcm5Uas(15537),
                    oduflexTcm5Ses(15538),
                    oduflexTcm5Es(15539),
                    oduflexTcm5Bbe(15540),
                    oduflexTcm5Biaes(15541),
                    oduflexTcm5Iaes(15542),
                    oduflexTcm4Biaes(15543),
                    oduflexTcm4Iaes(15544),
                    oduflexTcm4Febber(15545),
                    oduflexTcm4Fesesr(15546),
                    oduflexTcm4Feuas(15547),
                    oduflexTcm4Feses(15548),
                    oduflexTcm4Fees(15549),
                    oduflexTcm4Febbe(15550),
                    oduflexTcm4Uas(15551),
                    oduflexTcm4Ses(15552),
                    oduflexTcm4Bber(15553),
                    oduflexTcm4Sesr(15554),
                    oduflexTcm4Es(15555),
                    oduflexTcm4Bbe(15556),
                    oduflexTcm4Tmp(15557),
                    oduflexTcm1Fesesr(15558),
                    oduflexTcm1Biaes(15559),
                    oduflexTcm1Febber(15560),
                    oduflexTcm1Iaes(15561),
                    oduflexTcm1Feuas(15562),
                    oduflexTcm1Feses(15563),
                    oduflexTcm1Sesr(15564),
                    oduflexTcm1Bber(15565),
                    oduflexTcm1Fees(15566),
                    oduflexTcm1Bbe(15567),
                    oduflexTcm1Es(15568),
                    oduflexTcm1Ses(15569),
                    oduflexTcm1Uas(15570),
                    oduflexTcm1Tmp(15571),
                    oduflexTcm2Febbe(15572),
                    oduflexTcm2Fees(15573),
                    oduflexTcm2Feses(15574),
                    oduflexTcm2Feuas(15575),
                    oduflexTcm2Fesesr(15576),
                    oduflexTcm2Febber(15577),
                    oduflexTcm2Iaes(15578),
                    oduflexTcm2Biaes(15579),
                    oduflexTcm2Bber(15580),
                    oduflexTcm2Sesr(15581),
                    oduflexTcm2Es(15582),
                    oduflexTcm2Ses(15583),
                    oduflexTcm2Bbe(15584),
                    oduflexTcm2Tmp(15585),
                    oduflexTcm3Uas(15586),
                    oduflexTcm3Sesr(15587),
                    oduflexTcm3Ses(15588),
                    oduflexTcm3Fees(15589),
                    oduflexTcm3Feses(15590),
                    oduflexTcm3Bber(15591),
                    oduflexTcm3Febbe(15592),
                    oduflexTcm3Febber(15593),
                    oduflexTcm3Feuas(15594),
                    oduflexTcm3Fesesr(15595),
                    oduflexTcm3Bbe(15596),
                    oduflexTcm3Es(15597),
                    oduflexTcm3Biaes(15598),
                    oduflexTcm3Iaes(15599),
                    oduflexTcm3Tmp(15600),
                    cfpLstmpcur(15666),
                    cfpLsbiasmax(15668),
                    cfpLsbiasmin(15669),
                    cfpLsbiascur(15670),
                    qValueEerAver15m(15674),
                    qValueEerAver24h(15675),
                    cprirxerr(15700),
                    cpritxerr(15701),
                    cfpLsclcmax(15713),
                    cfpLsclcmin(15714),
                    cfpLsclccur(15715),
                    odux5Pmbbe(15716),
                    odux5Pmes(15717),
                    odux5Pmses(15718),
                    odux5Pmuas(15719),
                    odux5Pmsesr(15720),
                    odux5Pmbber(15721),
                    odux5Pmfebbe(15722),
                    odux5Pmfees(15723),
                    odux5Pmfeses(15724),
                    odux5Pmfeuas(15725),
                    odux5Pmfesesr(15726),
                    odux5Pmfebber(15727),
                    otux5Bbe(15728),
                    otux5Es(15729),
                    otux5Ses(15730),
                    otux5Uas(15731),
                    otux5Sesr(15732),
                    otux5Bber(15733),
                    otux5Febbe(15734),
                    otux5Fees(15735),
                    otux5Feses(15736),
                    otux5Feuas(15737),
                    otux5Fesesr(15738),
                    otux5Febber(15739),
                    otux5iaes(15741),
                    otux5tmp(15742),
                    otux5biaes(15743),
                    odux5pmtmp(15744),
                    obsaitxerr(15835),
                    obsairxerr(15836),
                    laneLsoopmax(15883),
                    laneLsoopmin(15884),
                    laneLsoopcur(15885),
                    laneLsiopmax(15886),
                    laneLsiopmin(15887),
                    laneLsiopcur(15888),
                    laneLsbiasmax(15889),
                    laneLsbiasmin(15890),
                    laneLsbiascur(15891),
                    bcvmax(118),
                    bcvmin(119),
                    bcvcur(120),
                    oscBbe(15074),
                    oscEs(15075),
                    oscSes(15076),
                    oscUas(15077),
                    oscSesr(15078),
                    oscBber(15079),
                    oscFebbe(15080),
                    oscFees(15081),
                    oscFeses(15082),
                    oscFeuas(15083),
                    oscFesesr(15084),
                    oscFebber(15085),
                    oscIaes(15086),
                    oscBiaes(15087),
                    fswiopmax(15868),
                    fswsnrmax(15874),
                    fswsnrmin(15875),
                    fswsnrcur(15876),
                    fswiopmin(15869),
                    fswiopcur(15870),
                    fswoopmax(15871),
                    fswoopmin(15872),
                    fswoopcur(15873),
                    fclsopmax(15880),
                    fclsopmin(15881),
                    fclsopcur(15882),
                    lsvolmax(15983),
                    sopcur(16097),
                    sopmin(16098),
                    sopmax(16099),
                    lsvolmin(15984),
                    lsvolcur(15985),
                    fpclswlomax(15920),
                    fpclswlomin(15921),
                    fpclswlocur(15922),
                    edtplmax(121),
                    edtplmin(122),
                    edtplcur(123),
                    pclswlmax(228),
                    pclswlmin(229),
                    pclswlcur(230),
                    pclswlomax(231),
                    pclswlomin(232),
                    pclswlocur(233),
                    pclsopmax(234),
                    pclsopmin(235),
                    pclsopcur(236),
                    pclssnmax(237),
                    pclssnmin(238),
                    pclssncur(239),
                    ooprlmax(8612),
                    ooprlmin(8613),
                    ooprlcur(8614),
                    apdtemmax(14976),
                    apdtemmin(14977),
                    apdtemcur(14978),
                    apdcoolmax(14994),
                    apdcoolmin(14995),
                    apdcoolcur(14996),
                    rmiopmax(15476),
                    rmiopmin(15477),
                    rmiopcur(15478),
                    aswiopmax(15483),
                    aswiopmin(15484),
                    aswiopcur(15485),
                    aaospcur(15486),
                    aswoopmax(15487),
                    aswoopmin(15488),
                    aswoopcur(15489),
                    aswsnrmax(15490),
                    aswsnrmin(15491),
                    aswsnrcur(15492),
                    aswsnlmax(15493),
                    aswsnlmin(15494),
                    aswsnlcur(15495),
                    aainpmax(15496),
                    aainpmin(15497),
                    aainpcur(15498),
                    aaispmax(15499),
                    aaispmin(15500),
                    aaispcur(15501),
                    aaonpmax(15502),
                    aaonpmin(15503),
                    aaonpcur(15504),
                    aaospmax(15505),
                    aaospmin(15506),
                    pumporpcur(15862),
                    pumporpmax(15863),
                    pumporpmin(15864),
                    fswsnlmax(15877),
                    fswsnlmin(15878),
                    fswsnlcur(15879),
                    subcardtmpmax(15900),
                    subcardtmpmin(15901),
                    subcardtmpcur(15902),
                    gaincur(15980),
                    gainmax(15981),
                    gainmin(15982),
                    mcsoopmax(16135),
                    mcsoopmin(16136),
                    mcsoopcur(16137),
                    evoaattncur(16164),
                    evoaattnmax(16165),
                    evoaattnmin(16166),
                    oducnTcm1Iaes(15989),
                    oducnTcm2Iaes(15990),
                    oducnTcm3Iaes(15991),
                    oducnTcm4Iaes(15992),
                    oducnTcm5Iaes(15993),
                    oducnTcm6Iaes(15994),
                    oducnTcm1Biaes(15995),
                    oducnTcm2Biaes(15996),
                    oducnTcm3Biaes(15997),
                    oducnTcm4Biaes(15998),
                    oducnTcm5Biaes(15999),
                    oducnTcm6Biaes(16000),
                    oducnTcm1Bbe(16001),
                    oducnTcm2Bbe(16002),
                    oducnTcm3Bbe(16003),
                    oducnTcm4Bbe(16004),
                    oducnTcm5Bbe(16005),
                    oducnTcm6Bbe(16006),
                    oducnTcm1Es(16007),
                    oducnTcm2Es(16008),
                    oducnTcm3Es(16009),
                    oducnTcm4Es(16010),
                    oducnTcm5Es(16011),
                    oducnTcm6Es(16012),
                    oducnTcm1Ses(16013),
                    oducnTcm2Ses(16014),
                    oducnTcm3Ses(16015),
                    oducnTcm4Ses(16016),
                    oducnTcm5Ses(16017),
                    oducnTcm6Ses(16018),
                    oducnTcm1Uas(16019),
                    oducnTcm2Uas(16020),
                    oducnTcm3Uas(16021),
                    oducnTcm4Uas(16022),
                    oducnTcm5Uas(16023),
                    oducnTcm6Uas(16024),
                    oducnTcm1Sesr(16025),
                    oducnTcm2Sesr(16026),
                    oducnTcm3Sesr(16027),
                    oducnTcm4Sesr(16028),
                    oducnTcm5Sesr(16029),
                    oducnTcm6Sesr(16030),
                    oducnTcm1Bber(16031),
                    oducnTcm2Bber(16032),
                    oducnTcm3Bber(16033),
                    oducnTcm4Bber(16034),
                    oducnTcm5Bber(16035),
                    oducnTcm6Bber(16036),
                    oducnTcm1Febbe(16037),
                    oducnTcm2Febbe(16038),
                    oducnTcm3Febbe(16039),
                    oducnTcm4Febbe(16040),
                    oducnTcm5Febbe(16041),
                    oducnTcm6Febbe(16042),
                    oducnTcm1Fees(16043),
                    oducnTcm2Fees(16044),
                    oducnTcm3Fees(16045),
                    oducnTcm4Fees(16046),
                    oducnTcm5Fees(16047),
                    oducnTcm6Fees(16048),
                    oducnTcm1Feses(16049),
                    oducnTcm2Feses(16050),
                    oducnTcm3Feses(16051),
                    oducnTcm4Feses(16052),
                    oducnTcm5Feses(16053),
                    oducnTcm6Feses(16054),
                    oducnTcm1Feuas(16055),
                    oducnTcm2Feuas(16056),
                    oducnTcm3Feuas(16057),
                    oducnTcm4Feuas(16058),
                    oducnTcm5Feuas(16059),
                    oducnTcm6Feuas(16060),
                    oducnTcm1Fesesr(16061),
                    oducnTcm2Fesesr(16062),
                    oducnTcm3Fesesr(16063),
                    oducnTcm4Fesesr(16064),
                    oducnTcm5Fesesr(16065),
                    oducnTcm6Fesesr(16066),
                    oducnTcm1Febber(16067),
                    oducnTcm2Febber(16068),
                    oducnTcm3Febber(16069),
                    oducnTcm4Febber(16070),
                    oducnTcm5Febber(16071),
                    oducnTcm6Febber(16072),
                    oducnTcm1Tmp(16073),
                    oducnTcm2Tmp(16074),
                    oducnTcm3Tmp(16075),
                    oducnTcm4Tmp(16076),
                    oducnTcm5Tmp(16077),
                    oducnTcm6Tmp(16078),
                    
                    ictmpmax(249),
                    ictmpmin(250),
                    ictmpcur(251),
                    xcstmpfluct(16110),
                    fanspeedmax(16111),
                    fanspeedmin(16112),
                    fanspeedcur(16113),
                    fanspeedfluct(16114),
                    esnrmin(16115),
                    esnrmax(16116),
                    esnrcur(16117),
                    esnravg(16118),
                    pdlmax(16119),
                    pdlmin(16120),
                    pdlcur(16121),
                    pdlavg(16122),
                    pmdmax(16123),
                    pmdmin(16124),
                    pdmcur(16125),
                    pdmavg(16126),
                    qvalueeermin(16144),
                    qvalueeermax(16145),
                    befcorerfloatmin(16146),
                    befcorerfloatmax(16147),
                    aftcorerfloatmax(16148),
                    befcorerfloatavr(16149),
                    aftcorerfloatavr(16150),
                    aftcorerfloatmin(16163),
                    feccorbitscnt(16171),
                    bdcurpwer(16172),
                    inputvoltmax(16174),
                    inputvoltcur(16175),
                    inputvoltmin(16176),
                    outputvoltmax(16177),
                    outputvoltcur(16178),
                    outputvoltmin(16179),
                    outputcurrentmax(16180),
                    outputcurrentcur(16181),
                    outputcurrentmin(16182),
                    inputcurrentmax(16183),
                    inputcurrentcur(16184),
                    inputcurrentmin(16185),
                    lswfrequency(16186),
                    cpuusagemax(14919),
                    cpuusagemin(14920),
                    cpuusagecur(14921),
                    memusagemax(14922),
                    memusagemin(14923),
                    memusagecur(14924),
                    Otu1Sesr(14342),
                    Otu1Bber(14343),
                    Otu3Biaes(14379),
                    Otu3Bbe(14380),
                    Otu3Es(14381),
                    Otu3Ses(14382),
                    Otu3Uas(14383),
                    Otu3Sesr(14384),
                    Otu3Bber(14385),
                    Otu3Febbe(14386),
                    Otu3Fees(14387),
                    Otu3Feses(14388),
                    Otu3Feuas(14389),
                    Otu3Fesesr(14390),
                    Otu3Febber(14391),
                    Odu1PmBbe(14392),
                    Odu1PmEs(14393),
                    Odu1PmSes(14394),
                    Odu1PmUas(14395),
                    Odu1PmSesr(14396),
                    Odu1PmBber(14397),
                    Odu1Tcm1Iaes(14440),
                    Odu1Tcm2Iaes(14441),
                    Odu1Tcm3Iaes(14442),
                    Odu1Tcm4Iaes(14443),
                    Odu1Tcm5Iaes(14444),
                    Odu1Tcm6Iaes(14445),
                    Odu1Tcm1Biaes(14446),
                    Odu1Tcm2Biaes(14447),
                    Odu1Tcm3Biaes(14448),
                    Odu1Tcm4Biaes(14449),
                    Odu1Tcm5Biaes(14450),
                    Odu1Tcm6Biaes(14451),
                    Odu1Tcm1Bbe(14452),
                    Odu1Tcm1Es(14453),
                    Odu1Tcm1Ses(14454),
                    Odu1Tcm1Uas(14455),
                    Odu1Tcm1Sesr(14456),
                    Odu1Tcm1Bber(14457),
                    Odu1Tcm2Bbe(14458),
                    Odu1Tcm2Es(14459),
                    Odu1Tcm2Ses(14460),
                    Odu1Tcm2Uas(14461),
                    Odu1Tcm2Sesr(14462),
                    Odu1Tcm2Bber(14463),
                    Odu1Tcm3Bbe(14464),
                    Odu1Tcm3Es(14465),
                    Odu1Tcm3Ses(14466),
                    Odu1Tcm3Uas(14467),
                    Odu1Tcm3Sesr(14468),
                    Odu1Tcm3Bber(14469),
                    Odu1Tcm4Bbe(14470),
                    Odu1Tcm4Es(14471),
                    Odu1Tcm4Ses(14472),
                    Odu1Tcm4Uas(14473),
                    Odu1Tcm4Sesr(14474),
                    Odu1Tcm4Bber(14475),
                    Odu1Tcm5Bbe(14476),
                    Odu1Tcm5Es(14477),
                    Odu1Tcm5Ses(14478),
                    Odu1Tcm5Uas(14479),
                    Odu1Tcm5Sesr(14480),
                    Odu1Tcm5Bber(14481),
                    Odu1Tcm6Bbe(14482),
                    Odu1Tcm6Es(14483),
                    Odu1Tcm6Ses(14484),
                    Odu1Tcm6Uas(14485),
                    Odu1Tcm6Sesr(14486),
                    Odu1Tcm6Bber(14487),
                    Odu1Tcm1Febbe(14488),
                    Odu1Tcm1Fees(14489),
                    Odu1Tcm1Feses(14490),
                    Odu1Tcm1Feuas(14491),
                    Odu1Tcm1Fesesr(14492),
                    Odu1Tcm1Febber(14493),
                    Odu1Tcm2Febbe(14494),
                    Odu1Tcm2Fees(14495),
                    Odu1Tcm2Feses(14496),
                    Odu1Tcm2Feuas(14497),
                    Odu1Tcm2Fesesr(14498),
                    Odu1Tcm2Febber(14499),
                    Odu1Tcm3Febbe(14500),
                    Odu1Tcm3Fees(14501),
                    Odu1Tcm3Feses(14502),
                    Odu1Tcm3Feuas(14503),
                    Odu1Tcm3Fesesr(14504),
                    Odu1Tcm3Febber(14505),
                    Odu1Tcm4Febbe(14506),
                    Odu1Tcm4Fees(14507),
                    Odu1Tcm4Feses(14508),
                    Odu1Tcm4Feuas(14509),
                    Odu1Tcm4Fesesr(14510),
                    Odu1Tcm4Febber(14511),
                    Odu1Tcm5Febbe(14512),
                    Odu1Tcm5Fees(14513),
                    Odu1Tcm5Feses(14514),
                    Odu1Tcm5Feuas(14515),
                    Odu1Tcm5Fesesr(14516),
                    Odu1Tcm5Febber(14517),
                    Maxpositivedelay(15103),
                    Minpositivedelay(15104),
                    Avgpositivedelay(15105),
                    Maxnegativedelay(15106),
                    Minnegativedelay(15107),
                    Avgnegativedelay(15108),
                    Maxsumphaseoffset(15671),
                    Minsumphaseoffset(15672),
                    Avgsumphaseoffset(15673),
                    SdiBbe(15913),
                    SdiBber(15914),
                    SdiUas(15916),
                    SdiEs(15917),
                    SdiSes(15918),
                }

        DataPmEventType ::= TEXTUAL-CONVENTION
            STATUS current
            DESCRIPTION 
                "Performance ID."
            SYNTAX INTEGER
                {   
                    pmRXPKT64(101),
                    pmRXPKT65(102),
                    pmRXPKT128(103),
                    pmRXPKT256(104),
                    pmRXPKT512(105),
                    pmRXPKT1024(106),
                    pmTXPKT64(107),
                    pmTXPKT65(108),
                    pmTXPKT128(109),
                    pmTXPKT256(110),
                    pmTXPKT512(111),
                    pmTXPKT1024(112),
                    pmRXUNICAST(113),
                    pmRXMULCAST(114),
                    pmRXBRDCAST(115),
                    pmTXUNICAST(116),
                    pmTXMULCAST(117),
                    pmTXBRDCAST(118),
                    pmRXPAUSE(119),
                    pmTXPAUSE(120),
                    pmETHDROP(121),
                    pmETHUNDER(122),
                    pmETHOVER(123),
                    pmETHFRG(124),
                    pmETHJAB(125),
                    pmRXBGOOD(126),
                    pmTXBGOOD(127),
                    pmRXBBAD(128),
                    pmTXBBAD(129),
                    pmETHCOL(130),
                    pmETHALI(131),
                    pmETHFCS(132),
                    pmETHUNICOL(133),
                    pmETHMULCOL(134),
                    pmETHLATECOL(135),
                    pmETHEXCCOL(136),
                    pmTXDEFFRM(137),
                    pmETHCARERR(138),
                    pmRXPKT1519(139),     
                    pmTXPKT1519(140), 
                    pmRXGOODFULLFRAMESPEED(190),
                    pmTXGOODFULLFRAMESPEED(191),
                    pmRXFULLBGOOD(192),
                    pmTXFULLBGOOD(193),
                    pmRXCTLPKTS(194),
                    pmTXCTLPKTS(195),
                    pmTXETHDROP(196),
                    pmTXETHOVER(197),
                    pmTXPKTS(198),
                    pmTXOCTETS(199),
                    pmRXOCTETS(200),
                    pmRXPKTS(201),
                    pmETHCRCALI(202),
                    pmETHUTILIZ(203),
                    pmFCClientCrcErr(303),
                    pmFCLinkRstCnt(304),
                    pmFCClientRxFrmCntC1(305),
                    pmFCClientRxFrmCntC2(306),
                    pmFCClientRxFrmCntC3(307),
                    pmFCClientRxFrmCntC4(308),
                    pmFCClientRxFrmCntCf(309),
                    pmFCClinetRxFrmCntsum(310),
                    pmFCClientTxFrmCntC1(311),
                    pmFCClientTxFrmCntC2(312),
                    pmFCClientTxFrmCntC3(313),
                    pmFCClientTxFrmCntC4(314),
                    pmFCClientTxFrmCntCf(315),
                    pmFCClientTxFrmCntsum(316),
                    pmFCClientRxByteCntsum(317),
                    pmFCClientTxByteCntsum(318),
                    pmFCClientunsuposcnt(319),
                    pmFCClientOverLongFrmSum(321),
                    pmFCClientTruncatedFrmCntSum(322),
                    pmFCClientCreditZeroCnt(323),
                    pmFCClientTxNOSCnt(325),
                    pmFCClientRxNOSCnt(326),
                    pmFCClientInvld10BCodeCnt(327),
                    pmFCClientRxLRPrimCnt(328),
                    pmFCClientTxLRPrimCnt(329),
                    pmFCClientRxLRRPrimCnt(330),
                    pmFCClientTxLRRPrimCnt(331),
                    pmFCClientRxOLSPrimCnt(332),
                    pmFCClientTxOLSPrimCnt(333),
                    pmFCClientTxUtilization(336),
                    pmFCClientRxUtilization(337),
                    pmFCWsysCrcErrCnt(338),
                    pmFCWsysOverLongFrmSum(340),
                    pmFCWsysTruncatedFrmCntsum(341),
                    pmFCWsysunsuposcnt(342),
                    pmFCWsysLinkDownCnt(344),
                    pmFCWsysTxPausePrimCnt(345),
                    pmFCWsysRxPausePrimCnt(346),
                    pmFCWsysTxResumePrimCnt (347),
                    pmFCWsysRxResumePrimCnt(348),
                    pmFCWsysTxPingPrimCnt(349),
                    pmFCWsysRxPingAckPrimCnt(401),
                    pmFCWsysRxPingPrimCnt(402),
                    pmFCWsysTxPingAckPrimCnt(403),
                    pmMPLSTUNNELFLR(485),
                    pmMPLSTUNNELFL(486),
                    pmMPLSTUNNELFD(487),
                    pmMPLSTUNNELFDV(488),
                    pmATMPWLOSPKTS(493),
                    pmATMPWMISORDERPKTS(494),
                    pmATMPWSNDCELLS(495),
                    pmATMPWRCVCELLS(496),
                    pmATMPWUNKNOWNCELLS(497),
                    pmATMUNI1INCELLS(498),
                    pmATMUNI1OUTCELLS(499),                
                    pmATMCORRECTED_HCSERR(500),
                    pmATMUNCORRECTED_HCSERR(501),
                    pmATMRCVCELLS(502),
                    pmATMRCVIDLECELLS(503),
                    pmATMSNDCELLS(504),
                    pmPORTRXBYTESAVAILABILITY(505),
                    pmPWDROPBYTES(507),
                    pmPWBANDWIDTHUTILISATION(508),
                    pmPWAVAILABILITY(509),
                    pmATMIFINRATEMAX(513),
                    pmATMIFINRATEMIN(514),
                    pmATMIFINRATEAVG(515),
                    pmATMIFOUTRATEMAX(516),
                    pmATMIFOUTRATEMIN(517),
                    pmATMIFOUTRATEAVG(518),
                    pmATMCELLAVAILABILITY(519),
                    pmATMUNI1INRATEMAX(520),
                    pmATMUNI1INRATEMIN(521),
                    pmATMUNI1INRATEAVG(522),
                    pmATMUNI1OUTRATEMAX(523),
                    pmATMUNI1OUTRATEMIN(524),
                    pmATMUNI1OUTRATEAVG(525),
                    pmPORTRXBWUTILIZATION(567),
                    pmPORTTXBWUTILIZATION(568),
                    pmTNLBWUTILISATION(577),
                    pmATMUNI2INCELLS(578),
                    pmATMUNI2OUTCELLS(579),
                    pmATMUNI2INRATEMAX(580),
                    pmATMUNI2INRATEMIN(581),
                    pmATMUNI2INRATEAVG(582),
                    pmATMUNI2OUTRATEMAX(583),
                    pmATMUNI2OUTRATEMIN(584),
                    pmATMUNI2OUTRATEAVG(585),
                    pmCESLOSPKTS(450),
                    pmCESMISORDERPKTS(451),
                    pmCESSTRAYPKTS(452),
                    pmCESMALPKTS(453),
                    pmCESJTRUDR(454),
                    pmCESJTROVR(455),
                    pmTUNNELRCVPKTS(469),
                    pmTUNNELRCVBYTES(470),
                    pmTUNNELSNDPKTS(471),
                    pmTUNNELSNDBYTES(472),
                    pmPWRCVPKTS(473),
                    pmPWRCVBYTES(474),
                    pmPWSNDPKTS(475),
                    pmPWSNDBYTES(476),
                    pmPWDROPPKTS(506),
                    pmCESRXPKTS(532),
                    pmTUNNELREVERSESNDPKTS(586),
                    pmCESTXPKTS(906),
                    pmTUNNELREVERSESNDBYTES(587),
                    pmTUNNELREVERSERCVPKTS(588),
                    pmTUNNELREVERSERCVBYTES(589),
                    pmMPLSPWFLR(590),
                    pmMPLSPWFL(591),
                    pmMPLSPWFD(592),
                    pmMPLSPWFDV(593),
                    pmDSLTRUNKRCVPKTS(594),
                    pmDSLTRUNKSNDPKTS(595),
                    pmDSLTRUNKRCVBYTES(596),
                    pmDSLTRUNKSNDBYTES(597),
                    pmDSLTRUNKRXLOSPKTS(598),
                    pmDSLTRUNKTXLOSPKTS(599),
                    pmTNLREVERSEBW_UTILISATION(600),
                    pmMPLSTUNNEL1WFD(624),        
                    pmMPLSTUNNEL1WFDV(625),
                    pmMPLSPW1WFD(626),        
                    pmMPLSPW1WFDV(627),
                    pmVUNITXUTILIZATION(657),
                    pmVUNIGROUPSNDPKTS(658),
                    pmVUNIGROUPSNDBYTES(659),
                    pmVUNIGROUPRCVPKTS(660),  
                    pmVUNIGROUPRCVBYTES(661),   
                    pmVGROUPTXUTILIZATION(662),
                    pmVUNIQUEUESNDDROPPKTS(663),
                    pmVUNIQUEUESNDDROPBYTES(664),
                    pmVUNIQUEUESNDDROPRATIO(665),
                    pmVUNIGROUPSNDDROPPKTS(666),
                    pmVUNIGROUPSNDDROPBYTES(667),
                    pmVUNIGROUPSNDDROPRATIO(668),
                    pmPWQUEUESNDDROPPKTS(669),
                    pmPWQUEUESNDDROPBYTES(670),
                    pmPWQUEUESNDDROPRATIO(671),
                    pmTNLSNDDROPPKTS(672),
                    pmTNLSNDDROPBYTES(673),
                    pmTNLSNDDROPRATIO(674),
                    pmQOSCARREDRATIO(675),
                    pmTNLREVERSESNDDROPPKTS(676),
                    pmTNLREVERSESNDDROPBYTES(677),
                    pmTNLREVERSESNDDROPRATIO(678),
                    pmVUNISNDDROPPKTS(689),
                    pmVUNISNDDROPBYTES(690),
                    pmVUNISNDDROPRATIO(691),
                    pmTUNNELREVERSERXBPS(698),
                    pmTUNNELREVERSETXBPS(699),
                    pmTUNNELREVERSERXPPS(700),
                    pmTUNNELREVERSETXPPS(701),
                    pmTUNNELRXBPS(702),
                    pmTUNNELTXBPS(703),
                    pmTUNNELRXPPS(704),
                    pmTUNNELTXPPS(705),
                    pmPWRXBPS(706),
                    pmPWTXBPS(707),
                    pmPWRXPPS(708),
                    pmPWTXPPS(709),
                    pmVUNIRXBPS(710),
                    pmVUNITXBPS(711),
                    pmVUNIRXPPS(712),
                    pmVUNITXPPS(713),
                    pmPWQUEUETXBPS(724),
                    pmPWQUEUETXPPS(725),
                    pmETHCFMFLRPRI0(726),    
                    pmETHCFMFLPRI0(727),    
                    pmETHCFMFDPRI0(728),    
                    pmETHCFMFDVPRI0(729),    
                    pmETHCFMFLRPRI1(730),    
                    pmETHCFMFLPRI1(731),    
                    pmETHCFMFDPRI1(732),    
                    pmETHCFMFDVPRI1(733),    
                    pmETHCFMFLRPRI2(734),    
                    pmETHCFMFLPRI2(735),    
                    pmETHCFMFDPRI2(736),    
                    pmETHCFMFDVPRI2(737),    
                    pmETHCFMFLRPRI3(738),    
                    pmETHCFMFLPRI3(739),    
                    pmETHCFMFDPRI3(740),    
                    pmETHCFMFDVPRI3(741),    
                    pmETHCFMFLRPRI4(742),    
                    pmETHCFMFLPRI4(743),    
                    pmETHCFMFDPRI4(744),    
                    pmETHCFMFDVPRI4(745),    
                    pmETHCFMFLRPRI5(746),    
                    pmETHCFMFLPRI5(747),    
                    pmETHCFMFDPRI5(748),    
                    pmETHCFMFDVPRI5(749),    
                    pmETHCFMFLRPRI6(750),    
                    pmETHCFMFLPRI6(751),    
                    pmETHCFMFDPRI6(752),    
                    pmETHCFMFDVPRI6(753),    
                    pmETHCFMFLRPRI7(754),    
                    pmETHCFMFLPRI7(755),    
                    pmETHCFMFDPRI7(756),    
                    pmETHCFMFDVPRI7(757),
                    pmETHCFMLANFLTX(758),
                    pmETHCFMLANFLRRX(759),
                    pmETHCFMLANFLRX(760),
                    pmETHCFMLANFD(761),
                    pmETHCFMLANFDV(762),
                    pmETHCFMLANFPSTX(765),
                    pmETHCFMLANFBPSTX(766),
                    pmETHCFMLANFPSRX(767),
                    pmETHCFMLANFBPSRX(768),
                    pmETHCFMFLRTXMAX(769),
                    pmETHCFMFLRTXMIN(770),
                    pmETHCFMFLRTXAVG(771),
                    pmETHCFMFLRRXMAX(772),
                    pmETHCFMFLRRXMIN(773),
                    pmETHCFMFLRRXAVG(774),
                    pmETHCFMLANFPSTXMAX(775),
                    pmETHCFMLANFPSTXMIN(776),
                    pmETHCFMLANFPSTXAVG(777),
                    pmETHCFMLANFBPSTXMAX(778),
                    pmETHCFMLANFBPSTXMIN(779),
                    pmETHCFMLANFBPSTXAVG(780),
                    pmETHCFMLANFPSRXMAX(781),
                    pmETHCFMLANFPSRXMIN(782),
                    pmETHCFMLANFPSRXAVG(783),
                    pmETHCFMLANFBPSRXMAX(784),
                    pmETHCFMLANFBPSRXMIN(785),
                    pmETHCFMLANFBPSRXAVG(786),
                    pmETHCFMLANFDMAX(787),
                    pmETHCFMLANFDMIN(788),
                    pmETHCFMLANFDAVG(789),
                    pmETHCFMLANFDVMAX(790),
                    pmETHCFMLANFDVMIN(791),
                    pmETHCFMLANFDVAVG(792),
                    pmETHCFMLANFLRTX(799),
                    pmMPLSPWFLN(801),
                    pmMPLSPWFLRN(802),
                    pmMPLSTUNNELFLN(803),
                    pmMPLSTUNNELFLRN(804),
                    pmETHCFMFLRN(805),
                    pmETHCFMFLN(806),
                    pmPORTRXBWUTILIZATIONMIN(839),
                    pmPORTRXBWUTILIZATIONAVG(840),
                    pmPORTRXBWUTILIZATIONMAX(841),
                    pmPORTTXBWUTILIZATIONMIN(842),
                    pmPORTTXBWUTILIZATIONAVG(843),
                    pmPORTTXBWUTILIZATIONMAX(844),
                    pmRXPBAD(944),
                    pmTXPBAD(945),
                    pmRXPGOOD(946),
                    pmTXPGOOD(947),
                    
                    
                    
                    pmVUNIRCVPKTS(465),
                    pmVUNIRCVBYTES(466),
                    pmVUNISNDPKTS(467),
                    pmVUNISNDBYTES(468),
                    pmETHCFMFLR(489),
                    pmETHCFMFL(490),
                    pmETHCFMFD(491),
                    pmETHCFMFDV(492),
                    pmQOSPRIDROPPKTS(510),
                    pmQOSPRIDROPBYTES(511),
                    pmDSCVLANPRIPKTS(638),
                    pmDSCVLANPRIBYTES(639),
                    pmDSSVLANPRIPKTS(640),
                    pmDSSVLANPRIBYTES(641),
                    pmDSDSCPPKTS(642),
                    pmDSDSCPBYTES(643),
                    pmVLANRCVPKTS(644),
                    pmVLANRCVBYTES(645),
                    pmVLANSNDPKTS(646),
                    pmVLANSNDBYTES(647),
                    pmPORTPRISNDPKTS(648),
                    pmPORTPRISNDBYTES(649),
                    pmQOSPORTQUEUEDROPRATIO(654),
                    pmRXBPS(679),
                    pmTXBPS(680),
                    pmRXPPS(681),
                    pmTXPPS(682),
                    pmETHRXTHROUGHPUTMAX(683),
                    pmETHRXTHROUGHPUTMIN(684),
                    pmETHRXTHROUGHPUTAVG(685),
                    pmETHTXTHROUGHPUTMAX(686),
                    pmETHTXTHROUGHPUTMIN(687),
                    pmETHTXTHROUGHPUTAVG(688),
                    pmRXDROPRATIO(692),
                    pmTXDROPRATIO(693),
                    pmVLANRXBPS(714),
                    pmVLANTXBPS(715),
                    pmVLANRXPPS(716),
                    pmVLANTXPPS(717),
                    pmPORTPRITXBPS(722),
                    pmPORTPRITXPPS(723),
                    pmTXDROPPKTS(868),
                    pmRXDROPPKTS(869),
                    pmECMPRSRATIO(941),
                    pmRXBRDCASTRATIO(957),
                    pmTXBRDCASTRATIO(958),
                    pmQOSPORTSTRMRCVMATCHPKTS(614),
                    pmQOSPORTSTRMRCVMATCHBYTES(615),
                    pmQOSPORTSTRMSNDMATCHPKTS(616),
                    pmQOSPORTSTRMSNDMATCHBYTES(617),
                    pmQOSPORTCARMARKEDREDPKTS(618),
                    pmQOSPORTCARMARKEDYELLOWPKTS(620),
                    pmQOSPORTCARMARKEDGREENPKTS(622),
                    pmPORTSTRMSHAPINGDROPPKTS(650),
                    pmPORTSTRMSHAPINGDROPRATIO(652),
                    pmQOSPORTCARMARKEDREDRATIO(653),
                    pmQOSPORTSTRMRXBPS(718),
                    pmQOSPORTSTRMTXBPS(719),
                    pmQOSPORTSTRMRXPPS(720),
                    pmQOSPORTSTRMTXPPS(721),
                    pmQOSSTRMMATCHPKTS(477),
                    pmQOSSTRMMATCHBYTES(478),
                    pmQOSCARGRNPKTS(479),
                    pmQOSCARGRNBYTES(480),
                    pmQOSCARYLWPKTS(481),
                    pmQOSCARYLWBYTES(482),
                    pmQOSCARREDPKTS(483),
                    pmQOSCARREDBYTES(484),
                    pmFLOWRXUTILIZATION(655),

                    pmPORTRXBANDWIDTH(964),
                    pmPORTTXBANDWIDTH(965),
                    pmRXMAXBWUTILIZATIONCAPACITY(966),
                    pmTXMAXBWUTILIZATIONCAPACITY(967),
                    pmPKT64(141),
                    pmPKT65(142),
                    pmPKT128(143),
                    pmPKT256(144),
                    pmPKT512(145),
                    pmPKT1024(146),
                    pmPKT1519(147),
                    pmVCGRXOCTETS(350),
                    pmVCGTXOCTETS(351),
                    pmVCGRXPACKETS(352),
                    pmVCGTXPACKETS(353),
                    pmVCGRXGOODPACKETS(354),
                    pmVCGTXGOODPACKETS(355),
                    pmVCGRXSPEED(356),
                    pmVCGTXSPEED(357),
                    pmRisingAlarm(1),
                    pmFallingAlarm(2),

                }
                    
                    
        ValidflagType ::= TEXTUAL-CONVENTION
            STATUS current
            DESCRIPTION 
                "Valid flag,sorted by ID."
            SYNTAX INTEGER
                {
                    invalid(0),
                    valid(1)
                }
       HKOprDueType ::= TEXTUAL-CONVENTION
            STATUS current
            DESCRIPTION 
                "Hourse Keeping Ext Cont Due Type."
            SYNTAX INTEGER  
                {
                    opr-mntry(65538),
                    opr-conts(65537),
                    rls-mntry(2),
                    rls-conts(1)
                }

                      
       HKOprStateType ::= TEXTUAL-CONVENTION
            STATUS current
            DESCRIPTION 
                "Hourse Keeping Ext Cont Operate State."
            SYNTAX INTEGER
                {
                    rls(0),
                    opr(1)
                }
       HKDefStateType ::= TEXTUAL-CONVENTION
            STATUS current
            DESCRIPTION 
                "Hourse Keeping Def State."
            SYNTAX INTEGER
                {
                    hkNOTONDEFAULT(255),
                    hkDEFAULTOPEN(1),
                    hkDEFAULTCLOSE(0)
                }
      HKEnvAIDType ::= TEXTUAL-CONVENTION
            STATUS current
            DESCRIPTION 
                "Hourse Keeping Env."
            SYNTAX INTEGER
                {
                    env-1(1),
                    env-2(2),
                    env-3(3),
                    env-4(4),
                    env-5(5),
                    env-6(6),
                    env-7(7),
                    env-8(8),
                    env-9(9),
                    env-10(10),
                    env-11(11),
                    env-12(12),
                    env-13(13),
                    env-14(14),
                    env-15(15),
                    env-16(16)
                } 
                
      HKContAIDType ::= TEXTUAL-CONVENTION
            STATUS current
            DESCRIPTION 
                "Hourse Keeping Cont."
            SYNTAX INTEGER
                {
                    cont-1(1),
                    cont-2(2),
                    cont-3(3),
                    cont-4(4),
                    cont-5(5),
                    cont-6(6),
                    cont-7(7),
                    cont-8(8),
                    cont-9(9),
                    cont-10(10),
                    cont-11(11),
                    cont-12(12),
                    cont-13(13),
                    cont-14(14),
                    cont-15(15),
                    cont-16(16)
                }
    ObjType  ::= TEXTUAL-CONVENTION
            STATUS current
            DESCRIPTION 
                "Objtype."
            SYNTAX INTEGER
                {
                    obj-cp-node(7),
                    obj-cp-service(8),
                    obj-cp-lsp(9),
                    obj-cp-cc(10),
                    obj-cp-tel(11),
                    obj-cp-tel-path(12),
                    obj-cp-rsvp-nbr(13),
                    obj-cp-ospf-cl(14),
                    obj-cp-ospf-nbr(15),
                    obj-ne(20),
                    obj-board(21),
                    obj-powerbd(22),
                    obj-sccbd(23),
                    obj-fanbd(24),
                    obj-crossclockbd(25),
                    obj-subcard(26),
                    obj-laser(27),
                    obj-apsgroup(82),
                    obj-tpsgroup(83),
                    obj-synsource(86),
                    obj-port(28),
                    obj-ethport(29),
                    obj-e1port(30),
                    obj-sdhport(31),
                    obj-atmport(32),
                    obj-posport(33),
                    obj-virtualport(35),
                    obj-atmtrunk(36),
                    obj-vc4path(37),
                    obj-vc12path(38),
                    obj-vc3path(39),
                    obj-tunnel(40),
                    obj-pwindex(41),
                    obj-pwofatm(42),
                    obj-pwofces(43),
                    obj-pwofl2vpn(44),
                    obj-atmconnection(45),
                    obj-l2vpnservice(46),
                    obj-vuniofces(47),
                    obj-vuniofl2vpn(48),
                    obj-mep(49),
                    obj-classifier(50),
                    obj-mlpppgroup(51),
                    obj-apsgroup(52),
                    obj-tpsgroup(53),
                    obj-mstpportgroup(54),
                    obj-lag(55),
                    obj-synsource(56),
                    obj-sysclock(57),
                    obj-lpsgroup(58),
                    obj-mepperf(59),
                    obj-port-pri(60),
                    obj-och(61),
                    obj-ason-control-channel(62),
                    obj-ason-lsp(63),
                    obj-ason-node(64),
                    obj-ason-ospf-control-link(65),
                    obj-ason-ospf-neighbor(66),
                    obj-ason-rsvp-neighbor(67),
                    obj-ason-service(68),
                    obj-ason-te-link-och(69),
                    obj-ason-te-link-path(70),
                    obj-ason-te-link(71),       
                    obj-bfd(72),
                    obj-g-shdsl(73),
                    obj-adsl(74),
                    obj-efm(75),
                    obj-new-board(76),
                    obj-new-scc-board(77),
                    obj-new-fan-board(78),
                    obj-new-power-board(79),
                    obj-client-port(80),
                    obj-och-port(81),
                    obj-new-laser(84),
                    obj-edfa(85),
                    obj-osc-path(87),
                    obj-otu1-path(88),
                    obj-otu2-path(89),
                    obj-otu3-path(90),
                    obj-otu5g-path(91),
                    obj-odu1-path(92),
                    obj-odu2-path(93),
                    obj-odu5g-path(94),
                    obj-odu3-path(95),
                    obj-sdh-path(96),
                    obj-new-eth-port(97),
                    obj-eth-path(98),
                    obj-fc-path(99),
                    obj-fec(100),
                    obj-new-port(101),
                    obj-new-ethport(102),
                    obj-new-pppe1(103),
                    obj-new-atmport(104),
                    obj-new-atmtrunk(105),
                    obj-new-och(106),
                    obj-new-port-pri(107),
                    obj-new-e1port(108),
                    obj-atmgroup(109),
                    obj-ifport(110),
                    obj-oduport(111),
                    obj-ifbd(112),
                    obj-odubd(113),
                    obj-group1j1(114),
                    obj-cp-msp(115),
                    obj-cp-uni-tna(116),
                    obj-cp-uni-ip(117),
                    obj-vuniofl3vpn(118),
                    obj-laser-group(119),
                    obj-odu1-tcm1(120),
                    obj-odu1-tcm2(121),
                    obj-odu1-tcm3(122),
                    obj-odu1-tcm4(123),
                    obj-odu1-tcm5(124),
                    obj-odu1-tcm6(125),
                    obj-odu2-tcm1(126),
                    obj-odu2-tcm2(127),
                    obj-odu2-tcm3(128),
                    obj-odu2-tcm4(129),
                    obj-odu2-tcm5(130),
                    obj-odu2-tcm6(131),
                    obj-odu3-tcm1(132),
                    obj-odu3-tcm2(133),
                    obj-odu3-tcm3(134),
                    obj-odu3-tcm4(135),
                    obj-odu3-tcm5(136),
                    obj-odu3-tcm6(137),
                    obj-odu5g-tcm1(138),
                    obj-odu5g-tcm2(139),
                    obj-odu5g-tcm3(140),
                    obj-odu5g-tcm4(141),
                    obj-odu5g-tcm5(142),
                    obj-odu5g-tcm6(143),
                    obj-sdh-optport(144),
                    obj-sdh-au3path(145),
                    obj-sdh-vc12path(146),
                    obj-sdh-vc3path(147),
                    obj-new-rprport(148),
                    obj-new-eth-vcgport(149),
                    obj-new-powerbd(150),
                    obj-new-sccbd(151),
                    obj-new-crossclockbd(152),
                    obj-new-subcard(153),
                    obj-new-sdhport(154),
                    obj-new-virtualport(155),
                    obj-new-vc4path(156),
                    obj-new-vc12path(157),
                    obj-new-vc3path(158),
                    obj-gsp-rip-nbr(159),
                    obj-gsp-ospf-nbr(160),
                    obj-gsp-rsvp-nbr(161),
                    obj-gsp-isis-nbr(162),
                    obj-topsrv(163),
                    obj-l3vpnservice(164),
                    obj-ason-odukspr(165),
                    obj-voa(166),
                    obj-efi(167),
                    obj-odu0-path(168),
                    obj-otu0-path(169),
                    obj-ext-clock-if(170),
                    obj-l3vpn-cls(171),
                    obj-wpid-laser(172),
                    obj-new-ext-clock-if(173),
                    obj-new-sanport(174),
                    obj-pwapsgroup(175),
                    obj-mcsp(177), 
                    obj-lpt(178), 
                    obj-rmsp(187),
                    obj-lmsp(188),
                    obj-otu4-path(189),
                    obj-odu4-path(190),
                    obj-odu4-tcm1(191),
                    obj-odu4-tcm2(192),
                    obj-odu4-tcm3(193),
                    obj-odu4-tcm4(194),
                    obj-odu4-tcm5(195),
                    obj-odu4-tcm6(196),
                    obj-cesacr(197),
                    obj-t1port(198),
                    obj-bgp(199),
                    obj-ldp-peer(200),
                    obj-new-vc11path(201),
                    obj-oduflex-path(202),
                    obj-odu0-tcm1(203),
                    obj-odu0-tcm2(204),
                    obj-odu0-tcm3(205),
                    obj-odu0-tcm4(206),
                    obj-odu0-tcm5(207),
                    obj-odu0-tcm6(208),
                    obj-portflow(209),  
                    obj-vlanofvuni(215),
                    obj-vnniofvuni(216),
                    obj-vunigroup(221),
                    obj-vuniqueue(222),
                    obj-pwqueue(223),
                    obj-shelf(226), 
                    obj-oduflex-tcm1(234),
                    obj-oduflex-tcm2(235),
                    obj-oduflex-tcm3(236),
                    obj-oduflex-tcm4(237),
                    obj-oduflex-tcm5(238),
                    obj-oduflex-tcm6(239),
                    obj-otucn-path(248),
                    obj-oducn-path(249),
                    obj-ochm-port(257),
                    obj-otux5-path(263),
                    obj-odux5-path(264),
                    obj-sncp(279),
                    obj-flex-och(282),
                    obj-laser-lane(283),
                    obj-oducn-tcm6(289),
                    obj-oducn-tcm1(290),
                    obj-oducn-tcm2(291),
                    obj-oducn-tcm3(292),
                    obj-oducn-tcm4(293),
                    obj-oducn-tcm5(294),
                    obj-new-au3path(802),
                    obj-objtype1(888),
                    obj-flexe-group(304),
                    obj-pl-path(34),
                }
                

   
--
-- Node definitions
--


    END

--
-- OPTIX-SONET-TC-MIB.mib
--

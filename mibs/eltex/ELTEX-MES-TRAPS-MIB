ELTEX-MES-TRAPS-MIB DEFINITIONS ::= BEGIN

-- Title:                ELTEX MES-Series Wwitches
--                       Private TRAPS MIB
-- Version:              1.0
-- Date:                 1-Jan-2012

IMPORTS
    NOTIFICATION-TYPE                                   FROM SNMPv2-SMI
    eltMes                                              FROM ELTEX-MES
    rndErrorDesc, rndErrorSeverity                      FROM RADLAN-DEVICEPARAMS-MIB
    rldot1dStpTrapVrblifIndex, rldot1dStpTrapVrblVID    FROM RADLAN-BRIDGEMIBOBJECTS-MIB;

eltMesNotifications MODULE-IDENTITY
                LAST-UPDATED "201207130000Z"
                ORGANIZATION "Eltex Enterprise Co, Ltd."
                CONTACT-INFO
                      "www.eltex.nsk.ru"
                DESCRIPTION
                      "This private MIB module defines Eltex's private notifications"
                REVISION "201207130000Z"
                DESCRIPTION
                      "Initial revision."
        ::= { eltMes 0 }

-- Enterprise-specific traps for Eltex
-- Each enterprise-specific trap has two bound variables describing the exact nature of
-- the trap. rndErrorDesc provides a detailed description of the problem, including the
-- related interface number, board number or any other applicable variable.
-- rndErrorSeverity describes the severity of this problem.

-- Trap template
-- -------------
--    TRAP-TYPE
--       ENTERPRISE  eltMesNotifications
--       VARIABLES   { rndErrorDesc, rndErrorSeverity }
--       DESCRIPTION
--             ""
--       ::=
-- -------------

eltdot1dStpTopologyChange NOTIFICATION-TYPE
	OBJECTS   { rndErrorDesc, rndErrorSeverity, rldot1dStpTrapVrblifIndex, rldot1dStpTrapVrblVID }
	STATUS current
	DESCRIPTION
		"The trap is sent by a bridge when it 
		receives topology change BPDU."
	::= { eltMesNotifications 7 }


eltdot1dStpRootBridgeChange NOTIFICATION-TYPE
    OBJECTS   { rndErrorDesc, rndErrorSeverity, rldot1dStpTrapVrblifIndex, rldot1dStpTrapVrblVID }
    STATUS current
    DESCRIPTION
        "The trap is sent by a bridge when new root bridge is detected." 
    ::= { eltMesNotifications 8 }

eltdot1dStpTcProtectionThresholdReached NOTIFICATION-TYPE
    OBJECTS   { rndErrorDesc, rndErrorSeverity, rldot1dStpTrapVrblVID}
    STATUS current
    DESCRIPTION
        "The trap is sent by a bridge when TC protection feature is enabled
         and TC threshold limit is exceeded." 
    ::= { eltMesNotifications 9 }

END

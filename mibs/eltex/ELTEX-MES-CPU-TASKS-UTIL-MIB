ELTEX-MES-CPU-TASKS-UTIL-MIB DEFINITIONS ::= BEGIN

-- Title:      ELTEX MES Cpu Tasks Util Private
-- Version:    1.0
-- Date:       27 Jul 2016

IMPORTS
    MODULE-IDENTITY,
    OBJECT-TYPE
        FROM SNMPv2-SMI
    TruthValue, 
    DisplayString
        FROM SNMPv2-TC
    eltMesCpuTasksUtilMIB
        FROM ELTEX-MES-MNG-MIB;

eltMesCpuTasksUtilObjects OBJECT IDENTIFIER
    ::= { eltMesCpuTasksUtilMIB 1 }

eltMesCpuTasksUtilConfig OBJECT IDENTIFIER
    ::= { eltMesCpuTasksUtilObjects 1 }

eltMesCpuTasksUtilStatistics OBJECT IDENTIFIER
    ::= { eltMesCpuTasksUtilObjects 2 }

-- ------------------------
-- CPU Tasks Util Enable --
-- ------------------------

eltCpuTasksUtilEnable OBJECT-TYPE
    SYNTAX          TruthValue
    MAX-ACCESS      read-write
    STATUS          current
    DESCRIPTION
        "Enables measurement of the device CPU tasks utilization.
         In order to get real values for eltCpuTasksUtilStatisticsUtilizationDuringLast5Seconds, 
         eltCpuTasksUtilStatisticsUtilizationDuringLastMinute
         and eltCpuTasksUtilStatisticsUtilizationDuringLast5Minutes, 
         the value of this object must be true."
    DEFVAL { true }
    ::= { eltMesCpuTasksUtilConfig 1 }

-- ----------------------------------
-- CPU Tasks Util Statistics Table --
-- ----------------------------------
    
eltCpuTasksUtilStatisticsTable OBJECT-TYPE
    SYNTAX          SEQUENCE OF EltCpuTasksUtilStatisticsEntry
    MAX-ACCESS      not-accessible
    STATUS          current
    DESCRIPTION     "A list of measurement of the device CPU tasks utilization."
    ::= { eltMesCpuTasksUtilStatistics 1 }

eltCpuTasksUtilStatisticsEntry OBJECT-TYPE
    SYNTAX          EltCpuTasksUtilStatisticsEntry
    MAX-ACCESS      not-accessible
    STATUS          current
    DESCRIPTION     "An entry containing measurement of the device CPU tasks utilization."
    INDEX           { eltCpuTasksUtilStatisticsTaskIndex }
    ::= { eltCpuTasksUtilStatisticsTable 1 }

EltCpuTasksUtilStatisticsEntry ::= SEQUENCE {
        eltCpuTasksUtilStatisticsTaskIndex                         INTEGER,
        eltCpuTasksUtilStatisticsTaskName                          DisplayString,
        eltCpuTasksUtilStatisticsUtilizationDuringLast5Seconds     INTEGER,
        eltCpuTasksUtilStatisticsUtilizationDuringLastMinute       INTEGER,
        eltCpuTasksUtilStatisticsUtilizationDuringLast5Minutes     INTEGER
}

eltCpuTasksUtilStatisticsTaskIndex OBJECT-TYPE
    SYNTAX          INTEGER
    MAX-ACCESS      read-only
    STATUS          current
    DESCRIPTION     "Index of the device CPU task."
    ::= { eltCpuTasksUtilStatisticsEntry 1 }

eltCpuTasksUtilStatisticsTaskName OBJECT-TYPE
    SYNTAX          DisplayString
    MAX-ACCESS      read-only
    STATUS          current
    DESCRIPTION     "Name of the device CPU task."
    ::= { eltCpuTasksUtilStatisticsEntry 2 }

eltCpuTasksUtilStatisticsUtilizationDuringLast5Seconds OBJECT-TYPE
    SYNTAX          INTEGER (0..101)
    MAX-ACCESS      read-only
    STATUS          current
    DESCRIPTION
        "Percentage of the device CPU task utilization during last 5 seconds.
         The value 101 is a dummy value, indicating that the CPU tasks utilization was
         not measured (since measurement is disabled or was disabled during last second)."
    ::= { eltCpuTasksUtilStatisticsEntry 3 }

eltCpuTasksUtilStatisticsUtilizationDuringLastMinute OBJECT-TYPE
    SYNTAX          INTEGER (0..101)
    MAX-ACCESS      read-only
    STATUS          current
    DESCRIPTION
        "Percentage of the device CPU task utilization during last minute.
         The value 101 is a dummy value, indicating that the CPU tasks utilization was
         not measured (since measurement is disabled or was disabled during last minute)."
    ::= { eltCpuTasksUtilStatisticsEntry 4 }

eltCpuTasksUtilStatisticsUtilizationDuringLast5Minutes OBJECT-TYPE
    SYNTAX          INTEGER (0..101)
    MAX-ACCESS      read-only
    STATUS          current
    DESCRIPTION
        "Percentage of the device CPU task utilization during the last 5 minutes.
         The value 101 is a dummy value, indicating that the CPU tasks utilization was
         not measured (since measurement is disabled or was disabled during last 5 minutes)."
    ::= { eltCpuTasksUtilStatisticsEntry 5 }

END

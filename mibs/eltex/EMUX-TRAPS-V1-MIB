EMUX-TRAPS-V1-MIB DEFINITIONS ::= BEGIN
	IMPORTS                                 
		e1RecvStatus,
		e1SendStatus,
		tdmAdminStatus,
		tdmLinkStatus,
		emux				FROM EMUX-MIB
		TRAP-TYPE FROM RFC-1215;
		
	e1LinkChangeV1 TRAP-TYPE
	ENTERPRISE emux
--	VARIABLES { e1ChIndex, e1RecvStatus, e1SendStatus}
	VARIABLES { e1RecvStatus, e1SendStatus}
    DESCRIPTION
            "A e1linkChange signifies that the SNMP entity, acting in
            an agent role, has detected that the send or recv status changed" 
    ::= 1

	tdmLinkDownV1 TRAP-TYPE
    ENTERPRISE emux
--    VARIABLES { tdmChIndex, tdmAdminStatus, tdmLinkStatus }
    VARIABLES { tdmAdminStatus, tdmLinkStatus }
    DESCRIPTION
            "A tdmlinkDown signifies that the SNMP entity, acting in
            an agent role, has detected a link down" 
    ::= 2

	tdmLinkUpV1 TRAP-TYPE
    ENTERPRISE emux
--    VARIABLES { tdmChIndex, tdmAdminStatus, tdmLinkStatus }
    VARIABLES { tdmAdminStatus, tdmLinkStatus }
    DESCRIPTION
            " tdmlinkDown signifies that the SNMP entity, acting in
            an agent role, has detected a link up" 
    ::= 3
	
	trapDyingGasp TRAP-TYPE
	ENTERPRISE emux
	VARIABLES { sysObjectID }
	DESCRIPTION "Device is going to die"
	::= 6
	
END

--***************** With RAD Modificaions and additions  **********************
--
--Project:      ATM Forum Voice and Multimedia over ATM Group
--Title:    SNMP based LES Phase 1 MIB  
--Date:             Sept 5-7, 2000
--AAL2 MIB
-- ver 5.06
-- last update  07-February-06 By Smadar Tauber


CPIWF-R-MIB DEFINITIONS ::= BEGIN


      IMPORTS
        RowStatus						       FROM SNMPv2-TC
        MODULE-IDENTITY,
        OBJECT-TYPE, Counter32, Integer32      FROM SNMPv2-SMI ;
--         MODULE-COMPLIANCE, OBJECT-GROUP     FROM SNMPv2-CONF ;
                                

  
        --   **************************************************************   
      
        --  The following OBJECT IDENTIFIER definition should be moved to
        --  some other location, to conform with the statement in RFC 1442
        --  that the MODULE-IDENTITY section must appear immediately after
        --  any IMPORTs or EXPORTs statements.
        --
        --  However, some MIB utilities don't like MODULE-IDENTITY OIDs of
        --  the form { enterprises atmForum(353) ... 1 }.  Separate OBJECT
        --  IDENTIFIER definitions appear to be more widely accepted - so,
        --  in the interests of compatibility, it remains.
        --
        -- ***************************************************************

    
    -- The object identifier subtree for ATM Forum Loop Emulation Service MIBs

--  atmfLoopEmulationService  OBJECT IDENTIFIER ::= {
--      enterprises
--          atmForum(353)
--              atmForumNetworkManagement(5)
--                  10
--  }

      cpIwfMIB MODULE-IDENTITY
      LAST-UPDATED "200008150000Z"
      ORGANIZATION "ATM Forum VMOA Working Group"
      CONTACT-INFO
            "
          The ATM Forum
                        303 Vintage Park Drive
                        Foster City, CA  94404
                        United States of America
                        Tel: 415-578-6860
                        E-mail: info@atmforum.com"
          DESCRIPTION
          "This module defines a portion of the management information
          base (MIB) for managing LES CP-IWFs. It is meant to be used
          in connection with the ILMI/AToM MIB and MIB-II's System Group 
          and RFC 2863 which defines the 'ifTable'"
          REVISION      "200008150000Z"  -- August 15, 2000
          DESCRIPTION
          "This is a draft adopted under RAD MIB."
          ::= { radExperimental 5 }

radExperimental  OBJECT IDENTIFIER  ::= { iso (1) org (3) dod (6) internet (1) private (4) enterprises (1) rad (164) 20} 


cpIwfMIBObjects     OBJECT IDENTIFIER ::= { cpIwfMIB 1 }

    -- The cpIwfMIB Group

    -- Implementation of this group is mandatory for all
    -- systems that implement the LES as defined in af-vmoa-0145.000

-- The cpIwfMIB Group consists of the following:
--  cpIwf Group

--  cpIwfAal2Profile Group
--  cpIwf Pots Port Configuration Table
--  cpIwf ISDN-BRI Port Configuration Table
--  cpIwf DS0 bundle Configuration Table    (RAD addition)

--  cpIwfStats Group (not supported now in RAD)

--  cpIwfAal2Stats Group

-- *****************************************************************  
        --
        --  cpIwf Group                         
        --

cpIwf   OBJECT IDENTIFIER ::= { cpIwfMIBObjects 1 }


-- RAD addition  

cpIwfIfIndex     OBJECT-TYPE	
     SYNTAX      Integer32
     MAX-ACCESS  read-only
     STATUS      current                
     DESCRIPTION        
      "The index of the AAL2 to which this CP-IWF is associated.
       Default value  0 "               
     ::= {cpIwf 1 }

cpIwfVpi        OBJECT-TYPE
     SYNTAX     Integer32
     MAX-ACCESS read-write
     STATUS     current
     DESCRIPTION
      "The VPI of the AAL2 VCC to which this CP-IWF is associated.
       Default value  0 "
     ::= { cpIwf 2  }

cpIwfVci        OBJECT-TYPE
     SYNTAX     Integer32
     MAX-ACCESS read-write
     STATUS     current
     DESCRIPTION
      "The VCI of the AAL2 VCC to which this CP-IWF is associated.
       Default value  40 " 
     ::= { cpIwf 3 }           

cpIwfVccMib     OBJECT-TYPE
     SYNTAX     INTEGER {
                 af-nm-0165(1),
                 rfc2515(2)
                         }
     MAX-ACCESS read-only
     STATUS     current
     DESCRIPTION
     "This object points to the MIB where the VCC configuration
      information can be found. The value of this object should
      be as follows:-
      af-nm-0165 - indicates that the CP-IWF supports ILMI 
       for PVC auto-configuration. And the CO-IWF should apply 
       the index objects, vpi and vci, to the atmfVccTable in
       the ILMI MIB (af-nm-0165.000).

      rfc2515 - indicates that the CP-IWF supports the AToM MIB.
       And the CO-IWF should apply the index objects, vpi and vci,
       to the atmVclTable in the AToM MIB (RFC 2515).
       The CP-IWF shall support one or other of these MIBs for
       holding VCC configuration information.
      Default value is  atmfAutoConfigGroup" 
     ::= { cpIwf 4 }

cpIwfNumPotsPorts  OBJECT-TYPE
     SYNTAX        Integer32
     MAX-ACCESS    read-only
     STATUS        current
     DESCRIPTION       
      "The total number of POTS user ports on the CP-IWF."
     ::= { cpIwf 5 }

cpIwfNumIsdnBriPorts OBJECT-TYPE
     SYNTAX          Integer32
     MAX-ACCESS      read-only
     STATUS          current
     DESCRIPTION
      "The total number of ISDN-BRI user ports on the CP-IWF."
     ::= { cpIwf 6 }

 cpIwfTimingReference OBJECT-TYPE
      SYNTAX    	  INTEGER {
                	   ntr(1),
                	   adaptiveVoice(2),
                	   freeRun(3)
                	           }
      MAX-ACCESS      read-only
      STATUS          current
      DESCRIPTION
       "ntr - network timing reference, voice timing derived from
              the WAN interface.
       adaptiveVoice - voice timing derived from incoming
                       cell rate.
       freeRun - voice timing derived from an internal free
                 running timing source.
      Default value  adaptiveVoice 	 "
      ::= { cpIwf 7 }



 cpIwfPotsPortEncodingSelectionMode OBJECT-TYPE
      SYNTAX      INTEGER {
                   independent(1),
                   master-slave(2)
                          }
      MAX-ACCESS  read-write
      STATUS      current
      DESCRIPTION
      "This objects controls the encoding switching for POTS user
       ports. 
       masterSlave, the profile entry used by the CP-IWF is the same
       as that selected  by the CO-IWF.
	   indepndent - the CP-IWF can select the profile entry used for 
	   transmission independently of the CO-IWF.
       Default value  master-slave "    
      ::= { cpIwf 8 }

 cpIwfIsdnBriPortEncodingSelectionMode OBJECT-TYPE
      SYNTAX     INTEGER {
                  independent(1),
                  master-slave(2)
                         }
      MAX-ACCESS read-write
      STATUS     current
      DESCRIPTION
      "This objects controls the encoding switching for ISDN-BRI user
       ports. 
       masterSlave, the profile entry used by the CP-IWF is the same
       as that selected  by the CO-IWF.
	   indepndent - the CP-IWF can select the profile entry used for 
	   transmission independently of the CO-IWF.
       Default value  independent "    
      ::= { cpIwf 9 }
                                                                           
-- RAD  addition
cpIwfNumDs0Bundles OBJECT-TYPE
     SYNTAX        Integer32
     MAX-ACCESS    read-only
     STATUS        current
     DESCRIPTION
     "The total number of DS0 bundles on the CP-IWF."
     ::= { cpIwf 10 }

-- RAD  addition
cpIwfLineSignaling OBJECT-TYPE
	 SYNTAX  OCTET STRING
     MAX-ACCESS  read-write
     STATUS      current
     DESCRIPTION
      "This object defines the line signal coding for CAS.
       It represents four parameters, by two octet (nibble per parameter
       Bit 7 = MSB, Bit 0 = LSB ) as follows:
       RINGING Code- MSB nibble, default value is 0000	(h'0)
	   NORMAL  Code- 3rd nibble, default value is 0101	(h'5)
       ONHOOK  Code- 2nd nibble, default value is 0101	(h'5)
       OFFHOOK Code- LSB nibble. default value is 1111	(h'F)"
--     (default Octet String Value is 055F) 
     ::= { cpIwf 11 }

--Additional PRI objects copied from April 2002 draft.
	
cpIwfNumIsdnPriPorts OBJECT-TYPE
	SYNTAX		Integer32
	MAX-ACCESS	read-only
	STATUS		current
	DESCRIPTION
		"The total number of ISDN-PRI user ports on the CP-IWF."
	::= { cpIwf 28 }

cpIwfIsdnPriPortEncodingSelectionMode OBJECT-TYPE
	SYNTAX		INTEGER {
				independent(1),
				masterSlave(2)
			}
	MAX-ACCESS	read-write
	STATUS		current
	DESCRIPTION
		"This object controls the encoding switching for ISDN PRI user
		ports.
		masterSlave - the profile entry used by the CP-IWF is the same
		as that selected by the CO-IWF.
		independent - the CP-IWF can select the profile entry used for
		transmission independently of the CO-IWF."
	DEFVAL { masterSlave }
	::= { cpIwf 29 }


cpIwfUpstreamPhysicalBandwidth OBJECT-TYPE
	SYNTAX		Integer32
	MAX-ACCESS	read-write
	STATUS		current
	DESCRIPTION
		"This object defines the new physical bandwidth in the upstream
		direction of the CP-IWF."
	::= { cpIwfMIBObjects 9 }

cpIwfDownstreamPhysicalBandwidth OBJECT-TYPE
	SYNTAX		Integer32
	MAX-ACCESS	read-write
	STATUS		current
	DESCRIPTION
		"This object defines the new physical bandwidth in the downstream
		direction of the CP-IWF."
	::= { cpIwfMIBObjects 10 }


-- *****************************************************************
  
--     cpIwfAal2Profile Group ( comment below Copied from 00 0332 r1)
--
-- *****************************************************************  
--  This group specifies AAL2 CPS and SSCS parameters of operation
--  for the AAL2 VCC which is used by this CP-IWF.These include
--  I.363.2 (CPS), I.366.1 (SSSAR SSCS), I.366.2 9trunking SSCS) and 
--  LES specific CPS parameters.  
--
--  The CO-IWF is responsible for provisioning the AAL2 CPS and SSCS
--  parameters by setting appropriate values in this MIB. In the
--  absence of explicit provisioning of this group, the objects
--  in this group shall take the default values as specified. 
--
--  Furthermore, these objects are read-write, however, it is possible
--  that certain AAL2 parameters may not be supported, e.g. an encoding
--  profile (aal2SscsPredefinedProfileIdentifier). In such cases an 
--  attempt to set a value for an object that is not supported shall
--  result an SNMP response with an error status of badValue(3).
-- 

   
cpIwfAal2Profile 	OBJECT IDENTIFIER ::= { cpIwfMIBObjects 2 }
   
cpIwfAal2ApplicationIdentifier OBJECT-TYPE
    SYNTAX Integer32 
    MAX-ACCESS read-write
    STATUS current
    DESCRIPTION
    "This attribute describes the application identifier, which
    describes the type of signaling used. The value of this object
    should be one of those values given in the administered list of
    AppIDs in section 5 of the ATM Forum document of well-known
    addresses and assigned codes which can be located at 
   	http://www.atmforum.com/pages/aboutatmtech/committees/
   	public_assigned_codes.pdf
    Default value { '0000000A'H }"
    ::= { cpIwfAal2Profile 1 }


cpIwfAal2CpsMaxMultiplexedChannels OBJECT-TYPE
     SYNTAX        Integer32 (1..255)
     MAX-ACCESS    read-write
     STATUS        current
     DESCRIPTION
     "Maximum number of multiplexed channels.
     Default value { 255 }"
     ::= { cpIwfAal2Profile  2 }

cpIwfAal2CpsMaxSDULength OBJECT-TYPE
     SYNTAX       Integer32 (45 | 64) 
     MAX-ACCESS   read-write
     STATUS       current
     DESCRIPTION
     "Maximum CPS-SDU size given in octets.
     Default value { 45 }"
     ::= { cpIwfAal2Profile 3 }

cpIwfAal2CpsCIDLowerLimit OBJECT-TYPE
     SYNTAX       Integer32 (16..255)
     MAX-ACCESS   read-write
     STATUS       current
     DESCRIPTION
     "The minimum value the CID can take for AAL2 bearer channels and
     ISDN D Channels.
     Default value { 16 }"
     ::= {cpIwfAal2Profile 4 } 

cpIwfAal2CpsCIDUpperLimit OBJECT-TYPE
     SYNTAX       Integer32 (16..255)
     MAX-ACCESS   read-write
     STATUS       current
     DESCRIPTION
     "The maximum value the CID can take for AAL2 bearer channels and
	 ISDN D Channels.
	 Default value { 255 }"
     ::= { cpIwfAal2Profile 5 }

cpIwfAal2CpsOptimisation OBJECT-TYPE
     SYNTAX       INTEGER {
                   singleCpsPacketPerCpsPduNoOverlap (1),
                   multipleCpsPacketPerCpsPduWithOverlap (2)
                           }
     MAX-ACCESS   read-write
     STATUS       current
     DESCRIPTION
     "This object refers to the mode of operation of the CPS on the 
	  CP-IWF. The value of this object imposes a restriction on the CPS
	  SDU length and hence must override the value of cpIwfAal2CpsMaxSDULength.
      
      singleCpsPacketPerCpsPduNoOverlap - a single CPS packet is contained 
      within a  CPS-PDU and no overlap can occur into the next CPS PDU. if 
      this option is selected, the Timer_CU is not applicable. Also MAX
      CPS SDU size must be less than or equal to 44 octets.
      
      multipleCpsPacketPerCpsPduWithOverlap - multiple CPS packets are
      contained within a  CPS-PDU and overlap can occur into the next CPS
      PDU. if this option is selected, the Timer_CU is applicable. Also 
      MAX CPS SDU size must be less than or equal to 64 octets.

     Default value { singleCpsPacketPerCpsPduNoOverlap }"
     ::= {cpIwfAal2Profile 6 }


cpIwfAal2SscsFaxModulationTransport OBJECT-TYPE
     SYNTAX       INTEGER {
                   disabled (1),
                   enabled  (2)
                          }
 
     MAX-ACCESS   read-write
     STATUS       current
     DESCRIPTION
     "This specifies whether fax demodulation is enabled or disabled.
     An SNMP Set to enable(2) when Fax Demodulation is not supported
     must result in an SNMP response with error status of badValue(3).
     Default value {disabled}"
     ::= { cpIwfAal2Profile 7 }



cpIwfAal2SscsCasSignalingTransport OBJECT-TYPE
     SYNTAX       INTEGER {
                   disabled (1),
                   enabled  (2)
                           }
     MAX-ACCESS   read-write
     STATUS       current
     DESCRIPTION
     "This attribute describes whether CAS signaling is transport is
      enabled or disabled.
     Default value {disabled}"
     ::= { cpIwfAal2Profile 8 }

cpIwfAal2SscsDtmfDigitPacketTransport  OBJECT-TYPE
     SYNTAX       INTEGER {
                   disabled (1),
                   enabled  (2)
                          }
     MAX-ACCESS   read-write
     STATUS       current
     DESCRIPTION
     "This attribute describes whether DTMF digit packets transport is
      enabled or disabled.
     Default value { disabled }"
    ::= { cpIwfAal2Profile 9 }



cpIwfAal2SscsPcmEncoding OBJECT-TYPE
     SYNTAX       INTEGER {
                   a-law (1),
                   u-law (2)
                          }
     MAX-ACCESS   read-write
     STATUS       current
     DESCRIPTION
      "This attribute describes the type of PCM encoding used.
     Default value { a-law }"
     ::= {cpIwfAal2Profile 10 }


cpIwfAal2SscsMaxSssarSduLength  OBJECT-TYPE
     SYNTAX       Integer32 
     MAX-ACCESS   read-write
     STATUS       current
     DESCRIPTION
     "This is the maximum size that SSSAR_SDU can take as defined in
     ITU  - I.366.1.  This parameter only applies to those AAl2 Channels 
     using I.366.1. SSSAR."
     ::= { cpIwfAal2Profile 11 }


cpIwfAal2SscsPredefinedProfileIdentifier OBJECT-TYPE
     SYNTAX       Integer32 (1..255)
     MAX-ACCESS   read-write 
     STATUS       current
     DESCRIPTION
      "The ITU-T predefined profile: 1..255.
       Default value { 1}
       
       For LA-140 Agent version Greater or equal to 2.0, 
       ATM Forum Identifier for predefined profile are used,
       according to *Loop Emulation Service Using AAL2*
       AF-VMOA-0145.000 Annex A, Table A-1 
       *Identifiers for ATM Forum Predefined Profiles*
        0      Not used 
        1-6    Allocated to af-vtoa-0113.000
        7      PCM-64, ADPCM-32, 44 octet packets, 
               and silence (Table A-2) 
        8      PCM-64, 44 octet packets, 
               and silence (Table A-3) 
        9      PCM-64, 44 octet packets,
               without silence (Table A-4) 
        10     PCM-64 and ADPCM-32, 44 octet packets,
               without silence (Table A-5) 
        11     PCM-64, ADPCM-32, 40 octet packets, 
               without silence (Table A-6) 
        12     PCM-64, ADPCM-32, 40 octet packets, 
               with silence (Table A-7) 
        13-255 Reserved for future ATM Forum assignment" 
   ::= { cpIwfAal2Profile 12 }

cpIwfAal2SscsIeeeOui OBJECT-TYPE
     SYNTAX       Integer32 
     MAX-ACCESS   read-write
     STATUS       current
     DESCRIPTION
     "This attribute contains the IEEE Organizationally Unique
      Identifier (OUI) of the entity that specified the profile
      being used, if other than ITU-T. For example, if the source
      is the ATM Forum, the value of this object is 00A03E. This
      attribute is only meaningful if aal2SccsProfileSource
      has the value 'other'. An SNMP Set on this object to an
      unsupported profile source must result in an SNMP Response with
      error status of badValue(3).
      Default value { '00A03E'h }"
     ::= {  cpIwfAal2Profile  13 }


-- *****************************************************************
--
--  cpIwfPotsPortTable
--          
-- *****************************************************************

cpIwfPotsPortTable OBJECT-TYPE
     SYNTAX       SEQUENCE OF CpIwfPotsPortEntry
     MAX-ACCESS   not-accessible
     STATUS       current
     DESCRIPTION
     "This table contains information on the configuration of the 
      POTS ports on the CP-IWF in addition to the information 
      contained in the ifTable about the physical interfaces to which 
      the CP-IWF POTS ports are peering with currently."         
     ::= { cpIwfMIBObjects 3 }

cpIwfPotsPortEntry OBJECT-TYPE
     SYNTAX       CpIwfPotsPortEntry
     MAX-ACCESS   not-accessible
     STATUS       current
     DESCRIPTION    
     "An entry in the cpIwfPotsPortTable that represents a single
      POTS port."
     INDEX      { cpIwfPotsPortNumber }
     ::= { cpIwfPotsPortTable 1 }

CpIwfPotsPortEntry ::= SEQUENCE {
     cpIwfPotsPortNumber            Integer32,
     cpIwfPotsPortPhysicalPort      Integer32,
     cpIwfPotsPortChannelId         Integer32,
     cpIwfPotsPortTestMode          INTEGER,
     cpIwfPotsPortSignalingMethod   INTEGER,
     cpIwfPotsPortRxBytesPerCell    Integer32,
     cpIwfPotsPortTxBytesPerCell    Integer32,
     cpIwfPotsPortContCheck         INTEGER,
     cpIwfPotsPortStatus            INTEGER
                                }  

cpIwfPotsPortNumber OBJECT-TYPE
     SYNTAX       Integer32
     MAX-ACCESS   not-accessible
     STATUS       current
     DESCRIPTION
     "The POTS port number."
     ::= { cpIwfPotsPortEntry 1 }

cpIwfPotsPortPhysicalPort OBJECT-TYPE
     SYNTAX       Integer32
     MAX-ACCESS   read-write
     STATUS       current
     DESCRIPTION
     "This has the value of the ifIndex of the ifEntry of the physical POTS
      port to which this CP-IWF POTS port is connected. The value of (0) has
      the special meaning that this POTS port is blocked and is not connected
      to any physical port on the LES device"
     ::= { cpIwfPotsPortEntry 2 }

cpIwfPotsPortChannelId OBJECT-TYPE
     SYNTAX       Integer32 (16..255)
     MAX-ACCESS   read-write
     STATUS       current
     DESCRIPTION
     "The CID of the AAL2 connection transporting this port's traffic 
      over the AAL2 VCC.
	  When the cpIwfAal2ApplicationIdentifier indicates the presence of ELCP,
	  this object should not be use for CID allocation and the value of 
	  this object is not applicable. In addition, if an SNMP operation 
	  is attmpted on this object, an SNMP response with error status of
	  badValue (3) should be returned."
     ::= { cpIwfPotsPortEntry 3 }

cpIwfPotsPortTestMode OBJECT-TYPE
     SYNTAX       INTEGER {
                        none (1),
                        codecLoopback (2),
                        aal2Loopback (3)
                          }
     MAX-ACCESS   read-write
     STATUS       current
     DESCRIPTION
     "The value of this object only applies if adminStatus in ifEntry 
      is testing (3)."
     ::= { cpIwfPotsPortEntry 4 }

cpIwfPotsPortSignalingMethod OBJECT-TYPE
     SYNTAX       INTEGER {
                      loopStartNormalBattery(1),
                      loopStartReverseBattery(2),
                      groundStart(3)
                          }
     MAX-ACCESS   read-write
     STATUS       current
     DESCRIPTION
      "The signalling method to use for this user port.
       Default value  loopStart  "
     ::= { cpIwfPotsPortEntry 5 }


--RAD addition V 

cpIwfPotsPortRxBytesPerCell OBJECT-TYPE
     SYNTAX       Integer32  (10..44)  
     MAX-ACCESS   read-write
     STATUS       current
     DESCRIPTION
     "Selects the maximum number of payload bytes to be excepted in 
      a cell in the receive direction. the available range is 10 to 44
      Default value  44 	"
     ::= { cpIwfPotsPortEntry 6 }


--RAD addition V 

cpIwfPotsPortTxBytesPerCell OBJECT-TYPE
     SYNTAX       Integer32  (10..44)    
     MAX-ACCESS   read-write
     STATUS       current
     DESCRIPTION
     "In AAL2, the maximum number of payload bytes that can 
     be inserted in one cell is 44.  
     Padding bytes can be inserted to fill the cell and 
     transmit it immediately. Default value  44 "
     ::= { cpIwfPotsPortEntry 7 }

--RAD addition V 

cpIwfPotsPortContCheck OBJECT-TYPE
     SYNTAX       INTEGER
                   {
                   off-two-way (2),
                   on-source   (3),
                   on-sink     (4),
                   on-two-way  (5),
                   off-sink    (6),
                   off-source  (7)
                   }  
     MAX-ACCESS   read-write
     STATUS       current
     DESCRIPTION
     "Specifies the initial method used for a new connection to perform 
      checks in the ATM network interface. The available selections are:
      off-two-way, on-source, on-sink, on-two-way, off-sink, off-source
      Default value 2 "
     ::= { cpIwfPotsPortEntry 8 }

    
--RAD addition V 

cpIwfPotsPortStatus OBJECT-TYPE
     SYNTAX       INTEGER
                   {
                   busy (2),
                   idle  (3),
                   faulty (4),
				   underTest (5)
                   }  
     MAX-ACCESS   read-only
     STATUS       current
     DESCRIPTION
     "Pots status - Free, Busy, faulty,under test "
     ::= { cpIwfPotsPortEntry 9 }
    


-- *****************************************************************
--
--  cpIwfIsdnBriPortTable
--          
-- *****************************************************************

cpIwfIsdnBriPortTable OBJECT-TYPE
     SYNTAX        SEQUENCE OF CpIwfIsdnBriPortEntry
     MAX-ACCESS    not-accessible
     STATUS        current
     DESCRIPTION
     "This table contains information on the configuration of the 
      ISDN BRI ports on the CP-IWF in addition to the information 
      contained in the ifTable about the physical interfaces to which 
      the CP-IWF ports are peering with currently."
     ::= { cpIwfMIBObjects 4 }

cpIwfIsdnBriPortEntry OBJECT-TYPE
     SYNTAX        CpIwfIsdnBriPortEntry
     MAX-ACCESS    not-accessible
     STATUS        current
     DESCRIPTION 
     "An entry in the cpIwfIsdnBriPortTable that represents a single
      ISDN BRI port."
     INDEX       { cpIwfIsdnBriPortNumber }
     ::= { cpIwfIsdnBriPortTable 1 }

CpIwfIsdnBriPortEntry ::= SEQUENCE {
     cpIwfIsdnBriPortNumber            Integer32,
     cpIwfIsdnBriPortPhysicalPort      Integer32,
     cpIwfIsdnBriPortChannelIdD        Integer32,
     cpIwfIsdnBriPortChannelIdB1       Integer32,
     cpIwfIsdnBriPortChannelIdB2       Integer32,        
     cpIwfIsdnBriPortRxBytesPerCell    Integer32,
     cpIwfIsdnBriPortTxBytesPerCell    Integer32,
     cpIwfIsdnBriPortContCheck         INTEGER,
	 cpIwfIsdnBriPortEchoCanceler	   INTEGER,
	 cpIwfIsdnBriPortL1Status          INTEGER,
	 cpIwfIsdnBriPortDChRxPCMStatus	   INTEGER,
	 cpIwfIsdnBriPortB1ChRxPCMStatus   INTEGER,
	 cpIwfIsdnBriPortB2ChRxPCMStatus   INTEGER,
	 cpIwfIsdnBriPortDChTxPCMStatus	   INTEGER,
	 cpIwfIsdnBriPortB1ChTxPCMStatus   INTEGER,
	 cpIwfIsdnBriPortB2ChTxPCMStatus   INTEGER
                                   }

cpIwfIsdnBriPortNumber OBJECT-TYPE
     SYNTAX       Integer32
     MAX-ACCESS   not-accessible
     STATUS       current
     DESCRIPTION
     "The ISDN BRI port number."
     ::= { cpIwfIsdnBriPortEntry 1 }

cpIwfIsdnBriPortPhysicalPort OBJECT-TYPE
     SYNTAX       Integer32
     MAX-ACCESS   read-write
     STATUS       current
     DESCRIPTION
     "This has the value of the ifIndex of the ifEntry of the physical ISDN BRI
      port to which this CP-IWF ISDN BRI port is connected. The value of (0) has
      the special meaning that this ISDN BRI port is blocked and is not connected 
      to any physical port on the LES device"
     ::= { cpIwfIsdnBriPortEntry 2 }

cpIwfIsdnBriPortChannelIdD OBJECT-TYPE
     SYNTAX       Integer32 (16..255)
     MAX-ACCESS   read-write
     STATUS       current
     DESCRIPTION
     "The CID of the AAL2 connection transporting the D channel of this  
      ISDN BRI port over the AAL2 VCC.
	  When the cpIwfAal2ApplicationIdentifier indicates the presence of ELCP,
	  this object should not be use for CID allocation and the value of 
	  this object is not applicable. In addition, if an SNMP operation 
	  is attmpted on this object, an SNMP response with error status of
	  badValue (3) should be returned."
    ::= { cpIwfIsdnBriPortEntry 3 }

cpIwfIsdnBriPortChannelIdB1 OBJECT-TYPE
     SYNTAX       Integer32 (16..255)
     MAX-ACCESS   read-write
     STATUS       current
     DESCRIPTION
     "The CID of the AAL2 connection transporting the B1 channel of this  
      ISDN BRI port over the AAL2 VCC.
	  When the cpIwfAal2ApplicationIdentifier indicates the presence of ELCP,
	  this object should not be use for CID allocation and the value of 
	  this object is not applicable. In addition, if an SNMP operation 
	  is attmpted on this object, an SNMP response with error status of
	  badValue (3) should be returned."
    ::= { cpIwfIsdnBriPortEntry 4 }

cpIwfIsdnBriPortChannelIdB2 OBJECT-TYPE
     SYNTAX       Integer32 (16..255)
     MAX-ACCESS   read-write
     STATUS       current
     DESCRIPTION
     "The CID of the AAL2 connection transporting the B2 channel of this  
      ISDN BRI port over the AAL2 VCC.
	  When the cpIwfAal2ApplicationIdentifier indicates the presence of ELCP,
	  this object should not be use for CID allocation and the value of 
	  this object is not applicable. In addition, if an SNMP operation 
	  is attmpted on this object, an SNMP response with error status of
	  badValue (3) should be returned."
     ::= { cpIwfIsdnBriPortEntry 5 }




--RAD addition V 

cpIwfIsdnBriPortRxBytesPerCell OBJECT-TYPE
     SYNTAX       Integer32   (10..44)  
     MAX-ACCESS   read-write
     STATUS       current
     DESCRIPTION
     "Selects the maximum number of payload bytes to be excepted in a cell in the 
      receive direction. the available range is 10 to 44
      Default value  44 "
     ::= { cpIwfIsdnBriPortEntry 6 }


--RAD addition V 

cpIwfIsdnBriPortTxBytesPerCell OBJECT-TYPE
     SYNTAX       Integer32     (10..44) 
     MAX-ACCESS   read-write
     STATUS       current
     DESCRIPTION
     "In AAL2, the maximum number of payload bytes that can be inserted 
      in one cell is 44.  Padding bytes can be inserted to fill 
      the cell and transmit it immediately.
      Default value  44 "
     ::= { cpIwfIsdnBriPortEntry 7 }

--RAD addition V 

cpIwfIsdnBriPortContCheck OBJECT-TYPE
     SYNTAX       INTEGER
                   {
                   off-two-way (2),
                   on-source   (3),
                   on-sink     (4),
                   on-two-way  (5),
                   off-sink    (6),
                   off-source  (7)
                   }  
     MAX-ACCESS   read-write
     STATUS       current
     DESCRIPTION
     "Specifies the initial method used for a new connection to perform 
      checks in the ATM network interface. The available selections are:
      off-two-way, on-source, on-sink, on-two-way, off-sink, off-source
      Default value 2 "
     ::= { cpIwfIsdnBriPortEntry 8 }

--RAD addition V 

cpIwfIsdnBriPortEchoCanceler  OBJECT-TYPE
     SYNTAX       INTEGER
                   {
                   notApplicable  (1),
                   b1-Off-B2-Off  (2),
                   b1-Off-B2-On   (3),
				   b1-On-B2-off   (4),
				   b1-On-B2-On	  (5)
				   }  
     MAX-ACCESS   read-write
     STATUS       current
     DESCRIPTION
     "Echo Cancellation activation 
      Default value =  b1-On-B2-On "
     ::= { cpIwfIsdnBriPortEntry 9 }
 							
--RAD addition V 
 
cpIwfIsdnBriPortL1Status    OBJECT-TYPE
     SYNTAX       INTEGER
                   {
                   notApplicable     (1),
                   deactivated       (2),
                   accessActivated   (3),
                   accessDeactivated (4),
                   losLofDeactivated (5),
                   losLofActivated   (6),
                   lostSignal        (7),
                   lostFrame         (8),
                   deactivateST      (9),
                   activateST        (10),
                   sendInfo2         (11),
                   sendInfo4         (12), 
                   frameSlip         (13),
                   loopActivated     (14),
                   loopNotStopped    (15)
                   }  
     MAX-ACCESS   read-only
     STATUS       current
     DESCRIPTION
     "This object indicates the current state
      of Layer 1 of the ISDN port, according to definitions in
      ITU-T Recommendation I-430 11/95, paragraph 6.2"
     ::= { cpIwfIsdnBriPortEntry 10 }     

--RAD addition V 
cpIwfIsdnBriPortDChRxPCMStatus    OBJECT-TYPE
     SYNTAX       INTEGER
                   {
                   notApplicable  (1),
                   close          (2),
				   open           (3)                   
                   }  
     MAX-ACCESS   read-only
     STATUS       current
     DESCRIPTION
     "This object indicates  the state of the 
      D Rx channel of the selected port"
     ::= { cpIwfIsdnBriPortEntry 11 }  	

--RAD addition V 
cpIwfIsdnBriPortB1ChRxPCMStatus  OBJECT-TYPE
     SYNTAX       INTEGER
                   {
                   notApplicable  (1),
                   close          (2),
				   open           (3)                   
                   }  
     MAX-ACCESS   read-only
     STATUS       current
     DESCRIPTION
     "This object indicates  the state of the 
      B1 Rx channel of the selected port"
     ::= { cpIwfIsdnBriPortEntry 12 }  

--RAD addition V 
cpIwfIsdnBriPortB2ChRxPCMStatus  OBJECT-TYPE
     SYNTAX       INTEGER
                   {
                   notApplicable  (1),
                   close          (2),
				   open           (3)                   
                   }  
     MAX-ACCESS   read-only
     STATUS       current
     DESCRIPTION
     "This object indicates  the state of the 
      B2 Rx channel of the selected port"
     ::= { cpIwfIsdnBriPortEntry 13 }  


--RAD addition V 
cpIwfIsdnBriPortDChTxPCMStatus    OBJECT-TYPE
     SYNTAX       INTEGER
                   {
                   notApplicable  (1),
                   close          (2),
				   open           (3)                   
                   }  
     MAX-ACCESS   read-only
     STATUS       current
     DESCRIPTION
     "This object indicates  the state of the 
      D Tx channel of the selected port"
     ::= { cpIwfIsdnBriPortEntry 14 }  	

--RAD addition V 
cpIwfIsdnBriPortB1ChTxPCMStatus  OBJECT-TYPE
     SYNTAX       INTEGER
                   {
                   notApplicable  (1),
                   close          (2),
				   open           (3)                   
                   }  
     MAX-ACCESS   read-only
     STATUS       current
     DESCRIPTION
     "This object indicates  the state of the 
      B1 Tx channel of the selected port"
     ::= { cpIwfIsdnBriPortEntry 15 }  

--RAD addition V 
cpIwfIsdnBriPortB2ChTxPCMStatus  OBJECT-TYPE
     SYNTAX       INTEGER
                   {
                   notApplicable  (1),
                   close          (2),
				   open           (3)                   
                   }  
     MAX-ACCESS   read-only
     STATUS       current
     DESCRIPTION
     "This object indicates  the state of the 
      B2 Tx channel of the selected port"
     ::= { cpIwfIsdnBriPortEntry 16 }  



--RAD addition below (whole table)
-- *****************************************************************
--
--  cpIwfIsdnBriPortStats
--            
-- *****************************************************************


cpIwfIsdnBriPortStatTable OBJECT-TYPE
	SYNTAX		SEQUENCE OF CpIwfIsdnBriPortStatEntry
	MAX-ACCESS	not-accessible
	STATUS		current
	DESCRIPTION
		"This table contains performance statistics pertinent to 
		ISDN BRI channel (B1/B2 or D) or port specified by ifindex"
	::= { cpIwfMIBObjects  18}

cpIwfIsdnBriPortStatEntry OBJECT-TYPE
	SYNTAX		CpIwfIsdnBriPortStatEntry
	MAX-ACCESS	not-accessible
	STATUS		current
	DESCRIPTION	
		"An entry in the cpIwfIsdnBriPortStatsTable that represents
		statistics for a single channel of the ISDN BRI port."
	INDEX { cpIwfIsdnBriPortNumber, cpIwfIsdnBriPortChannel}
	::= { cpIwfIsdnBriPortStatTable 1 }

CpIwfIsdnBriPortStatEntry ::= SEQUENCE 
        {
		cpIwfIsdnBriPortChannel 		   INTEGER,
		cpIwfIsdnBriPortHdlcFrames         Counter32,
		cpIwfIsdnBriPortHdlcErrors    	   Counter32,
		cpIwfIsdnBriPortSStedRxPacket      Counter32,
		cpIwfIsdnBriPortSStedRxCRCErrors   Counter32,
		cpIwfIsdnBriPortSStedRxLenErrors   Counter32,
		cpIwfIsdnBriPortSStedRxErrors	   Counter32,
		cpIwfIsdnBriChAAL2TxCells	       Counter32,
		cpIwfIsdnBriChAAL2RxCells	       Counter32,
		cpIwfIsdnBriChAAL2RxErrors	       Counter32
	    }										  

cpIwfIsdnBriPortChannel  OBJECT-TYPE
     SYNTAX       INTEGER
                   {
                   wholePort   (1),
                   briDchannel (2),
				   channelB1   (3),
				   channelB2   (4)
                   }  
     MAX-ACCESS   not-accessible
     STATUS       current
     DESCRIPTION
     "Identify ISDN BRI specific channel
      (B1,B2 or D) or all port."
     ::= { cpIwfIsdnBriPortStatEntry 1 }

cpIwfIsdnBriPortHdlcFrames OBJECT-TYPE
	SYNTAX		Counter32
	MAX-ACCESS	read-only
	STATUS		current
	DESCRIPTION
		"Total number of HDLC frames received 
		 by the D channel of the selected port."
	::= { cpIwfIsdnBriPortStatEntry 2 }


cpIwfIsdnBriPortHdlcErrors  OBJECT-TYPE
	SYNTAX		Counter32
	MAX-ACCESS	read-only
	STATUS		current
	DESCRIPTION
		"Total number of HDLC frames received
		 by the D channel of the selected port
		 in which errors have been detected"
	::= { cpIwfIsdnBriPortStatEntry 3 }

   	 
cpIwfIsdnBriPortSStedRxPacket  OBJECT-TYPE
	SYNTAX		Counter32
	MAX-ACCESS	read-only
	STATUS		current
	DESCRIPTION
      "Total number of packets handled by the SSTED 
       (Service Specific Transmission Error Detection)
       sublayer, used to carry the LES  
       Embedded Operations Channel (EOC) 
       serving the connections of the selected port"
	::= { cpIwfIsdnBriPortStatEntry 4 }
   
cpIwfIsdnBriPortSStedRxCRCErrors OBJECT-TYPE
	SYNTAX		Counter32
	MAX-ACCESS	read-only
	STATUS		current
	DESCRIPTION
      "Total number of LES Embedded Operations
       Channel (EOC) packets rejected because of CRC
       errors detected at the SSTED sublayer
       (Service Specific Transmission Error Detection)"
::= { cpIwfIsdnBriPortStatEntry 5 }

cpIwfIsdnBriPortSStedRxLenErrors OBJECT-TYPE
	SYNTAX		Counter32
	MAX-ACCESS	read-only
	STATUS		current
	DESCRIPTION
	  "Total number of LES Embedded Operations Channel
       (EOC) packets rejected because of 
       length errors detected at the SSTED sublayer
       (Service Specific Transmission Error Detection)"
 	::= { cpIwfIsdnBriPortStatEntry 6 }

cpIwfIsdnBriPortSStedRxErrors  OBJECT-TYPE
	SYNTAX		Counter32
	MAX-ACCESS	read-only
	STATUS		current
	DESCRIPTION
      "Total number of LES Embedded Operations Channel
       (EOC)  packets rejected because of other
       types of errors detected at the SSTED sublayer.
       (Service Specific Transmission Error Detection)"
 	::= { cpIwfIsdnBriPortStatEntry 7 }
	 
cpIwfIsdnBriChAAL2TxCells OBJECT-TYPE
	SYNTAX		Counter32
	MAX-ACCESS	read-only
	STATUS		current
	DESCRIPTION
       "Total number of AAL2 cells
        transmitted by the ISDN channel 
        indicated by cpIwfIsdnBriPortChannel"
	::= { cpIwfIsdnBriPortStatEntry 8 }
	 
cpIwfIsdnBriChAAL2RxCells OBJECT-TYPE
	SYNTAX		Counter32
	MAX-ACCESS	read-only
	STATUS		current
	DESCRIPTION
       "Total number of AAL2 cells 
        in which errors occurred,
        transmitted by the ISDN channel 
        indicated by cpIwfIsdnBriPortChannel."
	::= { cpIwfIsdnBriPortStatEntry 9 }
	 
	 
cpIwfIsdnBriChAAL2RxErrors   OBJECT-TYPE
	SYNTAX		Counter32
	MAX-ACCESS	read-only
	STATUS		current
	DESCRIPTION
      "Total number of AAL2 cells 
       with errors received through
       the ISDN channel indicated by cpIwfIsdnBriPortChannel"
	::= { cpIwfIsdnBriPortStatEntry 10 }
	 
 
--RAD addition below (whole table)
-- *****************************************************************
--
--  cpIwfDs0BundleTable
--            
-- *****************************************************************

cpIwfDs0BundleTable OBJECT-TYPE
     SYNTAX       SEQUENCE OF CpIwfDs0BundleEntry
     MAX-ACCESS   not-accessible
     STATUS       current
     DESCRIPTION
     "This table contains information on the configuration of the 
      DS0 Bundles  on the CP-IWF in addition to the information 
      contained in the ifTable about the physical interfaces to which 
      the CP-IWF ports are peering with currently."
     ::= { cpIwfMIBObjects 5 }

cpIwfDs0BundleEntry OBJECT-TYPE
     SYNTAX       CpIwfDs0BundleEntry
     MAX-ACCESS   not-accessible
     STATUS       current
     DESCRIPTION    
     "An entry in the cpIwfDs0BundleTable that represents a single
      DS0 Bundle."
     INDEX      { cpIwfDs0BundleNumber }
     ::= { cpIwfDs0BundleTable 1 }

CpIwfDs0BundleEntry ::= SEQUENCE {
     cpIwfDs0BundleNumber            Integer32,
     cpIwfDs0BundleIfIndex	         Integer32,
     cpIwfDs0BundleChannelId         Integer32, 
     cpIwfDs0BundleRxBytesPerCell    Integer32,
     cpIwfDs0BundleTxBytesPerCell    Integer32,
     cpIwfDs0BundleContCheck         INTEGER,
	 cpIwfDs0BundleLineSignaling	 OCTET STRING
                                  } 

cpIwfDs0BundleNumber OBJECT-TYPE
     SYNTAX       Integer32
     MAX-ACCESS   not-accessible
     STATUS       current
     DESCRIPTION
     "The DS0 bundle port number."
     ::= { cpIwfDs0BundleEntry 1 }

                   
cpIwfDs0BundleIfIndex OBJECT-TYPE
     SYNTAX       Integer32
     MAX-ACCESS   read-write
     STATUS       current
     DESCRIPTION
     "This has the value of the ifIndex of the ifEntry of the physical DS0 bundle
      port to which this CP-IWF DS0 bundle port is connected. The value of (0) has
      the special meaning that this DS0 bundle port 
      is blocked and is not connected to any physical port on the LES device"
     ::= { cpIwfDs0BundleEntry 2 }

cpIwfDs0BundleChannelId OBJECT-TYPE
     SYNTAX       Integer32 (16..255)
     MAX-ACCESS   read-write
     STATUS       current
     DESCRIPTION
     "The CID of the AAL2 connection transporting this DS0 bundle  
      port over the AAL2 VCC.
      When the cpIwfAal2ApplicationIdentifier indicates the presence of ELCP,
	  this object should not be use for CID allocation and the value of 
	  this object is not applicable. In addition, if an SNMP operation 
	  is attmpted on this object, an SNMP response with error status of
	  badValue (3) should be returned."
    ::= { cpIwfDs0BundleEntry 3 }


cpIwfDs0BundleRxBytesPerCell OBJECT-TYPE
     SYNTAX       Integer32   (10..44)  
     MAX-ACCESS   read-write
     STATUS       current
     DESCRIPTION
     "Selects the maximum number of payload bytes to be excepted in a cell in the 
      receive direction. the available range is 10 to 44
      Default value  44 	"
     ::= { cpIwfDs0BundleEntry 6 }


cpIwfDs0BundleTxBytesPerCell OBJECT-TYPE
     SYNTAX       Integer32   (10..44)   
     MAX-ACCESS   read-write
     STATUS       current
     DESCRIPTION
     "In AAL2, the maximum number of payload bytes that 
     can be inserted in one cell is 44.  
     Padding bytes can be inserted to fill the cell and 
     transmit it immediately.
     Default value  44 "
     ::= { cpIwfDs0BundleEntry 7 }


cpIwfDs0BundleContCheck OBJECT-TYPE
     SYNTAX       INTEGER
                   {
                   off-two-way (2),
                   on-source   (3),
                   on-sink     (4),
                   on-two-way  (5),
                   off-sink    (6),
                   off-source  (7)
                   }  
     MAX-ACCESS   read-write
     STATUS       current
     DESCRIPTION
     "Specifies the initial method used for a new connection to perform 
      checks in the ATM network interface. The available selections are:
      off-two-way, on-source, on-sink, on-two-way, off-sink, off-source
      Default value 2 "
     ::= { cpIwfDs0BundleEntry 8 }
    
 
cpIwfDs0BundleLineSignaling OBJECT-TYPE
	 SYNTAX  OCTET STRING
     MAX-ACCESS  read-write
     STATUS      current
     DESCRIPTION
      "This object defines the line signal coding for CAS.
       It represents three parameters, by two octet (nibble per parameter
       Bit 7 = MSB, Bit 0 = LSB ) as follows:
       ONHOOK  Code- MSB nibble, default value is 0101	(h'5)
       OFFHOOK Code- 2nd nibble. default value is 1111	(h'F)
       MASK    Code- 3rd nibble, default value is 1111	(h'F)
	   spare   Code- LSB nibble, padded with 0    0000 	(h'0)"
--     (default Octet String Value is 5FF0) 
     ::= { cpIwfDs0BundleEntry 9 }



--RAD addition above (whole table) ^ 

-- *****************************************************************
--
--  cpIwfStats Group
--
-- ****************************************************************

--  No objects under this group as yet              

cpIwfStats    OBJECT IDENTIFIER ::= { cpIwfMIBObjects 6 }

-- ***************************************************************** 
--
--  cpIwfAal2Stats Group
--              
-- ***************************************************************** 

cpIwfAal2Stats      OBJECT IDENTIFIER ::= { cpIwfMIBObjects 7 }

cpIwfAal2StatsCpsInPkts OBJECT-TYPE
     SYNTAX       Counter32
     MAX-ACCESS   read-only
     STATUS       current
     DESCRIPTION
      "Number of CPS packets received"
    ::= { cpIwfAal2Stats 1 }
    
cpIwfAal2StatsCpsOutPkts OBJECT-TYPE
     SYNTAX       Counter32
     MAX-ACCESS   read-only
     STATUS       current
     DESCRIPTION
      "Number of CPS packets transmitted"
     ::= { cpIwfAal2Stats 2 }

cpIwfAal2StatsCpsParityErrors OBJECT-TYPE
     SYNTAX       Counter32
     MAX-ACCESS   read-only
     STATUS       current
     DESCRIPTION
     "Number of CPS PDUs discarded because of incorrect parity 
      value in the STF field.
      Number of errors encountered as specified in Table 6/ ITU I.363.2
      (errnum = 0)"
     ::= { cpIwfAal2Stats 3 }

cpIwfAal2StatsCpsSeqNumErrors OBJECT-TYPE
     SYNTAX       Counter32
     MAX-ACCESS   read-only
     STATUS       current
     DESCRIPTION
     "Number of CPS PDUs received with incorrect sequence number
      in the STF field.
      Number of errors encountered as specified in Table 6/ ITU I.363.2
      (errnum = 1)"
     ::= { cpIwfAal2Stats 4 }


cpIwfAal2StatsCpsOsfErrors OBJECT-TYPE
     SYNTAX       Counter32
     MAX-ACCESS   read-only
     STATUS       current
     DESCRIPTION
     "Number of CPS PDUs discarded because of the incorrect OSF 
      value (>=48) in the STF field.
      Number of errors encountered as specified in Table 6/ ITU I.363.2
      (errnum = 3)"
     ::= { cpIwfAal2Stats 5 }


cpIwfAal2StatsCpsHecErrors OBJECT-TYPE
    SYNTAX        Counter32
    MAX-ACCESS    read-only
    STATUS        current
    DESCRIPTION
    "Number of CPS Packets received with the HEC code overlapping a CPS
     PDU boundary.
      Number of errors encountered as specified in Table 6/ ITU I.363.2
      (errnum = 4)"
    ::= { cpIwfAal2Stats 6 }
											   
cpIwfAal2StatsCpsUuiErrors OBJECT-TYPE
     SYNTAX       Counter32
     MAX-ACCESS   read-only
     STATUS       current
     DESCRIPTION
     "Number of CPS packets received with the incorrect UUI value
      (28 or 29 which are reserved for future).
      Number of errors encountered as specified in Table 6/ ITU I.363.2
      (errnum = 8)"
     ::= { cpIwfAal2Stats 7 }

cpIwfAal2StatsCpsCidErrors OBJECT-TYPE
     SYNTAX       Counter32
     MAX-ACCESS   read-only
     STATUS       current
     DESCRIPTION
     "Number of CPS packets received with the incorrect CID value
      (a CID value that is not associated with any SAP).
      Number of errors encountered as specified in Table 6/ ITU I.363.2
      (errnum = 9)"
      ::= { cpIwfAal2Stats 8 } 


 -- V5 PSTN Group

cpIwfV5Pstn OBJECT IDENTIFIER ::= { cpIwfMIBObjects 8 }


-- V5 PSTN scalar objects.

cpIwfV5PstnGeneral 	OBJECT IDENTIFIER ::= { cpIwfV5Pstn 1 }


cpIwfCallCollisionPriority OBJECT-TYPE
     SYNTAX INTEGER {
                    originatingCallPriority (2),
                    terminatingCallPriority (3)
     }
     MAX-ACCESS read-write
     STATUS current
     DESCRIPTION
      "This indicates whether, in the case of colliding V5 PSTN
      ESTABLISH messages, the originating or the terminating call shall
      prevail."
     ::= { cpIwfV5PstnGeneral 1 }

cpIwfNationalProfile OBJECT-TYPE
     SYNTAX INTEGER
                   {
                   nationalProfile1 (2),
                   nationalProfile2 (3),
                   nationalProfile3 (4),
                   nationalProfile4 (5),
                   nationalProfile5 (6),
                   nationalprofile6 (7),
				   nationalProfile7 (8),
				   nationalProfile8 (9),
				   nationalProfile9 (10),
				   nationalProfile10 (11)
				   }  
 
     MAX-ACCESS read-write
     STATUS current
     DESCRIPTION
	 "This object indicates which country is selected.
	  Each nationalProfile is accosiated with a country.
	  The specific country name was not specified to allow 
	  maximum  flexibility.

	  The nationalProfile# selected, points to a range 
	  of up to 10 Cadence-Ringing Types (cpIwfCadencedRingingType)
	  e.g  nationalProfile1 enable ringing types 0-9,
	  nationalProfile2 enable ringing types 10-19, and so on
	  for ringing cadence table see cpIwfCadencedRingingTypeTable."
     ::= {cpIwfV5PstnGeneral 2}


cpIwfMeterPulseFrequency OBJECT-TYPE
     SYNTAX Integer32 (12000 | 16000)
     MAX-ACCESS read-write
     STATUS current
     DESCRIPTION
     "This is the frequency of the meter pulses generated by the
     CP-IWF. The allowed values are 12 kHz and 16 kHz."
     ::= {cpIwfV5PstnGeneral 3}

cpIwfOffHookMinTime OBJECT-TYPE
     SYNTAX Integer32
     MAX-ACCESS read-write
     STATUS current
     DESCRIPTION
      "A time period in milliseconds. The loop closed periods shorter
      than this are filtered out while the analog line is in on hook
      state."
     ::= {cpIwfV5PstnGeneral 4}

cpIwfOnHookMinTime OBJECT-TYPE
     SYNTAX Integer32
     MAX-ACCESS read-write
     STATUS current
     DESCRIPTION
      "A time period in milliseconds. A transition from off hook to on
      hook state is reported by the CP-IWF, if a loop open period longer
      than, or equal to, the onHookMinTime is detected.
      NOTE: The provisioned onHookMinTime is overrideable via CCS."
     ::= {cpIwfV5PstnGeneral 5}

cpIwfRegisterRecallMinTime OBJECT-TYPE
     SYNTAX Integer32
     MAX-ACCESS read-write
     STATUS current
     DESCRIPTION
      "A time period in milliseconds. Register recall detection is
      enabled while the registerRecallMinTime is less than the
      onHookMinTime.
      If then the CP-IWF detects a loop open period longer than the
      registerRecallMinTime but shorter than the onHookMinTime,
      it shall report a register recall line signal to the CO-IWF via
      CCS."
     ::= {cpIwfV5PstnGeneral 6}

cpIwfDigitMinBreakPeriod	 OBJECT-TYPE
     SYNTAX Integer32
     MAX-ACCESS read-write
     STATUS current
     DESCRIPTION
      "Minimum Break (onhook)  period (in milliseconds) of digit pulse."
     ::= {cpIwfV5PstnGeneral 7}


cpIwfDigitMaxBreakPeriod	 OBJECT-TYPE
     SYNTAX Integer32
     MAX-ACCESS read-write
     STATUS current
     DESCRIPTION
      "Maximum  Break (onhook) period (in milliseconds) of digit pulse."
     ::= {cpIwfV5PstnGeneral 8}


cpIwfDigitMinMakePeriod OBJECT-TYPE
     SYNTAX Integer32
     MAX-ACCESS read-write
     STATUS current
     DESCRIPTION
      "Minimum make (offhook) period (in milliseconds) of digit pulse."
     ::= {cpIwfV5PstnGeneral 9}

cpIwfDigitMaxMakePeriod OBJECT-TYPE
     SYNTAX Integer32
     MAX-ACCESS read-write
     STATUS current
     DESCRIPTION
      "Minimum make (offhook) period (in milliseconds) of digit pulse."
     ::= {cpIwfV5PstnGeneral 10}


cpIwfInterDigitTime OBJECT-TYPE
     SYNTAX Integer32
     MAX-ACCESS read-write
     STATUS current
     DESCRIPTION
      "period (in milliseconds) between one digit 
      to another in a sequence of digits pulses."
     ::= {cpIwfV5PstnGeneral 11}
  

cpIwfCadencedRingingTypeTable OBJECT-TYPE
     SYNTAX SEQUENCE OF CpIwfCadencedRingingTypeEntry
     MAX-ACCESS not-accessible
     STATUS current
     DESCRIPTION
      "This table is used to map a cadenced ringing type identifier to
      an actual ringing cadence. The index to the table is the value of
      the Cadenced-ringing type sub-element contained in the cadenced
      ringing information element in the V5 PSTN messages.

      Refer also to cpIwfNationalProfile above, which is used to select
	  group of Cadenced-ringing types for a specific country"
     ::= { cpIwfV5Pstn 2 }


cpIwfCadencedRingingTypeEntry OBJECT-TYPE
     SYNTAX CpIwfCadencedRingingTypeEntry
     MAX-ACCESS not-accessible
     STATUS current
     DESCRIPTION
      "An entry in the cpIwfCadencedRingingTypeTable that represents a
      single ringing cycle. This entry contains a list of integers that
      represent consecutive ON/OFF periods (in milliseconds). The
      integer cadencedRingingNumPeriods indicates how many
      cadencedRingingOnPeriod/cadencedRingingOffPeriod pairs in this row
      have a meaning. 
      The maximum value of cadencedRingingNumPeriods is 10.
      There are two special ringing cadences: no ringing and continous
      ringing. The former is indicated by setting
      cadencedRingingNumPeriods == 1 and cadencedRingingOnPeriod1 == 0.

      The latter is indicated by setting cadencedRingingNumPeriods == 1
      and cadencedRingingOffPeriod1 == 0.
      Otherwise a valid cadencedRingingOnPeriod or
      cadencedRingingOffPeriod must always be greater than zero."
     INDEX { cpIwfCadencedRingingType }
     ::= { cpIwfCadencedRingingTypeTable 1 }

CpIwfCadencedRingingTypeEntry ::= SEQUENCE {
     cpIwfCadencedRingingType            Integer32,
     cpIwfCadencedRingingNumPeriods      Integer32,
     cpIwfCadencedRingingOnPeriod1       Integer32,
     cpIwfCadencedRingingOffPeriod1      Integer32,
     cpIwfCadencedRingingOnPeriod2       Integer32,
     cpIwfCadencedRingingOffPeriod2      Integer32,
     cpIwfCadencedRingingOnPeriod3       Integer32,
     cpIwfCadencedRingingOffPeriod3      Integer32,
     cpIwfCadencedRingingOnPeriod4       Integer32,
     cpIwfCadencedRingingOffPeriod4      Integer32,
     cpIwfCadencedRingingOnPeriod5       Integer32,
     cpIwfCadencedRingingOffPeriod5      Integer32,
     cpIwfCadencedRingingOnPeriod6       Integer32,
     cpIwfCadencedRingingOffPeriod6      Integer32,
     cpIwfCadencedRingingOnPeriod7       Integer32,
     cpIwfCadencedRingingOffPeriod7      Integer32,
     cpIwfCadencedRingingOnPeriod8       Integer32,
     cpIwfCadencedRingingOffPeriod8      Integer32,
     cpIwfCadencedRingingOnPeriod9       Integer32,
     cpIwfCadencedRingingOffPeriod9      Integer32,
     cpIwfCadencedRingingOnPeriod10      Integer32,
     cpIwfCadencedRingingOffPeriod10     Integer32,
     cpIwfCadencedRingingTypeRowStatus   RowStatus
     }

cpIwfCadencedRingingType OBJECT-TYPE
     SYNTAX Integer32 (0..127)
     MAX-ACCESS not-accessible
     STATUS current
     DESCRIPTION
      "Index to the cpIwfCadencedRingingTypeTable.
	 
	   Refer also to cpIwfNationalProfile above, which is used to select
       group of Cadenced-ringing types for a specific country"
     ::= { cpIwfCadencedRingingTypeEntry 1 }

cpIwfCadencedRingingNumPeriods OBJECT-TYPE
     SYNTAX Integer32 (1..10)
     MAX-ACCESS read-create
     STATUS current
     DESCRIPTION
      "Number of onPeriod/offPeriod pairs in the ringing cadence."
     ::= { cpIwfCadencedRingingTypeEntry 2 }

cpIwfCadencedRingingOnPeriod1 OBJECT-TYPE
     SYNTAX Integer32
     MAX-ACCESS read-create
     STATUS current
     DESCRIPTION
      "The duration of the first on period, in milliseconds, in the
      ringing cycle."
	  DEFVAL {1000}
     ::= { cpIwfCadencedRingingTypeEntry 3 }

cpIwfCadencedRingingOffPeriod1 OBJECT-TYPE
     SYNTAX Integer32
     MAX-ACCESS read-create
     STATUS current
     DESCRIPTION
      "The duration of the first off period, in milliseconds, in the
       ringing cycle."
	  DEFVAL {1000}
     ::= { cpIwfCadencedRingingTypeEntry 4 }

cpIwfCadencedRingingOnPeriod2 OBJECT-TYPE
     SYNTAX Integer32
     MAX-ACCESS read-create
     STATUS current
     DESCRIPTION
      "The duration of the second on period, in milliseconds, in the
      ringing cycle."
	  DEFVAL {1000}
     ::= { cpIwfCadencedRingingTypeEntry 5 }


cpIwfCadencedRingingOffPeriod2 OBJECT-TYPE
     SYNTAX Integer32
     MAX-ACCESS read-create
     STATUS current
     DESCRIPTION
      "The duration of the second off period, in milliseconds, in the
      ringing cycle."
	  DEFVAL {1000}
     ::= { cpIwfCadencedRingingTypeEntry 6 }

cpIwfCadencedRingingOnPeriod3 OBJECT-TYPE
     SYNTAX Integer32
     MAX-ACCESS read-create
     STATUS current
     DESCRIPTION
      "The duration of the third on period, in milliseconds, in the
      ringing cycle."
	  DEFVAL {1000}
     ::= { cpIwfCadencedRingingTypeEntry 7 }

cpIwfCadencedRingingOffPeriod3 OBJECT-TYPE
     SYNTAX Integer32
     MAX-ACCESS read-create
     STATUS current
     DESCRIPTION
      "The duration of the third off period, in milliseconds, in the
      ringing cycle."
	  DEFVAL {1000}
     ::= { cpIwfCadencedRingingTypeEntry 8 }

cpIwfCadencedRingingOnPeriod4 OBJECT-TYPE
     SYNTAX Integer32
     MAX-ACCESS read-create
     STATUS current
     DESCRIPTION
     "The duration of the fourth on period, in milliseconds, in the
      ringing cycle."
	  DEFVAL {1000}
     ::= { cpIwfCadencedRingingTypeEntry 9 }

cpIwfCadencedRingingOffPeriod4 OBJECT-TYPE
     SYNTAX Integer32
     MAX-ACCESS read-create
     STATUS current
     DESCRIPTION
      "The duration of the fourth off period, in milliseconds, in the
       ringing cycle."
	  DEFVAL {1000}
     ::= { cpIwfCadencedRingingTypeEntry 10 }

cpIwfCadencedRingingOnPeriod5 OBJECT-TYPE
     SYNTAX Integer32
     MAX-ACCESS read-create
     STATUS current
     DESCRIPTION
      "The duration of the fifth on period, in milliseconds, in the
       ringing cycle."
	  DEFVAL {1000}
     ::= { cpIwfCadencedRingingTypeEntry 11 }

cpIwfCadencedRingingOffPeriod5 OBJECT-TYPE
     SYNTAX Integer32
     MAX-ACCESS read-create
     STATUS current
     DESCRIPTION
      "The duration of the fifth off period, in milliseconds, in the
       ringing cycle."
	  DEFVAL {1000}
     ::= { cpIwfCadencedRingingTypeEntry 12 }

cpIwfCadencedRingingOnPeriod6 OBJECT-TYPE
     SYNTAX Integer32
     MAX-ACCESS read-create
     STATUS current
     DESCRIPTION
     "The duration of the sixth on period, in milliseconds, in the
     ringing cycle."
	  DEFVAL {1000}
     ::= { cpIwfCadencedRingingTypeEntry 13 }

 cpIwfCadencedRingingOffPeriod6 OBJECT-TYPE
     SYNTAX Integer32
     MAX-ACCESS read-create
     STATUS current
     DESCRIPTION
     "The duration of the sixth off period, in milliseconds, in the
     ringing cycle."
	  DEFVAL {1000}
     ::= { cpIwfCadencedRingingTypeEntry 14 }

cpIwfCadencedRingingOnPeriod7 OBJECT-TYPE
     SYNTAX Integer32
     MAX-ACCESS read-create
     STATUS current
     DESCRIPTION
     "The duration of the seventh on period, in milliseconds, in the
     ringing cycle."
	  DEFVAL {1000}
     ::= { cpIwfCadencedRingingTypeEntry 15 }

cpIwfCadencedRingingOffPeriod7 OBJECT-TYPE
     SYNTAX Integer32
     MAX-ACCESS read-create
     STATUS current
     DESCRIPTION
     "The duration of the seventh off period, in milliseconds, in the
     ringing cycle."
	  DEFVAL {1000}
     ::= { cpIwfCadencedRingingTypeEntry 16 }

cpIwfCadencedRingingOnPeriod8 OBJECT-TYPE
     SYNTAX Integer32
     MAX-ACCESS read-create
     STATUS current
     DESCRIPTION
     "The duration of the eighth on period, in milliseconds, in the
     ringing cycle."
	  DEFVAL {1000}
     ::= { cpIwfCadencedRingingTypeEntry 17 }

cpIwfCadencedRingingOffPeriod8 OBJECT-TYPE
     SYNTAX Integer32
     MAX-ACCESS read-create
     STATUS current
     DESCRIPTION
     "The duration of the eighth off period, in milliseconds, in the
     ringing cycle."
	  DEFVAL {1000}
     ::= { cpIwfCadencedRingingTypeEntry 18 }
     	  
cpIwfCadencedRingingOnPeriod9 OBJECT-TYPE
     SYNTAX Integer32
     MAX-ACCESS read-create
     STATUS current
     DESCRIPTION
     "The duration of the ninth on period, in milliseconds, in the
     ringing cycle."
	  DEFVAL {1000}
     ::= { cpIwfCadencedRingingTypeEntry 19 }

cpIwfCadencedRingingOffPeriod9 OBJECT-TYPE
     SYNTAX Integer32
     MAX-ACCESS read-create
     STATUS current
     DESCRIPTION
     "The duration of the ninth off period, in milliseconds, in the
     ringing cycle."
	  DEFVAL {1000}
     ::= { cpIwfCadencedRingingTypeEntry 20 }

cpIwfCadencedRingingOnPeriod10 OBJECT-TYPE
     SYNTAX Integer32
     MAX-ACCESS read-create
     STATUS current
     DESCRIPTION
     "The duration of the tenth on period, in milliseconds, in the
     ringing cycle."
	  DEFVAL {1000}
     ::= { cpIwfCadencedRingingTypeEntry 21 }

cpIwfCadencedRingingOffPeriod10 OBJECT-TYPE
     SYNTAX Integer32
     MAX-ACCESS read-create
     STATUS current
     DESCRIPTION
     "The duration of the tenth off period, in milliseconds, in the
     ringing cycle."
	  DEFVAL {1000}
     ::= { cpIwfCadencedRingingTypeEntry 22 }

  cpIwfCadencedRingingTypeRowStatus OBJECT-TYPE
       SYNTAX RowStatus
       MAX-ACCESS read-create
       STATUS current
       DESCRIPTION
       "Status of one row in this table."
       ::= { cpIwfCadencedRingingTypeEntry 23 }

cpIwfPulseDurationTypeTable OBJECT-TYPE
     SYNTAX SEQUENCE OF CpIwfPulseDurationTypeEntry
     MAX-ACCESS not-accessible
     STATUS current
     DESCRIPTION
     "This table contains the mapping from a Pulse duration type
     identifier to the actual pulse pattern. This table is indexed by
     both the value of the Pulse type sub-element and the the value of
     the Pulse duration type sub-element within the Pulsed-signal
     information element contained in a V5 PSTN message."
     ::= { cpIwfV5Pstn 3 }

 cpIwfPulseDurationTypeEntry OBJECT-TYPE
     SYNTAX CpIwfPulseDurationTypeEntry
     MAX-ACCESS not-accessible
     STATUS current
     DESCRIPTION
     "An entry in the cpIwfPulseDurationTypeTable that represents a
     pulse pattern. This entry contains a list of integers that
     represent consecutive ON/OFF pulsing periods (in milliseconds).
     The integer pulseDurationNumPeriods indicates how many 
     onPeriod/offPeriod pairs in this row have a meaning. The maximum
     value of pulseDurationNumPeriods is 5."
     INDEX { cpIwfPulseType, cpIwfPulseDurationType }
     ::= { cpIwfPulseDurationTypeTable 1 }

 CpIwfPulseDurationTypeEntry ::= SEQUENCE {
     cpIwfPulseType                       Integer32,
     cpIwfPulseDurationType               Integer32,
     cpIwfPulseDurationNumPeriods         Integer32,
     cpIwfPulseDurationOnPeriod1          Integer32,
     cpIwfPulseDurationOffPeriod1         Integer32,
     cpIwfPulseDurationOnPeriod2          Integer32,
     cpIwfPulseDurationOffPeriod2         Integer32,
     cpIwfPulseDurationOnPeriod3          Integer32,
     cpIwfPulseDurationOffPeriod3         Integer32,
     cpIwfPulseDurationOnPeriod4          Integer32,
     cpIwfPulseDurationOffPeriod4         Integer32,
     cpIwfPulseDurationOnPeriod5          Integer32,
     cpIwfPulseDurationOffPeriod5         Integer32,
     cpIwfPulseDurationTypeRowStatus      RowStatus
     }

 cpIwfPulseType OBJECT-TYPE
     SYNTAX Integer32 (0..127)
     MAX-ACCESS not-accessible
     STATUS current
     DESCRIPTION
     "First index to the cpIwfPulseDurationTypeTable."
     ::= { cpIwfPulseDurationTypeEntry 1 }

 cpIwfPulseDurationType OBJECT-TYPE
     SYNTAX Integer32 (0..31)
     MAX-ACCESS not-accessible
     STATUS current
     DESCRIPTION
     "Second index to the cpIwfPulseDurationTypeTable."
     ::= { cpIwfPulseDurationTypeEntry 2 }

 cpIwfPulseDurationNumPeriods OBJECT-TYPE
     SYNTAX Integer32 (1..5)
     MAX-ACCESS read-create
     STATUS current
     DESCRIPTION
     "Number of onPeriod/offPeriod pairs in the pulse pattern."
     ::= { cpIwfPulseDurationTypeEntry 3 }

 cpIwfPulseDurationOnPeriod1 OBJECT-TYPE
     SYNTAX Integer32 (0..5000)
     MAX-ACCESS read-create
     STATUS current
     DESCRIPTION
     "The duration of the first on period, in milliseconds, in the
     pulse pattern."
	 DEFVAL {1000}
     ::= { cpIwfPulseDurationTypeEntry 4 }

 cpIwfPulseDurationOffPeriod1 OBJECT-TYPE
     SYNTAX Integer32 (0..5000)
     MAX-ACCESS read-create
     STATUS current
     DESCRIPTION
     "The duration of the first off period, in milliseconds, 
     in the pulse pattern."
	 DEFVAL {1000}
     ::= { cpIwfPulseDurationTypeEntry 5 }

cpIwfPulseDurationOnPeriod2 OBJECT-TYPE
     SYNTAX Integer32 (0..5000)
     MAX-ACCESS read-create
     STATUS current
     DESCRIPTION
     "The duration of the second on period, in milliseconds, in the
     pulse pattern."
	 DEFVAL {1000}
     ::= { cpIwfPulseDurationTypeEntry 6 }

cpIwfPulseDurationOffPeriod2 OBJECT-TYPE
     SYNTAX Integer32 (0..5000)
     MAX-ACCESS read-create
     STATUS current
     DESCRIPTION
     "The duration of the second off period, in milliseconds, in the
     pulse pattern."
	 DEFVAL {1000}
     ::= { cpIwfPulseDurationTypeEntry 7 }

cpIwfPulseDurationOnPeriod3 OBJECT-TYPE
     SYNTAX Integer32 (0..5000)
     MAX-ACCESS read-create
     STATUS current
     DESCRIPTION
     "The duration of the third on period, in milliseconds, in the
     pulse pattern."
	 DEFVAL {1000}
     ::= { cpIwfPulseDurationTypeEntry 8 }

cpIwfPulseDurationOffPeriod3 OBJECT-TYPE
     SYNTAX Integer32 (0..5000)
     MAX-ACCESS read-create
     STATUS current
     DESCRIPTION
     "The duration of the third off period, in milliseconds, in the
     pulse pattern."
	 DEFVAL {1000}
     ::= { cpIwfPulseDurationTypeEntry 9 }

cpIwfPulseDurationOnPeriod4 OBJECT-TYPE
     SYNTAX Integer32 (0..5000)
     MAX-ACCESS read-create
     STATUS current
     DESCRIPTION
     "The duration of the fourth on period, in milliseconds, in the
     pulse pattern."
	 DEFVAL {1000}
     ::= { cpIwfPulseDurationTypeEntry 10 }

cpIwfPulseDurationOffPeriod4 OBJECT-TYPE
     SYNTAX Integer32 (0..5000)
     MAX-ACCESS read-create
     STATUS current
     DESCRIPTION
     "The duration of the fourth off period, in milliseconds, in the
     pulse pattern."
	 DEFVAL {1000}
     ::= { cpIwfPulseDurationTypeEntry 11 }

cpIwfPulseDurationOnPeriod5 OBJECT-TYPE  
     SYNTAX Integer32 (0..5000)
     MAX-ACCESS read-create
     STATUS current
     DESCRIPTION
     "The duration of the fifth on period, in milliseconds, in the
     pulse pattern."
	 DEFVAL {1000}
     ::= { cpIwfPulseDurationTypeEntry 12 }

cpIwfPulseDurationOffPeriod5 OBJECT-TYPE
     SYNTAX Integer32 (0..5000)
     MAX-ACCESS read-create
     STATUS current
     DESCRIPTION
     "The duration of the fifth off period, in milliseconds, in the
     pulse pattern."
	 DEFVAL {1000}
     ::= { cpIwfPulseDurationTypeEntry 13 }

 cpIwfPulseDurationTypeRowStatus OBJECT-TYPE
      SYNTAX RowStatus
      MAX-ACCESS read-create
      STATUS current
      DESCRIPTION
      "Status of one row in this table."
      ::= { cpIwfPulseDurationTypeEntry 14 }

cpIwfDurationTypeTable OBJECT-TYPE
     SYNTAX SEQUENCE OF CpIwfDurationTypeEntry
     MAX-ACCESS not-accessible
     STATUS current
     DESCRIPTION
     "This table contains the mapping from the Duration type identifier
     to an actual period of time (in milliseconds). This table is
     indexed by both the value of the Signal sub-element and the value
     of the Duration type sub-element within in the Recognition-time
     information element contained in a V5 PSTN message."
     ::= { cpIwfV5Pstn 4 }

cpIwfDurationTypeEntry OBJECT-TYPE
     SYNTAX CpIwfDurationTypeEntry
     MAX-ACCESS not-accessible
     STATUS current
     DESCRIPTION
     "An entry in the cpIwfDurationTypeTable that specifies a time
     interval in milliseconds."
     INDEX { cpIwfSignal, cpIwfDurationType }
     ::= { cpIwfDurationTypeTable 1 }

CpIwfDurationTypeEntry ::= SEQUENCE {
     cpIwfSignal                 Integer32,
     cpIwfDurationType           Integer32,
     cpIwfDuration               Integer32,
     cpIwfDurationTypeRowStatus  RowStatus
     }

cpIwfSignal OBJECT-TYPE
     SYNTAX Integer32 (0..127)
     MAX-ACCESS not-accessible
     STATUS current
     DESCRIPTION
     "First index to the cpIwfDurationTypeTable."
     ::= { cpIwfDurationTypeEntry 1 }

cpIwfDurationType OBJECT-TYPE
     SYNTAX Integer32 (0..63)
     MAX-ACCESS not-accessible
     STATUS current
     DESCRIPTION
     "Second index to the cpIwfDurationTypeTable."
     ::= { cpIwfDurationTypeEntry 2 }

cpIwfDuration OBJECT-TYPE
     SYNTAX Integer32
     MAX-ACCESS read-create
     STATUS current
     DESCRIPTION
     "A time period expressed in milliseconds."
     ::= { cpIwfDurationTypeEntry 3 }

 cpIwfDurationTypeRowStatus OBJECT-TYPE
      SYNTAX RowStatus
      MAX-ACCESS read-create
      STATUS current
      DESCRIPTION
      "Status of one row in this table."
      ::= { cpIwfDurationTypeEntry 4 }

cpIwfRateTypeTable OBJECT-TYPE
     SYNTAX SEQUENCE OF CpIwfRateTypeEntry
     MAX-ACCESS not-accessible
     STATUS current
     DESCRIPTION
     "This table contains the mapping from a Rate type identifier to
      the actual pulse generation frequency in the CP-IWF. The index to
      the table is the value of the Rate type sub-element contained in
      the Enable-metering information element in the V5 PSTN messages."
     ::= { cpIwfV5Pstn 5 }

cpIwfRateTypeEntry OBJECT-TYPE
     SYNTAX CpIwfRateTypeEntry
     MAX-ACCESS not-accessible
     STATUS current
     DESCRIPTION
     "An entry in the cpIwfRateTypeTable that contains the rate at
      which the metering pulses are generated. The rate is expressed as
      pulses per hour."
     INDEX { cpIwfRateType }
     ::= { cpIwfRateTypeTable 1 }

CpIwfRateTypeEntry ::= SEQUENCE {
     cpIwfRateType            Integer32,
     cpIwfRate                Integer32,
     cpIwfRateTypeRowStatus   RowStatus
     }

cpIwfRateType OBJECT-TYPE
     SYNTAX Integer32 (1..127)
     MAX-ACCESS not-accessible
     STATUS current
     DESCRIPTION
     "Index to the cpIwfRateTypeTable.
      NOTE: Value zero is invalid, as [EN 300 324-1] assigns a special
      meaning for that."
     ::= { cpIwfRateTypeEntry 1 }

cpIwfRate OBJECT-TYPE
     SYNTAX Integer32
     MAX-ACCESS read-create
     STATUS current
     DESCRIPTION
     "The rate at which CP-IWF generates pulses to the analog line,
      expressed as pulses per hour."
     ::= { cpIwfRateTypeEntry 2 }

 cpIwfRateTypeRowStatus OBJECT-TYPE
      SYNTAX RowStatus
      MAX-ACCESS read-create
      STATUS current
      DESCRIPTION
      "Status of one row in this table."
      ::= { cpIwfRateTypeEntry 3 }
 
cpIwfAttenuationValueTable OBJECT-TYPE
     SYNTAX SEQUENCE OF CpIwfAttenuationValueEntry
     MAX-ACCESS not-accessible
     STATUS current
     DESCRIPTION
     "This table contains the mapping from a Attenuation value
     identifier, contained in the Enable-metering information element,
     to the actual attenuation applied by the CP-IWF."
     ::= { cpIwfV5Pstn 6 }

cpIwfAttenuationValueEntry OBJECT-TYPE
     SYNTAX CpIwfAttenuationValueEntry
     MAX-ACCESS not-accessible
     STATUS current
     DESCRIPTION
     "An entry in the cpIwfAttenuationValueTable. The attenuation is
     expressed as decibels."
     INDEX { cpIwfAttenuationValue }
     ::= { cpIwfAttenuationValueTable 1 }

     CpIwfAttenuationValueEntry ::= SEQUENCE {
     cpIwfAttenuationValue              Integer32,
     cpIwfAttenuation                   INTEGER,
     cpIwfAttenuationValueRowStatus     RowStatus,
	 cpIwfTxAttenuation                 INTEGER
     }

cpIwfAttenuationValue OBJECT-TYPE
     SYNTAX Integer32 (0..127)
     MAX-ACCESS not-accessible
     STATUS current
     DESCRIPTION								
     "Index to the cpIwfAttenuationValueTable."
     ::= { cpIwfAttenuationValueEntry 1 }

cpIwfAttenuation OBJECT-TYPE
     SYNTAX INTEGER
	 {
	 neg10dB (2),
	 neg8dB	 (3),
	 neg6dB  (4),
	 neg4dB	 (5),
	 neg2dB	 (6),
	 zerodB	 (7),
	 pos2dB  (8),
	 pos4dB	 (9), 
	 pos5dB  (10)
	 }
     MAX-ACCESS read-create
     STATUS current
     DESCRIPTION
     "The Rx attenuation, in decibels, (e.g neg10db= -10dB) corresponding 
     to the value of an Attenuation value sub-element inside the 
     Enable-metering information element."
     ::= { cpIwfAttenuationValueEntry 2 }

cpIwfAttenuationValueRowStatus OBJECT-TYPE
      SYNTAX RowStatus
      MAX-ACCESS read-create
      STATUS current
      DESCRIPTION
      "Status of one row in this table."
      ::= { cpIwfAttenuationValueEntry 3 }

cpIwfTxAttenuation OBJECT-TYPE
     SYNTAX INTEGER
	 {
	 neg10dB (2),
	 neg8dB	 (3),
	 neg6dB  (4),
	 neg4dB	 (5),
	 neg2dB	 (6),
	 zerodB	 (7),
	 pos2dB  (8),
	 pos4dB	 (9), 
	 pos5dB  (10)
	 }
     MAX-ACCESS read-create
     STATUS current
     DESCRIPTION
     "The Tx attenuation, in decibels, (e.g neg10db= -10dB) corresponding 
     to the value of an Attenuation value sub-element inside the 
     Enable-metering information element."
     ::= { cpIwfAttenuationValueEntry 4 }

-- ------------------------------------------------------------- --
-- PRI tables were copied from CPIWF-MIB draft dated April -2002
--
--
--  cpIwfIsdnPriPortTable
--

cpIwfIsdnPriPortTable OBJECT-TYPE
	SYNTAX		SEQUENCE OF CpIwfIsdnPriPortEntry
	MAX-ACCESS	not-accessible
	STATUS		current
	DESCRIPTION
		"This table contains information on the configuration of the 
		ISDN PRI ports on the CP-IWF in addition to the information 
		contained in the ifTable about the physical interfaces to which 
		the CP-IWF ports are peering with currently."
	::= { cpIwfMIBObjects 13 }

cpIwfIsdnPriPortEntry OBJECT-TYPE
	SYNTAX		CpIwfIsdnPriPortEntry
	MAX-ACCESS	not-accessible
	STATUS		current
	DESCRIPTION	
		"An entry in the cpIwfIsdnPriPortTable that represents a single
		ISDN PRI port."
	INDEX		{ isdnPriPortNumber }
	::= { cpIwfIsdnPriPortTable 1 }

CpIwfIsdnPriPortEntry ::= SEQUENCE {
		isdnPriPortNumber		   Integer32,
		isdnPriPhysicalPort		   Integer32,
		isdnPriNumBChannels		   Integer32,
        isdnPriDAal2ChannelId	   INTEGER,
		isdnPriPortLabel		   OCTET STRING,
		isdnPriPortTestType		   INTEGER,
		isdnPriPortChannelsStatus  OCTET STRING
	}

isdnPriPortNumber OBJECT-TYPE
	SYNTAX		Integer32
	MAX-ACCESS	not-accessible
	STATUS		current
	DESCRIPTION
		" The number identifying the ISDN PRI user port on the CP-IWF."
	::= { cpIwfIsdnPriPortEntry 1 }

isdnPriPhysicalPort OBJECT-TYPE
	SYNTAX		Integer32
	MAX-ACCESS	read-write
	STATUS		current
	DESCRIPTION
		"This has the value of the ifIndex of the ifEntry of the physical
		ISDN PRI port to which this CP-IWF ISDN PRI port is connected. The
		value of (0) has the special meaning that this ISDN PRI port is
		not connected to any physical port on the LES device."
	::= { cpIwfIsdnPriPortEntry 2 }

isdnPriNumBChannels OBJECT-TYPE
	SYNTAX		Integer32
	MAX-ACCESS	read-only
	STATUS		current
	DESCRIPTION
		"Maximum number of B channels supported by this ISDN PRI port."
	::= { cpIwfIsdnPriPortEntry 3 }

isdnPriDAal2ChannelId OBJECT-TYPE
	SYNTAX		INTEGER (16..255)
	MAX-ACCESS	read-write
	STATUS		current
	DESCRIPTION
		"The CID of the AAL2 connection transporting the D channel of this
		ISDN PRI port over the AAL2 VCC. The default value of this object 
        is determined by the formula defined in revision 1 of af-vmoa-0145 
        section 4.4.2.
		When the aal2ApplicationIdentifier indicates the presence of ELCP,
		this object should not be used for CID allocation and the value of
		this object is not applicable.  In addition, if an SNMP operation
		is attempted on this object, an SNMP response with error status of
		badValue (3) should be returned."
	::= { cpIwfIsdnPriPortEntry 4 }

isdnPriPortLabel OBJECT-TYPE
	SYNTAX		OCTET STRING (SIZE(0..32))
	MAX-ACCESS	read-write
	STATUS		current
	DESCRIPTION
	"Label assigned by service provider to identify this CP-IWF port."
	::= { cpIwfIsdnPriPortEntry 5 }

isdnPriPortTestType OBJECT-TYPE
	SYNTAX		INTEGER {
				physicalPortLoopback (1),
				dChannelPhysicalPortLoopback (2),
				dChannelAal2Loopback (3)
			}
	MAX-ACCESS	read-write
	STATUS		current
	DESCRIPTION
		"This object is used to specify the type of test to run for
         the ISDN-PRI D channel or all channels. There are no results 
         stored locally for a loopback test. 
         Loopback of the whole ISDN-PRI physical user port is supported where all 
         the D and B channels are looped back simultaneously, along 
         with individual loopbackof the D channel.
         AAL2 Loopback is also supported on the D channel. 
         
         In order to run these tests, the CO-IWF must first set the value 
         of this object appropriate to	the test that needs to be run. 
         The CO-IWF should then set the value of ifAdminStatus 
         in the corresponding ifEntry to 'testing'.
		 The CO-IWF should verify that the test is in progress by checking
		 that the value of ifOperStatus in the corresponding ifEntry is
		 equal to 'testing'. Once testing is complete the CO-IWF must set
         the ifAdminStatus to a value other than 'testing'. 
         Note that the LES device must not allow a CO-IWF to manipulate
		 the ifAdminStatus of physical user ports that do not belong to
		 its managed CP-IWF."
	::= { cpIwfIsdnPriPortEntry 6 }

isdnPriPortChannelsStatus      OBJECT-TYPE
    SYNTAX OCTET STRING (SIZE(15))
    MAX-ACCESS read-write
    STATUS  current
        DESCRIPTION
        "This object is used to reflect the desired state and echo canceler
         usage for ALL 30  ISDN PRI B Channels. 
         The actual state of each B channel  is given by isdnPriBChannelOperStatus. 
          Each channel is represented by 1 octet. 
          Channel 1  is represented by 1st octet, 
          Channel 30 is represented by octet #30. 
          Bits order 01234567...
                     00000000 - down
                     00000001 - up
                     00000010 - shuttingDown 
                     00000011 - testing 
                     00000100 - up with echo canceler
                     00000101 - testing with echo canceler
          'down'-  all existing calls on the channel are cleared immediately. 
          'shuttingDown' - no further calls shall be accepted  - either incoming or 
                           outgoing on the B channel. Once any call on the B Channel 
                           has benn cleared, the value of this object moves to 'down'."
::= { cpIwfIsdnPriPortEntry 7 }

--  cpIwfIsdnPriBChannelTable
--

cpIwfIsdnPriBChannelTable OBJECT-TYPE
  	SYNTAX SEQUENCE OF CpIwfIsdnPriBChannelEntry
	MAX-ACCESS	not-accessible
	STATUS		current
	DESCRIPTION
	"This table contains information on the configuration of the 
	ISDN PRI B channels for each PRI port. 
	The number of entries is given by the value of isdnPriNumBChannels. "
	::= { cpIwfMIBObjects  14}
           
cpIwfIsdnPriBChannelEntry OBJECT-TYPE
	SYNTAX		CpIwfIsdnPriBChannelEntry
	MAX-ACCESS	not-accessible
	STATUS		current
	DESCRIPTION	
    "An entry in the cpIwfIsdnPriBChannelTable 
    that represents a single ISDN PRI B channel."
	INDEX {isdnPriPortNumber, isdnPriBChannelNumber }
	::= { cpIwfIsdnPriBChannelTable 1 }

CpIwfIsdnPriBChannelEntry ::= SEQUENCE {
		isdnPriBChannelNumber       Integer32,
		isdnPriBAal2ChannelId	    INTEGER,
		isdnPriBChannelAdminStatus  INTEGER,
		isdnPriBChannelOperStatus   INTEGER,
		isdnPriBChannelLabel	    OCTET STRING,
		isdnPriBChannelTestType	    INTEGER,
		isdnPriBChannelEchoCanceler INTEGER
	}

isdnPriBChannelNumber OBJECT-TYPE
	SYNTAX		Integer32
	MAX-ACCESS	not-accessible
	STATUS		current
	DESCRIPTION
    "The number identifying the ISDN PRI B channel on the CP-IWF."
	::= { cpIwfIsdnPriBChannelEntry 1 }

isdnPriBAal2ChannelId OBJECT-TYPE
	SYNTAX		INTEGER (16..255)
	MAX-ACCESS	read-write
	STATUS		current
	DESCRIPTION
    "The CID of the AAL2 connection transporting this B channel 
    over the AAL2 VCC. The default value of this object is determined 
    by the formula defined in revision 1 of af-vmoa-0145 section 4.4.2.
	When the aal2ApplicationIdentifier indicates the presence of ELCP,
	this object should not be used for CID allocation and the value of
	this object is not applicable.  In addition, if an SNMP operation
	is attempted on this object, an SNMP response with error status of 
	badValue (3) should be returned."
	::= { cpIwfIsdnPriBChannelEntry 2 }

isdnPriBChannelAdminStatus OBJECT-TYPE
	SYNTAX INTEGER {
                up (1),
                down (2),
                shuttingDown (3),
                testing (4)
		        	}
	MAX-ACCESS	read-write
	STATUS		current
	DESCRIPTION
    "This object is used to reflect the desired state of the 
    ISDN PRI B Channel. The actual state of the B channel 
    is given by isdnPriBChannelOperStatus. 
    When this object is set to 'down', all existing calls on the 
    B channel are cleared immediately. 
    If this object is set to 'shuttingDown', 
    no further calls shall be accepted either incoming or 
    outgoing on the B channel. Once any call on the B Channel 
    has cleared gracefully  the value of this object moves to 'down'."
	::= { cpIwfIsdnPriBChannelEntry 3 }

isdnPriBChannelOperStatus OBJECT-TYPE
	SYNTAX		INTEGER {
				up (1),
				down (2),
				testing (3)
			}
	MAX-ACCESS	read-only
	STATUS		current
	DESCRIPTION
	"Provides the current operational status of the B channel."
	::= { cpIwfIsdnPriBChannelEntry 4 }

isdnPriBChannelLabel OBJECT-TYPE
	SYNTAX		OCTET STRING (SIZE(0..32))
	MAX-ACCESS	read-write
	STATUS		current
	DESCRIPTION
	"Label assigned by service provider to identify this B channel.
    For example, may be used to hold Directory Number."
	::= { cpIwfIsdnPriBChannelEntry 5 }

isdnPriBChannelTestType OBJECT-TYPE
	SYNTAX		INTEGER {
				bChannelPhysicalPortLoopback (1),
				bChannelAal2Loopback (2)
			}
	MAX-ACCESS	read-write
	STATUS		current
	DESCRIPTION
	"This object is used to specify the type of test to run for
     the ISDN-PRI B channel. There are no results stored locally 
     for a loopback test. Loopback of the individual B channels 
     is supported. AAL2 Loopback is also supported on the D channel.
     In order to run these tests, the CO-IWF must first set the value 
     of this object appropriate to the test that needs to be run. 
     The CO-IWF should then set the value of isdnPriBChannelAdminStatus 
     to 'testing'.	 The CO-IWF should verify that the test is in progress 
     by checking that the value of isdnPriBChannelOperStatus 
     is	equal to 'testing'. Once testing is complete the CO-IWF must 
     set the isdnPriBChannelAdminStatus to a value other than 'testing'."
	::= { cpIwfIsdnPriBChannelEntry 6 }


isdnPriBChannelEchoCanceler	 OBJECT-TYPE
      SYNTAX  INTEGER
       {
       notApplicable (1),
       off           (2),
       on            (3)
       }
      MAX-ACCESS  read-write
      STATUS  current
      DESCRIPTION
      "Echo canceler activation.
       notApplicable - for channels with 
       isdnPriBChannelAdminStatus = down."
	::= { cpIwfIsdnPriBChannelEntry 7 }


-- =======================================================
--  cpIwfIsdnPriBChannelStatsTable - 
--  copied from CPIWF-MIB draft dated April -2002
--  with 1st three objects:
--	  cpIwfIsdnPriPortBChannelActiveSeconds
--	  cpIwfIsdnPriPortBChannelFillerOctets	
--	  cpIwfIsdnPriPortBChannelDroppedOctets


cpIwfIsdnPriBChannelStatsTable OBJECT-TYPE
  	SYNTAX SEQUENCE OF CpIwfIsdnPriBChannelStatsEntry
	MAX-ACCESS	not-accessible
	STATUS		current
	DESCRIPTION
    "This table contains performance statistics
     pertinent to ISDN PRI B Channels. 
     The number of entries is given by the value of 
     isdnPriNumBChannels multiplied by the number of
     ISDN PRI ports. "
	::= { cpIwfMIBObjects 15 }

cpIwfIsdnPriBChannelStatsEntry OBJECT-TYPE
	SYNTAX		CpIwfIsdnPriBChannelStatsEntry
	MAX-ACCESS	not-accessible
	STATUS		current
	DESCRIPTION	
    "An entry in the cpIwfIsdnPriBChannelStatsTable 
    that represents a single ISDN PRI B channel."
	INDEX { isdnPriPortNumber, isdnPriBChannelNumber }
	::= { cpIwfIsdnPriBChannelStatsTable 1 }

CpIwfIsdnPriBChannelStatsEntry ::= SEQUENCE {
		cpIwfIsdnPriPortBChannelActiveSeconds	Counter32,
		cpIwfIsdnPriPortBChannelFillerOctets	Counter32,
		cpIwfIsdnPriPortBChannelDroppedOctets	Counter32,
		cpIwfIsdnPriPortBChannelAal2TxCells	    Counter32,
		cpIwfIsdnPriPortBChannelAal2RxCells	    Counter32
	}

cpIwfIsdnPriPortBChannelActiveSeconds OBJECT-TYPE
	SYNTAX		Counter32
	MAX-ACCESS	read-only
	STATUS		current
	DESCRIPTION
		"Total length of time the AAL2 channel associated with this
		port/channel has been active, in seconds."
	::= { cpIwfIsdnPriBChannelStatsEntry 1 }

cpIwfIsdnPriPortBChannelFillerOctets OBJECT-TYPE
	SYNTAX		Counter32
	MAX-ACCESS	read-only
	STATUS		current
	DESCRIPTION
		"Total number of PCM filler octets injected into active media
		stream on this port/channel due to playout buffer underflow."
	::= { cpIwfIsdnPriBChannelStatsEntry 2 }

cpIwfIsdnPriPortBChannelDroppedOctets OBJECT-TYPE
	SYNTAX		Counter32
	MAX-ACCESS	read-only
	STATUS		current
	DESCRIPTION
		"Total number of PCM payload octets dropped due to buffer overflow
		on this port/channel.  Octets that are dropped because they
		arrived late, and which have already been substituted by filler
		PCM octets, shall not be counted."
	::= { cpIwfIsdnPriBChannelStatsEntry 3 }

-- RAD additon
										  
cpIwfIsdnPriPortBChannelAal2TxCells	OBJECT-TYPE
	SYNTAX		Counter32
	MAX-ACCESS	read-only
	STATUS		current
	DESCRIPTION
	"Total number of AAL2 cells
     transmitted by the ISDN PRI B channel 
     indicated by isdnPriBChannelNumber."
	::= { cpIwfIsdnPriBChannelStatsEntry 4 }

-- RAD additon

cpIwfIsdnPriPortBChannelAal2RxCells	OBJECT-TYPE
	SYNTAX		Counter32
	MAX-ACCESS	read-only
	STATUS		current
	DESCRIPTION
    "Total number of AAL2 cells
     received by the ISDN PRI B channel 
     indicated by isdnPriBChannelNumber."
	::= { cpIwfIsdnPriBChannelStatsEntry 5 }



-- Rad addition - New Table, dedicated for D channels statistics
   
   
cpIwfIsdnPriDChannelStatsTable OBJECT-TYPE
  	SYNTAX SEQUENCE OF CpIwfIsdnPriDChannelStatsEntry
	MAX-ACCESS	not-accessible
	STATUS		current
	DESCRIPTION
    "This table contains performance statistics
     pertinent to ISDN PRI D Channels. 
     The number of entries is given by the number of
     ISDN PRI ports."
	::= { cpIwfMIBObjects 17 }

cpIwfIsdnPriDChannelStatsEntry OBJECT-TYPE
	SYNTAX		CpIwfIsdnPriDChannelStatsEntry
	MAX-ACCESS	not-accessible
	STATUS		current
	DESCRIPTION	
    "An entry in the cpIwfIsdnPriDChannelStatsTable 
    that represents a single ISDN PRI D channel."
	INDEX { isdnPriPortNumber}
	::= { cpIwfIsdnPriDChannelStatsTable 1 }

CpIwfIsdnPriDChannelStatsEntry ::= SEQUENCE {
   		cpIwfIsdnPriPortDChannelActiveSeconds	Counter32,
  		cpIwfIsdnPriPortDChannelFillerOctets	Counter32,
 		cpIwfIsdnPriPortDChannelDroppedOctets	Counter32,
		cpIwfIsdnPriPortDChannelAal2TxCells	    Counter32,
		cpIwfIsdnPriPortDChannelAal2RxCells	    Counter32,
		cpIwfIsdnPriPortDChannelHdlcTxCells	    Counter32,
		cpIwfIsdnPriPortDChannelHdlcRxCells	    Counter32,
		cpIwfIsdnPriPortDChannelSstedTxCells	Counter32,
		cpIwfIsdnPriPortDChannelSstedRxCells	Counter32
	    }

cpIwfIsdnPriPortDChannelActiveSeconds OBJECT-TYPE
   	SYNTAX		Counter32
   	MAX-ACCESS	read-only
   	STATUS		current
   	DESCRIPTION
   	"Total length of time the AAL2 channel associated with this
   	 port/channel has been active, in seconds."
   	::= { cpIwfIsdnPriDChannelStatsEntry 1 }
   
cpIwfIsdnPriPortDChannelFillerOctets OBJECT-TYPE
   	SYNTAX		Counter32
   	MAX-ACCESS	read-only
   	STATUS		current
   	DESCRIPTION
   	"Total number of PCM filler octets injected into active media
   	 stream on this port/channel due to playout buffer underflow."
   	::= { cpIwfIsdnPriDChannelStatsEntry 2 }
   
cpIwfIsdnPriPortDChannelDroppedOctets OBJECT-TYPE
   	SYNTAX		Counter32
   	MAX-ACCESS	read-only
   	STATUS		current
   	DESCRIPTION
   	"Total number of PCM payload octets dropped due to buffer overflow
   	 on this port/channel.  Octets that are dropped because they
   	 arrived late, and which have already been substituted by filler
   	 PCM octets, shall not be counted."
   	::= { cpIwfIsdnPriDChannelStatsEntry 3 }
  										  
cpIwfIsdnPriPortDChannelAal2TxCells	OBJECT-TYPE
	SYNTAX		Counter32
	MAX-ACCESS	read-only
	STATUS		current
	DESCRIPTION
	"Total number of AAL2 cells
     transmitted by the ISDN PRI D channel 
     indicated by isdnPriDChannelNumber."
	::= { cpIwfIsdnPriDChannelStatsEntry 4 }

cpIwfIsdnPriPortDChannelAal2RxCells	OBJECT-TYPE
	SYNTAX		Counter32
	MAX-ACCESS	read-only
	STATUS		current
	DESCRIPTION
	"Total number of AAL2 cells
     received by the ISDN PRI D channel 
     indicated by isdnPriDChannelNumber."
	::= { cpIwfIsdnPriDChannelStatsEntry 5 }

cpIwfIsdnPriPortDChannelHdlcTxCells	OBJECT-TYPE
	SYNTAX		Counter32
	MAX-ACCESS	read-only
	STATUS		current
	DESCRIPTION
	"Total number of HDLC cells
     transmitted by the ISDN PRI D channel 
     indicated by isdnPriDChannelNumber."
	::= { cpIwfIsdnPriDChannelStatsEntry 6 }

cpIwfIsdnPriPortDChannelHdlcRxCells	OBJECT-TYPE
	SYNTAX		Counter32
	MAX-ACCESS	read-only
	STATUS		current
	DESCRIPTION
	"Total number of HDLC cells
     received by the ISDN PRI D channel 
     indicated by isdnPriDChannelNumber."
	::= { cpIwfIsdnPriDChannelStatsEntry 7 }

cpIwfIsdnPriPortDChannelSstedTxCells	OBJECT-TYPE
	SYNTAX		Counter32
	MAX-ACCESS	read-only
	STATUS		current
	DESCRIPTION
	"Total number of SSTED layer cells
     transmitted by the ISDN PRI D channel 
     indicated by isdnPriDChannelNumber."
	::= { cpIwfIsdnPriDChannelStatsEntry 8 }
										  
cpIwfIsdnPriPortDChannelSstedRxCells	OBJECT-TYPE
	SYNTAX		Counter32
	MAX-ACCESS	read-only
	STATUS		current
	DESCRIPTION
	"Total number of SSTED layer cells
     received by the ISDN PRI D channel 
     indicated by isdnPriDChannelNumber."
	::= { cpIwfIsdnPriDChannelStatsEntry 9 }



END

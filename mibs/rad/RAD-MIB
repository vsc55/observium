-- 
-- file :rad0545.pkb
-- 
RAD-MIB


--RAD0545-MIB  
--Last revision: 04/11/08  SMI-v2
--
--                 

			DEFINITIONS ::= BEGIN

-- Title:     rad0545   MIB
-- Copyright 2000 RAD Data Communications, Ltd.
-- All Rights Reserved.  

-- It is RAD's intent to encourage the widespread use of
-- this Specification in connection with the management of
-- RAD products. RAD grants vendors, end-users,
-- and other interested parties a non-exclusive license to
-- use this Specification in connection with the management
-- of RAD products.

-- This Specification is supplied "as is," and RAD makes
-- no warranty, either express or implied, as to the use,
-- operation, condition, or performance of the Specification.

IMPORTS
	  fddimibPORTPCMState             FROM FDDI-SMT73-MIB
	  rptrGroupOperStatus,            
	  rptrPortOperStatus			  FROM SNMP-REPEATER-MIB
	  rpMauMediaAvailable             FROM MAU-MIB
--      OBJECT-TYPE , 
      Integer32 , Counter32,
      TimeTicks,enterprises,
      IpAddress, Gauge32, Unsigned32,
      OBJECT-TYPE, MODULE-IDENTITY,
      NOTIFICATION-TYPE, 
      OBJECT-IDENTITY, Counter64      FROM SNMPv2-SMI
      TimeStamp, TAddress,
      TEXTUAL-CONVENTION, 
      DisplayString, RowStatus, 
      DateAndTime, TruthValue,
      RowPointer 				         FROM SNMPv2-TC
--      MODULE-COMPLIANCE, OBJECT-GROUP FROM SNMPv2-CONF
      AtmTrafficDescrParamIndex       FROM ATM-TC-MIB
--      AtmTrafficDescrParamIndex,
      atmVplVpi, atmVclVpi, atmVclVci,
	  aal5VccVpi, aal5VccVci,
	  atmVpCrossConnectEntry,
	  atmVcCrossConnectEntry,
	  atmTrafficDescrParamEntry,
      atmVclEntry, aal5VccEntry       FROM ATM-MIB
      frPVCEndptDLCIIndex             FROM FRNETSERV-MIB
	  VlanIndex, PortList, 
	  dot1qVlanStaticEntry            FROM Q-BRIDGE-MIB
	  atmfCESCbrIndex,
	  atmfCESConfEntry                FROM ATMF-CES
      InterfaceIndex, ifAlias, 
      ifIndex, InterfaceIndexOrZero, ifDescr FROM IF-MIB
      imaGroupIndex, imaLinkIfIndex,
      imaGroupFailureStatus           FROM IMA-MIB 
      dsx1LineStatus, 
      dsx1LineStatusLastChange,
      dsx1CurrentIndex, dsx1LineIndex,
      dsx1IntervalIndex, dsx1IntervalNumber, 
      dsx1LoopbackStatus, 
      dsx1TotalIndex                  FROM DS1-MIB
      dsx3LineStatus, dsx3ConfigEntry,
      dsx3LoopbackStatus              FROM DS3-MIB
      PerfCurrentCount, 
      PerfIntervalCount,
      PerfTotalCount                  FROM PerfHist-TC-MIB
      MmTAddressTag,MmEndpointID,
      MmAliasAddress,MmH323EndpointType, 
	  MmGatekeeperID,MmAliasTag       FROM MULTI-MEDIA-MIB-TC
	  SnmpAdminString                 FROM SNMP-FRAMEWORK-MIB
	  isdnSignalingEntry              FROM ISDN-MIB
	  frAtmIwfConnectionEntry		  FROM FR-ATM-PVC-SERVICE-IWF-MIB
      hdsl2ShdslEndpointCurrEntry,
      hdsl2ShdslInvIndex, 
      hdsl2ShdslEndpointSide,
	  hdsl2ShdslSpanConfProfileEntry  FROM HDSL2-SHDSL-LINE-MIB
	  IANAifType					  FROM IANAifType-MIB	
	  ipoaLisIfMappingEntry			  FROM IPOA-MIB
	  Timeout, BridgeId, 
	  dot1dBasePortEntry              FROM BRIDGE-MIB
	  apsConfigEntry                  FROM APS-MIB
--	  MplsTunnelIndex, MplsOwner, 
--	  MplsLabel                       FROM MPLS-TC-STD-MIB
	  IndexIntegerNextFree, 
	  IndexInteger 		              FROM DIFFSERV-MIB 
	  InetAddressType, InetAddress,
	  InetPortNumber            	  FROM INET-ADDRESS-MIB
      dsx0BundleEntry                 FROM DS0BUNDLE-MIB
      MplsLabel, MplsTunnelIndex,
      MplsOwner, MplsLdpIdentifier,
      MplsLsrIdentifier               FROM MPLS-TC-STD-MIB 
	  schedEntry                      FROM DISMAN-SCHEDULE-MIB
	  LldpPortIdSubtype               FROM LLDP-MIB	 
	  dot1agCfmMdIndex, 
	  dot1agCfmMaIndex,
      dot1agCfmMepIdentifier,
      dot1agCfmMepDbRMepIdentifier    FROM IEEE8021-CFM-MIB
      dot3OamEntry, dot3OamOperStatus FROM DOT3-OAM-MIB	  
      IfIndexType					  FROM RFC1381-MIB;

-- Some MIB compilers need those two lines:
-- enterprises OBJECT IDENTIFIER ::=
--		     { iso org(3) dod(6) internet(1) private(4) 1 }

     rad MODULE-IDENTITY
         LAST-UPDATED "200811041700Z"
         ORGANIZATION "RAD MIB"
         CONTACT-INFO
           "        Smadar Tauber

            Postal: RAD Data Communications LTD.
                    24 Raoul Wallenberg St.	(Ziv-Towers)
                    Tel-Aviv, Israel

                    Tel: +972-3-765-9973
                    Fax: +972-3-644-0930

            E-mail: smadar_t@rad.com"
         DESCRIPTION
            "RAD MIB." 
         REVISION     "200811041700Z"
         DESCRIPTION
            "RAD MIB, version 545."
         REVISION     "200808050830Z"
         DESCRIPTION
            "RAD MIB, version 541."
         REVISION     "200805271200Z"
         DESCRIPTION
            "RAD MIB, version 540."
         REVISION     "200801291815Z"
         DESCRIPTION
            "RAD MIB, version 535."
         REVISION     "200710111000Z"
         DESCRIPTION
            "RAD MIB, version 532."
         REVISION     "200707081500Z"
         DESCRIPTION
            "RAD MIB, version 531."
         REVISION     "200706071100Z"
         DESCRIPTION
            "RAD MIB, version 530."
         REVISION     "200611191300Z"
         DESCRIPTION
            "RAD MIB, version 527."
         REVISION     "200609281130Z"
         DESCRIPTION
            "RAD MIB, version 526."
        REVISION     "200604261030Z"
         DESCRIPTION
            "RAD MIB, version 525."
         REVISION     "200604051200Z"
         DESCRIPTION
            "RAD MIB, version 523.
             Three new product OIDs added." 
         REVISION     "200602140830Z"
         DESCRIPTION
            "RAD MIB, version 522." 
         REVISION     "200512271000Z"
         DESCRIPTION
            "RAD MIB, version 521."             
	   REVISION     "200512011400Z"
         DESCRIPTION
            "RAD MIB, version 520." 
         REVISION     "200505291315Z"
         DESCRIPTION
            "RAD MIB, version 517." 
         REVISION     "200505221400Z"
         DESCRIPTION
            "RAD MIB, version 516." 
         REVISION     "200505080815Z"
         DESCRIPTION
            "RAD MIB, version 515." 
         REVISION     "200412051030Z"
         DESCRIPTION
            "RAD MIB, version 511." 
         REVISION     "200411210930Z"
         DESCRIPTION
            "RAD MIB, version 510." 
         REVISION     "200408301115Z"
         DESCRIPTION
            "RAD MIB, version 507." 
         REVISION     "200406291244Z"
         DESCRIPTION
            "RAD MIB, version 506." 
         REVISION     "200405171500Z"
         DESCRIPTION
            "RAD MIB, version 505." 
         REVISION     "200404290745Z"
         DESCRIPTION
            "RAD MIB, version 501." 
         REVISION     "200401131025Z"
         DESCRIPTION
            "RAD MIB, version 500." 
         REVISION     "200401081100Z"
         DESCRIPTION
            "RAD MIB, version 496." 
         REVISION     "200310091556Z"
         DESCRIPTION
            "RAD MIB, version 495." 
         REVISION     "200304211240Z"
         DESCRIPTION
            "RAD MIB, version 491." 
         REVISION     "200302090830Z"
         DESCRIPTION
            "RAD MIB, version 490." 
         REVISION     "200210011220Z"
         DESCRIPTION
            "RAD MIB, version 485." 
         REVISION     "200202191210Z"
         DESCRIPTION
            "RAD MIB, version 480."
         ::= { enterprises 164 }


-- rad OBJECT IDENTIFIER ::= { enterprises 164 }
radTokenRing OBJECT IDENTIFIER ::= { rad 1 } -- RAD Token Ring tree
radFddi      OBJECT IDENTIFIER ::= { rad 2 } -- rad FDDI Tree
radWan       OBJECT IDENTIFIER ::= { rad 3 } -- RAD WAN
radBridges   OBJECT IDENTIFIER ::= {rad 4 }
radConverters OBJECT IDENTIFIER ::= { rad 5 }  -- RAD Converters products' tree
radGen       OBJECT IDENTIFIER ::= { rad 6} -- General information
radStkHub    OBJECT IDENTIFIER ::=  { rad 7 } -- stackable products
radPS        OBJECT IDENTIFIER ::= { rad 8 }  -- Packet Switch
--radEthRptr  OBJECT IDENTIFIER ::= { rad 9 }  - Ethernet Repeaters products 
radMpls      OBJECT IDENTIFIER ::= { rad 10 }  -- MPLS 
radRouter    OBJECT IDENTIFIER ::= { rad 11 }  -- Routers
rtrBridge    OBJECT IDENTIFIER ::= { radRouter 7 }  
radAtm		 OBJECT IDENTIFIER ::= { rad 12 }  -- ATM Products
radPw		 OBJECT IDENTIFIER ::= { rad 14 }  -- Pseudo Wire
--radEMS 	 OBJECT IDENTIFIER ::= { rad 15 }  - RAD EMS

radExperimental OBJECT IDENTIFIER ::= { rad 20 }  -- Drafts that have no MIB tree yet
-- igmpStdMIB		MODULE-IDENTITY   ::= { radExperimental 1 }
-- apsMIB			OBJECT IDENTIFIER ::= { radExperimental 2 } ; APS-R-MIB (ver522)
-- atmApsMIB		OBJECT IDENTIFIER ::= { radExperimental 3 }
-- frsldMIB			OBJECT IDENTIFIER ::= { radExperimental 4 }
-- cpIwfMIB			OBJECT IDENTIFIER ::= { radExperimental 5 } ; CPIWF-R-MIB (atmaal2,ver522)
-- hdsl2ShdslMIB	OBJECT IDENTIFIER ::= { radExperimental 6 }
-- dot3OamMIBR		OBJECT IDENTIFIER ::= { radExperimental 7 } ; DOT3-OAM-R-MIB  (ethOamAh, ver530)
-- mefMIBR			OBJECT IDENTIFIER ::= { radExperimental 8 } ; MEF-R-MIB
-- ianaPwe3MIBR		OBJECT IDENTIFIER ::= { radExperimental 9 } ; IANA-PWE3-R-MIB	(same file with next)
-- pwStdMIBR		OBJECT IDENTIFIER ::= { radExperimental 10 }; PW-STD-R-MIB   	(same file with previous)
-- pwTcStdMIBR		OBJECT IDENTIFIER ::= { radExperimental 11 }; PW-TC-STD-R-MIB
-- pwMplsStdMIBR	OBJECT IDENTIFIER ::= { radExperimental 12 }; PW-MPLS-STD-R-MIB
-- pwCTDMMIBR		OBJECT IDENTIFIER ::= { radExperimental 13 }; PW-TDM-R-MIB
-- syslogMIBR		OBJECT IDENTIFIER ::= { radExperimental 14 }; SYSLOG-R-MIB
-- bfdMIBR			OBJECT IDENTIFIER ::= { radExperimental 15 }; BFD-STD-R-MIB
-- pwAtmMIBR		OBJECT IDENTIFIER ::= { radExperimental 16 }; PW-ATM-R-MIB

MacAddress ::= OCTET STRING (SIZE(6))
TimeSlots  ::= OCTET STRING (SIZE(4))

-- 
-- file :D:\Synergy\WorkArea\545\mib_rad\txt\radgen.txt
-- 
-- File: RadGen.txt

systems OBJECT IDENTIFIER ::= { radGen 1}  --  list of RAD products

--agnt OBJECT IDENTIFIER ::= { radGen 2}  agent general tree
--services OBJECT IDENTIFIER ::= { radGen 3}  See services.txt
--radTransport OBJECT IDENTIFIER ::= { radGen 4} RAD transport tree

radSysTR  OBJECT IDENTIFIER ::= { systems 1 } -- RAD Token Ring 

radRADring    OBJECT IDENTIFIER  ::= { radSysTR  1 }

radTMA  OBJECT IDENTIFIER  ::= { radSysTR  2 }

radRingMonitor    OBJECT IDENTIFIER  ::= { radSysTR  3 }

radSysFddi OBJECT IDENTIFIER ::= { systems 2 } -- RAD Fddi 

radFDX100  OBJECT IDENTIFIER ::= { radSysFddi  1 } -- RAD Fddi
 
radSysWan OBJECT IDENTIFIER ::= { systems 3 }  -- RAD Wan products

radSysWanEvents OBJECT-IDENTITY
     STATUS  current
     DESCRIPTION
     "The events for RAD Wan products."
     ::= { radSysWan 0 }

radMP2100      OBJECT IDENTIFIER ::= { radSysWan  1 }
radMP2104      OBJECT IDENTIFIER ::= { radSysWan  2 }
radMP2100B     OBJECT IDENTIFIER ::= { radSysWan  3 }
radMP2100F     OBJECT IDENTIFIER ::= { radSysWan  4 }

radMP2100H      OBJECT IDENTIFIER ::= { radSysWan  5 }
radMP2104H      OBJECT IDENTIFIER ::= { radSysWan  6 }
radMP2200B      OBJECT IDENTIFIER ::= { radSysWan  7 }
radMP2200F      OBJECT IDENTIFIER ::= { radSysWan  8 }

radMX3000       OBJECT IDENTIFIER ::= { radSysWan  9 }
radMX3004       OBJECT IDENTIFIER ::= { radSysWan 10 }
radMX30			OBJECT IDENTIFIER ::= { radSysWan 11 }
radMX300		OBJECT IDENTIFIER ::= { radSysWan 12 }

radVOIP         OBJECT IDENTIFIER ::= { radSysWan 13 }

radKM2100	    OBJECT IDENTIFIER ::= { radSysWan 15 }
radKM2104		OBJECT IDENTIFIER ::= { radSysWan 16 }

radDXC30        OBJECT IDENTIFIER ::= { radSysWan 20 }
radDXC10A       OBJECT IDENTIFIER ::= { radSysWan 21 }
radDXC8R        OBJECT IDENTIFIER ::= { radSysWan 22 }
radDXC30E       OBJECT IDENTIFIER ::= { radSysWan 23 }
radDXC3000      OBJECT IDENTIFIER ::= { radSysWan 24 }
radDXC8RNew     OBJECT IDENTIFIER ::= { radSysWan 25 }

radFcdT1LC       OBJECT IDENTIFIER ::= { radSysWan 26 }
radFcdE1LC       OBJECT IDENTIFIER ::= { radSysWan 27 }
radFcdT1L        OBJECT IDENTIFIER ::= { radSysWan 28 }
radFcdE1L        OBJECT IDENTIFIER ::= { radSysWan 29 }
radFcdT1         OBJECT IDENTIFIER ::= { radSysWan 30 }
radFcdE1         OBJECT IDENTIFIER ::= { radSysWan 31 }
radFcdE1I        OBJECT IDENTIFIER ::= { radSysWan 32 }
radFcdT1M        OBJECT IDENTIFIER ::= { radSysWan 33 }
radFcdE1M        OBJECT IDENTIFIER ::= { radSysWan 34 }
radFcdIP         OBJECT IDENTIFIER ::= { radSysWan 35} 
radFcdT1A        OBJECT IDENTIFIER ::= { radSysWan 36 }
radFcdE1A        OBJECT IDENTIFIER ::= { radSysWan 37 }
radFcdW          OBJECT IDENTIFIER ::= { radSysWan 38 }
radFcdSTM        OBJECT IDENTIFIER ::= { radSysWan 39 }

radHtuE1Sa      OBJECT IDENTIFIER ::= { radSysWan 40 }
radHtuE1        OBJECT IDENTIFIER ::= { radSysWan 41 }	 --card
radHtu2Sa       OBJECT IDENTIFIER ::= { radSysWan 42 }
radHtu2         OBJECT IDENTIFIER ::= { radSysWan 43 }	 --card
radAsmi450R768Sa OBJECT IDENTIFIER ::= { radSysWan 44 }
radAsmi450R768  OBJECT IDENTIFIER ::= { radSysWan 45 }	 --card
radAsmi450R1152Sa  OBJECT IDENTIFIER ::= { radSysWan 46 }
radAsmi450R1152 OBJECT IDENTIFIER ::= { radSysWan 47 }	 --card

radLrs12F        OBJECT IDENTIFIER ::= { radSysWan 48 }
radLrs12B        OBJECT IDENTIFIER ::= { radSysWan 49 }
radLrs52         OBJECT IDENTIFIER ::= { radSysWan 50 }

radHcdE1Sa       OBJECT IDENTIFIER ::= { radSysWan 51 }
radHcdE1         OBJECT IDENTIFIER ::= { radSysWan 52 }  --card
radHtuT1Sa       OBJECT IDENTIFIER ::= { radSysWan 53 }
radHtuT1         OBJECT IDENTIFIER ::= { radSysWan 54 }	 --card

radOptimux4E1         OBJECT IDENTIFIER ::= { radSysWan 55 }
radOptimux4T1         OBJECT IDENTIFIER ::= { radSysWan 56 }
radOptimuxXLE1         OBJECT IDENTIFIER ::= { radSysWan 57 }
radOptimuxXLT1         OBJECT IDENTIFIER ::= { radSysWan 58 }
radOptimuxXL16E1       OBJECT IDENTIFIER ::= { radSysWan 59 }

radImx64        OBJECT IDENTIFIER ::= { radSysWan 60 }
radImx6L        OBJECT IDENTIFIER ::= { radSysWan 61 }
radImx2         OBJECT IDENTIFIER ::= { radSysWan 62 }
radImx4T1       OBJECT IDENTIFIER ::= { radSysWan 63 }
radImx4E1       OBJECT IDENTIFIER ::= { radSysWan 64 }
radImx2T1E1     OBJECT IDENTIFIER ::= { radSysWan 65 }
radImxi4		OBJECT IDENTIFIER ::= { radSysWan 66 }

radOptimux155     OBJECT IDENTIFIER ::= { radSysWan 67 }  --SA
radOptimux4T1L    OBJECT IDENTIFIER ::= { radSysWan 68 }  --SA Low Cost
radOptimux4E1L    OBJECT IDENTIFIER ::= { radSysWan 69 }  --SA Low Cost
radHtuE1SaV2      OBJECT IDENTIFIER ::= { radSysWan 70 }
radHtuE1V2        OBJECT IDENTIFIER ::= { radSysWan 71 }  --card
radFomiE3         OBJECT IDENTIFIER ::= { radSysWan 72 }  --card
radFomiT3         OBJECT IDENTIFIER ::= { radSysWan 73 }  --card
radOpt4E1C        OBJECT IDENTIFIER ::= { radSysWan 74 }  --card
radOpt4T1C        OBJECT IDENTIFIER ::= { radSysWan 75 }  --card
radPrbiE3         OBJECT IDENTIFIER ::= { radSysWan 76 }  --SA
radPrbiT3         OBJECT IDENTIFIER ::= { radSysWan 77 }  --SA
radHcd4Sa         OBJECT IDENTIFIER ::= { radSysWan 78 }  --SA
radOptimuxT3      OBJECT IDENTIFIER ::= { radSysWan 79 }  --SA

radFRmon          OBJECT IDENTIFIER ::= { radSysWan 80 } 
radIpMux4         OBJECT IDENTIFIER ::= { radSysWan 81 } 
radIpMux1         OBJECT IDENTIFIER ::= { radSysWan 82 } 
radIpMux16        OBJECT IDENTIFIER ::= { radSysWan 83 } 
radIpMux1E        OBJECT IDENTIFIER ::= { radSysWan 84 }
radVmux2100       OBJECT IDENTIFIER ::= { radSysWan 85 }
radMP104          OBJECT IDENTIFIER ::= { radSysWan 86 }
radMP204          OBJECT IDENTIFIER ::= { radSysWan 87 }
radVmux110        OBJECT IDENTIFIER ::= { radSysWan 88 }
-- reserved for radVmux105        OBJECT IDENTIFIER ::= { radSysWan 89 }

radFcd155        OBJECT IDENTIFIER ::= { radSysWan 90 } --SA
radIpMux8        OBJECT IDENTIFIER ::= { radSysWan 91 }
radOptimux155DS3 OBJECT IDENTIFIER ::= { radSysWan 92 }  --SA
radOptimuxT3L    OBJECT IDENTIFIER ::= { radSysWan 93 }  --SA Low Cost
radGmux2000      OBJECT IDENTIFIER ::= { radSysWan 94 }
radOp16E1L		 OBJECT IDENTIFIER ::= { radSysWan 95 }  --19 inch box
radOp16E1LS      OBJECT IDENTIFIER ::= { radSysWan 96 }  --half 19 inch box (single)
radPRBm20        OBJECT IDENTIFIER ::= { radSysWan 97 }  -- half 19 inch box
radPRBm22        OBJECT IDENTIFIER ::= { radSysWan 98 }  -- 19 inch box 
radAsmi52A       OBJECT IDENTIFIER ::= { radSysWan 99 }  -- SA

radOpXLE1        OBJECT IDENTIFIER ::= { radSysWan 100 } -- New-Look
radOpXLT1        OBJECT IDENTIFIER ::= { radSysWan 101 } -- New-Look
radOpXL16E1      OBJECT IDENTIFIER ::= { radSysWan 102 } -- New-Look
radOp4E1         OBJECT IDENTIFIER ::= { radSysWan 103 } -- New-Look
radOp4T1         OBJECT IDENTIFIER ::= { radSysWan 104 } -- New-Look

radDxc4			 OBJECT IDENTIFIER ::= { radSysWan 105 }

radIpMux11       OBJECT IDENTIFIER ::= { radSysWan 106 }
radIpMux14       OBJECT IDENTIFIER ::= { radSysWan 107 }
radOp1550		  OBJECT IDENTIFIER ::= { radSysWan 108 }
-- reserved for radVplsMtu OBJECT IDENTIFIER ::= { radSysWan 109 }

radFdsl101       OBJECT IDENTIFIER ::= { radSysWan 110 } 
radFdsl201       OBJECT IDENTIFIER ::= { radSysWan 111 } 

radVmux120        OBJECT IDENTIFIER ::= { radSysWan 112 }													
radVmux2200       OBJECT IDENTIFIER ::= { radSysWan 113 }
radVmux400        OBJECT IDENTIFIER ::= { radSysWan 114 }

radIpMux116       OBJECT IDENTIFIER ::= { radSysWan 115 }

radOp4E1LNew      OBJECT IDENTIFIER ::= { radSysWan 116 } -- New SA Low Cost
radOp4T1LNew      OBJECT IDENTIFIER ::= { radSysWan 117 } -- New SA Low Cost

radFcd155E       OBJECT IDENTIFIER ::= { radSysWan 118 } -- 19 inch box, non APS
radFcd155ES      OBJECT IDENTIFIER ::= { radSysWan 119 } -- half 19 inch box, APS

radMP4100       OBJECT IDENTIFIER ::= { radSysWan 120 }

radAsmi52L       OBJECT IDENTIFIER ::= { radSysWan 121 }  -- SA Low Cost
radVmux210       OBJECT IDENTIFIER ::= { radSysWan 122 }
radOp34E1	     OBJECT IDENTIFIER ::= { radSysWan 123 }
radVmux312       OBJECT IDENTIFIER ::= { radSysWan 124 }
radVmux404       OBJECT IDENTIFIER ::= { radSysWan 125 }
radVmux420       OBJECT IDENTIFIER ::= { radSysWan 126 }
radIpMux12	     OBJECT IDENTIFIER ::= { radSysWan 127 }

radOptimux4E1V3dot5    OBJECT IDENTIFIER ::= { radSysWan 128 }
radOptimux4E1Mar06	   OBJECT IDENTIFIER ::= { radSysWan 129 }

radFcd155EwAPS       OBJECT IDENTIFIER ::= { radSysWan 130 } -- 19 inch box, APS

radOptimux4T1Mar06	   OBJECT IDENTIFIER ::= { radSysWan 131 }

radFcd155EwAPS2pdh       OBJECT IDENTIFIER ::= { radSysWan 132 } -- 19 inch box, APS,E3 & E1

radVmux320       OBJECT IDENTIFIER ::= { radSysWan 133 }

radMP2100VoIP    OBJECT IDENTIFIER ::= { radSysWan  134 }
radMP2104VoIP    OBJECT IDENTIFIER ::= { radSysWan  135 }

radIpMux24	     OBJECT IDENTIFIER ::= { radSysWan 136 }

radOp4E1NG1      OBJECT IDENTIFIER ::= { radSysWan 137 } -- OP-108
radOp4T1NG1      OBJECT IDENTIFIER ::= { radSysWan 138 } -- OP-106 
radOp25			 OBJECT IDENTIFIER ::= { radSysWan 139 } -- T1 interface

radAsmi54        OBJECT IDENTIFIER ::= { radSysWan 140 }  -- SA

radVmux314       OBJECT IDENTIFIER ::= { radSysWan 141 }

radFcd622        OBJECT IDENTIFIER ::= { radSysWan 142 }

radLrs22         OBJECT IDENTIFIER ::= { radSysWan 143 }

radUNT20E1        OBJECT IDENTIFIER ::= { radSysWan 144 }  
radIpMux2L	      OBJECT IDENTIFIER ::= { radSysWan 145 }  
radFcdE1E         OBJECT IDENTIFIER ::= { radSysWan 146 }  

radIpMux216	      OBJECT IDENTIFIER ::= { radSysWan 147 }

radLrs102         OBJECT IDENTIFIER ::= { radSysWan 148 }

radGmux2004 	  OBJECT IDENTIFIER ::= { radSysWan 149 }

radLrs102unbal   OBJECT IDENTIFIER ::= { radSysWan 150 } -- LRS102 Unbalanced 

radLrs16 	  OBJECT IDENTIFIER ::= { radSysWan 151 }

radVmux405		OBJECT IDENTIFIER ::= { radSysWan 152 }
radVmux425		OBJECT IDENTIFIER ::= { radSysWan 153 }
radMiniCVS    	OBJECT IDENTIFIER ::= { radSysWan 154 }

radIpMux155		OBJECT IDENTIFIER ::= { radSysWan 155 }


radSysBRG OBJECT IDENTIFIER ::= { systems 4 }  -- RAD Bridges products

radTRE1  OBJECT IDENTIFIER ::= { radSysBRG 1 }  -- RAD Bridges products

radTRE1D  OBJECT IDENTIFIER ::= { radSysBRG 2 }  -- RAD Bridges products

radTRE8  OBJECT IDENTIFIER ::= { radSysBRG 3 }  -- RAD Bridges products

radTRE8D  OBJECT IDENTIFIER ::= { radSysBRG 4 }  -- RAD Bridges products

radMBE1  OBJECT IDENTIFIER ::= { radSysBRG 5 }  -- RAD Bridges products

radMBE1D  OBJECT IDENTIFIER ::= { radSysBRG  6 }  -- RAD Bridges products

radMBE8  OBJECT IDENTIFIER ::= { radSysBRG  7 }  -- RAD Bridges products

radMBE8D  OBJECT IDENTIFIER ::= { radSysBRG  8 }  -- RAD Bridges products

radMLBT   OBJECT IDENTIFIER ::= { radSysBRG  9 }  -- RAD Bridges products 

radFEB4DAS    OBJECT IDENTIFIER ::= { radSysBRG  10 }  -- RAD Bridges products

radTrimBrg10  OBJECT IDENTIFIER ::= { radSysBRG 11 }  -- RAD Bridges products

radTrimBrg16  OBJECT IDENTIFIER ::= { radSysBRG 12 }  -- RAD Bridges products

radRRTRE8  OBJECT IDENTIFIER ::= { radSysBRG 13 }  -- RAD Bridges products

radRRTRE8D  OBJECT IDENTIFIER ::= { radSysBRG 14 }  -- RAD Bridges products

radRRMLBT   OBJECT IDENTIFIER ::= { radSysBRG 15 }  -- RAD Bridges products 

radRRMLBTF   OBJECT IDENTIFIER ::= { radSysBRG 16 }  -- RAD Bridges products 

radRRTRE1D  OBJECT IDENTIFIER ::= { radSysBRG 17 }  -- RAD Bridges products

radTRERAS  OBJECT IDENTIFIER ::= { radSysBRG 18 }  -- RAD Bridges products

radTRERASa  OBJECT IDENTIFIER ::= { radSysBRG 19 }  -- RAD Bridges products

radMBERAS  OBJECT IDENTIFIER ::= { radSysBRG 20 }  -- RAD Bridges products

radMBERASa  OBJECT IDENTIFIER ::= { radSysBRG 21 }  -- RAD Bridges products
 
radFEB4FDX   OBJECT IDENTIFIER ::= { radSysBRG 22 }  -- RAD Bridges products

radFEB4SAS  OBJECT IDENTIFIER ::= { radSysBRG 23 }  -- RAD Bridges products

radRRFTBDAS  OBJECT IDENTIFIER ::= { radSysBRG 24 }  -- RAD Bridges products

radRRFTBSAS  OBJECT IDENTIFIER ::= { radSysBRG 25 }  -- RAD Bridges products

radFTBDAS    OBJECT IDENTIFIER ::= { radSysBRG 26 }  -- RAD Bridges products

radFTBSAS    OBJECT IDENTIFIER ::= { radSysBRG 27 }  -- RAD Bridges products

radFastWay100    OBJECT IDENTIFIER ::= { radSysBRG 28 }  -- RAD Bridges products

radSysCnvrtr OBJECT IDENTIFIER ::= { systems 5 }  -- RAD Converters products

radSTC1   OBJECT IDENTIFIER ::= { radSysCnvrtr 1 }  -- RAD Converters products

radSTC2   OBJECT IDENTIFIER ::= { radSysCnvrtr 3 }  -- RAD Converters products

radSTC1UDP  OBJECT IDENTIFIER ::= { radSysCnvrtr 4 }  -- RAD Converters products

radSTC2UDP  OBJECT IDENTIFIER ::= { radSysCnvrtr 6 }  -- RAD Converters products

radFTC1   OBJECT IDENTIFIER ::= { radSysCnvrtr 10 }  -- RAD Converters products

radFTC2   OBJECT IDENTIFIER ::= { radSysCnvrtr 12 }  -- RAD Converters products

radFTC1UDP    OBJECT IDENTIFIER ::= { radSysCnvrtr 13 }  -- RAD Converters products

radFTC2UDP    OBJECT IDENTIFIER ::= { radSysCnvrtr 15 }  -- RAD Converters products

radSEC1   OBJECT IDENTIFIER ::= { radSysCnvrtr 20 }  -- RAD Converters products

radSEC2   OBJECT IDENTIFIER ::= { radSysCnvrtr 22 }  -- RAD Converters products

radSEC1UDP   OBJECT IDENTIFIER ::= { radSysCnvrtr 23 }  -- RAD Converters products

radSEC2UDP   OBJECT IDENTIFIER ::= { radSysCnvrtr 25 }  -- RAD Converters products

radFEC1   OBJECT IDENTIFIER ::= { radSysCnvrtr 30 }  -- RAD Converters products

radFEC2   OBJECT IDENTIFIER ::= { radSysCnvrtr 32 }  -- RAD Converters products

radFEC1UDP   OBJECT IDENTIFIER ::= { radSysCnvrtr 33 }  -- RAD Converters products

radFEC2UDP   OBJECT IDENTIFIER ::= { radSysCnvrtr 35 }  -- RAD Converters products

radRIC155   OBJECT IDENTIFIER ::= { radSysCnvrtr 36 }  -- RAD Converters products

radRICE1   OBJECT IDENTIFIER ::= { radSysCnvrtr 37 }  -- RAD Converters products

radETX102  OBJECT IDENTIFIER ::= { radSysCnvrtr 38 }  -- RAD Converters products

radRIC155GE OBJECT IDENTIFIER ::= { radSysCnvrtr 39 }  -- RAD Converters products

radRiciT3   OBJECT IDENTIFIER ::= { radSysCnvrtr 40 }  -- RAD Converters products

radRiciE3   OBJECT IDENTIFIER ::= { radSysCnvrtr 41 }  -- RAD Converters products

radRiciT1   OBJECT IDENTIFIER ::= { radSysCnvrtr 42 }  -- RAD Converters products

radETX202  OBJECT IDENTIFIER ::= { radSysCnvrtr 43 }  -- RAD Converters products

radETX105  OBJECT IDENTIFIER ::= { radSysCnvrtr 44 }  -- RAD Converters products

radETX205  OBJECT IDENTIFIER ::= { radSysCnvrtr 45 }  -- RAD Converters products

radRiciSE  OBJECT IDENTIFIER ::= { radSysCnvrtr 46 }  -- RAD Converters products

radRIC622GE OBJECT IDENTIFIER ::= { radSysCnvrtr 47 }  -- RAD Converters products

radSPH OBJECT IDENTIFIER ::= { radSysCnvrtr 48 }  -- RAD Converters products

radMiricE1T1 OBJECT IDENTIFIER ::= { radSysCnvrtr 49 }  -- RAD Converters products
radMiricE3T3 OBJECT IDENTIFIER ::= { radSysCnvrtr 50 }  -- RAD Converters products

radSPH4 OBJECT IDENTIFIER ::= { radSysCnvrtr 51 }  -- RAD Converters products

radEthAccess   OBJECT IDENTIFIER ::= {systems 6}

radETX510 		OBJECT IDENTIFIER ::= { radEthAccess  1 }
radEGate100		OBJECT IDENTIFIER ::= { radEthAccess  2 }
radEGate20 		OBJECT IDENTIFIER ::= { radEthAccess  3 }
radRici8E1		OBJECT IDENTIFIER ::= { radEthAccess  4 }	
radRici8T1		OBJECT IDENTIFIER ::= { radEthAccess  5 }	
radRici4E1		OBJECT IDENTIFIER ::= { radEthAccess  6 }	
radRici4T1		OBJECT IDENTIFIER ::= { radEthAccess  7 }	
radIMXI4		OBJECT IDENTIFIER ::= { radEthAccess  8 }-- for Khazahstan only
radETX550		OBJECT IDENTIFIER ::= { radEthAccess  9 }
radRici16		OBJECT IDENTIFIER ::= { radEthAccess 10 }
radETX102A		OBJECT IDENTIFIER ::= { radEthAccess 11 }
radETX202A		OBJECT IDENTIFIER ::= { radEthAccess 12 }
radETX201A		OBJECT IDENTIFIER ::= { radEthAccess 13 }
radETX201		OBJECT IDENTIFIER ::= { radEthAccess 14 }
radUNT20Ric	  	OBJECT IDENTIFIER ::= { radEthAccess 15 }
radRici4E1L		OBJECT IDENTIFIER ::= { radEthAccess 16 }	
radRici8E1L		OBJECT IDENTIFIER ::= { radEthAccess 17 }
radRici155GE 	OBJECT IDENTIFIER ::= { radEthAccess 18 }
radRici622GE 	OBJECT IDENTIFIER ::= { radEthAccess 19 }
radETX208		OBJECT IDENTIFIER ::= { radEthAccess 20 }
radETX202AW		OBJECT IDENTIFIER ::= { radEthAccess 21 }--for wide box of ETX202A
radETX102H		OBJECT IDENTIFIER ::= { radEthAccess 22 } -- Hardened metal box
radETX202H		OBJECT IDENTIFIER ::= { radEthAccess 23 } -- Hardened metal box


radSysStkHub  OBJECT IDENTIFIER ::= { systems 7 }  -- RAD Stackable products

radRBHE    OBJECT IDENTIFIER ::= { radSysStkHub 1 }  -- RAD Stackable products

radRBHT    OBJECT IDENTIFIER ::= { radSysStkHub 2 }  -- RAD Stackable products

radRBHEEvents OBJECT-IDENTITY
     STATUS  current
     DESCRIPTION
     "The events for RAD Stackable products."
     ::= { radRBHE 0 }

radRBHTEvents OBJECT-IDENTITY
     STATUS  current
     DESCRIPTION
     "The events for RAD Stackable products."
     ::= { radRBHT 0 }

radETS4fddiDAS   OBJECT IDENTIFIER ::= { radSysStkHub 3 }  -- RAD Stackable products

radETS4fddiSAS   OBJECT IDENTIFIER ::= { radSysStkHub 4 }  -- RAD Stackable products

radSAHEMX  OBJECT IDENTIFIER ::= { radSysStkHub 5 }  -- RAD Stackable products

radSAHTM   OBJECT IDENTIFIER ::= { radSysStkHub 6 }  -- RAD Stackable products

radETS4   OBJECT IDENTIFIER ::= { radSysStkHub 7 }  -- RAD Stackable products

radSAHEMU  OBJECT IDENTIFIER ::= { radSysStkHub 8 }  -- RAD Stackable products


unknown    	OBJECT IDENTIFIER ::= { radSysStkHub 9 }  -- RAD Stackable products

radSAH16Eint   OBJECT IDENTIFIER ::= { radSysStkHub 10 }  -- RAD Stackable products

radSAH16Tint   OBJECT IDENTIFIER ::= { radSysStkHub 11 }  -- RAD Stackable products

radSAH16Eext   OBJECT IDENTIFIER ::= { radSysStkHub 12 }  -- RAD Stackable products

radSAH16Text   OBJECT IDENTIFIER ::= { radSysStkHub 13 }  -- RAD Stackable products



radSysPS OBJECT IDENTIFIER ::=  { systems 8 } -- RAD Packet Switch  (PS) products 

radSysPSEvents OBJECT-IDENTITY
     STATUS  current
     DESCRIPTION
     "The events for RAD Packet Switch  (PS) products."
     ::= { radSysPS 0 }

radSPS2  OBJECT IDENTIFIER ::=  { radSysPS 1 } -- RAD Packet Switch  (PS) products
radSPS3  OBJECT IDENTIFIER ::=  { radSysPS 2 } -- RAD Packet Switch  (PS) products
radSPS6  OBJECT IDENTIFIER ::=  { radSysPS 3 } -- RAD Packet Switch  (PS) products
radSPS9  OBJECT IDENTIFIER ::=  { radSysPS 4 } -- RAD Packet Switch  (PS) products
radSPS12 OBJECT IDENTIFIER ::=  { radSysPS 5 } -- RAD Packet Switch  (PS) products

radAPD2  OBJECT IDENTIFIER ::=  { radSysPS 6 } -- RAD Packet Switch  (PS) products
radAPD8  OBJECT IDENTIFIER ::=  { radSysPS 7 } -- RAD Packet Switch  (PS) products

radAPS8  OBJECT IDENTIFIER ::=  { radSysPS 8 } -- RAD Packet Switch  (PS) products
radAPS16 OBJECT IDENTIFIER ::=  { radSysPS 9 } -- RAD Packet Switch  (PS) products
radAPS24 OBJECT IDENTIFIER ::=  { radSysPS 10 } -- RAD Packet Switch  (PS) products

radSPS3S  OBJECT IDENTIFIER ::=  { radSysPS 11} -- RAD Packet Switch  (PS) products

radFPS8  OBJECT IDENTIFIER ::=  { radSysPS 12} -- RAD Packet Switch  (PS) products
radFPS12  OBJECT IDENTIFIER ::=  { radSysPS 13} -- RAD Packet Switch  (PS) products

radSPS3ScSL  OBJECT IDENTIFIER ::= { radSysPS 14} -- RAD Packet Switch  (PS) products
radSPS3Sc2S  OBJECT IDENTIFIER ::=  { radSysPS 15} -- RAD Packet Switch  (PS) products

radFPS8c OBJECT IDENTIFIER ::=  { radSysPS 16} -- RAD Packet Switch  (PS) products	  
radFPS4 OBJECT IDENTIFIER ::=  { radSysPS 17} -- RAD Packet Switch  (PS) products

radSPS4 OBJECT IDENTIFIER ::=  { radSysPS 18} -- RAD Packet Switch  (PS) products



radSysEth  OBJECT IDENTIFIER ::= { systems 9 } -- RAD Ethernet products 

radEP8T    OBJECT IDENTIFIER ::= {radSysEth 1} -- RAD Ethernet products

radEP4TAUI   OBJECT IDENTIFIER ::= {radSysEth 2} -- RAD Ethernet products

radEP4T2FL   OBJECT IDENTIFIER ::= {radSysEth 3} -- RAD Ethernet products

radEP4TFL    OBJECT IDENTIFIER ::= {radSysEth 4} -- RAD Ethernet products

radEP4FL     OBJECT IDENTIFIER ::= {radSysEth 5} -- RAD Ethernet products


radEPR8T   OBJECT IDENTIFIER ::= {radSysEth 7} -- RAD Ethernet products

radEPR4TAUI  OBJECT IDENTIFIER ::= {radSysEth 8} -- RAD Ethernet products

radEPR4T2FL  OBJECT IDENTIFIER ::= {radSysEth 9} -- RAD Ethernet products

radEPR4TFL   OBJECT IDENTIFIER ::= {radSysEth 10} -- RAD Ethernet products

radEPR4FL    OBJECT IDENTIFIER ::= {radSysEth 11} -- RAD Ethernet products



radSysRtr  OBJECT IDENTIFIER ::= { systems 11 } -- RAD Router products 

radSysRtrEvents OBJECT-IDENTITY
     STATUS  current
     DESCRIPTION
     "The events for RAD Router products."
     ::= { radSysRtr 0 }

radRTED    OBJECT IDENTIFIER ::= {radSysRtr 1} -- RAD Router products

radRTEM    OBJECT IDENTIFIER ::= {radSysRtr 2} -- RAD Router products

radRTEC    OBJECT IDENTIFIER ::= {radSysRtr 3} -- RAD Router products

radWebRanger    OBJECT IDENTIFIER ::= {radSysRtr 4} -- RAD Router products

radTinyRouter   OBJECT IDENTIFIER ::= {radSysRtr 5} -- RAD Router products

radLA240	    OBJECT IDENTIFIER ::= {radSysRtr 6} -- RAD Router products

radSuperLan	    OBJECT IDENTIFIER ::= {radSysRtr 7} -- RAD Router products (LA-240)

radLA240I	    OBJECT IDENTIFIER ::= {radSysRtr 8} -- RAD Router products

radFcdIsdn      OBJECT IDENTIFIER ::= {radSysRtr 9} -- RAD Router products

radEFcdIp	    OBJECT IDENTIFIER ::= {radSysRtr 10} -- RAD Router products (FCD-IP/D)

radFcdIpD       OBJECT IDENTIFIER ::= {radSysRtr 11} -- RAD Router products

radFcdIpM       OBJECT IDENTIFIER ::= {radSysRtr 12} -- RAD Router products (LA-240)

radFcdIpL       OBJECT IDENTIFIER ::= {radSysRtr 13} -- RAD Router products


radSysAtm  OBJECT IDENTIFIER ::= { systems 12 } -- RAD ATM products 

radSysAtmEvents OBJECT-IDENTITY
     STATUS  current
     DESCRIPTION
     "The events for RAD ATM products."
     ::= { radSysAtm 0 }

radStarSwitch    OBJECT IDENTIFIER ::= {radSysAtm 1} --RAD StartSwitch products

radStarSwitchATM25    OBJECT IDENTIFIER ::= {radStarSwitch 1} --RAD StartSwitch products
radStarSwitchATM25L   OBJECT IDENTIFIER ::= {radStarSwitch 2} --RAD StartSwitch products
radStarSwitchATM155   OBJECT IDENTIFIER ::= {radStarSwitch 3} --RAD StartSwitch products


radAtmCsuDsu  OBJECT IDENTIFIER ::= {radSysAtm 2} --RAD CSU/DSU products 

radAmcdE1  OBJECT IDENTIFIER ::= {radAtmCsuDsu 1} -- RAD CSU/DSU products
radAmcdT1  OBJECT IDENTIFIER ::= {radAtmCsuDsu 2} -- RAD CSU/DSU products
radAce20E  OBJECT IDENTIFIER ::= {radAtmCsuDsu 3} -- RAD CSU/DSU products
radAce20T  OBJECT IDENTIFIER ::= {radAtmCsuDsu 4} -- RAD CSU/DSU products

radAce2005 OBJECT IDENTIFIER ::= { radAtmCsuDsu 5} -- RAD ACE2005
radAce2002 OBJECT IDENTIFIER ::= { radAtmCsuDsu 6} -- RAD ACE2002
radAce2002E OBJECT IDENTIFIER ::= { radAtmCsuDsu 7} -- RAD ACE2002E

radAce2E  OBJECT IDENTIFIER ::= {radAtmCsuDsu 8} -- RAD CSU/DSU products
radAce2T  OBJECT IDENTIFIER ::= {radAtmCsuDsu 9} -- RAD CSU/DSU products

radMlAtmE1  OBJECT IDENTIFIER ::= {radAtmCsuDsu 10} -- RAD ATM Piggy
radMlAtmT1  OBJECT IDENTIFIER ::= {radAtmCsuDsu 11} -- RAD ATM Piggy

radAmc102  OBJECT IDENTIFIER ::= {radAtmCsuDsu 12} -- RAD AMC102
radAmc102c  OBJECT IDENTIFIER ::= {radAtmCsuDsu 13} -- RAD AMC102 CARD

radAce202 OBJECT IDENTIFIER ::= { radAtmCsuDsu 14} -- RAD ACE202

radAce			OBJECT IDENTIFIER ::= {radSysAtm 3}	--RAD ACE products 
radAce101		OBJECT IDENTIFIER ::= {radAce 1}	-- RAD ACE101
radAce102		OBJECT IDENTIFIER ::= {radAce 2}	-- RAD ACE102
radAce50		OBJECT IDENTIFIER ::= {radAce 3}	-- RAD ACE50
radAce52		OBJECT IDENTIFIER ::= {radAce 4}	-- RAD ACE52
radAce52L		OBJECT IDENTIFIER ::= {radAce 5}	-- RAD ACE52L
-- for radAce51 which was canceled 
radAce201		OBJECT IDENTIFIER ::= {radAce 7}	-- RAD ACE201
radAce3200		OBJECT IDENTIFIER ::= {radAce 8}	-- RAD ACE3200
radAce3100		OBJECT IDENTIFIER ::= {radAce 9}	-- RAD ACE3100
radAce3400		OBJECT IDENTIFIER ::= {radAce 10}	-- RAD ACE3400
radAce3402		OBJECT IDENTIFIER ::= {radAce 11}	-- RAD ACE3402
radAce3100PSN	OBJECT IDENTIFIER ::= {radAce 12}	-- RAD ACE3100/PSN
radAce3200PSN	OBJECT IDENTIFIER ::= {radAce 13}	-- RAD ACE3200/PSN
radAce3400PSN	OBJECT IDENTIFIER ::= {radAce 14}	-- RAD ACE3400/PSN
radAce3402PSN	OBJECT IDENTIFIER ::= {radAce 15}	-- RAD ACE3402/PSN
radAce3600		OBJECT IDENTIFIER ::= {radAce 16}	-- RAD ACE3600
radAce3205		OBJECT IDENTIFIER ::= {radAce 17}	-- RAD ACE3205
radAce3105		OBJECT IDENTIFIER ::= {radAce 18}	-- RAD ACE3105
radAce3220		OBJECT IDENTIFIER ::= {radAce 19}	-- RAD ACE3220

radSysLA	  OBJECT IDENTIFIER ::= {systems 13} --RAD  IAD (Integrated Access Device) products
radLA140      OBJECT IDENTIFIER ::= {radSysLA 1} -- RAD LA-140
radLA110      OBJECT IDENTIFIER ::= {radSysLA 2} -- RAD LA-110
radLA104      OBJECT IDENTIFIER ::= {radSysLA 3} -- RAD LA-104 (LA-110 with IMA)
radLA130	  OBJECT IDENTIFIER ::= {radSysLA 4}
radLA210	  OBJECT IDENTIFIER ::= {radSysLA 5} -- RAD LA-210 

radSysTerminal  OBJECT IDENTIFIER ::= {systems 100} --RAD Terminal Meta-MIB; 
-- no objects should be added to this branch in RAD MIB.                                     


agnt OBJECT IDENTIFIER ::= { radGen 2} 
-- agent general tree
-- Agent General  
agnHwVersion OBJECT-TYPE
      SYNTAX  DisplayString
      MAX-ACCESS  read-write
      STATUS  current
      DESCRIPTION
      "ASCII string for description and display of the agent hardware version,
      as it is known by the agent software.The user can update the version
       upon request when he changes   components in the agent's module  "
      ::= { agnt 1 }

agnTrapMask OBJECT-TYPE   
      SYNTAX  Integer32 
      MAX-ACCESS  read-write    
      STATUS  current
      DESCRIPTION
      "The value of this attribute determines the type of traps the 
       agent should mask and not send to the management console. The 
       value is differently determined for different products. There are 
       mainly two methods:
       - an integer number, specifying the traps' severity.
       - a sum of 2**n, where n is a bit assigned to a certain 
         masked trap group.
       User should consult the product specification, to find out 
       the method employed."
      ::= { agnt 2 }

agnTrapValue OBJECT-TYPE
	SYNTAX  OCTET STRING
	MAX-ACCESS  read-only
	STATUS deprecated
	DESCRIPTION
	"The value of the trap decoded in internal RAD format. Full description is given
	  in the Trap definition file"
	::= {agnt 3}

agnChangeCnt OBJECT-TYPE
	SYNTAX  Counter32
	MAX-ACCESS  read-only
	STATUS current
	DESCRIPTION
	"The number of changes in system configuration that were  reported to the 
	manager since last cold start"
	::= {agnt 4 }

agnSpecific OBJECT-TYPE
      SYNTAX  OBJECT IDENTIFIER
      MAX-ACCESS  read-only
      STATUS  current
      DESCRIPTION
      " Object identifier of entity containing additional information 
      regarding this instance."
      ::= { agnt 5}

agnConfigMsg OBJECT-TYPE   
      SYNTAX  OCTET STRING
      MAX-ACCESS  read-only
      STATUS  current
      DESCRIPTION
      "Full configuration message  coded in internal RAD application format.
       This entry describes agent's configuration.

       For MP-2200 R3, this object describes agent's support of the V5.1
       feature: 1 octet ; bit 0 (LSB). 
       '1' - V5.1 feature is supported
       '0' - V5.1 feature is not supported."
      ::= { agnt 6 }

-- Manager table to record all IP addresses

mngTrapIpTable  OBJECT-TYPE
	SYNTAX  SEQUENCE OF MngEntry
	MAX-ACCESS  not-accessible
	STATUS current
	DESCRIPTION
	"This table indicates  the destination address of the traps.
	  Internally it will be limited to ten addresses. "
	::= { agnt 7 }

mngEntry OBJECT-TYPE
	SYNTAX  MngEntry
	MAX-ACCESS  not-accessible
	STATUS current
	DESCRIPTION  "An entry in table."
	INDEX {  mngID }
	::= { mngTrapIpTable 1 }


MngEntry  ::=
	    SEQUENCE {
	mngID
	  Integer32,
	mngIP
	  IpAddress,
	mngIPMask
	  IpAddress,
    mngTrapMask
      Integer32,
    mngAlarmTrapMask
      OCTET STRING,
    mngSnmpTrapUdpPort
      Unsigned32	
    }

mngID OBJECT-TYPE
	SYNTAX  Integer32 
	MAX-ACCESS  read-only
	STATUS current
	DESCRIPTION
	" This value indicates an index of a specific IP address"
	::= { mngEntry 1 }

mngIP OBJECT-TYPE
	SYNTAX  IpAddress 
	MAX-ACCESS  read-write
	STATUS current
	DESCRIPTION
	"This value indicates  the  destination address of the traps. IP 0.0.0.0 removes the entry. "
	::= { mngEntry 2 }

mngIPMask OBJECT-TYPE
	SYNTAX  IpAddress 
	MAX-ACCESS  read-write
	STATUS deprecated
	DESCRIPTION
	"This value indicates  the  mask of the destination addresses of the traps. "
	::= { mngEntry 3 }

mngTrapMask OBJECT-TYPE
	SYNTAX  Integer32 
	MAX-ACCESS  read-write
	STATUS current
	DESCRIPTION
      "The value of this attribute determines the type of traps the 
       agent should mask and not send to this NMS. The 
       value is differently determined for different products. There are 
       mainly two methods:
       - an integer number, specifying the traps' severity.
       - a sum of 2**n, where n is a bit assigned to a certain 
         masked trap group.
       User should consult the product specification, to find out 
       the method employed."
	::= { mngEntry 4 }

mngAlarmTrapMask OBJECT-TYPE
     SYNTAX  OCTET STRING
     MAX-ACCESS  read-write
     STATUS current
     DESCRIPTION
     "The value of this object determines the alarm traps that the 
      agent should mask (not send to this manager).
      The value is an Octet String, where each bit 
      is assigned to a certain trap.
        If the bit = 1, the trap will be masked.
        If the bit = 0, the trap will not be masked.
      For more details on the specific alarm traps masked, 
      see product specification."
    ::= { mngEntry 5 }

mngSnmpTrapUdpPort OBJECT-TYPE
	SYNTAX  Unsigned32 
	MAX-ACCESS  read-write
	STATUS  current
	DESCRIPTION
	"This variable enables to set the UDP port (socket) used for SNMP traps."
	::= { mngEntry 6 }
 

agnIndication OBJECT-TYPE   
      SYNTAX  INTEGER {
		 faulty  (1), -- =major
		 warning (2),
		 normal  (3), -- off
		 minor   (4),
		 major   (5),
		 event   (6),
		 critical(7)
		}
      MAX-ACCESS  read-only
      STATUS  current
      DESCRIPTION
      "Attribute describing the state of the entity the agent is responsible for.
       In case of a modular entity, the value of this attribute will be according
       to the component which is in the worst state.
       The order of severity (from top to bottom) is:
       critical-> major (or faulty)-> minor-> event-> warning-> normal (off)."   
      ::= { agnt 8 }


agnMonitorModeCmd OBJECT-TYPE
	SYNTAX  INTEGER {
	notApplicable(1),
	off(2),
	on(3)
	}
	MAX-ACCESS  read-write
	STATUS current
	DESCRIPTION
	"Setting this attribute to ON, will enforce the agent to change its mode of operation to
	 Monitor Mode"
	::= {agnt 9}

agnLed OBJECT-TYPE
	SYNTAX  OCTET STRING
	MAX-ACCESS  read-only
	STATUS current
	DESCRIPTION
	"This entry specifies  the LEDs status of the agent module . Each led will be represented by 4 
	 bits  where the first 2 bits (left) will specify  the status :
	 (00=NA, 01=OFF, 10=ON, 11=BLINK),
     and the next two bits (right) will specify the color :
     (00=GREEN, 01=RED, 10=YELLOW, 11=GRAY)"
	::= {agnt 10}

trapTable  OBJECT-TYPE
	SYNTAX  SEQUENCE OF TrapEntry
	MAX-ACCESS  not-accessible
	STATUS current
	DESCRIPTION
	"This table may include the last few traps generated by the agent, for future retrieval. The table
	 has a limited capacity. If traps are not retrieved in proper time, they will be
	 over-written by new traps.
	 For other devices, it can include generic variables that will be attached to traps
	 as 'accessible-for-notify'."
	::= {agnt 11}

trapEntry OBJECT-TYPE
	SYNTAX  TrapEntry
	MAX-ACCESS  not-accessible
	STATUS current
	DESCRIPTION  "An entry in trapTable."
	INDEX {  trapID }
	::= { trapTable 1 }

TrapEntry  ::=
	    SEQUENCE {
	trapID
	  Integer32,
	trapVal
	  DisplayString,
    trapTimeSinceOccurrence
	   TimeTicks,
	trapNumeric
	  Integer32
	}

trapID OBJECT-TYPE
	SYNTAX  Integer32 
	MAX-ACCESS  read-only
	STATUS current
	DESCRIPTION
	" This object indicates an index of a specific trap.
	  Can be used also for any trap, while trapVal is used
	  as 'accessible-for-notify' or trapNumeric is used."
	::= { trapEntry 1 }

trapVal OBJECT-TYPE
	SYNTAX  DisplayString 
	MAX-ACCESS  read-only
	STATUS current
	DESCRIPTION
	"This object is the actual ASCII description  of the trap.
	 It can be used also as attached variable of traps, in order
	 to detail in explicit ASCII text, data of the trap.
	 In this case, it is used as 'accessible-for-notify'."
	::= { trapEntry 2 }

trapTimeSinceOccurrence OBJECT-TYPE
	 SYNTAX    TimeTicks
	MAX-ACCESS  read-only
	STATUS current
	DESCRIPTION
	"This object indicates the amount of  time passed since the occurrence of the event that
	 triggered this trap. "
	::= { trapEntry 3 }

trapNumeric OBJECT-TYPE
	SYNTAX  Integer32 
	MAX-ACCESS  accessible-for-notify
	STATUS current
	DESCRIPTION
	" This object is a numeric general parameter, that can be attached to any trap.
	  Values can be positive or negative."
	::= { trapEntry 4 }


fileTransfer  OBJECT IDENTIFIER ::= { agnt 12 }

fileServerIP  OBJECT-TYPE
	SYNTAX  IpAddress
	MAX-ACCESS  read-write
	STATUS  current
	DESCRIPTION
	"The IP address of the server from which the file is loaded "
	::= { fileTransfer 1 }

fileName  OBJECT-TYPE
	SYNTAX  DisplayString
	MAX-ACCESS  read-write
	STATUS  current
	DESCRIPTION
	"The name of the file to be loaded. For protection, read returns
	 NULL. "
	::= { fileTransfer 2 }

fileTransCmd  OBJECT-TYPE
	SYNTAX  INTEGER {
	                 swDwnLoad         (1),
					 configDwnLoad     (2),
					 configUpLoad      (3),
					 coProcDwnLoad     (4),
					 stateUpLoad       (5),
					 dwnLoadUserFile   (6),
					 upLoadUserFile    (7), 
					 swDwnLoadAndReset (8),
					 swUpLoad          (9),
					 swDwnLoad2BkupStorage(10),
					 bootDwnLoad      (11),
					 bootUpLoad       (12), 
					 swUpLoadFromBkupStorage(13),
					 licenseDwnLoad   (14),
					 configDwnLoadToDefaultFile(15),
					 noOp            (255)
					}
	MAX-ACCESS  read-write
	STATUS  current
	DESCRIPTION
	"The command to be executed on fileName at fileServerIP."
	::= { fileTransfer 3 }
 
-- tftp  group  

tftpRetryTimeOut OBJECT-TYPE
    SYNTAX  Integer32
    MAX-ACCESS  read-write
    STATUS  current
    DESCRIPTION
        " General Retransmission time-out value (seconds) "
    -- DEFVAL  { 15 }
    ::= { fileTransfer 4 }

tftpTotalTimeOut OBJECT-TYPE
    SYNTAX  Integer32
    MAX-ACCESS  read-write
    STATUS  current
    DESCRIPTION
        " Total Retransmission time-out value (seconds) "
    -- DEFVAL  { 60 }
    ::= { fileTransfer 5 }

tftpStatus OBJECT-TYPE
    SYNTAX  INTEGER {
		noOp(2),
		connecting(3),
		transferringData(4),
		endedTimeOut(5),
		endedOk(6),
		error(7)
	}
    MAX-ACCESS  read-write
    STATUS  current
    DESCRIPTION
    "Status of tftp session. When a session ended with success,
    the tftpStatus should be endedOk(6). Before restarting a
    tftp session, the NMS should set the tftpStatus to noOp(2).
    That's the reason of MAX-ACCESS read-write to this field."
    DEFVAL  { noOp}
    ::= { fileTransfer 6 }

tftpError OBJECT-TYPE
    SYNTAX  OCTET STRING ( SIZE(2) )
    MAX-ACCESS  read-only
    STATUS  current
    DESCRIPTION
    " The MSB represents the standard error code.
    The LSB represents the private error code.
    0x0000 is No Error
    0x0100 is File Not Found
	0x0200 is Access violation
	0x0300 is Disk full or allocation exceeded
    0x0400 is Illegal TFTP operation
    0x0500 is Unknown transfer ID
	0x0600 is File already exists
	0x0700 is No such user
    0x0001 is Server Overflow
    0x0002 is No empty UDP port
    0x0003 is No empty connection
    0x0004 is Illegal File Mode
    0x0007 is Illegal PDU size
	0x0008 is TFTP Server does not exist 
	0x0009 is Incorrect File
	0x000A is Wrong License format
	0x000B is License ID already used"
    DEFVAL  { '0000'h }
    ::= { fileTransfer 7 }

fileTransferToSubSystems OBJECT-TYPE
    SYNTAX  OCTET STRING 
    MAX-ACCESS  read-write
    STATUS  current
    DESCRIPTION
    " This object represents the sub-systems the fileTransCmd 
      refers to. It should be used when a system is divided 
      to sub-systems and each sub-system (or part of them) can 
	  have a different SW/Configuration.

	  Each bit of this object will represent one of the sub-systems.
	  Bit='1' - APPLY to respective sub-system
	  Bit='0' - DO NOT APPLY to respective sub-system

	  For the meaning of each bit, see product's specification.
	  User will select the sub-systems envolved by filling-in the bits
      that represent these sub-systems.
      In this case, the file represented by 'fileName' will 
	  include several parts, each representing one of the sub-systems.
	  The agent will refer only to the part/s indicated by this object.

      0 Octet Strings = not applicable  
      DEFVAL = 0h	for  the products that support this object."
    ::= { fileTransfer 8 }

fileNameWithinProduct  OBJECT-TYPE
	SYNTAX  DisplayString
	MAX-ACCESS  read-write
	STATUS  current
	DESCRIPTION
	"The file name used by the product within the product file system."
	::= { fileTransfer 9 }

--Internal SW Download table

intSwdlTable  OBJECT-TYPE 
      SYNTAX SEQUENCE OF IntSwdlEntry
      MAX-ACCESS not-accessible
      STATUS  current
      DESCRIPTION
      "This parameters table is for 
       internal Software down load. It also includes data 
       about all files contained in the Object from which 
       down-load is performed."
      ::= { fileTransfer 10 }

intSwdlEntry OBJECT-TYPE
      SYNTAX IntSwdlEntry
      MAX-ACCESS not-accessible
      STATUS current
	DESCRIPTION  "An entry in table."
	INDEX {intSwdlObjIdx, intSwdlFileIdx }
      ::= { intSwdlTable 1}

IntSwdlEntry ::=
      SEQUENCE {
      intSwdlObjIdx            Integer32,
	  intSwdlFileIdx           Integer32,
	  intSwdlFileName		   DisplayString,
	  intSwdlFileSwVer		   DisplayString,
	  intSwdlSwDate			   DisplayString,
	  intSwdlSize			   DisplayString,
	  intSwdlCmd			   INTEGER,
	  intSwdlToSubSystem	   OCTET STRING,
	  intSwdlCardType		   INTEGER,
	  intSwdlFlashIdx	   	   Integer32
      }

intSwdlObjIdx OBJECT-TYPE
      SYNTAX  Integer32
      MAX-ACCESS  read-only
      STATUS  current
      DESCRIPTION
      "The index of the object from which down-load is performed."
      ::= {intSwdlEntry 1}

intSwdlFileIdx OBJECT-TYPE
      SYNTAX  Integer32
      MAX-ACCESS  read-only
      STATUS  current
      DESCRIPTION
      "The index of the files included in intSwdlObjIdx.
       One of these files can be selected to be internally 
       downloaded."
      ::= {intSwdlEntry 2}

intSwdlFileName OBJECT-TYPE
      SYNTAX  	 DisplayString
      MAX-ACCESS  read-only
      STATUS  current
      DESCRIPTION
      "The name of the file."
      ::= {intSwdlEntry 3}

intSwdlFileSwVer OBJECT-TYPE
      SYNTAX  	 DisplayString
      MAX-ACCESS  read-only
      STATUS  current
      DESCRIPTION
      "The software version of the file."
      ::= {intSwdlEntry 4}

intSwdlSwDate OBJECT-TYPE
      SYNTAX  	 DisplayString
      MAX-ACCESS  read-only
      STATUS  current
      DESCRIPTION
      "The software version date of the file."
      ::= {intSwdlEntry 5}

intSwdlSize OBJECT-TYPE
      SYNTAX  	 DisplayString
      MAX-ACCESS  read-only
      STATUS  current
      DESCRIPTION
      "The size of the file."
      ::= {intSwdlEntry 6}

intSwdlCmd OBJECT-TYPE
      SYNTAX  	  INTEGER
	  				{
					notApplicable		(1),
					off		(2),
					on		(3)
					}
      MAX-ACCESS  read-write
      STATUS  current
      DESCRIPTION
      "The command to down-load a SW file to an object.
       The Agent will change the value of this MIB object to off(2) 
	  automatically, after accepting the command."
      ::= {intSwdlEntry 7}

intSwdlToSubSystem	OBJECT-TYPE   
      SYNTAX  OCTET STRING
      MAX-ACCESS  read-write
      STATUS  current
      DESCRIPTION
      " This object defines the subsystem for download.
       Bit='1'- APPLY to respective sub system.
       Bit='0'- DO NOT APPLY to respective sub system.
       For more details see product specification. 
       For every octet bit0=LSB, bit7=MSB"
      ::= { intSwdlEntry  8 }

intSwdlCardType OBJECT-TYPE
      SYNTAX  	  INTEGER
	  				{
  unknown        (1),  
  gstm1		 	 (220),   -- GMUX-2000 STM1 card
  goc3		 	 (221),   -- GMUX-2000 OC3 card
  gstm1D		 (222),   -- GMUX-2000 STM1 card with 2 ports
  goc3D 		 (223),   -- GMUX-2000 OC3 card	with 2 ports
  serverE1       (270),	  -- GMUX-2000 Server E1 Card
  serverT1       (271),	  -- GMUX-2000 Server T1 Card
  serverE1Pw     (272),   -- Gmux2000 Server E1 PW Card
  serverT1Pw     (273),   -- Gmux2000 Server T1 PW Card
  gigabitEth     (280),	  -- GMUX-2000 Gigabit ETH Card
  gigabitEth2    (281),	  -- Gmux2000 new Gigabit ETH Card	 - 2 GbE ports with SFP connector
  eth2           (282),	  -- Gmux2000 new ETH Card - 2 ETH ports with RJ45 connectors (10/100/1000)
  gigabitEth8    (283),	  -- Gmux2000 new Gigabit ETH Card	 - 8 GbE ports with SFP connector
  eth8           (284),	  -- Gmux2000 new ETH Card - 8 ETH ports with RJ45 connectors (10/100/1000)
  channelizedT3Pw1 (290),	 -- Gmux2000 Channelized T3 PW Card
  cesT128		 (300),	 -- Gmux-2000 CES T1 28 ports (external T1 ports) card.
  cesE128		 (301),	 -- Gmux-2000 CES E1 28 ports (external E1 ports) card.
  cesT1Pw28      (302),	 -- Gmux2000 CES T1 PW ports (external T1 ports) card.
  cesE1Pw28      (303),    -- Gmux2000 CES E1 PW ports (external E1 ports) card.
  vmxE1VeDe		 (310),	  -- Gmux-2000 Vmux E1 card with 16 external voice + 2 external Data ports.
  vmxE1VeDi		 (311),	  -- Gmux-2000 Vmux E1 card with 16 external voice + 2 internal Data ports.
  vmxE1ViDe		 (312),	  -- Gmux-2000 Vmux E1 card with 16 internal voice + 2 external Data ports.
  vmxE1ViDi		 (313),	  -- Gmux-2000 Vmux E1 card with 16 internal voice + 2 internal Data ports.
  vmxT1VeDe		 (314),	  -- Gmux-2000 Vmux T1 card with 16 external voice + 2 external Data ports.
  vmxT1VeDi		 (315),	  -- Gmux-2000 Vmux T1 card with 16 external voice + 2 internal Data ports.
  vmxT1ViDe		 (316),	  -- Gmux-2000 Vmux T1 card with 16 internal voice + 2 external Data ports.
  vmxT1ViDi		 (317),	  -- Gmux-2000 Vmux T1 card with 16 internal voice + 2 internal Data ports.
  vc12E1UeNe  (318),   -- Gmux-2000 Vmux E1 card with 12 external User (voice) + 2 external Network (Data) ports.
  vc12E1UeNi  (319),   -- Gmux-2000 Vmux E1 card with 12 external User (voice) + 2 internal Network (Data) ports.
  vc12E1UiNe  (320),   -- Gmux-2000 Vmux E1 card with 12 internal User (voice) + 2 external Network (Data) ports.
  vc12E1UiNi  (321),   -- Gmux-2000 Vmux E1 card with 12 internal User (voice) + 2 internal Network (Data) ports.
  vc12T1UeNe  (322),   -- Gmux-2000 Vmux T1 card with 12 external User (voice) + 2 external Network (Data) ports.
  vc12T1UeNi  (323),   -- Gmux-2000 Vmux T1 card with 12 external User (voice) + 2 internal Network (Data) ports.
  vc12T1UiNe  (324),   -- Gmux-2000 Vmux T1 card with 12 internal User (voice) + 2 external Network (Data) ports.
  vc12T1UiNi  (325),   -- Gmux-2000 Vmux T1 card with 12 internal User (voice) + 2 internal Network (Data) ports.
  vca16E1UeNe  (326),   -- Gmux-2000 VCA E1 card with 16 external User (voice) + 2 external Network (Data) ports.
  vca16E1UeNi  (327),   -- Gmux-2000 VCA E1 card with 16 external User (voice) + 2 internal Network (Data) ports.
  vca16E1UiNe  (328),   -- Gmux-2000 VCA E1 card with 16 internal User (voice) + 2 external Network (Data) ports.
  vca16E1UiNi  (329),   -- Gmux-2000 VCA E1 card with 16 internal User (voice) + 2 internal Network (Data) ports.
  vca16T1UeNe  (330),   -- Gmux-2000 VCA T1 card with 16 external User (voice) + 2 external Network (Data) ports.
  vca16T1UeNi  (331),   -- Gmux-2000 VCA T1 card with 16 external User (voice) + 2 internal Network (Data) ports.
  vca16T1UiNe  (332),   -- Gmux-2000 VCA T1 card with 16 internal User (voice) + 2 external Network (Data) ports.
  vca16T1UiNi  (333),   -- Gmux-2000 VCA T1 card with 16 internal User (voice) + 2 internal Network (Data) ports.
  vca12E1UeNe  (334),   -- Gmux-2000 VCA E1 card with 12 external User (voice) + 2 external Network (Data) ports.
  vca12E1UeNi  (335),   -- Gmux-2000 VCA E1 card with 12 external User (voice) + 2 internal Network (Data) ports.
  vca12E1UiNe  (336),   -- Gmux-2000 VCA E1 card with 12 internal User (voice) + 2 external Network (Data) ports.
  vca12E1UiNi  (337),   -- Gmux-2000 VCA E1 card with 12 internal User (voice) + 2 internal Network (Data) ports.
  vca12T1UeNe  (338),   -- Gmux-2000 VCA T1 card with 12 external User (voice) + 2 external Network (Data) ports.
  vca12T1UeNi  (339),   -- Gmux-2000 VCA T1 card with 12 external User (voice) + 2 internal Network (Data) ports.
  vca12T1UiNe  (340),   -- Gmux-2000 VCA T1 card with 12 internal User (voice) + 2 external Network (Data) ports.
  vca12T1UiNi  (341),   -- Gmux-2000 VCA T1 card with 12 internal User (voice) + 2 internal Network (Data) ports.
  vmg16E1Ue    (342),	-- Gmux-2000 VMG (Media Gateway) E1 card with 16 external User ports
  vmg16E1Ui    (343),	-- Gmux-2000 VMG (Media Gateway) E1 card with 16 internal User ports
  vmg16T1Ue    (344),	-- Gmux-2000 VMG (Media Gateway) T1 card with 16 external User ports
  vmg16T1Ui    (345),	-- Gmux-2000 VMG (Media Gateway) T1 card with 16 internal User ports
  vmg12E1Ue    (346),	-- Gmux-2000 VMG (Media Gateway) E1 card with 12 external User ports
  vmg12E1Ui    (347),	-- Gmux-2000 VMG (Media Gateway) E1 card with 12 internal User ports
  vmg12T1Ue    (348),	-- Gmux-2000 VMG (Media Gateway) T1 card with 12 external User ports
  vmg12T1Ui    (349)	-- Gmux-2000 VMG (Media Gateway) T1 card with 12 internal User ports


 }
      MAX-ACCESS  read-only
      STATUS  current
      DESCRIPTION
      "This object defines the Card type that this file is relevant for."
      ::= {intSwdlEntry 9}

intSwdlFlashIdx OBJECT-TYPE
      SYNTAX  Integer32
      MAX-ACCESS  read-only
      STATUS  current
      DESCRIPTION
      "The index of the flash memory this file is stored in (1 or 2)
      (Example: 1= The file is stored in flash No.1).
      ASMi52 file will always be stored in Flash No.2 (intSwdlFlashIdx=2)."
      ::= {intSwdlEntry 10}

--SW Download Status table

swdlStatusTable  OBJECT-TYPE 
      SYNTAX SEQUENCE OF SwdlStatusEntry
      MAX-ACCESS not-accessible
      STATUS  current
      DESCRIPTION
      "This parameters table is for software download status. 
       It also includes data about the files down-loaded or 
       attempted to be down-loaded."
      ::= { fileTransfer 11 }

swdlStatusEntry OBJECT-TYPE
      SYNTAX SwdlStatusEntry
      MAX-ACCESS not-accessible
      STATUS current
	DESCRIPTION  "An entry in table."
	INDEX {swdlStatusTypeIdx, swdlStatusIdx }
      ::= { swdlStatusTable 1}

SwdlStatusEntry ::=
      SEQUENCE {
      swdlStatusTypeIdx            Integer32,
	  swdlStatusIdx       		   Integer32,
	  swdlStatusFileName		   DisplayString,
	  swdlStatusSlot			   DisplayString,
	  swdlStatusSubSystem		   DisplayString,
	  swdlStatusStatus			   Integer32,
	  swdlStatusTime			   DisplayString
	       }

swdlStatusTypeIdx OBJECT-TYPE
      SYNTAX  Integer32
      MAX-ACCESS  read-only
      STATUS  current
      DESCRIPTION
      "The index of the down-load type (e.g. external (1) or internal (2))."
      ::= {swdlStatusEntry 1}

swdlStatusIdx OBJECT-TYPE
      SYNTAX  Integer32
      MAX-ACCESS  read-only
      STATUS  current
      DESCRIPTION
      "The index of the status rows."
      ::= {swdlStatusEntry 2}

swdlStatusFileName OBJECT-TYPE
      SYNTAX  	 DisplayString
      MAX-ACCESS  read-only
      STATUS  current
      DESCRIPTION
      "The name of the file."
      ::= {swdlStatusEntry 3}

swdlStatusSlot OBJECT-TYPE
      SYNTAX  	 DisplayString
      MAX-ACCESS  read-only
      STATUS  current
      DESCRIPTION
      "The slot of the updated (or attempted to be updated) object."
      ::= {swdlStatusEntry 4}

 swdlStatusSubSystem OBJECT-TYPE
      SYNTAX  	 DisplayString
      MAX-ACCESS  read-only
      STATUS  current
      DESCRIPTION
      "The subsystem that updated (or attempted to be updated)."
      ::= {swdlStatusEntry 5}

swdlStatusStatus  OBJECT-TYPE
      SYNTAX  	  Integer32
      MAX-ACCESS  read-only
      STATUS  current
      DESCRIPTION
      "The status of the down load process.
	  Value:  Fail (2), OK (3), InProcess (4)."
      ::= {swdlStatusEntry 6}

swdlStatusTime	   OBJECT-TYPE
          SYNTAX   DisplayString
          MAX-ACCESS  read-only
          STATUS  current
          DESCRIPTION
          "This MIB parameter indicates the time SW download was finished.
           The format shuld be YYYY-MM-DD, hh:mm:ss"
          ::= {swdlStatusEntry 7}

clearDwldStatusLog  OBJECT-TYPE
	SYNTAX  Integer32
	MAX-ACCESS  read-write
	STATUS  current
	DESCRIPTION
	"This object clears the status log.
	  Value: off(2), external(3), internal(4)
	  The Agent will change the value of this MIB object to off(2) 
	  automatically, after accepting the command ."
	::= { fileTransfer 12 }
									
autoFileTransfer  OBJECT IDENTIFIER ::= { fileTransfer 13}

-- Agent initiated auto file transfer.
									
autoFileTransferTable  OBJECT-TYPE 
      SYNTAX SEQUENCE OF AutoFileTransferEntry
      MAX-ACCESS not-accessible
      STATUS  current
      DESCRIPTION
      "Scheduling configuration table for 
       Agent initiated file transfer."
      ::= { autoFileTransfer 1 }

autoFileTransferEntry OBJECT-TYPE
      SYNTAX AutoFileTransferEntry
      MAX-ACCESS not-accessible
      STATUS current
      DESCRIPTION  "An entry in the table."
      INDEX { autoFileTransferType}
      ::= { autoFileTransferTable 1}

AutoFileTransferEntry ::=
      SEQUENCE {
                autoFileTransferType 
                  INTEGER,
                autoFileTransferServerIp
                  IpAddress,
                autoFileTransferFileName
                  SnmpAdminString,		
                autoFileTransferScheduling
                  INTEGER,
                autoFileTransferTimeRecurrence
                  Integer32,
                autoFileTransferOccurrenceRecurrence
                  Integer32 
               }

autoFileTransferType  OBJECT-TYPE
	SYNTAX INTEGER
	{
	alarmsBuffer    (1)
	}
	MAX-ACCESS  read-only
	STATUS  current
	DESCRIPTION
	"This object defines the type of file to be transferred 
	 by agent. "
	::= { autoFileTransferEntry 1 }

autoFileTransferServerIp  OBJECT-TYPE
	SYNTAX  IpAddress
	MAX-ACCESS  read-write
	STATUS  current
	DESCRIPTION
	"This object defines the IP Address of the
	 server to which the file is uploaded."
	::= { autoFileTransferEntry 2 }

autoFileTransferFileName  OBJECT-TYPE
	SYNTAX  SnmpAdminString
	MAX-ACCESS  read-write
	STATUS  current
	DESCRIPTION
	"This object defines the name of 
	 the file to be uploaded."
	::= { autoFileTransferEntry 3 }

autoFileTransferScheduling  OBJECT-TYPE
	SYNTAX INTEGER
	{
	notApplicable  (1),
	now            (2),
	recurrence     (3)	
	}
	MAX-ACCESS  read-write
	STATUS  current
	DESCRIPTION
	"This object defines schedule for TFTP Automatic session(s) 
	 initiated by Agent, according to the value selected:
     now          -  initiate immediate single session.

     recurrence- initiate single session 'every M time units'. 
                 or 'every N occurrences' or upon both, (earliest event).
                 Time reccurence period (M) is defined by
				 fileTransferTimeRecurrence.
				 Occurrence reccurence (N) is defined by 
				 fileTransferOccurrenceRecurrence.
                 Zero value means that the object is not relevant (not
                 taken into account for the recurrence). It is invalid 
                 that both will have zero values in our case (recurrence).
				 When both are non zero, file is transferred
				 upon earliest event"
	::= { autoFileTransferEntry 4 }

autoFileTransferTimeRecurrence  OBJECT-TYPE
	SYNTAX      Integer32 
	MAX-ACCESS  read-write
	STATUS      current
	DESCRIPTION										   
	"This object defines time reccurence interval, 
	 e.g. M can be 'every M days', 'every M hours' etc.
	 Zero is used to indicate 
	 there's no time reccurence (0= notApplicable).
	 This object is taken into account only 
	 if autoFileTransferScheduling = recurrence
	 For LA-110 time units are days."
	::= { autoFileTransferEntry 5 }

autoFileTransferOccurrenceRecurrence   OBJECT-TYPE
	SYNTAX      Integer32 
	MAX-ACCESS  read-write
	STATUS      current
	DESCRIPTION
	"This object defines Occurrence reccurence interval, 
	 e.g N can be in 'every N alarms', 'every N log entries' etc.
	 zero is used to indicate 
	 There's no Event Reccurence. (0= notApplicable) 
 	 This object is taken into account only 
	 if autoFileTransferScheduling = recurrence
	 Occurence Type (Alarms, etc.) is according
	 to autoFileTransferType."
	::= { autoFileTransferEntry 6 }

fileTransferServerPort OBJECT-TYPE
    SYNTAX  Unsigned32
    MAX-ACCESS  read-write
    STATUS  current
    DESCRIPTION
    "Server Port number used for File Transfer. 
     Applicable for SFTP.
     Valid values: 0..65535."
    -- DEFVAL  { 22 }
    ::= { fileTransfer 14 }

fileTransferProtocol OBJECT-TYPE
    SYNTAX  INTEGER
	{
	 tftp (1),	--default
	 sftp (2)
    }
    MAX-ACCESS  read-write
    STATUS  current
    DESCRIPTION
    "File Transfer protocol used."
    ::= { fileTransfer 15 }


systemReset  OBJECT-TYPE
	SYNTAX  INTEGER	{
	                 off          (2),
					 on           (3), --HW
					 resetConfig  (4),
					 resetMapping (5),
					 resetStandby (6) 
				    }
	MAX-ACCESS  read-write
	STATUS  current
	DESCRIPTION
	"Reset action to be performed on the system.
	 - resetMapping - reset SDH/SONET mapping to 
	   default for all SDH/SONET links.
	 - resetStandby(6) - can be used only by devices with redundancy on MAIN/CL."
	::= { agnt 13 }

systemTiming  OBJECT IDENTIFIER ::= { agnt 14 }

systemDate OBJECT-TYPE
        SYNTAX  DisplayString
        MAX-ACCESS  read-write
        STATUS  current
        DESCRIPTION
           "System date."
        ::= { systemTiming 1 }
        
systemTime OBJECT-TYPE
        SYNTAX  DisplayString
        MAX-ACCESS  read-write
        STATUS  current
        DESCRIPTION
           "System time."
        ::= { systemTiming 2 }

systemTimeElapsed OBJECT-TYPE
       SYNTAX  Integer32 (0..899)
       MAX-ACCESS  read-only
       STATUS  current
       DESCRIPTION
       "The number of seconds that have elapsed since the
        beginning of the current error-measurement
        period. Same for all ports of the device."
       ::= { systemTiming 3 }


systemNtp  OBJECT IDENTIFIER ::= { systemTiming 4 }	-- Network Time Protocol

systemNtpMode OBJECT-TYPE
	SYNTAX		INTEGER
	{
		disable			(2),
		broadcastClient	(3),
		unicastClient	(4)
	}
	MAX-ACCESS	read-write
	STATUS		current
	DESCRIPTION
	"This variable represents the NTP Mode."
	::= { systemNtp 1 }

systemNtpGmt OBJECT-TYPE
	SYNTAX		Integer32
	MAX-ACCESS	read-write
	STATUS		current
	DESCRIPTION
	"This variable represents the NTP GMT (Greenwich Mean Time),
	 Possible values range is -12..12.
	 For new devices/versions this variable will be in minutes."   
	::= { systemNtp 2 }

systemNtpServerAddressType OBJECT-TYPE
	SYNTAX		InetAddressType
	MAX-ACCESS	read-write
	STATUS		current
	DESCRIPTION
	"This variable represents the NTP Server Address Type."
	::= { systemNtp 3 }

systemNtpServerAddress OBJECT-TYPE
	SYNTAX		InetAddress
	MAX-ACCESS	read-write
	STATUS		current
	DESCRIPTION
	"This variable represents the NTP Server Address."
	::= { systemNtp 4 }

systemNtpUpdateInterval OBJECT-TYPE
	SYNTAX		Unsigned32
	MAX-ACCESS	read-write
	STATUS		current
	DESCRIPTION
	"This variable represents the NTP Update Interval,
	 measured in seconds. It means, minimum time between two
	 consecutive NTP requests."
	::= { systemNtp 5 }

systemNtpCmd OBJECT-TYPE
	SYNTAX		INTEGER
	{
		off					(2),
		sendUpdateRequest	(3)
	}
	MAX-ACCESS	read-write
	STATUS		current
	DESCRIPTION
	"This variable represents NTP possible commands.
	 After the Agent accepts a command, it will automatically change
	 the value to off(2)."
	::= { systemNtp 6 }

systemNtpTimeSinceLastPoll OBJECT-TYPE
    SYNTAX Unsigned32
       MAX-ACCESS read-only
       STATUS current
    DESCRIPTION
    "Time in seconds, that passed from last polling of the configured 
     SNTP servers. 0=Not Applicable (when this time is not known)."
    ::= { systemNtp 7 }

systemNtpModeBITS OBJECT-TYPE
	SYNTAX	    BITS{
	broadcastClient(0)
	}
	MAX-ACCESS	read-write
	STATUS		current
	DESCRIPTION
	"If Bit 0 (broadcastClient) is '1', Broadcast Mode is enabled, 
	 meaning that the device listens to the NTP broadcast messages 
	 and learns timestamps from them.
     If disabled (Bit 0 = '0'), the device ignores NTP broadcast 
     messages.
     Unicast mode is always enabled, therefore there is no special 
     Bit for it."
	::= { systemNtp 8 }

systemNtpCurrentSourceType OBJECT-TYPE
    SYNTAX    InetAddressType  
	MAX-ACCESS	read-only
	STATUS		current
	DESCRIPTION
	"Type IP address of the NTP server currently providing system TOD."
	::= { systemNtp 9 }

systemNtpCurrentSource OBJECT-TYPE
	SYNTAX		InetAddress
	MAX-ACCESS	read-only
	STATUS		current
	DESCRIPTION
	"IP Address (ipv4) of the Server (or Local HW) providing the 
	 current Date and Time of the device.
	 127.0.0.1 = local HW clock is used.
	 0.0.0.0 = no clock is available."
	::= { systemNtp 10 }

sntpServerTable OBJECT-TYPE
    SYNTAX      SEQUENCE OF SntpServerEntry
    MAX-ACCESS  not-accessible
    STATUS      current
    DESCRIPTION
    "This table contains parameters for each NTP Server. 
     Entries in the table can be dynamically created.
	 The entries created by user via sntpServerRowStatus, can also be 
	 changed or removed.
     The table may include also Broadcast Servers, when Broadcast 
     Client Mode is enabled. These are Servers from which the device 
     received timestamp by Broadcast. Their entries are automatically
     created by the device. Entries of these Servers cannot 
     be changed or removed."
    ::= { systemNtp 11 }

sntpServerEntry OBJECT-TYPE
    SYNTAX      SntpServerEntry
    MAX-ACCESS  not-accessible
    STATUS      current
    DESCRIPTION
    "An entry in the NTP Server table."
    INDEX {  sntpServerID }
    ::= { sntpServerTable 1 }

SntpServerEntry ::= SEQUENCE {
    sntpServerID                        Unsigned32,
    sntpServerRowStatus                 RowStatus,
    sntpServerAddressType               InetAddressType,
    sntpServerAddress                   InetAddress,
    sntpServerPort                      InetPortNumber,
    sntpServerPreference                Unsigned32,
    sntpServerAdminStatus               INTEGER,
    sntpServerType                      INTEGER,
    sntpServerLastReceivedTimestamp     DateAndTime,
    sntpServerLastReceivedStratum       Unsigned32,
    sntpServerTimeSinceLastReceivedMessage TimeTicks,
    sntpServerSendRequestNow            INTEGER
    }

sntpServerID    OBJECT-TYPE
    SYNTAX      Unsigned32 
    MAX-ACCESS  not-accessible
    STATUS      current
    DESCRIPTION
    "The number (index) of the NTP Server."
    ::= { sntpServerEntry 1 }

sntpServerRowStatus OBJECT-TYPE
    SYNTAX      RowStatus
    MAX-ACCESS  read-create
    STATUS      current
    DESCRIPTION
    "This object enables creation and deletion of entries
     in the sntpServerTable."
    ::= { sntpServerEntry 2 }

sntpServerAddressType OBJECT-TYPE
    SYNTAX      InetAddressType  
    MAX-ACCESS  read-create
    STATUS      current
    DESCRIPTION
    "Server Address type, indicating IPv4(1) or IPv6(2)."
    ::= { sntpServerEntry 3 }

  sntpServerAddress OBJECT-TYPE
    SYNTAX      InetAddress  
    MAX-ACCESS  read-create
    STATUS      current
    DESCRIPTION
    "IP Address of the NTP Server."
    ::= { sntpServerEntry 4 }

sntpServerPort OBJECT-TYPE
    SYNTAX      InetPortNumber  
    MAX-ACCESS  read-create
    STATUS      current
    DESCRIPTION
    "Source UDP port of the device for sending requests to 
     a configured NTP Server."
	DEFVAL {123}
    ::= { sntpServerEntry 5 }

sntpServerPreference OBJECT-TYPE
    SYNTAX      Unsigned32	   
    MAX-ACCESS  read-create
    STATUS      current
    DESCRIPTION
    "This object marks the Preferred Server. 
     1 = Preferred (only one Server can have this value)
     2 - Not Preferred."
    ::= { sntpServerEntry 6 }

sntpServerAdminStatus OBJECT-TYPE
    SYNTAX      INTEGER {
                up  (1),
                down(2)  
                        }
    MAX-ACCESS  read-create
    STATUS      current
    DESCRIPTION
    "Administrative Status of the NTP Server."
    ::= { sntpServerEntry 7 }

sntpServerType OBJECT-TYPE
    SYNTAX     INTEGER {
               unicast  (1),
               broadcast(2)  
                     }
    MAX-ACCESS  read-only
    STATUS      current
    DESCRIPTION
    "Type of the NTP Server."
    ::= { sntpServerEntry 8 }

sntpServerLastReceivedTimestamp OBJECT-TYPE
    SYNTAX      DateAndTime   	
    MAX-ACCESS  read-only
    STATUS      current
    DESCRIPTION
    "Last received Date and Time from the NTP Server, according to 
     Local Time.
     0000 0000 = Not Applicable."
    ::= { sntpServerEntry 9 }

sntpServerLastReceivedStratum OBJECT-TYPE
    SYNTAX      Unsigned32
    MAX-ACCESS  read-only
    STATUS      current
    DESCRIPTION
    "Last received Stratum from the NTP Server.
     0xFFFFFFFF = Not Applicable."
    ::= { sntpServerEntry 10 }

sntpServerTimeSinceLastReceivedMessage OBJECT-TYPE
    SYNTAX      TimeTicks
    MAX-ACCESS  read-only
    STATUS      current
    DESCRIPTION
    "Time passed since last received message from the NTP Server."
    ::= { sntpServerEntry 11 }

sntpServerSendRequestNow OBJECT-TYPE
    SYNTAX      INTEGER {
                off(2),
                on (3)  
                        }
    MAX-ACCESS  read-create
    STATUS      current
    DESCRIPTION
    "Upon setting this parameter to 'on', an immediate request
     should be sent to the specified NTP Server.
     After sending the request, the value 'off' will be resumed.
     No action when setting this parameter to 'off'"
    ::= { sntpServerEntry 12 }


schedXTable OBJECT-TYPE
	SYNTAX  	SEQUENCE OF SchedXEntry
    MAX-ACCESS  not-accessible
    STATUS  	current
    DESCRIPTION
		"An Augment to the Schedule table
		 (schedTable in DISMAN-SCHEDULE-MIB; RFC-3231)."
     ::= { systemTiming 5 }

schedXEntry OBJECT-TYPE
	SYNTAX  	SchedXEntry
    MAX-ACCESS	not-accessible
    STATUS  	current
    DESCRIPTION
       "An entry in the table."
    AUGMENTS { schedEntry }
     ::= { schedXTable 1 }

SchedXEntry ::=
    SEQUENCE {
		schedYear				Unsigned32,
		schedWeekInMonth		INTEGER,
		schedParam				Integer32
		}

schedYear OBJECT-TYPE
	SYNTAX		Unsigned32
	MAX-ACCESS  read-create
	STATUS  	current
	DESCRIPTION
	"The year during which the scheduled action should take place."
	::= { schedXEntry 1 }

schedWeekInMonth OBJECT-TYPE
	SYNTAX		INTEGER {
     	first		(1),
	 	second 		(2),
	 	third 		(3),
	 	fourth 		(4),
	 	last 		(5)
	}
	MAX-ACCESS  read-create
	STATUS  	current
	DESCRIPTION
	"The week in month (schedMonth) during which the scheduled action
	 should take place."
	::= { schedXEntry 2 }

schedParam OBJECT-TYPE
	SYNTAX		Integer32
	MAX-ACCESS  read-create
	STATUS  	current
	DESCRIPTION
	"A Parameter that might be used whenever the scheduled action takes place.
	 
	 For summer-time schedule -
	 This variable represents the time offset (in minutes), meaning:
	 the number of minutes that should be added for summer-time."
	::= { schedXEntry 3 }


systemPort  OBJECT IDENTIFIER ::= { agnt 15 }

physicalConnectorTable OBJECT-TYPE
	SYNTAX  SEQUENCE OF PhysicalConnectorEntry
	MAX-ACCESS  not-accessible
	STATUS current
	DESCRIPTION
	"This table includes the connector type of ports or interfaces."
	::= {systemPort 1}

physicalConnectorEntry OBJECT-TYPE
	SYNTAX  PhysicalConnectorEntry
	MAX-ACCESS  not-accessible
	STATUS current
	DESCRIPTION  "An entry in table."
	INDEX {portIdx}
	::= { physicalConnectorTable 1 }

PhysicalConnectorEntry  ::=
	    SEQUENCE {
	portIdx
	  Integer32,
	physicalConnector
	  INTEGER,
	portOptWaveLength
	  INTEGER,
	portOptMode
	  INTEGER,
	portBalance
	  INTEGER,
    portDdmSupport
      INTEGER,
    portMfgName
      SnmpAdminString,
    portTypicalMaxRange
      Unsigned32,
    physicalConnectorString
   	  SnmpAdminString,
	portVendorPartNo
	  SnmpAdminString	
	
	  	}

portIdx OBJECT-TYPE
	SYNTAX  Integer32 
	MAX-ACCESS  read-only
	STATUS current
	DESCRIPTION
	"This object is an index of the specific port or interface.
	 For a port, the index will be as agreed between agent and 
	 application.
	 For an interface, ifIndex may be used."
	::= { physicalConnectorEntry 1 }

physicalConnector OBJECT-TYPE
	SYNTAX  INTEGER 
	        {
			other (1),
			v35   (2),	  --34 pin female
			rs530 (3),	  --DB25
			x21   (4),	  --DB15
			bnc   (5),
			utp   (6),	  --RJ45
			aui   (7),
			rs422 (8),	  --DB25
			crossUtp (9), --RJ45
			rj45    (10),
			v24     (11), --DB25
			g703    (12), --TB5
			termBlock3AndRj45 (13),
			terminalBlock3    (14),
			terminalBlock5    (15),
			terminalBlock7    (16),
			db25              (17),
			db15              (18),
			rj45ethernet      (19),
			termBlock5AndRj45 (20),
			db9               (21),
			g703E1            (22),  --BNC-RJ45-BNC	
			g703E1-LTU        (23),  --BNC-RJ45-BNC
			sc                (24),	 --sc optical 
			st                (25),	 --st optical
			stl               (26),
			fc                (27),	 --fc optical
			tb5w              (28),  --Term-Block-5-Wire (for HCD)
			termBlock6AndRj45 (29),
			ethBnc            (30),
			scsi26            (31),  --SCSI with 26 pins
			eth4381           (32),  --RJ45 with two embeded LEDs
			twoBnc			  (33),  --Two BNC
			scsi50            (34),  --SCSI with 50 pins
			twoMiniBnc        (35),  --Two mini BNC
			sf1               (36),  --sf1=single fiber optical 
			terminalBlock4    (37),
			sf2         	  (38),  --sf2=single fiber optical
			db25Balanced      (39),  --DB25 Balanced
			v36               (40),
			block4W           (41),  --like in WR connector for Modems
			iripRj45          (42),
			irEthQRj45        (43),
			iripBnc           (44),
			rs530WA           (45),  --rs530/IR that solves a wander problem for SDH network	 
			v35WA             (46),  --v35/IR that solves a wander problem for SDH network
			irEthQBnc         (47),
			v35Db25           (48),  --V.35 with connector DB25
			rj11              (49),  --Used for FXS & FXO 	 
			mtrj              (50),  --optical
			lc                (51),  --optical
			terminalBlock2    (52),
			irEth10s100       (53),  --IR-ETH 10/100
			scsi68            (54),  -- SCSI 68 pins 
			sf3				  (55),  -- sf3=single fiber of sc optical  
			fcLH			  (56),  -- fc Long Haul
			telco50           (57),  -- TELCO 50
			telco64			  (58),	 -- TELCO 64
			irEthQN			  (59),
			terminalBlock6    (60),
			scLH			  (61),  -- sc Long Haul
			stLH			  (62),  -- st Long Haul
			lcLH			  (63),  -- lc Long Haul 
			sfpIn			  (64),	 -- SFP module is installed (In container)
			sfpOut			  (65),	 -- SFP module is not installed (Out of container)
			db44              (66),	 -- DB44 (High Density D-type)
			db62              (67),  -- DB62 (High Density D-type)
			v24Db9            (68),  -- V.24 with connector DB9
			scsi40            (69),  -- SCSI 40 pins
            sf1NineRow        (70),  -- sf1 9-row
			sf2NineRow        (71),  -- sf2 9-row
			sf3NineRow        (72),  -- sf3 9-row
			smartSerial26     (73),  -- QDC1113L (Cisco)
			miniUsb5          (74),
			db26              (75),  -- DB26 (High Density D-Type)
			comboUtpSfpIn	  (76),	 -- UTP+SFP combo, SFP module is installed
			comboUtpSfpOut	  (77),	 -- UTP+SFP combo, SFP module is not installed
			none              (255)    	
			}	 
	MAX-ACCESS  read-only
	STATUS current
	DESCRIPTION
	"The connector of the port/interface.
	 other - none of the specified connectors
	 none -  no connector."
	::= { physicalConnectorEntry 2 }

portOptWaveLength OBJECT-TYPE
    SYNTAX  INTEGER {
		notApplicable(1),
		nm850(2),
		nm1310(3),
		nm1310Laser(4),
		nm1550Laser(5),
		nm1470Laser(6),
		nm1490Laser(7),
		nm1510Laser(8),
		nm1530Laser(9),
		nm1570Laser(10),
		nm1590Laser(11),
		nm1610Laser(12)
	}
    MAX-ACCESS  read-only
    STATUS  current
    DESCRIPTION
     "Wave Length of an Optical interface/port in [nm] and specification if 
      Laser or not.
      notApplicable - for non-optical ports."
     ::= { physicalConnectorEntry 3 }

portOptMode OBJECT-TYPE
    SYNTAX  INTEGER {
		notApplicable(1),
		singleMode(2),
		multiMode(3)
	}
    MAX-ACCESS  read-only
    STATUS  current
    DESCRIPTION
     "Laser Mode of an Optical Laser interface/port.
       notApplicable - for non-Laser ports."
     ::= { physicalConnectorEntry 4 }

portBalance OBJECT-TYPE
    SYNTAX  INTEGER {
      notApplicable (1), 
      unbalanced    (2),
      balanced      (3)
      }
      MAX-ACCESS  read-write
      STATUS  current
      DESCRIPTION
      "This object is according to the port Impedance.
       For T1 - always balanced.
       For E1 - there are different impedance values for balanced
	            and unbalanced."
     ::= { physicalConnectorEntry 5 }

portDdmSupport  OBJECT-TYPE
    SYNTAX  INTEGER {
      notApplicable (1), 
      no     (2),
      yes    (3)
      }
    MAX-ACCESS  read-only
      STATUS  current
      DESCRIPTION
      "SFP (Small Form Pluggable) port -support
       Digital Diagnostics Monitoring."
     ::= { physicalConnectorEntry 6 }

portMfgName  OBJECT-TYPE
    SYNTAX  SnmpAdminString
    MAX-ACCESS  read-only
      STATUS  current
      DESCRIPTION
      "(SFP) Port Manufacturer name 
       (Maximum - 16 characters)."
     ::= { physicalConnectorEntry 7 }

portTypicalMaxRange  OBJECT-TYPE
    SYNTAX  Unsigned32
    MAX-ACCESS  read-only
      STATUS  current
      DESCRIPTION
      "Maximum range supported by SFP port, 
       in meter units."
     ::= { physicalConnectorEntry 8 }

physicalConnectorString  OBJECT-TYPE
    SYNTAX  SnmpAdminString
    MAX-ACCESS  read-only
      STATUS  current
      DESCRIPTION
      "(SFP) connector type. It can be Vendor Specific
       (unknown in advance). Being a string, the object is not 
       affected by any future new connectors.
       This object will usually not be used 
       for drawing the connector."
     ::= { physicalConnectorEntry 9 }

portVendorPartNo OBJECT-TYPE
    SYNTAX  SnmpAdminString
    MAX-ACCESS  read-only
      STATUS  current
      DESCRIPTION
      "SFP Vendor Part Number. Being a string, the object is not 
       affected by any future new SFPs."
     ::= { physicalConnectorEntry 10 }




prtSupervisory  OBJECT IDENTIFIER ::= { systemPort 2 }

prtSpTable OBJECT-TYPE
      SYNTAX SEQUENCE OF PrtSpEntry
      MAX-ACCESS not-accessible
      STATUS current
	DESCRIPTION  "A table."
	::=  {prtSupervisory 1}

prtSpEntry OBJECT-TYPE
      SYNTAX PrtSpEntry
      MAX-ACCESS not-accessible
      STATUS current
      DESCRIPTION
      "Supervisory port parameter table."
      INDEX {prtSupervisoryIndex }
      ::= { prtSpTable 1}

PrtSpEntry ::=
      SEQUENCE {
      prtSupervisoryIndex         Integer32,
	  prtSupervisoryRate          INTEGER,
	  prtSupervisoryDataBits      INTEGER,
	  prtSupervisoryParity        INTEGER,
	  prtSupervisoryStopBits      INTEGER,
	  prtSupervisoryUsage         INTEGER,
	  prtSupervisoryInterface     INTEGER,
	  prtSupervisoryCTS		      INTEGER,
	  prtSupervisoryDcdDelay      INTEGER,
	  prtSupervisoryDSR		      INTEGER,
	  prtSupervisoryRoutProtocol  INTEGER
      }				  

prtSupervisoryIndex OBJECT-TYPE
      SYNTAX  Integer32
      MAX-ACCESS  read-only
      STATUS  current
      DESCRIPTION
      "The SP port index.
       For some products, having modules (cards): 
       The LS byte of the integer is the port index 1..255. 
       The MS byte is different than 0 only if the port belongs to 
       a module. In	that case it is the module number.
       For other products' index see their specification."
      ::= { prtSpEntry 1}

prtSupervisoryRate     OBJECT-TYPE
      SYNTAX  INTEGER
	      {
        auto      (1),
        s300bps   (2),
        s1200bps  (3),
        s2400bps  (4),
        s4800bps  (5),
        s9600bps  (6),
        s19200bps (7),
        s38400bps (8),
        s57600bps (9),
        s115200bps (10)
	      }
      MAX-ACCESS  read-write
      STATUS  current
      DESCRIPTION
      "This attribute indicates the operation rate (speed) of the 
       port.
       auto - automatic rate selection, by the agent."
      ::= { prtSpEntry 2}

prtSupervisoryDataBits OBJECT-TYPE
      SYNTAX  INTEGER
	      {
        dataBits7 (1),
        dataBits8 (2)
	      }
      MAX-ACCESS  read-write
      STATUS  current
      DESCRIPTION
      "This attribute indicates the number of data bits in an async 
       frame"
      ::= { prtSpEntry 3}

prtSupervisoryParity OBJECT-TYPE
      SYNTAX  INTEGER
	      {
        none  (1),
        odd   (2),
        even  (3)
	      }
      MAX-ACCESS  read-write
      STATUS  current
      DESCRIPTION
      "This attribute indicates the parity mode in an async frame"
      ::= { prtSpEntry 4}

prtSupervisoryStopBits OBJECT-TYPE
      SYNTAX  INTEGER
	      {
		notApplicable  (1),
        stopBits1      (2),
        stopBits1dot5  (3),
        stopBits2      (4)
	      }
      MAX-ACCESS  read-write
      STATUS  current
      DESCRIPTION
      "This attribute indicates the parity mode in an async frame."
      ::= { prtSpEntry 5}

prtSupervisoryUsage OBJECT-TYPE
      SYNTAX  INTEGER
	      {
		unknown (1),
		noUse   (2),
		terminal(3),
		nmsSlip (4),
		nmsPpp  (5),
		muxSlip (6),
		muxPpp  (7),
		dialOut (8)
	      }
      MAX-ACCESS  read-write
      STATUS  current
      DESCRIPTION
      "This attribute indicates the usage of the SP port."
      ::= { prtSpEntry 6}

prtSupervisoryInterface OBJECT-TYPE
      SYNTAX  INTEGER
	      {
		  notApplicable(1),
          dce  (2),
          dte  (3)
	      }
      MAX-ACCESS  read-write
      STATUS  current
      DESCRIPTION
      "This attribute indicates the supervisory port interface."
      ::= { prtSpEntry 7}

prtSupervisoryCTS OBJECT-TYPE
      SYNTAX  INTEGER
	      {
          	notApplicable   (1),
          	on            	(2),        --Old value for DCE.
			rts           	(3),        --Old value for DCE 
			dteWait         (4),        --DTE will wait for CTS to become active before transmit date.
			dteIgnore       (5)         --DTE will Ignore CTS signal and will transmit date anyway.
	      }
      MAX-ACCESS  read-write
      STATUS  current
      DESCRIPTION
	  "CTS line state." 
      ::= { prtSpEntry 8}

prtSupervisoryDcdDelay OBJECT-TYPE
      SYNTAX  INTEGER
	      {
          notApplicable (1),
          d0   (2),
          d10  (3),
		  d50  (4),
		  d100 (5),
		  d200 (6),
		  d300 (7)
	      }
      MAX-ACCESS  read-write
      STATUS  current
      DESCRIPTION
	  "DCD delay in msec." 
      ::= { prtSpEntry 9}

prtSupervisoryDSR OBJECT-TYPE
      SYNTAX  INTEGER
	      {
          notApplicable (1),
          on   (2),
          dtr  (3)
	      }
      MAX-ACCESS  read-write
      STATUS  current
      DESCRIPTION
	  "DSR line state." 
      ::= { prtSpEntry 10}

prtSupervisoryRoutProtocol OBJECT-TYPE
      SYNTAX  INTEGER
       {
        notApplicable (1),
  		none          (2),
        proprietary   (3),
        rip2          (4)
       }
      MAX-ACCESS  read-write
      STATUS  current
      DESCRIPTION
      "This attribute indicates the routing protocol of the port.
       notApplicable - for DP."
      ::= { prtSpEntry 11}




--Port Performance Data

prtPerformance  OBJECT IDENTIFIER ::= { systemPort 3 }

prtPerfTable OBJECT-TYPE
	SYNTAX  SEQUENCE OF PrtPerfEntry
	MAX-ACCESS  not-accessible
	STATUS current
	DESCRIPTION
	"This table includes G.826 ports or interfaces."
	::= {prtPerformance 1}

prtPerfEntry OBJECT-TYPE
	SYNTAX  PrtPerfEntry
	MAX-ACCESS  not-accessible
	STATUS current
	DESCRIPTION  "An entry in table."
	INDEX {prtPerfIdx, prtPerfPeriodRef}
	::= { prtPerfTable 1 }

PrtPerfEntry  ::=
	    SEQUENCE {
	prtPerfIdx
	  Integer32,
	prtPerfPeriodRef
	  INTEGER,
	prtPerfElapsedTime
	  Integer32,
	prtPerfUAS
	  Integer32,
	prtPerfES
	  Integer32,
	prtPerfSES
	  Integer32,
	prtPerfBBE
	  Integer32,
	prtPerfBlocksPerSec
	  Integer32,
	prtPerfTimeTag
	  TimeTicks,
	prtPerfSaveAndResetCmd
	  INTEGER
	  }

prtPerfIdx OBJECT-TYPE
	SYNTAX  Integer32 
	MAX-ACCESS  read-only
	STATUS current
	DESCRIPTION
	"This object is an index of the specific port or interface.
	 For a port, the index will be as agreed between agent and 
	 application.
	 For an interface, ifIndex may be used."
	::= { prtPerfEntry 1 }

prtPerfPeriodRef OBJECT-TYPE
	SYNTAX  INTEGER 
	      {
          currentPeriod (1),
          lastPeriod    (2)
	      }
	MAX-ACCESS  read-only
	STATUS  current
	DESCRIPTION
	"This object is an index that specifies which period of time, the next
	 5 objects refer to.
	 currentPeriod - the period since last prtPerfSaveAndResetCmd received or
	           since Start-up (if no prtPerfSaveAndResetCmd was received since
	           Start-up) until now.
	 lastPeriod - the period between last two commands of prtPerfSaveAndResetCmd.
	           - If only one command occured since Start-up: the period between 
	             Start-up and last command.
	           - If no command occured since Start-up: this period will not 
	             actually exist. In this case, he following 5 objects will be 0."
	::= { prtPerfEntry 2 }

prtPerfElapsedTime OBJECT-TYPE
	SYNTAX  Integer32 
	MAX-ACCESS  read-only
	STATUS  current
	DESCRIPTION
	"Elapsed Time in seconds.
	 - for prtPerfPeriodRef=currentPeriod:
	   The period since last prtPerfSaveAndResetCmd received or	since Start-up 
	   (if no prtPerfSaveAndResetCmd was received since	Start-up) until now.
	 - for prtPerfPeriodRef=lastPeriod:
	   The value of prtPerfElapsedTime when last prtPerfSaveAndResetCmd
	   was received."
	::= { prtPerfEntry 3 }

prtPerfUAS OBJECT-TYPE
	SYNTAX  Integer32 
	MAX-ACCESS  read-only
	STATUS  current
	DESCRIPTION
	"Number of Unavailable Seconds for the reference period (prtPerfPeriodRef)."
	::= { prtPerfEntry 4 }

prtPerfES OBJECT-TYPE
	SYNTAX  Integer32 
	MAX-ACCESS  read-only
	STATUS  current
	DESCRIPTION
	"Number of Errored Seconds for the reference period (prtPerfPeriodRef)."
	::= { prtPerfEntry 5 }

prtPerfSES OBJECT-TYPE
	SYNTAX  Integer32 
	MAX-ACCESS  read-only
	STATUS  current
	DESCRIPTION
	"Number of Severely Errored Seconds for the reference period (prtPerfPeriodRef)."
	::= { prtPerfEntry 6 }

prtPerfBBE OBJECT-TYPE
	SYNTAX  Integer32 
	MAX-ACCESS  read-only
	STATUS  current
	DESCRIPTION
	"Number of Background Block (or Frame) Errors for the reference period 
	 (prtPerfPeriodRef)."
	::= { prtPerfEntry 7 }

prtPerfBlocksPerSec OBJECT-TYPE
	SYNTAX  Integer32 
	MAX-ACCESS  read-only
	STATUS  current
	DESCRIPTION
	"Blocks per second (or frames per second) of the port/interface indicated by 
	 portIdx. This object is constant for a certain port/interface.
	 It is not affected by the prtPerfPeriodRef index."
	::= { prtPerfEntry 8 }

prtPerfTimeTag OBJECT-TYPE
	SYNTAX  TimeTicks 
	MAX-ACCESS  read-only
	STATUS  current
	DESCRIPTION
	"Time Tag of Last Period: sysUpTime when last prtPerfSaveAndResetCmd was
	 executed.
	 This object is applicable only for prtPerfPeriodRef=lastPeriod.
	 For prtPerfPeriodRef=currentPeriod, the value will always be 0."
	::= { prtPerfEntry 9 }

prtPerfSaveAndResetCmd OBJECT-TYPE
    SYNTAX   INTEGER
	      {
    		off(2),
	    	on (3)
	      }
    MAX-ACCESS  read-write
    STATUS  current
    DESCRIPTION
    "A command per port/interface, to Save data of Current Period in Last Period
     data-set and start a new counting period for Current Period.
     This object is applicable only for prtPerfPeriodRef=currentPeriod.
     Setting this object to on(3) for prtPerfPeriodRef=last, will cause the agent
     to return: Bad Value response.
     When setting validly this object to on(3), agent will perform the required 
     command and will reset automatically the value of this object to off(2).
     Setting this object to off(2), will do nothing."
    ::= { prtPerfEntry 10 }

--Port Test Data

prtTest OBJECT IDENTIFIER ::= { systemPort 4 }

prtTestTable OBJECT-TYPE
	SYNTAX  SEQUENCE OF PrtTestEntry
	MAX-ACCESS  not-accessible
	STATUS current
	DESCRIPTION
	"This table includes test data for ports or interfaces."
	::= {prtTest 1}

prtTestEntry OBJECT-TYPE
	SYNTAX  PrtTestEntry
	MAX-ACCESS  not-accessible
	STATUS current
	DESCRIPTION  "An entry in table."
	INDEX {prtTestIdx}
	::= { prtTestTable 1 }

PrtTestEntry  ::=
	    SEQUENCE {
     	prtTestIdx
	    Integer32,
    	prtTestCmdAndStatus
        Integer32,
    	prtBertCounter
        Integer32,
		prtTestInitiator
		INTEGER,
		prtTestTimeout
		Integer32,
		prtTestVctRxResult
		INTEGER,
		prtTestVctTxResult
		INTEGER,
		prtTestVctRxDistance
		Integer32,
		prtTestVctTxDistance
		Integer32,
		prtTestVctCmd
		INTEGER,
		prtTestVctRxCrossPair
		Integer32,
		prtTestVctTxCrossPair
		Integer32,
		prtTestActivationDelay
		Unsigned32,
        prtTestMacSwapLoopDataMode
        INTEGER,
		prtTestMacSwapLoopVlanId
		Integer32,
		prtTestMacSwapLoopDirection
		INTEGER,
		prtTestMacSwapLoopDestAddr
		MacAddress,
		prtTestMacSwapLoopSrcAddr
		MacAddress,
		prtTestOamMinRoundTripDelay 
		Unsigned32,
		prtTestOamMaxRoundTripDelay 
		Unsigned32,
		prtTestOamAvgRoundTripDelay
		Unsigned32,
		prtTestOamTxInterval
		Unsigned32,
		prtTestDestinationIpAddress
		IpAddress,
		prtTestForceTTL
		Unsigned32,
		prtTestBwProfile
		Unsigned32,
		prtTestSourceIpAddress
		IpAddress,
		prtTestRemainTime
		Unsigned32			
        } 

prtTestIdx OBJECT-TYPE
	SYNTAX  Integer32  
	MAX-ACCESS  read-only
	STATUS current
	DESCRIPTION
	"This object is an index of the specific port or interface.
	 For a port, the index will be as agreed between agent and 
	 application.
	 For an interface, ifIndex may be used."
	::= { prtTestEntry 1 }

prtTestCmdAndStatus OBJECT-TYPE
      SYNTAX  Integer32
      MAX-ACCESS  read-write
      STATUS  current
      DESCRIPTION
      "Setting this object to a value as detailed further on 
       (except 0) will initiate a test on the specific port. 
       The test/s requested will be set according to the respective
       bit. The value of this object will be a sum of (2**n), where n is
       the Bit:
         TEST                          BIT	                     VALUE
        -----------                    ---						------
        reserved                        0						   1
		PayloadLoop=RLB              	1 (=Remote Loopback)	   2
        LineLoop=DIG                    2 (=Digital)			   4
        OtherLoop                       3						   8
        InwardLoop=LLB                  4 (=Local Loopback)       16
        BERT                            5						  32
        LC                              6                         64
		ToneInjection		         	7						 128
		Inband 				            8			   			 256
		BERT Remote	(or E1/T1 RLB)     	9 						 512
		Downstream-AIS (or E1/T1 LLB)  10						1024
		Upstream-AIS                   11						2048
		Rem-Loop-on-Rem-Unit           12                       4096
		MacSwapLoop                    13                       8192
		OamETHLoopback                 14					   16384
		OamETHLinkTrace				   15					   32768
		IPSwapLoop                     16                      65536


        e.g : If the requested value is 20 -> 010100  ->
              Bits 2 & 4 are set -> the requested tests are :
                                    LineLoopback=DIG
                                    InwardLoopback=LLB
                                      
       Not all tests combinations are valid.
	   For valid test combination, see each product's specification.
	   For LRS52, only single test is allowed simultaneously

       The terminology and order of the first tests (except BERT) 
       is according to the one used for Test Status of DS1 and DS3 standards.
	   The notations : RLB, LLB, DIG are the most used in RAD's products, but they 
	   can be different. For exact definition see product's spec. 

       Setting this object to stop (value=0 ; all bits are 0), 
       will stop all the user requested tests running on the 
       selected port.

       When no test is running on the port, the Get value (test status)
	   will be 0.

	   PayloadLoop=RLB
	     The received signal at this interface is looped
	     through the device.  Typically the received signal
	     is looped back for retransmission after it has
	     passed through the device's framing function.

	   LineLoop=DIG
	     The received signal at this interface does not
	     go through the device (minimum penetration) but
	     is looped back out.

	   OtherLoop
	     Loopbacks that are not defined here.

	   InwardLoop=LLB 
	     The sent signal at this interface is looped back
	     through the device.

	   LC
	     This loop is applicable only for HSSI interface, towards the router .
	   
	   ToneInjection
		 This loop is applicable for analog voice (like FXS).

	   Downstream-AIS 	 
	   E1 AIS signal (all ones) is transmitted in the relevant channel
	   toward the STM-1 line.

	   Upstream-AIS
	   E1 AIS signal (all ones) is generated in the relevant channel
	   toward the local received tributary channel output 

	   Rem-Loop-on-Rem-Unit 
	   Request from far end device to activate remote loopback 
	   towards near-end device
	   
	   MacSwapLoop
	     This loop is applicable for ethernet port. Loop is 
		 implemented by swapping the MAC addresses of the 
		 incoming message.
		 
	   OamETHLoopback
	      Ethernet Loopback is used to verify connectivity of a MEP with a MIP
	      or peer MEP(s) (ITU-T Y.1731, Clause 7.2).

	   OamETHLinkTrace
	      Ethernet Link Trace is an on-demand OAM function which can be used for
	      the two following purposes:
	      - Adjacent Relation Retrieval
	      - Fault Localization
	      (ITU-T Y.1731, Clause 7.3).
	      
	   IPSwapLoop
	     This loop is applicable for ethernet port. Loop is 
		 implemented by swapping the IP addresses of the 
		 incoming message.In ETX-202A, this test causes also swapping of 
		 the the MAC address (bit 13 should also be set to 1).
   
	      
	      "

   	  ::= { prtTestEntry 2 }

prtBertCounter   OBJECT-TYPE
      SYNTAX  Integer32
      MAX-ACCESS  read-only
      STATUS  current
      DESCRIPTION
      "This object indicates the number of BERT errors encountered
       during the BERT operation.
       It is valid only when BERT (Bit Error Rate Test) is active on the 
       specific port.
       The Counter starts from zero (0) anytime BERT is initiated."
      ::= { prtTestEntry 3}

prtTestInitiator OBJECT-TYPE
    SYNTAX   INTEGER
	      {
    		unknown   (1),
    		user      (2),
	    	remoteUnit(3),
			dteRouter (4)
	      }
    MAX-ACCESS  read-only
    STATUS  current
    DESCRIPTION
    "This object indicates who initiated this port's test/s."
    ::= { prtTestEntry 4 }

prtTestTimeout OBJECT-TYPE
   SYNTAX   Integer32  (0..86400)
   MAX-ACCESS  read-write
   STATUS  current
   DESCRIPTION
   "This object is applicable only when a single 
   test is running. It indicates the test 
   activation timeout in minutes.
   For RICi-E1T1, RICi-E3T3 and LRS-16, the measurement
   unit is in seconds.
   When the timeout expires, the test is stopped.
   Value of 0 indicates test may run Forever "
   ::= { prtTestEntry 5 }

prtTestVctRxResult OBJECT-TYPE
    SYNTAX   INTEGER
	      {
    		notApplicable  (1),
    		fail		   (2),
	    	normal		   (3),
			open		   (4),
			short		   (5),
			shortToCrossPair (6),
			coupleWithCrossPair (7)
	      }
    MAX-ACCESS  read-only
    STATUS  current
    DESCRIPTION
    "This object indicates the result of the Vct on 
    the cable connected to the RX connector."
    ::= { prtTestEntry 6 }

prtTestVctTxResult OBJECT-TYPE
    SYNTAX   INTEGER
	      {
    		notApplicable  (1),
    		fail		   (2),
	    	normal		   (3),
			open		   (4),
			short		   (5),
			shortToCrossPair (6),
			coupleWithCrossPair (7)
	      }
    MAX-ACCESS  read-only
    STATUS  current
    DESCRIPTION
    "This object indicates the result of the Vct on 
    the cable connected to the TX connector."
    ::= { prtTestEntry 7 }

prtTestVctRxDistance OBJECT-TYPE
   SYNTAX   Integer32  
   MAX-ACCESS  read-only
   STATUS  current
   DESCRIPTION
   "This object indicates the distance in Meters 
   to the RX cable Open/ Short location discovered by the Vct.
   This parameter is applicable for Vct Result = Normal or Fail only, 
   Else the value of this parameter will be equal to 0."
   ::= { prtTestEntry 8 }

prtTestVctTxDistance OBJECT-TYPE
   SYNTAX   Integer32  
   MAX-ACCESS  read-only
   STATUS  current
   DESCRIPTION
   "This object indicates the distance in Meters 
   to the TX cable Open/ Short location discovered by the Vct.
   This parameter is applicable for Vct Result = Normal or Fail only, 
   Else the value of this parameter will be equal to 0."
   ::= { prtTestEntry 9 }

prtTestVctCmd OBJECT-TYPE
	SYNTAX  INTEGER
	{
	 off  (2),
	 on   (3)
	 	 }
	MAX-ACCESS  read-write
	STATUS current
	DESCRIPTION
	"Vct command.
	 on (3) = Start Vct on both cables connected to 
	 RX and TX connectors of this port.
	 Agent will perform the required command and change automatically 
	 the value of this object to off(2)."
    ::= { prtTestEntry 10 }

prtTestVctRxCrossPair OBJECT-TYPE
   SYNTAX   Integer32  
   MAX-ACCESS  read-only
   STATUS  current
   DESCRIPTION
   "This object should be equal to the Index (prtTestIdx) of the Rx cross pair. 
    This object is applicable only for Vct Result = shortToCrossPair or coupleWithCrossPair.
    This object was especially created for ETX-202. Currently not in use."
   ::= { prtTestEntry 11 }

prtTestVctTxCrossPair OBJECT-TYPE
   SYNTAX   Integer32  
   MAX-ACCESS  read-only
   STATUS  current
   DESCRIPTION
   "This object should be equal to the Index (prtTestIdx) of the Tx cross pair.
    This object is applicable only for Vct Result = shortToCrossPair or coupleWithCrossPair."
   ::= { prtTestEntry 12 }


prtTestActivationDelay OBJECT-TYPE
   SYNTAX   Unsigned32  
   MAX-ACCESS  read-write
   STATUS  current
   DESCRIPTION
   "This object is applicable only when a single test is running. 
   It indicates test activation delay in seconds.
   A Value of 0 indicates that the test starts immediately."
   ::= { prtTestEntry 13 }


prtTestMacSwapLoopDataMode OBJECT-TYPE
   SYNTAX      INTEGER
   {
 	   all          (1),
	   allExceptMng (2),
	   specificVlan (3)
   }
   MAX-ACCESS  read-write
   STATUS      current
   DESCRIPTION
   "This object defines which part 
   of the data will be looped back."
   ::= { prtTestEntry 14 }


prtTestMacSwapLoopVlanId OBJECT-TYPE
   SYNTAX      Integer32
   MAX-ACCESS  read-write
   STATUS      current
   DESCRIPTION
   "This object specifies the VLAN ID  for 
   prtTestMacSwapLoopDataMode=specificVlan."
   ::= { prtTestEntry 15 }


prtTestMacSwapLoopDirection OBJECT-TYPE
   SYNTAX      INTEGER
   {
       local   (2),	  
       remote  (3) 
   }
   MAX-ACCESS  read-write
   STATUS      current
   DESCRIPTION
   "This object defines the direction of the performed loopback.
   In ETX102 'local' corresponds to Ingress loop
   (either on User port or on Network port), and
   'remote' corresponds to Egress loop
   (either on User port or on Network port)."
   ::= { prtTestEntry 16 }


prtTestMacSwapLoopDestAddr  OBJECT-TYPE
	SYNTAX  MacAddress 
	MAX-ACCESS  read-write
	STATUS current
	DESCRIPTION
	"Configures the MAC address that will be sent in the 
	 Destination field of the packet in the outgoing direction. "
	::= { prtTestEntry 17 }

prtTestMacSwapLoopSrcAddr  OBJECT-TYPE
	SYNTAX  MacAddress 
	MAX-ACCESS  read-write
	STATUS current
	DESCRIPTION
	"Configures the MAC address that will be sent in the 
	Source field of the packet in the outgoing direction. "
	::= { prtTestEntry 18 }

prtTestOamMinRoundTripDelay     OBJECT-TYPE
    SYNTAX        Unsigned32
    MAX-ACCESS    read-only
    STATUS        current
    DESCRIPTION
    "The mininal value of round trip delay of loopback message for a session of 
    OAM loopback.Units are msec."
     ::= { prtTestEntry 19 }

prtTestOamMaxRoundTripDelay     OBJECT-TYPE
    SYNTAX        Unsigned32
    MAX-ACCESS    read-only
    STATUS        current
    DESCRIPTION
    "The maximum value of round trip delay of loopback message for a session of 
    OAM loopback.Units are msec."
     ::= { prtTestEntry 20 }

prtTestOamAvgRoundTripDelay     OBJECT-TYPE
    SYNTAX        Unsigned32
    MAX-ACCESS    read-only
    STATUS        current
    DESCRIPTION
    "The average round trip delay of loopback message for a session of 
    OAM loopback.Units are msec."
     ::= { prtTestEntry 21 }

prtTestOamTxInterval  OBJECT-TYPE
     SYNTAX       Unsigned32
     MAX-ACCESS  read-write
     STATUS  current
     DESCRIPTION
     "Indicates the interval between loopback sent messages.Units are msec."
    ::= { prtTestEntry 22 }

prtTestDestinationIpAddress  OBJECT-TYPE
     SYNTAX       IpAddress
     MAX-ACCESS  read-write
     STATUS  current
     DESCRIPTION
     "Indicates the destination IP Address in the transmitted messages that
      are looped back."
    ::= { prtTestEntry 23 }

prtTestForceTTL  OBJECT-TYPE
     SYNTAX       Unsigned32
     MAX-ACCESS  read-write
     STATUS  current
     DESCRIPTION
     "Time-to-live.Number of hops the loopback message will go through the net 
      before deciding to discard it."
    ::= { prtTestEntry 24 }

prtTestBwProfile  OBJECT-TYPE
     SYNTAX       Unsigned32
     MAX-ACCESS  read-write
     STATUS  deprecated
     DESCRIPTION
     "Indicates the BW profile (from bwProfileTable) that is assigned to the loopback test
      in order to limit the traffic that is looped back."
    ::= { prtTestEntry 25 }

prtTestSourceIpAddress  OBJECT-TYPE
     SYNTAX       IpAddress
     MAX-ACCESS  read-write
     STATUS  current
     DESCRIPTION
     "Indicates the source IP Address in the transmitted messages that
      are looped back."
    ::= { prtTestEntry 26 }

prtTestRemainTime OBJECT-TYPE
   SYNTAX   Unsigned32
   MAX-ACCESS  read-write
   STATUS  current
   DESCRIPTION
   "Indicates the remain time for test activation 
   in seconds."
   ::= { prtTestEntry 27 }

		  
--Port General Parameters

prtParam OBJECT IDENTIFIER ::= { systemPort 5 }

prtParamTable OBJECT-TYPE
	SYNTAX  SEQUENCE OF PrtParamEntry
	MAX-ACCESS  not-accessible
	STATUS current
	DESCRIPTION
	"This table includes general port parameters. The meaning is
	 different for every product that supports it due to a general
     parameter - prtControlCnfg.
	 
	 For ACE2002:
	 -This table is used as a mechanism to create the next interface index.
      The algorithm description: 
      The NMS will send the agent the following get command: get(nextIfIndex.index), 
      where index=interface on which the new index is dependent on. 
      Upon this command the agent will generate and return the new index to the NMS.
     - This table is partially supported according to the interface type. 
       Upon getNext function the irrelevant parameters will be skipped."
	::= {prtParam 1}

prtParamEntry OBJECT-TYPE
	SYNTAX  PrtParamEntry
	MAX-ACCESS  not-accessible
	STATUS current
	DESCRIPTION  "An entry in table."
	INDEX {prtParamIdx}
	::= { prtParamTable 1 }

PrtParamEntry  ::=
	    SEQUENCE {
   prtParamIdx		            Integer32,
   prtControlCnfg 	            Integer32,
   prtParamClkSrc 	            INTEGER,
   prtParamPhantom	            INTEGER,
   prtParamResetStatsCmd	    INTEGER,
   prtParamLastResetStatsTime	TimeStamp,
   prtParamInterfaceType	  	INTEGER,
   prtParamClearAlarm		  	INTEGER,
   prtParamLeds			  	    OCTET STRING,
   prtParamLineLength		  	INTEGER,
   prtParamUsage			  	INTEGER,
   prtParamMappingMode		    INTEGER,
   prtParamAlarmIndication	  	INTEGER,
   prtParamClkQualityLevel	    OCTET STRING,
   prtParamClkWaveShape		    INTEGER,
   prtParamStatus			    INTEGER,
   prtParamSignalLevel		  	Integer32,
   prtParamClkUserQualityLevel  OCTET STRING,
   prtParamDataRate			    Unsigned32,
   prtParamLoopDetect		  	INTEGER,
   prtParamActUponLoopDetect    OCTET STRING,
   prtParamPSNLayer             INTEGER,
   prtParamRxSsm				INTEGER,
   prtParamClkSsmRxSource		INTEGER,
   prtParamFarEndDevice         Unsigned32,
   prtParamTxClk				INTEGER,
   prtParamSdBerThreshold       Unsigned32,
   prtParamLoopDetectStatus     INTEGER
		}

prtParamIdx OBJECT-TYPE
	SYNTAX  Integer32 
	MAX-ACCESS  read-only
	STATUS current
	DESCRIPTION
	"This object is an index of the specific port or interface.
	 For a port, the index will be as agreed between agent and 
	 application.
	 For an interface, ifIndex may be used.
	 
	 For ACE2002:
	 This parameter is the physical layer ifIndex of the slot on 
     which the NMS requires the next interface index."
	::= { prtParamEntry 1 }

prtControlCnfg OBJECT-TYPE
	SYNTAX  Integer32 
	MAX-ACCESS  read-write
	STATUS current
	DESCRIPTION
	"This object may be used for port RW general parameter/s.
	 For detailed meaning, see product's spec.
	 Supported by: PRBi-E3/T3.
	 
	 For ACE2002:
	 This parameter will include the value of the new index 
	 generated by agent.
	 
	 For Optimux-T3 and OP-155-1:
	 This parameter will be used for Release Remote LLB Command:
	 on=2= Set value only. Command to release LLB of Remote Unit.
	       Agent will return automatically to 'off' value after performing
	       the command.
	 off=3=Get value only.
	 
	 
	 For LA140
	 This parameter will be used as EchoCanceler per timeslot
	 off = 2 Echo Canceler is disabled
	 on =  3 Echo Canceler is enabled 
	 
	 For FCD-155
	 This parameter will be used to select the port that is
	 clock source for a PDH port, 
		 For E1/T1 PDH
		 VC12/VT1.5 = 2
		 SDH/SONET  = 3
		 For E3/T3 PDH
		 VC3/DS3  = 2
		 SDH/SONET = 3         
	 
	 For ACE-52
	 This parameter will be used as Transmit Frame Type, i.e. 
	 which type of frame the corresponding bridge port will transmit:
	 Untagged = 2
	 Tagged = 3 
	 ."
	::= { prtParamEntry 2 }

prtParamClkSrc OBJECT-TYPE
    SYNTAX  INTEGER {
       loopTiming    (1),
       localTiming   (2),
       throughTiming (3),
	   adaptive      (4),
	   master        (5),
	   fallback      (6),
	   station       (7),
       notApplicable (255)
    }
    MAX-ACCESS  read-write
    STATUS  current
    DESCRIPTION
       "The source of Transmit Clock.
        'loopTiming' or 'loopback' indicates that the recovered receive clock 
         is used as the transmit clock.

        'localTiming' or 'internal' indicates that a local clock
         source is used or when an external clock is
         attached to the box containing the interface.

        'throughTiming' or 'external' indicates that recovered receive clock 
         from another card or interface is used as the transmit clock.
         
        'adaptive' indicates that the clock is recovered according
         to the received data flow rate. 

        'master' and 'fallback' values may be used RO to 
         indicate active clock.
                  
         'station' - indicate clock received from station 
          port is used as transmit clock."      
	::= { prtParamEntry 3 }

prtParamPhantom OBJECT-TYPE
    SYNTAX  INTEGER {
       notApplicable (1),
       disable       (2),
       enable        (3)
	}
	MAX-ACCESS  read-write
	STATUS current
	DESCRIPTION
	"Power feeding to another device."
	::= { prtParamEntry 4 }

prtParamResetStatsCmd OBJECT-TYPE
    SYNTAX  INTEGER {
       off(2),
	   on (3)
	}
    MAX-ACCESS  read-write
    STATUS  current
    DESCRIPTION
    "Reset statistics of the selected port."
    ::= { prtParamEntry 5 }

prtParamLastResetStatsTime OBJECT-TYPE
     SYNTAX  TimeStamp
     MAX-ACCESS  read-only
     STATUS  current
     DESCRIPTION
     "The value of MIB II's sysUpTime object at the last time that 
      prtParamResetStatsCmd was Set to on(3) for this port.  
      If prtParamResetStatsCmd was never Set to on(3) since last 
      re-initialization of the agent, then this object contains a zero value.
      This object enables calculating the running time of Statistics
      counters for this port, by: [sysUpTime-prtParamLastResetStatsTime].
      For some devices other types of 'Reset' may affect this parameter"
     ::= { prtParamEntry 6 }

prtParamInterfaceType OBJECT-TYPE
    SYNTAX  INTEGER {
	   notApplicable (1),
       e1            (2),
       t1            (3),
       fr            (4),
	   hdlc          (5),
	   hdsl2         (6),
	   shdsl         (7),
	   adsl          (8),
	   adsl2         (9),
	   reAdsl2      (10),
	   mPair        (11),
	   efm          (12), --64-65 Octets
	   atmIma		(13),
	   ds1          (14)
    }
    MAX-ACCESS  read-write
    STATUS  current
    DESCRIPTION
       "The type of the port."
	::= { prtParamEntry 7 }

prtParamClearAlarm OBJECT-TYPE
    SYNTAX  INTEGER {
       off (2),
       on  (3)
    }
    MAX-ACCESS  read-write
    STATUS  current
    DESCRIPTION
       "Setting this attribute to ON, will enforce a clear 
       operation on the Port Alarms.
       Upon completion, the value will automatically change
       to off(2)."
	::= { prtParamEntry 8 }

prtParamLeds  OBJECT-TYPE
	SYNTAX  OCTET STRING
	MAX-ACCESS  read-only
	STATUS current
	DESCRIPTION
	"This entry specifies the LEDs status of the port.
	 Each led is represented by 4 bits where the first 2 bits
	 (left) specify  the status :
	 (00=NA, 01=OFF, 10=ON, 11=BLINK),
     and the next two bits (right) specify the color :
     (00=GREEN, 01=RED, 10=YELLOW, 11=GRAY).
     The order of the LEDS is from top to bottom, left to right:
     For each row starting from the top, 
     the LEDS are returned from left to right."
     ::= {prtParamEntry 9}

prtParamLineLength OBJECT-TYPE
    SYNTAX  INTEGER {
	   notApplicable (1),
       long    (2),
       normal  (3),
	   short   (4)
    }
    MAX-ACCESS  read-write
    STATUS  current
    DESCRIPTION
    "Line Length of the line connected to this port."
	::= { prtParamEntry 10 }

prtParamUsage OBJECT-TYPE
	SYNTAX  INTEGER {
	 notApplicable   (1),
	 user		     (2),
	 network	     (3)
	}
	MAX-ACCESS  read-write
	STATUS  current
	DESCRIPTION
	"Defines whether this port works as User port or as Network port."
	::= { prtParamEntry 11 }
		
prtParamMappingMode  OBJECT-TYPE
      SYNTAX INTEGER
      {
       notApplicable (1),
       off           (2),
       auto          (3),
	   manual        (4),
	   adjacent      (5)
      }
      MAX-ACCESS read-write
      STATUS current
      DESCRIPTION
      "This object defines path protection on SONET/SDH link
       Auto - SONET/SDH mapping for port is copied
       automatically to same TU on the redundant 
       SONET/SDH local (reside on same slot) link by agent.
       Manual - the user can configure the redundant 
       mapping for port on the same link
       or to the other link on any TU
       Adjacent - similar to auto, but mapping is copied
       automatically by agent to link on adjacent slot ."   
      ::= { prtParamEntry 12}

prtParamAlarmIndication OBJECT-TYPE
    SYNTAX INTEGER {
       notApplicable (1),
       off           (2),
       on            (3)
       }
    MAX-ACCESS read-only
    STATUS current
    DESCRIPTION
    "This object indicates status-aggregation of non-masked alarms 
    associated with all interface layers, related to this physical port.
    When at least one non-masked alarm exists on any layer, 
    value of this object is on (3). 
    
    Indication will be off (2) only when there's no active 
    non-masked alarm on any interface layer related to this port. 
    Masking an Alarm, will consider it as not exist for this indication.
    
    Example: When a port has an ATM higher layer and at least 
    one VC has alarm, value of this object will be on (3)"
    ::= {prtParamEntry 13}

prtParamClkQualityLevel OBJECT-TYPE
      SYNTAX  OCTET STRING	(SIZE (1))
      MAX-ACCESS  read-only
      STATUS  current
      DESCRIPTION
      "This parameter indicates quality level of clock signal.
       Quality is encoded according to SSM 
       (Synchronization Status Messages) encoding.
	   Bits 8 -5  of byte are encoded as follows (when bit1=0):
	   Left most bit - MSB(8) ---> LSB(5)
	   8765       
	   0000	Quality Unknown
       0010	PRC (Primary Reference Clock)    - Rec. G.811
       0100	SSU-T (Sync. Source Unit-Transit)- Rec. G.812 Transit
       1000	SSU-L (Sync. Source Unit Local)	 - Rec. G.812 Local
       1011	SEC (SDH Equipment Clock)
       1111	DNU (do not use for synchronization)
	   0001 PRS (=ST1 = Stratum 1 Traceable)
	   0111 ST2 (Stratum 2 Traceable)
	   1010 ST3 (Stratum 3 Traceable)
	   1100 SMC (SONET Minimum Clock Traceable)
	   1101 Stratum 3E Traceable
	   bit1 = '1' - indicates all octet is Not Applicable"
    ::= {prtParamEntry 14}

prtParamClkWaveShape OBJECT-TYPE
    SYNTAX  INTEGER {
	   notApplicable (1),
       sine          (2),
       square        (3)
    }
    MAX-ACCESS  read-write
    STATUS  current
    DESCRIPTION
       "Wave shape of station clock source signal."
	::= { prtParamEntry 15 }

prtParamStatus OBJECT-TYPE
    SYNTAX  INTEGER {
       notApplicable (1),
       up            (2),
       signalLoss    (3),
	   syncLoss      (4)
    }
    MAX-ACCESS  read-only
    STATUS  current
    DESCRIPTION
       "Station clock source Status."
	::= { prtParamEntry 16 }

prtParamSignalLevel	OBJECT-TYPE
    SYNTAX Integer32 
	MAX-ACCESS  read-only
	STATUS current
	DESCRIPTION 
	"This object indicates signal level (in thenth of dB units)
	 on selected port."
	::= { prtParamEntry 17 }

prtParamClkUserQualityLevel OBJECT-TYPE
   SYNTAX  OCTET STRING	(SIZE (1))
   MAX-ACCESS  read-write
   STATUS  current
   DESCRIPTION
   "This parameter allows user to mark quality level of clock.
    Quality is encoded according to SSM 
    (Synchronization Status Messages) encoding.
    Bits 8 -5  of byte are encoded as follows:
    Left most bit - MSB(8) ---> LSB(5)
    8765       
    0000	Quality Unknown
    0010	PRC (Primary Reference Clock) -   Rec. G.811
    0100	SSU-T (Sync. Source Unit-Transit) Rec. G.812 Transit
    1000	SSU-L (Sync. Source Unit Local)	- Rec. G.812 Local
    1011	SEC (SDH Equipment Clock)
    1111	DNU (do not use for synchronization)"
   ::= {prtParamEntry 18}

prtParamDataRate OBJECT-TYPE
     SYNTAX  Unsigned32 
     MAX-ACCESS  read-write
     STATUS  current
     DESCRIPTION
     "Rate of serial data port (V.11, V.24, V.35) 
      in kbps units."
     ::= { prtParamEntry 19}

prtParamLoopDetect OBJECT-TYPE
	SYNTAX  INTEGER
	{
	 disable   (2),
	 enable    (3)
	}
	MAX-ACCESS  read-write
	STATUS current
	DESCRIPTION
	"Enable/disable Loop Detection on a port.
	 Examples of ports: physical, Channelized Bundle over TDM Uplink,
	 Bridge Ports."
	::= { prtParamEntry 20 }

prtParamActUponLoopDetect OBJECT-TYPE
	SYNTAX  OCTET STRING
	MAX-ACCESS  read-write
	STATUS current
	DESCRIPTION
	"This parameter is used to indicate which actions
	should be taken in case a loop is detected in the network the port is part of.
	Each action is represented by a bit.
	Currently defined (for RIC155GE/RIC622GE):
	Bit 0 - Transmit Shut Down
	Bit 1 - Forward Alarms
	If bit value = '1' then the action is taken.
	If bit value = '0' then the actions is not taken."
	::= { prtParamEntry 21 }


prtParamPSNLayer OBJECT-TYPE
	SYNTAX INTEGER
	{
	   l2 	(2), -- lan
	   l3	(3)  -- wan
	}
	MAX-ACCESS read-write
	STATUS current
	DESCRIPTION
	"This object indicates the network layer from which clock is derived."
	::= { prtParamEntry 22 }


prtParamRxSsm OBJECT-TYPE
	SYNTAX INTEGER
	{
	   disabled	(2),
	   rx	(3)
	}
	MAX-ACCESS read-write
	STATUS current
	DESCRIPTION
	"This object indicates if Station Clock SSM messages  
	 received will serve as criteria for clock selection."
	::= { prtParamEntry 23 }

prtParamClkSsmRxSource OBJECT-TYPE
	SYNTAX INTEGER
	{
       sa4 	(2), 
	   sa5	(3),
	   sa6  (4),
	   sa7  (5), 
	   sa8  (6)
	}
	MAX-ACCESS read-write
	STATUS current
	DESCRIPTION
	"This object indicates the Sa-bit of the E1 frame,
	 in which SSM messages are carried."
	::= { prtParamEntry 24 }

-- 	::= { prtParamEntry 25 }  reserved 


prtParamFarEndDevice OBJECT-TYPE
     SYNTAX  Unsigned32 
     MAX-ACCESS  read-write
     STATUS  current
     DESCRIPTION
     "Programmed Far-End device connected to this port. 
      This object is relevant for products having multiple DBs.
	  It will enable configuring offline, the relevant data.
      For MP-4100, LRS-102 OP-108/106 cards, the options will be:
	  1 = None (when a port is not connected to any remote device)
      2 = OP-108
      3 = OP-108/ETH
      4 = OP-106
      5 = OP-106/ETH
      6 = card of MP or LRS-102"
     ::= { prtParamEntry 26}

prtParamTxClk OBJECT-TYPE
    SYNTAX  INTEGER {
	   notApplicable (1),
       disable       (2),
       enable        (3)
    }
    MAX-ACCESS  read-write
    STATUS  current
    DESCRIPTION
       "enable/disable station clock signal output."
	::= { prtParamEntry 27 }	 

prtParamSdBerThreshold	OBJECT-TYPE
    SYNTAX Unsigned32 (0..9) 
	MAX-ACCESS  read-write
	STATUS current
	DESCRIPTION 
	"The Signal Degrade Bit Error Rate Threshold.
	 The negated value of this number is used as the exponent of
     10 for computing the threshold value for the Bit Error Rate (BER).
     For example, a value of 5 indicates a BER threshold of 10^-5.
     
     For disabling the signal degradation, the value will be: 0"
     ::= { prtParamEntry 28 }

prtParamLoopDetectStatus OBJECT-TYPE
    SYNTAX  INTEGER {
       notApplicable (1),
       noLoop        (2),
       loopDetected  (3)
    }
    MAX-ACCESS  read-only
    STATUS  current
    DESCRIPTION
    "This object shows whether a loop was detected on the current port."
	::= { prtParamEntry 29 }



prtIP OBJECT IDENTIFIER ::= { systemPort 6 }

prtIpParamTable OBJECT-TYPE
	SYNTAX  SEQUENCE OF PrtIpParamEntry
	MAX-ACCESS  not-accessible
	STATUS current
	DESCRIPTION  "A table - Parameters for IP Ports."
	::= {prtIP 1}

prtIpParamEntry OBJECT-TYPE
	SYNTAX  PrtIpParamEntry
	MAX-ACCESS  not-accessible
	STATUS current
	DESCRIPTION  "An entry in table."
	INDEX { prtIpParamConfigIdx, prtIpParamSlotIdx, prtIpParamIdx }
	::= { prtIpParamTable 1 }

PrtIpParamEntry  ::=
    SEQUENCE {
    prtIpParamConfigIdx	      Integer32,
    prtIpParamSlotIdx  	      Integer32,
    prtIpParamIdx             Integer32,
	prtIpParamHostIP	      IpAddress,
	prtIpParamHostMask	      IpAddress,
	prtIpParamDefaultGateway  IpAddress,
	prtIpParamMediaMode		  INTEGER,
	prtIpParamMediaRate		  INTEGER,
	prtIpParamMngVlanSupport  INTEGER,
	prtIpParamMngVlanId       Integer32,
	prtIpParamMngVlanPriority Integer32,
	prtIpParamRingMode		  INTEGER,
	prtIpParamProtIpEnable    INTEGER,
	prtIpParamTrafficPriority INTEGER,
	prtIpParamRemoteIP	      IpAddress,
	prtIpParamMaxTxBandwidth  INTEGER,
	prtIpParamTos             Integer32,
	prtIpParamConnect         INTEGER,
	prtIpParamAgingTime       Integer32,
	prtIpParamEncapsulationProt INTEGER,
	prtIpParamEncapProtPort   Integer32,
	prtIpParamVlanSupport     INTEGER,
	prtIpParamVlanId          Integer32,
	prtIpParamVlanPriority    Integer32,
	prtIpParamDoubleTagVlanId        Integer32,
	prtIpParamDoubleTagVlanPriority  Integer32,
	prtIpParamVlanTagging	  INTEGER,
	prtIpParamRateLimit		  Integer32,
	prtIpParamDefInterface    Integer32,
	prtIpParamMng             INTEGER,
	prtIpParamFloodedRateLimit  Integer32,
	prtIpParamBurstSize         Unsigned32,
	prtIpParamLimitPacketType   INTEGER, 
	prtIpParamKeepAliveInterval Integer32,
	prtIpParamKeepAliveThresh   Integer32,
 	prtIpParamP2pKeepAliveVlanId   Integer32,
	prtIpParamP2pKeepAliveVlanPrio Integer32,
	prtIpParamRingAdjacentMacAddr  MacAddress
	}

prtIpParamConfigIdx OBJECT-TYPE
	SYNTAX  Integer32 
	MAX-ACCESS  read-only
	STATUS current
	DESCRIPTION 
	"This object indicates the Configuration number (1..255) 
     referred.
     Value of 255 specifies the TmpCnfg (Scratch).
     For products having Agent and Edit configurations, 
     Write operation for the table entries is allowed only to 
     Config=255."
	::= { prtIpParamEntry 1 }

prtIpParamSlotIdx OBJECT-TYPE
    SYNTAX  Integer32   
    MAX-ACCESS  read-only
    STATUS  current
    DESCRIPTION
    "This object indicates a unique number of the slot position 
     in which the module is inserted.
     notApplicable = 255 (for products that don't have slots).
       
     For KM:
     kmxMlA (103),
     kmxMlB (104)."
    ::= { prtIpParamEntry 2 }

prtIpParamIdx OBJECT-TYPE
	SYNTAX  Integer32 
	MAX-ACCESS  read-only
	STATUS current
	DESCRIPTION
	"This object indicates a unique Port Index."
	::= { prtIpParamEntry 3 }

prtIpParamHostIP OBJECT-TYPE
    SYNTAX  IpAddress 
    MAX-ACCESS  read-write
    STATUS  current
    DESCRIPTION
    "The host interface IP address."
    ::= { prtIpParamEntry 4 }

prtIpParamHostMask OBJECT-TYPE
    SYNTAX  IpAddress 
    MAX-ACCESS  read-write
    STATUS  current
    DESCRIPTION
    "The host interface subnet mask."
    ::= { prtIpParamEntry 5 }

prtIpParamDefaultGateway OBJECT-TYPE
    SYNTAX  IpAddress
    MAX-ACCESS  read-write
    STATUS  current
    DESCRIPTION
    "Default Gateway's IP Address."
    ::= { prtIpParamEntry 6 }

prtIpParamMediaMode OBJECT-TYPE
    SYNTAX  INTEGER
	{
       notApplicable (1),
       halfDuplex    (2),
       fullDuplex    (3) 
    }
    MAX-ACCESS  read-only
    STATUS  current
    DESCRIPTION
    "This object indicates the real Media Mode."
    ::= { prtIpParamEntry 7 }

prtIpParamMediaRate OBJECT-TYPE
    SYNTAX  INTEGER
	{
       notApplicable (1),
       r10Mbps       (2),
       r100Mbps      (3) 
    }
    MAX-ACCESS  read-only
    STATUS  current
    DESCRIPTION
    "This object indicates the real Media Rate (Mbps)."
    ::= { prtIpParamEntry 8 }

prtIpParamMngVlanSupport OBJECT-TYPE
    SYNTAX  INTEGER 
    {
    notApplicable(1),
    no		(2),
    yes	    (3)
    }
    MAX-ACCESS  read-write
    STATUS  current
    DESCRIPTION
    "Management VLAN support (Tagging).
     no - No support of VLAN Tagging.
     yes - 4 VLAN bytes will be added to the frame."
    ::= { prtIpParamEntry 9 }

prtIpParamMngVlanId OBJECT-TYPE
     SYNTAX  Integer32 
     MAX-ACCESS  read-write
     STATUS  current
     DESCRIPTION
     "Management VLAN ID."
     ::= { prtIpParamEntry 10 }
  
prtIpParamMngVlanPriority OBJECT-TYPE
     SYNTAX  Integer32 
     MAX-ACCESS  read-write
     STATUS  current
     DESCRIPTION
     "Management VLAN Frame priority."
     ::= { prtIpParamEntry 11 }

prtIpParamRingMode OBJECT-TYPE
    SYNTAX  INTEGER
	{
       notApplicable (1),
       disable       (2),
       enable        (3) 
    }
    MAX-ACCESS  read-write
    STATUS  current
    DESCRIPTION
    "This object indicates If Ring Mode is enabled or not."
    ::= { prtIpParamEntry 12 }

prtIpParamProtIpEnable OBJECT-TYPE
    SYNTAX  INTEGER
	{
       notApplicable (1),
       disable       (2),
       enable        (3) 
    }
    MAX-ACCESS  read-write
    STATUS  current
    DESCRIPTION
    "This object indicates whether a list of Protected IP Addresses 
     is enabled or not. This object is applicable only if 
     prtIpParamRingMode=enable."
    ::= { prtIpParamEntry 13 }

prtIpParamTrafficPriority OBJECT-TYPE
    SYNTAX  INTEGER
	{
       notApplicable (1),
       low           (2),
       high          (3) 
    }
    MAX-ACCESS  read-write
    STATUS  current
    DESCRIPTION
    "This object indicates the traffic priority of this port."
    ::= { prtIpParamEntry 14 }

prtIpParamRemoteIP  OBJECT-TYPE
    SYNTAX  IpAddress 
    MAX-ACCESS  read-write
    STATUS  current
    DESCRIPTION
    "This is the IP Address of the remote device that is connected to the
     current device (Point to Point Application). It is used for sending OAM packets
     on the LAN to the remote side in order to check that the connection is OK."
    ::= { prtIpParamEntry 15 }

prtIpParamMaxTxBandwidth OBJECT-TYPE
    SYNTAX  INTEGER
	{
       full  (2),
       e1    (3),
	   t1    (4)
    }
    MAX-ACCESS  read-write
    STATUS  current
    DESCRIPTION
    "This object shows the Max Bandwidth allowed on the LAN.
     Full - means that a Maximum of 100 Mega Byte Rate may go through the LAN.
	 e1(3) means that the maximum is an E1 rate. t1(4) is for a maximum of a T1 rate."
    ::= { prtIpParamEntry 16 } 

prtIpParamTos OBJECT-TYPE
     SYNTAX  Integer32 
     MAX-ACCESS  read-write
     STATUS  current
     DESCRIPTION
     "TOS = Type of Service transmitted.
      Valid values: 0..255."
     ::= { prtIpParamEntry 17 }

prtIpParamConnect OBJECT-TYPE
    SYNTAX  INTEGER 
    {
    notApplicable(1),
    no		(2),
    yes	    (3)
    }
    MAX-ACCESS  read-write
    STATUS  current
    DESCRIPTION
    "Port Connection."
    ::= { prtIpParamEntry 18 }

prtIpParamAgingTime OBJECT-TYPE
     SYNTAX  Integer32 
     MAX-ACCESS  read-write
     STATUS  current
     DESCRIPTION
     "Aging Time in seconds."
     ::= { prtIpParamEntry 19 }

prtIpParamEncapsulationProt OBJECT-TYPE
    SYNTAX  INTEGER 
    {
    notApplicable(1),
    tcp		(2),
    udp	    (3)
    }
    MAX-ACCESS  read-write
    STATUS  current
    DESCRIPTION
    "Encapsulation Protocol."
    ::= { prtIpParamEntry 20 }

prtIpParamEncapProtPort OBJECT-TYPE
     SYNTAX  Integer32 
     MAX-ACCESS  read-write
     STATUS  current
     DESCRIPTION
     "Encapsulation Protocol Port (TCP/UDP Port)."
     ::= { prtIpParamEntry 21 }

prtIpParamVlanSupport OBJECT-TYPE
    SYNTAX  INTEGER 
    {
    notApplicable(1),
    no		(2),
    yes	    (3)
	    }
    MAX-ACCESS  read-write
    STATUS  current
    DESCRIPTION
    "VLAN support (Tagging).
     'no' - No support of VLAN Tagging.
     'yes' - 4 VLAN bytes will be added to the frame."
    ::= { prtIpParamEntry 22 }

prtIpParamVlanId OBJECT-TYPE
     SYNTAX  Integer32 
     MAX-ACCESS  read-write
     STATUS  current
     DESCRIPTION
     "VLAN Identifier."
     ::= { prtIpParamEntry 23 }
  
prtIpParamVlanPriority OBJECT-TYPE
     SYNTAX  Integer32 
     MAX-ACCESS  read-write
     STATUS  current
     DESCRIPTION
     "VLAN Frame priority."
     ::= { prtIpParamEntry 24 }

prtIpParamDoubleTagVlanId OBJECT-TYPE
     SYNTAX  Integer32 
     MAX-ACCESS  read-write
     STATUS  current
     DESCRIPTION
     "VLAN Identifier of the Double Tagging VLAN."
     ::= { prtIpParamEntry 25 }
  
prtIpParamDoubleTagVlanPriority OBJECT-TYPE
     SYNTAX  Integer32 
     MAX-ACCESS  read-write
     STATUS  current
     DESCRIPTION
     "VLAN Frame priority of the Double Tagging VLAN."
     ::= { prtIpParamEntry 26 }

prtIpParamVlanTagging OBJECT-TYPE
     SYNTAX  INTEGER 
     {
     notApplicable(1),
     unmodified	  (2),
	 tag		  (3),
	 doubleTag 	  (4),
 	 doubleTagAndFallBack (5),
	 untag        (6) 
     }
     MAX-ACCESS  read-write
     STATUS  current
     DESCRIPTION
     "VLAN Tagging.
      'unmodified' - No change will be done to the Frame.
      'tag' - Add Tag to Untagged Frames.
      'doubleTag' - Add Tag to all Frames.
      'doubleTagAndFallBack' - Double Tagging will have different rules for 
       VLANs that this port is member in, than these it is not a member in.
      'untag' - Remove Tag from tagged frames."
     ::= { prtIpParamEntry 27 }

prtIpParamRateLimit OBJECT-TYPE
     SYNTAX  Integer32 
     MAX-ACCESS  read-write
     STATUS  current
     DESCRIPTION
     "The maximum rate permitted to transfer via this port, in Kbps."
     ::= { prtIpParamEntry 28 }

prtIpParamDefInterface OBJECT-TYPE
     SYNTAX  Integer32 
     MAX-ACCESS  read-write
     STATUS  current
     DESCRIPTION
     "The Default Interface for packets with unresolved destination subnet.
      For internal-X port: 100 + X ."
     ::= { prtIpParamEntry 29 }

prtIpParamMng OBJECT-TYPE
    SYNTAX  INTEGER
	{
       notApplicable (1),
       disable       (2),
       enable        (3) 
    }
    MAX-ACCESS  read-write
    STATUS  current
    DESCRIPTION
    "This object indicates whether Management is enabled/disabled
     via this port."
    ::= { prtIpParamEntry 30 }


prtIpParamFloodedRateLimit OBJECT-TYPE
     SYNTAX  Integer32 
     MAX-ACCESS  read-write
     STATUS  current
     DESCRIPTION
     "The maximum rate permitted to transfer broadcast, multicast,
     and unicast flooded frames via this port, in Kbps.
     0 - Disable.
     In Ipmux14 this parameter is applicable when prtIpParamRateLimit=0 (disable)."
     ::= { prtIpParamEntry 31 }

prtIpParamBurstSize	 OBJECT-TYPE
     SYNTAX  Unsigned32 
     MAX-ACCESS  read-write
     STATUS  current
     DESCRIPTION
     "The burst size that the port can support beyond rate limitation
     determined in prtIpParamRateLimit.
     Burst Size is measured in bytes."
     ::= { prtIpParamEntry 32 }

prtIpParamLimitPacketType  OBJECT-TYPE
     SYNTAX  INTEGER 
     {
       all                      (1),
	   broadMultiFloodedUnicast (2),
	   broadcastMulticast       (3),
       broadcast                (4)
     }
     MAX-ACCESS  read-write
     STATUS  current
     DESCRIPTION
     "The packet type that will be rate limited. Rate limitation 
     determined in prtIpParamRateLimit.
     all - All packet types are rate limited.
	 broadMultiFloodedUnicast - Broadcast, Multicast and Flooded Unicast packets are rate limited.
     broadcastMulticast - Broadcast and Multicast packets are rate limited.
     broadcast - Broadcast packets are rate limited."
     ::= { prtIpParamEntry 33 }

prtIpParamKeepAliveInterval   OBJECT-TYPE
     SYNTAX  Integer32
     MAX-ACCESS  read-write
     STATUS  current
     DESCRIPTION
     "This parameter indicates the period of time (in msec.) 
     between two consequent Keep Alive messages."
     ::= { prtIpParamEntry 34 }

prtIpParamKeepAliveThresh	 OBJECT-TYPE
     SYNTAX  Integer32
     MAX-ACCESS  read-write
     STATUS  current
     DESCRIPTION
     "This parameter indicates the maximum number of 
     missed Keep Alive answer messages acceptable, after which link status will be failed."
     ::= { prtIpParamEntry 35 }


prtIpParamP2pKeepAliveVlanId OBJECT-TYPE
     SYNTAX  Integer32 
     MAX-ACCESS  read-write
     STATUS  current
     DESCRIPTION
     "Dedicated VLAN ID for keep alive messages."
     ::= { prtIpParamEntry 36 }

prtIpParamP2pKeepAliveVlanPrio OBJECT-TYPE
     SYNTAX  Integer32 
     MAX-ACCESS  read-write
     STATUS  current
     DESCRIPTION
     "VLAN priority for P2P keep alive messages ."
     ::= { prtIpParamEntry 37 }

prtIpParamRingAdjacentMacAddr  OBJECT-TYPE
     SYNTAX     MacAddress
     MAX-ACCESS  read-only
     STATUS  current
     DESCRIPTION
     "The MAC address of the adjacent NE connected to this port in an ETH ring.
       If the port is not a member of a ring, the value of this parameter
       will be 00-00-00-00-00-00."
     ::= { prtIpParamEntry 38 }
  


prtClkSrc OBJECT IDENTIFIER ::= { systemPort 7 }

prtClkSrcTable OBJECT-TYPE
	SYNTAX  SEQUENCE OF PrtClkSrcEntry
	MAX-ACCESS  not-accessible
	STATUS current
	DESCRIPTION  
	"A table - Parameters for  master and fallback 
     clock source of ports ."
	::= {prtClkSrc 1}

prtClkSrcEntry OBJECT-TYPE
    SYNTAX PrtClkSrcEntry
    MAX-ACCESS not-accessible
    STATUS current
	DESCRIPTION  "An entry in table."
	INDEX {prtClkSrcCnfgIdx, prtClkSrcPrtIdx, prtClkSrcIdx}
    ::= { prtClkSrcTable 1}

PrtClkSrcEntry ::=
    SEQUENCE {
    prtClkSrcCnfgIdx   Integer32,
    prtClkSrcPrtIdx	   Integer32,
    prtClkSrcIdx       INTEGER,
    prtClkSrcMode      INTEGER,
    prtClkSrcPrt       Integer32
	}

prtClkSrcCnfgIdx OBJECT-TYPE
    SYNTAX Integer32 (1..255)
    MAX-ACCESS not-accessible
    STATUS current
    DESCRIPTION
    "This attribute indicates the Idx of the Cnfg(1..255) being 
     accessed ; Idx of 255 relates to the TmpCnfg."
    ::= { prtClkSrcEntry 1}

prtClkSrcPrtIdx OBJECT-TYPE
    SYNTAX  Integer32
    MAX-ACCESS  not-accessible
    STATUS  current
    DESCRIPTION
    "This object indicates a unique Port Index (receiving clock).
     Refer to device specification for port Index"
    ::= { prtClkSrcEntry 2}

prtClkSrcIdx OBJECT-TYPE
    SYNTAX  INTEGER 
    {
    master    (1),
    fallback  (2)
    }
    MAX-ACCESS  not-accessible
    STATUS  current
    DESCRIPTION
    "An index in the table. 
     master   - refers Master clock parameters 
     fallback - refers Fallback clock parameters"
    ::= { prtClkSrcEntry 3}

prtClkSrcMode OBJECT-TYPE
    SYNTAX  INTEGER
    {
--  none            (1),
    internal        (2),
    rxClk           (3),
--  station         (4),
--  lbt             (5),
--  ntr             (6),
--	adaptive        (7),  
    notApplicable (255)
    }
    MAX-ACCESS  read-write
    STATUS  current
    DESCRIPTION
    "This entry indicates the source the nodal timing is 
     locked to."
    ::= { prtClkSrcEntry 4}

prtClkSrcPrt OBJECT-TYPE
    SYNTAX  Integer32
    MAX-ACCESS  read-write
    STATUS  current
    DESCRIPTION
    "This entry is valid only when working in rxClk mode.
	 It specifies the port from which the clock willl be taken.
	 Refer to device specification for source port Index"      
    ::= { prtClkSrcEntry 5}


opticalPort OBJECT IDENTIFIER ::= { systemPort 8 }

optPrtMonitorTable OBJECT-TYPE
	SYNTAX  SEQUENCE OF OptPrtMonitorEntry
	MAX-ACCESS  not-accessible
	STATUS current
	DESCRIPTION  
	"A table -  optical port (e.g SFP) monitoring parameters,
     according to SFF-8472 Specification for Diagnostic Monitoring 
	 Interface for Optical Xcvrs. and ITU-T rec. G.958"
	::= {opticalPort 1}

optPrtMonitorEntry OBJECT-TYPE
    SYNTAX OptPrtMonitorEntry
    MAX-ACCESS not-accessible
    STATUS current
	DESCRIPTION  "An entry in table."
	INDEX {optPrtMonitorPrtIdx,optPrtMonitorSample}
    ::= { optPrtMonitorTable 1}

OptPrtMonitorEntry ::=
    SEQUENCE {
    optPrtMonitorPrtIdx        Integer32,
    optPrtMonitorSample        INTEGER,
    optPrtMonitorTxPower       Integer32,
    optPrtMonitorLaserBias     Integer32,
    optPrtMonitorLaserTemp     Integer32,
	optPrtMonitorRxPower       Integer32,
	optPrtMonitorSupplyVoltage Integer32
	}

optPrtMonitorPrtIdx OBJECT-TYPE
    SYNTAX  Integer32
    MAX-ACCESS  not-accessible
    STATUS  current
    DESCRIPTION
    "This object indicates a unique (optical) Port Index .
     Refer to device specification for port Index."
    ::= { optPrtMonitorEntry 1}

optPrtMonitorSample OBJECT-TYPE
     SYNTAX  INTEGER {
		 actual  (1), 
		 minimum (2),
		 maximum (3) 
		}
    MAX-ACCESS  not-accessible
    STATUS  current
    DESCRIPTION
    "This index indicates historic and current values - 
     minimum, maximum  and actual (current) value.  "
    ::= { optPrtMonitorEntry 2}
		  
optPrtMonitorTxPower  OBJECT-TYPE
    SYNTAX  Integer32
    MAX-ACCESS  read-only
    STATUS  current
    DESCRIPTION
    "Transmitted optical power level.
     Value is given in units of hundredth (1/100) of dBm. "      
    ::= { optPrtMonitorEntry 3}

optPrtMonitorLaserBias  OBJECT-TYPE
    SYNTAX  Integer32
    MAX-ACCESS  read-only
    STATUS  current
    DESCRIPTION
    "LASER bias current level. 
     Value is given in units of microAmper (uA)."      
    ::= { optPrtMonitorEntry 4}

optPrtMonitorLaserTemp OBJECT-TYPE
    SYNTAX  Integer32
    MAX-ACCESS  read-only
    STATUS  current
    DESCRIPTION
    "LASER temperature level,
     in hundredth (1/100) (C) degrees."      
    ::= { optPrtMonitorEntry 5}

optPrtMonitorRxPower  OBJECT-TYPE
    SYNTAX  Integer32
    MAX-ACCESS  read-only
    STATUS  current
    DESCRIPTION
    "Received optical power in units of hundredth (1/100) of dBm. "      
    ::= { optPrtMonitorEntry 6}

optPrtMonitorSupplyVoltage OBJECT-TYPE
    SYNTAX  Integer32
    MAX-ACCESS  read-only
    STATUS  current
    DESCRIPTION
    "Supply voltage, in hundredth (1/100) of volts (V)."      
    ::= { optPrtMonitorEntry 7}


optPrtCnfgTable OBJECT-TYPE
	SYNTAX  SEQUENCE OF OptPrtCnfgEntry
	MAX-ACCESS  not-accessible
	STATUS current
	DESCRIPTION  
	"A table -  optical port configuration"
	::= {opticalPort 2}

optPrtCnfgEntry OBJECT-TYPE
    SYNTAX OptPrtCnfgEntry
    MAX-ACCESS not-accessible
    STATUS current
	DESCRIPTION  "An entry in table."
	INDEX {optPrtCnfgIdx, optPrtCnfgPrtIdx}
    ::= { optPrtCnfgTable 1}

OptPrtCnfgEntry ::=
    SEQUENCE {
    optPrtCnfgIdx     Unsigned32,
    optPrtCnfgPrtIdx  Unsigned32,
    optPrtCnfgALS     INTEGER
	}

optPrtCnfgIdx OBJECT-TYPE
    SYNTAX  Unsigned32
    MAX-ACCESS  not-accessible
    STATUS  current
    DESCRIPTION
    "This attribute indicates the Idx of the Cnfg(1..255) being 
     accessed ; Idx of 255 relates to the TmpCnfg.x."
    ::= { optPrtCnfgEntry 1}

optPrtCnfgPrtIdx OBJECT-TYPE
    SYNTAX  Unsigned32
    MAX-ACCESS  not-accessible
    STATUS  current
    DESCRIPTION
    "This object indicates a unique (optical) Port Index .
     Refer to device specification for port Index."
    ::= { optPrtCnfgEntry 2}

optPrtCnfgALS  OBJECT-TYPE
     SYNTAX  INTEGER {
		 notApplicable (1), 
		 disable       (2),
		 enable        (3) 
		}
    MAX-ACCESS  read-write
    STATUS  current
    DESCRIPTION
    "enable/disable Automatic Laser Shutdown  "
    ::= { optPrtCnfgEntry 3}

systemResetAllStatsCmd OBJECT-TYPE
      SYNTAX   INTEGER
	      {
    		off(2),
	    	on (3)
	      }
      MAX-ACCESS  read-write
      STATUS  current
      DESCRIPTION
       "Reset statistics of all ports and connections of the device."
      ::= { agnt 16 }

systemClearTablesCmd OBJECT-TYPE
      SYNTAX   INTEGER
	      {
    		off(2),
	    	tempCnfgTables (3)
	      }
      MAX-ACCESS  read-write
      STATUS  current
      DESCRIPTION
       "tempCnfgTables - Set *RowStatus = destroy for all entries of 
                         some tables having *RowStatus object, for 
                         temporary configuration only! (255).
                         For the relevant tables, see product's specification.
                         This object should be used by WAN product applications 
                         before performing the Update operation, in order to clear 
                         old entries of these tables.
                         For MP-104/204 the entries will be destroyed for cnfg=1. 
        off - agent will automatically change to this value, after performing the 
              command. "
      ::= { agnt 17 }

systemParameter OBJECT-TYPE
      SYNTAX   Integer32
      MAX-ACCESS  read-write
      STATUS  current
      DESCRIPTION
       "This parameter can be used for different purposes: 
        - TELNET session time-out in seconds.
	   	- Ace20: when trying to create row in a table that already
				 has row with the same values, if set of values has to be unique
				 in table, this attribute is set to the index of the existing row.
		- Optimux-T3: when CH interfaces are RJ-45, user can select via this
		         object, the interface type for each Group of channels: T1 or E1:
		         The selection will be a sum of the following Bits.
		         '0' = T1
		         '1' = E1
		         Bit    Group               Value for each Bit having '1'
				  1		  1 (CH-1..CH-8)        	  1
				  2		  2 (CH-9..CH-12)       	  2
				  3		  3 (CH-13..CH-20)	          4
				  4		  4 (CH-21..CH-28)	          8
				 Examples:
				 15 = all Groups are selected to be E1
				  6 = Group 2 and Group 3 are selected to be E1 
				     (Group 1 and Group 4 are T1).
		- FCD-A, FCD-M: user can select via this object the configuration
		         used for Get values of MSDSL parameters that don't have
		         configuration index.
		         1  =active configuration
		         255=temporary configuration.
		         Set of this object should be done before Getting the MSDSL 
		         RW parameters.
		- Ace2002: This parameter indicates the number of intervals that
		         were successfully uploaded upon statistics collection session.        
		- FCD-IP, WR, FCD-IPD, LA-240:
		         This parameter indicates whether Telnet Access is enabled/disabled:
		         Values:
				 2 - Telnet Access is Disabled.
				 3 - Telnet Access is Enabled. 				 
        -Vmux-110: This parameter value equals to maximum number of bundles.
		-Optimux-155: Simmilar usage to Optimux T3. user can select via this
		         object, interface type T1 or E1 for each Group of 
		         channels (LIU):  LIU group consists of 7 channels. 
		         Up to 12 LIUs are represented (84 T1 Channels).
                 The selection will be a sum of the 2**n
                 For each bit:'0' = T1 ,'1' = E1
		         Bit    Group              
				  1		  1 (CH-1 ..  CH-7)   
				  2		  2 (CH-8 .. CH-14)  
				  3		  3 (CH-15 ..CH-21) 
                   ...
				  9		  9 (CH-56.. CH-63) 
                   ...
				  10	  10 (CH-64..CH-70) 
				  11	  11 (CH-71..CH-77) 
				  12	  12 (CH-78..CH-84) "
       ::= { agnt 18 }

 
agnGlobalAlarmMask OBJECT-TYPE   
      SYNTAX OCTET STRING 
      MAX-ACCESS  read-write    
      STATUS  current
      DESCRIPTION
      "The value of this attribute determines the alarm traps the 
       agent should mask and not send to the managers.
       Each bit from a certain octet represents a certain alarm."
      ::= { agnt 19 }

alarmSeverity   OBJECT-TYPE
      	SYNTAX   INTEGER
	      	{
			event		(3),
			minor		(4),
			major		(5),
	    	warning		(6),
			critical	(7)
	  		}
      	MAX-ACCESS  read-only
      	STATUS  current
      	DESCRIPTION
       	"This object specifies the severity of the alarms."
      ::= { agnt 20 }

alarmState   OBJECT-TYPE
      	SYNTAX   INTEGER
	      	{
			off (2), 	-- End, 
			on  (3) 	-- Start.
	  		}
      	MAX-ACCESS  read-only
      	STATUS  current
      	DESCRIPTION
       "."
      ::= { agnt 21 }


agnTestStatus OBJECT-TYPE
	SYNTAX	INTEGER
		{
		 off			(2),
		 on 			(3)
		}

	MAX-ACCESS	read-only
	STATUS	current
	DESCRIPTION
	"Indicates the current test status (for all levels: system,
	   card, port).
       This attribute will be set to: 
         on(3): when there is at least one test	in progress on the
                system/card/port
		 off(2): when there is NO test in progress on the
    	         system/card/port" 
      ::= {agnt 22  }

systemSaveAndResetAllStatsCmd OBJECT-TYPE
      SYNTAX   INTEGER
	      {
    		off(2),
	    	on (3)
	      }
    MAX-ACCESS  read-write
    STATUS  current
    DESCRIPTION
    "on  - a command to Save data of Current Period in Last Period
           data-set and start a new counting period for Current Period.
     off - agent will automatically change to this value, after performing the 
           command."
      ::= { agnt 23 }

systemDefaultGateway OBJECT-TYPE
      SYNTAX   IpAddress
    MAX-ACCESS  read-write
    STATUS  current
    DESCRIPTION
    "Default Gateway's IP Address."
      ::= { agnt 24 }

-- PS Table
systemPsTable OBJECT-TYPE
	SYNTAX  SEQUENCE OF SystemPsEntry
	MAX-ACCESS  not-accessible
	STATUS current
	DESCRIPTION
	"This table describes the PS types of a device.
	Usage of this table is specified in the device's NMS SRS"
	::= { agnt 25 }

systemPsEntry OBJECT-TYPE
	SYNTAX  SystemPsEntry
	MAX-ACCESS  not-accessible
	STATUS current
	DESCRIPTION  "An entry in table."
	INDEX {systemPsIndex1, systemPsIndex2}
	::= { systemPsTable 1 }

SystemPsEntry  ::=
	    SEQUENCE {
	systemPsIndex1
	  Integer32,
	systemPsIndex2
	  Integer32,
	systemPsType
	  INTEGER,
	systemPsStatus
	  INTEGER,
	systemPsHotSwap
	  INTEGER
	}

systemPsIndex1 OBJECT-TYPE
	SYNTAX  Integer32 
	MAX-ACCESS  read-only
	STATUS current
	DESCRIPTION
	"First Index. 
	In HUBs:
	1 = PS-A slot
	2 = PS-B slot
	3 = PS-C slot.
	In SA units:
	1 = PS1
	2 = PS2
	Default = 1"
	::= { systemPsEntry 1 }

systemPsIndex2 OBJECT-TYPE
	SYNTAX  Integer32 
	MAX-ACCESS  read-only
	STATUS current
	DESCRIPTION
	"Second Index. 
	In HUBs:
	1 always.
    In SA units:
	1 = Local
	2 = Remote
	Default = 1."
	::= { systemPsEntry 2 }

systemPsType OBJECT-TYPE
      SYNTAX  INTEGER
	      {
		  none      (1),
	      ac        (2),
	      dc        (3),
		  acDc      (4),
		  acPF      (5),
		  dcPF      (6),
		  acWithFan (7),  
		  dcWithFan	(8)	  
	      }
      MAX-ACCESS  read-only
      STATUS  current
      DESCRIPTION
      "The type of PS, for a stand-alone product.
      acDc - PS that supports both AC and DC.
      acPF - Power Feeding (phantom) box that is feeding another box by external AC.
      dcPF - Power Feeding (phantom) box that is feeding another box by external DC.
      acWithFan - AC PS with integrated FAN.
      dcWithFan	- DC PS with integrated FAN.
      "
      ::= { systemPsEntry 3 }

systemPsStatus OBJECT-TYPE
      SYNTAX  INTEGER
	      {
		  notApplicable  (1),
	      failed         (2),
	      ok             (3),
		  degraded		 (4)
	      }
      MAX-ACCESS  read-only
      STATUS  current
      DESCRIPTION
      "The Status of the PS unit."
      ::= { systemPsEntry 4 }

systemPsHotSwap	OBJECT-TYPE
      SYNTAX  INTEGER
	      {
		  notApplicable  (1),
	      fixed          (2),
	      hotSwap        (3)
	      }
      MAX-ACCESS  read-only
      STATUS  current
      DESCRIPTION
      "Is PS unit hot swap or fixed."
      ::= { systemPsEntry 5 }

agnFans OBJECT-TYPE
	SYNTAX  OCTET STRING
	MAX-ACCESS  read-only
	STATUS current
	DESCRIPTION
	"This entry specifies the FANs existence and status. 
	 Each fan will be represented by 2 bits,
	 where the first bit (right) will specify the existence:
	 (0= Not exist, 1=exist),
     and the left bit will specify it's status
     (0= OK, 1=FAIL), so for each fan:
     00 - FAN does not exist
     01 - FAN exists and OK (Low Mode)
	 10 - High Mode (FAN OK)
     11 - FAN exists and is Failed 
	 bits 0-1 are for first fan
	 bits 2-3 are for 2nd fan (if exists)
	 bits 4-5 are for 3nd fan (if exists)
	 bits 6-7 are for 4nd fan (if exists)
	 bits 8-9 are for 5nd fan (if exists)
	 bits 10-11 are for 6nd fan (if exists)
	 bits 12-13 are for 7nd fan (if exists)
	 bits 14-15 are for 8nd fan (if exists)."
     ::= { agnt 26 }

agnSendTrapParameter OBJECT-TYPE
	SYNTAX  Integer32
	MAX-ACCESS  read-write
	STATUS current
	DESCRIPTION
	"This object specifies if the agent will attach a specific
	parameter to a trap.
	
	For ACE2002 the agent will attach or not the openViewSeverity 
	parameter according to the value of this parameter:
	1 - will attach openViewSeverity.
	0 - will not attach openViewSeverity."
     ::= { agnt 27 }

agnSensorsStatus OBJECT-TYPE
	SYNTAX  OCTET STRING
	MAX-ACCESS  read-only
	STATUS current
	DESCRIPTION
	"This entry specifies the Sensors (Temperature sensors or others)
	 existence and status. 
	 Each sensor will be represented by 2 bits,
	 where the first bit (right) will specify the existence:
	 (0= Not exist, 1=exist),
     and the left bit will specify it's status
     (0= OK, 1=FAIL), so for each sensor:
     00 - sensor does not exist
     01 - sensor exists and status is OK
     11 - sensor exists and status is not OK 
                  ( e.g. temperature exceeds pre-defined threshold)
	 bits 0-1 are for first sensor
	 bits 2-3 are for 2nd sensor (if exists)
	 and so on...
	 Bit 0 is the LSB."
     ::= { agnt 28 }

agnStationClockCard OBJECT-TYPE
	SYNTAX  INTEGER
	{
	 notApplicable	(1),
	 notExist       (2),
	 notValid       (3),
	 ok             (4)
	 }
	MAX-ACCESS  read-only
	STATUS current
	DESCRIPTION
	"This entry specifies the station clock card
	 existence and status. 
     notExist - station clock card (piggy) does not exist.
     notValid - station clock card exists but clock status is not valid.
     ok       - station clock card exists, and its status is OK 
     When the sepcific reason for clock status not being valid is known,
     it may be reported by lossOfSync or lossOfSignal values."
     ::= { agnt 29 }

xcIndexNext  OBJECT-TYPE
          SYNTAX         Integer32 (0..2147483647)
          MAX-ACCESS         read-only
          STATUS         current
          DESCRIPTION
           "This object contains an appropriate value to
            be used for xcIndex when creating
            entries in the xcTable.  The value
            0 indicates that no unassigned entries are
            available. To obtain the xcIndex
            value for a new entry, the manager issues a
            management protocol retrieval operation to obtain
            the current value of this object.  After each
            retrieval, the agent should modify the value to
            the next unassigned index.
            After a manager retrieves a value the agent will
            determine through its local policy when this index
            value will be made available for reuse."
          ::= { agnt 30 }

--XC Table
xcTable OBJECT-TYPE
      SYNTAX SEQUENCE OF XcEntry
      MAX-ACCESS not-accessible
      STATUS current
      DESCRIPTION
      "Configuration of system cross-connect entries.
      The table follows the behavior described in RFC 2515, 
      RFC 1604 regarding the creation deletion and modification 
      of an entry within the table."
      ::= { agnt 31 }

xcEntry OBJECT-TYPE
      SYNTAX XcEntry
      MAX-ACCESS not-accessible
      STATUS current
	DESCRIPTION  "An entry in table."
	INDEX { xcIndex, xcIfIndex1, xcVpi, xcVci, xcIfIndex2 }
      ::= { xcTable 1}

XcEntry ::=
      SEQUENCE {
	 xcIndex        Integer32,
     xcIfIndex1   	Integer32,
     xcVpi 	        Integer32,
     xcVci 	        Integer32,
     xcIfIndex2   	Integer32,
	 xcRowStatus    RowStatus,
	 xcDescr        DisplayString,
     xcAdminStatus     INTEGER,
     xcOperStatus      INTEGER,
     xcAttachedIfType  INTEGER,
     xcInputPriority   Integer32,
	 xcBitMapping      Integer32
      }

xcIndex OBJECT-TYPE
      SYNTAX  Integer32
      MAX-ACCESS  not-accessible
      STATUS  current
      DESCRIPTION
      "Cross Connect Identifier."
      ::= { xcEntry 1 }

xcIfIndex1 OBJECT-TYPE
      SYNTAX  Integer32
      MAX-ACCESS  not-accessible
      STATUS  current
      DESCRIPTION
      "The interface Index from the ifTable, which identify one side 
      of the connection."
      ::= { xcEntry 2 }

xcVpi OBJECT-TYPE
      SYNTAX  Integer32 
      MAX-ACCESS  not-accessible
      STATUS  current
      DESCRIPTION
      "The VPI value."
      ::= { xcEntry 3 }

xcVci OBJECT-TYPE
      SYNTAX  Integer32 
      MAX-ACCESS  not-accessible
      STATUS  current
      DESCRIPTION
      "The VCI value."
      ::= { xcEntry 4 }

xcIfIndex2 OBJECT-TYPE
      SYNTAX  Integer32
      MAX-ACCESS  not-accessible
      STATUS  current
      DESCRIPTION
      "The interface Index from the ifTable, which identifies the other 
      side of the connection."
      ::= { xcEntry 5 }

xcRowStatus  OBJECT-TYPE
      SYNTAX  RowStatus
     MAX-ACCESS   read-create
     STATUS   current
     DESCRIPTION
     "This parameter allows NMS to create/delete entries of this table."
     ::= { xcEntry 6 }

xcDescr  OBJECT-TYPE
     SYNTAX  DisplayString
     MAX-ACCESS   read-create
     STATUS   current
     DESCRIPTION
     "A textual string containing information about the
      xc entry."
     ::= { xcEntry 7 }


xcAdminStatus OBJECT-TYPE
        SYNTAX   INTEGER {
           up(1),
           down(2)
            }
      MAX-ACCESS  read-create
      STATUS  current
      DESCRIPTION
                 "The desired administrative status of this
            bi-directional cross-connect."
      ::= { xcEntry 8 }

xcOperStatus OBJECT-TYPE
        SYNTAX   INTEGER {
           up(1),
           down(2),
           unknown(3)
           }
      MAX-ACCESS  read-only
      STATUS  current
      DESCRIPTION
      "The operational status of this bi-directional 
      cross-connect."
      ::= { xcEntry 9 }

xcAttachedIfType OBJECT-TYPE
        SYNTAX   INTEGER {
          notApplicable(1),
          free         (2),
          routerAtm    (3),
          lis          (4)
          }
      MAX-ACCESS  read-only
      STATUS  current
      DESCRIPTION
      "This object indicates if the specific VCC is
      already attached to any interface, and indicates
      the type of the interface.
      This object's purpose is to ease the checking to 
      the NMS.
      notApplicable - used for entries that are not LAN (as HDLC), 
                      or when the VCC was attached to a bridge, or 
                      when this parameter is irrelevant.
      free          - the LAN VCC wasn't attached yet to any router 
                      interface. 
      routerAtm      - attached to an ATM router interface.
      lis           - attached to a LIS interface."
      ::= { xcEntry 10 }

xcInputPriority OBJECT-TYPE
        SYNTAX   Integer32  (1..4)
      MAX-ACCESS  read-create
      STATUS  current
      DESCRIPTION
      "This object is the priority, by which the LAN frames will be 
      internaly sent to the ATM HW. This parameter is applicable if 
      atmNteMdlInputPriorityMechanism=enabled.
      
      1 -  Highest priority. Will be the first to be sent to the ATM HW.
      4 -  Lowest priority. Will be the last to be sent to the ATM HW."
      ::= { xcEntry 11 }

xcBitMapping OBJECT-TYPE
        SYNTAX   Integer32
      MAX-ACCESS  read-only
      STATUS  current
      DESCRIPTION
      "This object maps this entry to a bit of an octet string.
      For ACE2002 this object maps the LAN VCC to the bit of the 
      VLAN Port Lists. If the value is '0' then it means that 
      this VCC is not mapped to a port list or it may be an HDSL
      entry."
      ::= { xcEntry 12 }

systemModule  OBJECT IDENTIFIER ::= { agnt 32 }


modlParam  OBJECT IDENTIFIER ::= { systemModule 1 }

modlParamTable OBJECT-TYPE
      SYNTAX SEQUENCE OF ModlParamEntry
      MAX-ACCESS not-accessible
      STATUS current
      DESCRIPTION
      "This table include parameters for system modules."
      ::= { modlParam 1 }

modlParamEntry OBJECT-TYPE
      SYNTAX ModlParamEntry
      MAX-ACCESS not-accessible
      STATUS current
	DESCRIPTION  "An entry in table."
	INDEX { modlParamIndex }
      ::= { modlParamTable 1}


ModlParamEntry ::=
      SEQUENCE {
	 modlParamIndex        	Integer32,
     modlParamReset 	    INTEGER,
     modlParamSwdlStatus	INTEGER,
	 modlParamLeds          OCTET STRING,
     modlParamType			INTEGER,
	 modlParamSwVer			DisplayString
      }

modlParamIndex OBJECT-TYPE
      SYNTAX  Integer32
      MAX-ACCESS  read-only
      STATUS  current
      DESCRIPTION
      "The module index.
       The index can be the slot number or any other module index as described
       in the specifications of the device.
       For Vmux-2100 device, the index will have values of: 1..4 for slots 1..4."
      ::= { modlParamEntry 1 }

modlParamReset  OBJECT-TYPE
	SYNTAX  INTEGER	{
	                 off         (2),
					 on          (3),
					 factory	 (4) 			 
				    }
	MAX-ACCESS  read-write
	STATUS  current
	DESCRIPTION
	"Reset action to be performed on the module. 
	 Set the parameter will be done always to on(3) or factory (4). 
	 After performing the Reset operation, Agent will automatically set the parameter to off(2)."
	::= { modlParamEntry 2 }
		   
modlParamSwdlStatus  OBJECT-TYPE
    SYNTAX  INTEGER	{
	notApplicable	(1),
	off         	(2),
	inProcess   	(3) 
		    }
    MAX-ACCESS  read-only
    STATUS  current
    DESCRIPTION
      "This parameter indicates whatever the swdl is in process or not."
    ::= {modlParamEntry 3}

modlParamLeds  OBJECT-TYPE
	SYNTAX  OCTET STRING
	MAX-ACCESS  read-only
	STATUS current
	DESCRIPTION
	"This entry specifies the LEDs status of the module.
	 Each led is represented by 4 bits where the first 2 bits (left) specify  the status :
	 (00=NA, 01=OFF, 10=ON, 11=BLINK),
     and the next two bits (right) specify the color :
     (00=GREEN, 01=RED, 10=YELLOW, 11=GRAY).
     The order of the LEDS is from top to bottom, left to right:
     For each row starting from the top, the LEDS are returned from left to right."
     ::= {modlParamEntry 4}

modlParamType  OBJECT-TYPE
	SYNTAX  INTEGER	{
		unknown			(2),
		empty			(3),
		miRicE1			(4),
		miRicT1			(5),
		miRicE3			(6),
		miRicT3			(7)
		}
	MAX-ACCESS  read-only
	STATUS  current
	DESCRIPTION
	"This attribute indicates the Module Type."
	::= { modlParamEntry 5 }

modlParamSwVer  OBJECT-TYPE
	SYNTAX  DisplayString
	MAX-ACCESS  read-only
	STATUS  current
	DESCRIPTION
	"This attribute indicates the Module's Software Version."
	::= { modlParamEntry 6 }


agnNearFarConnection OBJECT-TYPE   
      SYNTAX  INTEGER {
		 notApplicable	(1),
		 disconnected  	(2), 
		 connected 		(3)
		 		}
      MAX-ACCESS  read-only
      STATUS  current
      DESCRIPTION
      "This parameter describes the connection between near-end and far-end agents."   
      ::= { agnt 33 }

agnAccess OBJECT IDENTIFIER ::= {agnt 34} 

agnTelnetAccess OBJECT-TYPE
	SYNTAX  INTEGER
	{
	 disable       (2),
	 enable        (3),
	 managersOnly  (4),
	 enableSecure  (5),		-- Deprecated; supported by agnSshAccess = enable(3)
	 managersOnlySecure(6)	-- Deprecated; supported by agnSshAccess = managersOnly(4)
	 }
	MAX-ACCESS  read-write
	STATUS current
	DESCRIPTION
	"Enable/Disable accessing the device via Telnet.
	
	 disable - no one will be allowed to access the device via Telnet.
	 enable - all users are allowed Telnet Access.
	 managersOnly - Only manager stations listed in the manager's list are allowed.
	 enableSecure - same as 'enable' above + only Secure data will be accepted (SSH)
	 managersOnlySecure - same as 'managersOnly' above + only Secure data will be 
	           accepted (SSH)."
     ::= { agnAccess 1 }

agnWebAccess OBJECT-TYPE
	SYNTAX  INTEGER
	{
	 disable       (2),
	 enable        (3),
	 managersOnly  (4),
	 enableSecure  (5), 
	 managersOnlySecure(6)
	 }
	MAX-ACCESS  read-write
	STATUS current
	DESCRIPTION
	"Enable/Disable accessing the device via Web.
	
	 disable - no one will be allowed to access the device via Web.
	 enable - all users are allowed Web Access.
	 managersOnly - Only manager stations listed in the manager's list are allowed.
	 enableSecure - same as 'enable' above + only Secure data will be accepted (SSL)
	 managersOnlySecure - same as 'managersOnly' above + only Secure data will be 
	           accepted (SSL)."
     ::= { agnAccess 2 }

agnRadiusAccess  OBJECT-TYPE
	SYNTAX  INTEGER
	{
	 disable       (2),
	 enable        (3)
    }
	MAX-ACCESS  read-write
	STATUS current
	DESCRIPTION
	"Enable/Disable authentication via RADIUS server."
     ::= { agnAccess 3 }

agnSshAccess OBJECT-TYPE
	SYNTAX  INTEGER
	{
	 disable       (2),
	 enable        (3),
	 managersOnly  (4)
	}
	MAX-ACCESS  read-write
	STATUS current
	DESCRIPTION
	"Enable/Disable accessing the device via SSH.
	
	 disable - no one will be allowed to access the device via SSH.
	 enable - all users are allowed SSH Access.
	 managersOnly - Only manager stations listed in the manager's list are allowed."
    ::= { agnAccess 4 }


systemInterface	 OBJECT IDENTIFIER  ::=  { agnt 35 }

SysIfEntityType ::= INTEGER
--	STATUS  current
--	DESCRIPTION
--	"This type defines the Entity Type above the created interface.
--   The values existing in IANAifType MIB
--	 should be taken from there only.
--	 Additional values can be added, starting from 1000 decimal,
--	 when necessary."
	{
		other(1),
        ethernetLan(6),
        atm(37),				
		fastEther(62),			-- Fast Ethernet (100BaseT)
        ipForward(142),			-- Router
		teLink(200),
		bridge(209)
	}

-- Interface Configuration Table

ifCreateTable OBJECT-TYPE
	SYNTAX  SEQUENCE OF IfCreateEntry
    MAX-ACCESS  not-accessible
    STATUS  current
    DESCRIPTION
	"The Interface Configuration Table.
	 This table enables to create interfaces of Entities."
    ::= { systemInterface 1 }

ifCreateEntry OBJECT-TYPE
    SYNTAX  IfCreateEntry
    MAX-ACCESS  not-accessible
    STATUS  current
    DESCRIPTION
    "An entry in the Interface Configuration table."
    INDEX   { ifCreateEntityType , ifCreateEntityIdx ,
    		  ifCreateNumber }
    ::= { ifCreateTable 1 }

IfCreateEntry ::=
    SEQUENCE {
        ifCreateEntityType			SysIfEntityType,
        ifCreateEntityIdx			Integer32,
		ifCreateNumber				Integer32,
		ifCreateRowStatus			RowStatus,
		ifCreateType				IANAifType,
		ifCreateIndex				Integer32,
		ifCreateConnectedTo			Integer32,
		ifCreateParams				Unsigned32,
		ifCreateConnectionPointer	RowPointer
    }
		
ifCreateEntityType OBJECT-TYPE
    SYNTAX  SysIfEntityType
    MAX-ACCESS  read-only
    STATUS  current
    DESCRIPTION
    "This object indicates the Type of the Entity that exists above the created interface.
	 For a Logical Port, this value can be: other (1) when there is no fixed entity above it."
     ::= { ifCreateEntry 1 }

ifCreateEntityIdx OBJECT-TYPE
    SYNTAX  Integer32
    MAX-ACCESS  read-only
    STATUS  current
    DESCRIPTION
    "This object indicates the Index of the Entity that exists above the created interface.
    For a Logical Port, this value can be: 9999 - N/A when there is no fixed entity above it."
    ::= { ifCreateEntry 2 }

ifCreateNumber OBJECT-TYPE
    SYNTAX  Integer32
    MAX-ACCESS  read-only
    STATUS  current
    DESCRIPTION
    "This object indicates the number of the Interface that is created."
    ::= { ifCreateEntry 3 }
	
ifCreateRowStatus OBJECT-TYPE
    SYNTAX      RowStatus
    MAX-ACCESS  read-create
    STATUS      current
    DESCRIPTION
    "This object enables the user to 
     create/delete entries in this table."
    ::= { ifCreateEntry 4 }

ifCreateType OBJECT-TYPE
    SYNTAX  IANAifType
    MAX-ACCESS  read-create
    STATUS  current
    DESCRIPTION
    "This object indicates the Type of the Interface that is created."
    ::= { ifCreateEntry 5 }

ifCreateIndex OBJECT-TYPE
    SYNTAX  Integer32
    MAX-ACCESS  read-only
    STATUS  current
    DESCRIPTION
    "This object indicates the ifIndex of the created Interface.
     The ifIndex is assigned by the device."
    ::= { ifCreateEntry 6 }

ifCreateConnectedTo OBJECT-TYPE
    SYNTAX  Integer32
    MAX-ACCESS  read-create
    STATUS  current
    DESCRIPTION
    "This object indicates the entity connected to the created Interface.
     The value of this object can be ifIndex of the connected entity or any other
     number that can identify it."
     ::= { ifCreateEntry 7 }

ifCreateParams OBJECT-TYPE
    SYNTAX  Unsigned32
    MAX-ACCESS  read-create
    STATUS  current
    DESCRIPTION
    "This object represents one or more parameters of the created Interface.
	 Each group of bits (one or more bits) represents a specific parameter
	 and its possible values.
	 This object's mapping and interpretation will be specified in each
	 device's specification documents.
     The parameter should be used within the create PDU assuming atomic operation."
    ::= { ifCreateEntry 8 }

ifCreateConnectionPointer OBJECT-TYPE
    SYNTAX      RowPointer
    MAX-ACCESS  read-create
    STATUS      current
    DESCRIPTION
    "This parameter represents the entity that is connected
     to this Interface.

	 It can be used instead of ifCreateConnectedTo.
	 
	 It is an OBJECT IDENTIFIER.
	 This parameter's SYNTAX allows the following possibilities:
	 - can be simply used for entity that is not an interface
	 - is not limited to include up to 32 bits 
		
	 The value of this parameter is a pointer to an existing row of a table,
	 where the entity connected to this Interface is defined
	 (i.e. the pointer uniquely identifies the connected entity).
		
	 Examples:

     In case of an interface (from 2863.ifTable):
     	points to 'ifEntry' of corresponding row
      	= <ifEntry OID>.<ifIndex>
        
     In case of a VPI/VCI (from 2515.atmVclTable): 
     	points to 'atmVclEntry' of corresponding row
        = <atmVclEntry OID>.<ATM>.VPI.VCI

     In case no entity is connected, value = 0
	 ."
    ::= { ifCreateEntry 9 }

interfacePerformance	 OBJECT IDENTIFIER  ::=  { systemInterface 2 }

ifPerfTable OBJECT-TYPE
    SYNTAX  SEQUENCE OF IfPerfEntry
    MAX-ACCESS  not-accessible
    STATUS  current
    DESCRIPTION
    "Interface Performance Table.
    The propose of this table is to support statistics counters having 64 bit 
    by using 2 parameters with syntax= Integer32.
    This is because SNMPv1 does not support Counter64 properly.
    For SNMPv3, ifPerfHCCounter (Counter64) may be supported. "
    ::= { interfacePerformance 1 }

ifPerfEntry OBJECT-TYPE
    SYNTAX  IfPerfEntry
    MAX-ACCESS  not-accessible
    STATUS  current
    DESCRIPTION
    "An entry in the Interface Performance Table."
    INDEX   { ifIndex, ifPerfCounterType } 
    ::= { ifPerfTable 1 }

IfPerfEntry ::=
   SEQUENCE {
   ifPerfCounterType			Integer32,
   ifPerfLowCounterPart			Unsigned32,
   ifPerfHighCounterPart		Unsigned32,
   ifPerfHCCounter				Counter64
                     }

ifPerfCounterType OBJECT-TYPE
   SYNTAX  Integer32 
   MAX-ACCESS  not-accessible
   STATUS  current
   DESCRIPTION
   "2nd index of the ifPerfTable.
   This parameter represents the Counter Type.
   Each application can have a different association between this object's
   value and counter type - see relevant application spec.
   For VPLS-MTU application use the following values:
   1= Rx Octets, 2= Tx Octets, 3= Rx Frames, 4= Tx Frames, 5=Rx Dropped Frames,
   6= Tx Dropped Frames.
   Optionally, counter type description appears in agnListDecodingTable "
   ::= { ifPerfEntry 1 }

ifPerfLowCounterPart OBJECT-TYPE
   SYNTAX  Unsigned32 
   MAX-ACCESS  read-only
   STATUS  current
   DESCRIPTION
   "In order to support Counters having 64 bit length, 
   the performance counter is divided into two 32 bit parameters as follows:
   [  64 bit parameter ] = [  High 32 bit parameter ][ Low 32 bit parameter ]. 
   This parameter holds the Low 32 bits of the counter, 
   while the following parameter holds the High 32 bits of the counter."
   ::= { ifPerfEntry 2 }

ifPerfHighCounterPart OBJECT-TYPE
   SYNTAX  Unsigned32 
   MAX-ACCESS  read-only
   STATUS  current
   DESCRIPTION
   "This parameter holds the High 32 bits of the counter
   (see description in the above parameter)."
   ::= { ifPerfEntry 3 }

ifPerfHCCounter OBJECT-TYPE
   SYNTAX  Counter64 
   MAX-ACCESS  read-only
   STATUS  current
   DESCRIPTION
   "This High Capacity counter holds whole 64 bits of the counter 
    indicated by ifPerfCounterType (concatenates both counter parts 
    ifPerfHighCounterPart&ifPerfLowCounterPart)
    This object can be supported only by agents using SNMPv2 or SNMPv3."
   ::= { ifPerfEntry 4 }


systemOam	 OBJECT IDENTIFIER  ::=  { agnt 36 }

systemOamTable OBJECT-TYPE
	SYNTAX  SEQUENCE OF SystemOamEntry
    MAX-ACCESS  not-accessible
    STATUS  current
    DESCRIPTION
	"The OAM Configuration Table."
	::= { systemOam 1 }

systemOamEntry OBJECT-TYPE
    SYNTAX  SystemOamEntry
    MAX-ACCESS  not-accessible
    STATUS  current
    DESCRIPTION
    "An entry in the OAM table."
    INDEX   { systemOamCnfgIdx }
    ::= { systemOamTable 1 }

SystemOamEntry ::=
    SEQUENCE {
        systemOamCnfgIdx            Integer32,
        systemOamFrequency			Integer32,
		systemOamTimeoutCycles		Integer32,
		systemOamLinkCheck          INTEGER		
    }

systemOamCnfgIdx OBJECT-TYPE
    SYNTAX Integer32 (1..255)
    MAX-ACCESS not-accessible
    STATUS current
    DESCRIPTION
    "This attribute indicates the Idx of the Cnfg(1..255) being 
     accessed ; Idx of 255 relates to the TmpCnfg."
    ::= {  systemOamEntry 1}

systemOamFrequency OBJECT-TYPE
    SYNTAX  Integer32
    MAX-ACCESS  read-write
    STATUS  current
    DESCRIPTION
    "Time in sec. between 2 OAM packets."
    ::= { systemOamEntry 2 }

systemOamTimeoutCycles OBJECT-TYPE
    SYNTAX  Integer32
    MAX-ACCESS  read-write
    STATUS  current
    DESCRIPTION
    "No. of cycles the agent will send OAM packets without receiving a response
     from the remote device before declaring that the connection to the remote side
     is down - Time Out."
    ::= { systemOamEntry 3 }

systemOamLinkCheck
    OBJECT-TYPE
     SYNTAX  INTEGER
      {
       disable       (2),
       enable        (3)
      }
     MAX-ACCESS  read-write
     STATUS  current
     DESCRIPTION
     "This MIB object determines whether continuous connectivity Link checks will be
      performed by the device for uplinks.

      For Vmux-2100: enable (3) value can be set upon device installation.
      In this case, TDM Link Connectivity checks can be performed even before the user
      configures the Links of the device.If the value is enable (3) and there is
      no connection with the remote side, the Test LED will blink on the
      Main Board Module."
     ::= { systemOamEntry 4 }


systemOamDescrTable OBJECT-TYPE
	SYNTAX  SEQUENCE OF SystemOamDescrEntry
    MAX-ACCESS  not-accessible
    STATUS  current
    DESCRIPTION
	"The OAM Descriptors Configuration Table."
	::= { systemOam 2 }

systemOamDescrEntry OBJECT-TYPE
    SYNTAX  SystemOamDescrEntry
    MAX-ACCESS  not-accessible
    STATUS  current
    DESCRIPTION
    "An entry in the OAM table."
    INDEX   { systemOamDescrIdx }
    ::= { systemOamDescrTable 1 }

SystemOamDescrEntry ::=
    SEQUENCE {
        systemOamDescrIdx					Integer32,
		systemOamDescrRowStatus				RowStatus,
        systemOamDescrMode					INTEGER,
        systemOamDescrCCDirection			INTEGER,
		systemOamDescrLoopbackOperation		INTEGER,
		systemOamDescrLoopbackDestAddr		OCTET STRING,
        systemOamDescrXcCounter				Gauge32
		}

systemOamDescrIdx OBJECT-TYPE
    SYNTAX Integer32
    MAX-ACCESS not-accessible
    STATUS current
    DESCRIPTION
    "The OAM Descriptor Index."
    ::= { systemOamDescrEntry 1 }

systemOamDescrRowStatus OBJECT-TYPE
	SYNTAX      RowStatus
	MAX-ACCESS  read-create
	STATUS      current
	DESCRIPTION
	"Enables the user to create/delete entries in this table."
	::= { systemOamDescrEntry 2 }

systemOamDescrMode OBJECT-TYPE
	SYNTAX  INTEGER {
		intermediate(1),
		segmentTermination(2),
		endToEndTermination(3)
	}
	MAX-ACCESS  read-create
	STATUS  current
	DESCRIPTION
	"The OAM Mode of the Descriptor."
	::= { systemOamDescrEntry 3 }

systemOamDescrCCDirection OBJECT-TYPE
	SYNTAX  INTEGER {
		both  (2),
		none  (3),
		source(4),
		sink  (5)     
	} 
	MAX-ACCESS read-create
	STATUS current
	DESCRIPTION
	"OAM Continuity Check function mode.
	 both(2)  - Agent sends OAM CC cells and checks received OAM CC cells.
	 none(3) - Agent does not send and does not check received OAM CC cells.
	 source(4)- Agent sends OAM CC cells.
	 sink(5)  - Agent checks received OAM CC cells."
	::= { systemOamDescrEntry 4 }

systemOamDescrLoopbackOperation OBJECT-TYPE
	SYNTAX INTEGER {
		off	(2),
		on	(3)
	} 
	MAX-ACCESS read-create
 	STATUS current
	DESCRIPTION
	"The OAM Loopback function mode.
	 off(2) - Stop sending loopback OAM cells.
	 on(3) - Start loopback OAM cells."
	::= { systemOamDescrEntry 5 }	 

systemOamDescrLoopbackDestAddr OBJECT-TYPE
	SYNTAX OCTET STRING 
	MAX-ACCESS read-create
 	STATUS current
	DESCRIPTION
	"Loopback Destination Address."
	::= { systemOamDescrEntry 6 }

systemOamDescrXcCounter OBJECT-TYPE
	SYNTAX Gauge32 
	MAX-ACCESS read-only
 	STATUS current
	DESCRIPTION
	"The number of connections that use this OAM Descriptor."
	::= { systemOamDescrEntry 7 }

agnDeviceView OBJECT-TYPE
	SYNTAX  INTEGER
	{
	 oldLook       (2),
	 newLook       (3),
	 newLook2	   (4),
	 plastic       (5),
	 metal         (6) 
	}
	MAX-ACCESS  read-only
	STATUS current
	DESCRIPTION
	"This variable denotes the view of the device:
	Look: old look, new look or new look 2.
	Material: Plastic or Metal."
     ::= { agnt 37 }

bitMappingTable OBJECT-TYPE
      SYNTAX SEQUENCE OF BitMappingEntry
      MAX-ACCESS not-accessible
      STATUS current
      DESCRIPTION
      "This table maps bits of an octet string to an interface.
      For ACE-2002 this table is used to map bits of VLAN port lists
      to LAN VCC's. This table is the opposite view of the xcTable for
      xcBitMapping. It is used to ease the bit translation for the NMS."
      ::= { agnt 38 }

bitMappingEntry OBJECT-TYPE
      SYNTAX BitMappingEntry
      MAX-ACCESS not-accessible
      STATUS current
	DESCRIPTION  
	"Each entry in the table describes a correlation of a bit location to 
	an interface.
	For ACE-2002 - Upon creation of a new LAN VCC the agent will add an 
	entry to this table that will define the bit location for that VCC."
	INDEX { bitMappingLocation }
      ::= { bitMappingTable 1}

BitMappingEntry ::=
      SEQUENCE {
	  bitMappingLocation       Integer32,
      bitMappingIndex          Integer32
      }

bitMappingLocation OBJECT-TYPE
      SYNTAX  Integer32
      MAX-ACCESS  not-accessible
      STATUS  current
      DESCRIPTION
      "The bit location in an octet string."
      ::= { bitMappingEntry 1 }

bitMappingIndex OBJECT-TYPE
      SYNTAX  Integer32
      MAX-ACCESS  read-only
      STATUS  current
      DESCRIPTION
      "The interface index or any other index that should be mapped."
      ::= { bitMappingEntry 2 }

bitMappingView OBJECT-TYPE
      SYNTAX  OCTET STRING
      MAX-ACCESS  read-only
      STATUS  current
      DESCRIPTION
      "A view of the bitMappingTable in one object - each entry in the 
      biMappingTable will have the corresponding Bit of this object 
      (bitMappingLocation) = '1'.
      For ACE-2002 it is used to describe all the existing LAN VCC's
      So that the NMS can easily calculate which VCC's can be selected
      as members for a VLAN, instead of reading all the bitMapping Table."
      ::= { agnt 39 }

hostTable OBJECT-TYPE
    SYNTAX  SEQUENCE OF HostEntry
    MAX-ACCESS  not-accessible
    STATUS  current
    DESCRIPTION
    "Host interface table."
    ::= { agnt 40 }

hostEntry OBJECT-TYPE
    SYNTAX  HostEntry
    MAX-ACCESS  not-accessible
    STATUS  current
    DESCRIPTION
    "An entry in the Host Table.
    The hostParam1, hostParam2, and hostParam3 entries may 
    have different use in different applications."
    INDEX   { hostIndex } 
    ::= { hostTable 1 }

HostEntry ::=
   SEQUENCE {
   hostIndex			Integer32,
   hostIP	    		IpAddress,
   hostIPMask			IpAddress,
   hostDefaultNextHop	IpAddress,
   hostMode				Integer32,
   hostParam1			Integer32,
   hostParam2			Integer32,
   hostParam3			Integer32,
   hostRowStatus		RowStatus,
   hostVlanTagging		INTEGER,
   hostVlanId			Integer32,
   hostVlanPriority		Integer32
                 }


hostIndex OBJECT-TYPE
   SYNTAX  Integer32 
   MAX-ACCESS  not-accessible
   STATUS  current
   DESCRIPTION
   "The Host Table Index. This index can have the same value as Host No."
   ::= { hostEntry 1 }

hostIP OBJECT-TYPE
   SYNTAX  IpAddress 
   MAX-ACCESS  read-create
   STATUS  current
   DESCRIPTION
   "The host interface IP address."
   ::= { hostEntry 2 }

hostIPMask OBJECT-TYPE
   SYNTAX  IpAddress 
   MAX-ACCESS  read-create
   STATUS  current
   DESCRIPTION
   "The host interface subnet mask."
   ::= { hostEntry 3 }

hostDefaultNextHop OBJECT-TYPE
   SYNTAX  IpAddress 
   MAX-ACCESS  read-create
   STATUS  current
   DESCRIPTION
   "The host interface Default Next Hop address."
   ::= { hostEntry 4 }

hostMode OBJECT-TYPE
   SYNTAX  Integer32 
   MAX-ACCESS  read-create
   STATUS  current
   DESCRIPTION
   "This parameter represents the Host mode of operation.
   There can be different values for each application.
   For example:
   Not Applicable = 1."
   ::= { hostEntry 5 }

hostParam1 OBJECT-TYPE
   SYNTAX  Integer32 
   MAX-ACCESS  read-create
   STATUS  current
   DESCRIPTION
   "This parameter represents the first Host parameter.
   There can be different values for each application.
   For example:
   Not Applicable = 1."
   ::= { hostEntry 6 }

hostParam2 OBJECT-TYPE
   SYNTAX  Integer32 
   MAX-ACCESS  read-create
   STATUS  current
   DESCRIPTION
   "This parameter represents the 2nd Host parameter.
   There can be different values for each application."
   ::= { hostEntry 7 }

hostParam3 OBJECT-TYPE
   SYNTAX  Integer32 
   MAX-ACCESS  read-create
   STATUS  current
   DESCRIPTION
   "This parameter represents the 3nd Host parameter.
   There can be different values for each application."
   ::= { hostEntry 8 }

hostRowStatus OBJECT-TYPE
   SYNTAX  RowStatus 
   MAX-ACCESS  read-create
   STATUS  current
   DESCRIPTION
   "Creation/Deletion of rows in the table."
   ::= { hostEntry 9 }

hostVlanTagging OBJECT-TYPE
    SYNTAX  INTEGER 
    {
    notApplicable(1),
    untag		(2),
    tag	    	(3)
    }
    MAX-ACCESS  read-create
    STATUS  current
    DESCRIPTION
    "Host VLAN support (Tagging).
     untag - No support of VLAN Tagging.
     tag - 4 VLAN bytes will be added to the frame."
    ::= { hostEntry 10 }

hostVlanId OBJECT-TYPE
     SYNTAX  Integer32 
     MAX-ACCESS  read-create
     STATUS  current
     DESCRIPTION
     "Host VLAN ID."
     ::= { hostEntry 11 }
  
hostVlanPriority OBJECT-TYPE
     SYNTAX  Integer32 
     MAX-ACCESS  read-create
     STATUS  current
     DESCRIPTION
     "Host VLAN Frame priority."
     ::= { hostEntry 12 }


invNameXCTable OBJECT-TYPE
	SYNTAX  SEQUENCE OF InvNameXCEntry
	MAX-ACCESS  not-accessible
	STATUS  current
	DESCRIPTION
	"Inverse Name XC Table.
	 This table can be used to ease the search for a connection first index
	 by the connection name."
	::= { agnt 41 }

invNameXCEntry OBJECT-TYPE
	SYNTAX  InvNameXCEntry
	MAX-ACCESS  not-accessible
	STATUS  current
	DESCRIPTION
	"An entry in the table."
	INDEX   { IMPLIED invNameXC } 
	::= { invNameXCTable 1 }

InvNameXCEntry ::= SEQUENCE {
	invNameXC			SnmpAdminString,
	invNameXCType		OBJECT IDENTIFIER,
	invNameXCIndex		Integer32
	}

invNameXC OBJECT-TYPE
	SYNTAX  SnmpAdminString (SIZE (1..64)) 
	MAX-ACCESS  not-accessible
	STATUS  current
	DESCRIPTION
	"The unique Connection name,
	 associated to a Cross-Connection."
	::= { invNameXCEntry 1 }

invNameXCType OBJECT-TYPE
	SYNTAX  OBJECT IDENTIFIER 
	MAX-ACCESS  read-only
	STATUS  current
	DESCRIPTION
	"The OBJECT IDENTIFIER of the respective XC Table.
	 Examples:
	 
	 XC Table					invNameXCType
	 ---------------------------------------------------
	 atmVpCrossConnectTable		1.3.6.1.2.1.37.1.9
	 atmVcCrossConnectTable		1.3.6.1.2.1.37.1.11
	 atmfCESConfTable			1.3.6.1.4.1.353.5.2.2.1.1
	 ."
	::= { invNameXCEntry 2 }

invNameXCIndex OBJECT-TYPE
	SYNTAX  Integer32 
	MAX-ACCESS  read-only
	STATUS  current
	DESCRIPTION
	"The XC Table (invNameXCType) may include more than one index.
	 This object represents the value of the first XC Index."
	::= { invNameXCEntry 3 }


agnDeviceCapabilities OBJECT-TYPE
	SYNTAX  OCTET STRING
	MAX-ACCESS  read-only
	STATUS current
	DESCRIPTION
	"Indicates the optional capabilities that are implemented by this device
     and are manageable through this MIB. 

	 For each capability 1 BIT is allocated in each Octet starting from the LSB.
	 If the value of the BIT = 1, the capability is Enabled.
	 If the value of the BIT = 0, the capability is Disabled.
     For bit assignment, refer to device specification.	 
	 Capabilities example:
	 Router - BIT 0 (0000 0001 = 01 Hex = 1 Decimal).
	 
	 The 2nd octet (MSB) will represent the maximum number of intervals that
	 the Agent can keep in its DB (same for all ports).
	 
     For Vmux, this object describes agent's support of LBRAD coder feature:
     1 octet ; bit 0 (LSB).
     '1' - LBRAD feature is supported
     '0' - LBRAD feature is not supported."
	::= {agnt 42}


rowInfoTable OBJECT-TYPE
	SYNTAX  SEQUENCE OF RowInfoEntry
	MAX-ACCESS  not-accessible
	STATUS  current
	DESCRIPTION
	"This table holds information of other tables."
	::= { agnt 43 }

rowInfoEntry OBJECT-TYPE
	SYNTAX  RowInfoEntry
	MAX-ACCESS  not-accessible
	STATUS  current
	DESCRIPTION
	"An entry in the table."
	INDEX   { rowInfoTableId } 
	::= { rowInfoTable 1 }

RowInfoEntry ::= SEQUENCE {
	rowInfoTableId		OBJECT IDENTIFIER,
	rowInfoCounter		Integer32,
	rowInfoIndexNext	Integer32,
	rowInfoMaxNoOfRows	Integer32
	}

rowInfoTableId OBJECT-TYPE
	SYNTAX  OBJECT IDENTIFIER 
	MAX-ACCESS  not-accessible
	STATUS  current
	DESCRIPTION
	"The OBJECT IDENTIFIER of the Table, 
	 which its information is held by this table (rowInfoTable).
	 Examples:
	 
	 Table Name					rowInfoTableId
	 ---------------------------------------------------
	 atmTrafficDescrParamTable	1.3.6.1.2.1.37.1.5
	 atmVpCrossConnectTable		1.3.6.1.2.1.37.1.9
	 atmVcCrossConnectTable		1.3.6.1.2.1.37.1.11
	 atmfCESConfTable			1.3.6.1.4.1.353.5.2.2.1.1
	 ."
	::= { rowInfoEntry 1 }

rowInfoCounter OBJECT-TYPE
	SYNTAX  Integer32 
	MAX-ACCESS  read-only
	STATUS  current
	DESCRIPTION
	"The Number of rows in the table, indicated by rowInfoTableId."
	::= { rowInfoEntry 2 }

rowInfoIndexNext OBJECT-TYPE
	SYNTAX  Integer32 
	MAX-ACCESS  read-only
	STATUS  current
	DESCRIPTION
	"The First Free Index of the table, indicated by rowInfoTableId."
	::= { rowInfoEntry 3 }

rowInfoMaxNoOfRows OBJECT-TYPE
	SYNTAX  Integer32 
	MAX-ACCESS  read-only
	STATUS  current
	DESCRIPTION
	"The maximum possible number of rows in the table, indicated by rowInfoTableId."
	::= { rowInfoEntry 4 }


agnStoreCmd OBJECT-TYPE
	SYNTAX  INTEGER
	{
	 off				(2),
	 inFlash			(3),
	 asDefConfigFile	(4)
	 	 }
	MAX-ACCESS  read-write
	STATUS current
	DESCRIPTION
	"Store command.
	 inFlash(3)			= store the current Agent configuration in Flash memory.
	 asDefConfigFile(4)	= store the current Agent configuration as
	                      Default Configuration file (e.g. 'DefConfig.cfg').
	 Agent will perform the required command and change automatically 
	 the value of this object to off(2)."
     ::= { agnt 44 }


agnFunctionTable OBJECT-TYPE
	SYNTAX  SEQUENCE OF AgnFunctionEntry
	MAX-ACCESS  not-accessible
	STATUS  current
	DESCRIPTION
	"This table is used in order to activate/deactivate device functions.
     The index indicates the function. Each function can be Enabled or Disabled."
	::= { agnt 45 }

agnFunctionEntry OBJECT-TYPE
	SYNTAX  AgnFunctionEntry
	MAX-ACCESS  not-accessible
	STATUS  current
	DESCRIPTION
	"An entry in the table."
	INDEX   { agnFunction } 
	::= { agnFunctionTable 1 }

AgnFunctionEntry ::= SEQUENCE {
	agnFunction                 INTEGER,
	agnFunctionActivation       INTEGER
	}

agnFunction		OBJECT-TYPE
	SYNTAX  INTEGER
	{
	 routing          (2),
	 backup           (3),
     alarmForwarding  (4),
	 uplinkLoopDetect (5),
	 systemClock      (6),
	 nps			  (7)
	 }
	MAX-ACCESS  not-accessible
	STATUS current
	DESCRIPTION
	"This MIB object indicates the function that will be enabled or disabled
     in the device.
	 alarmForwarding= Fault Propagation (usually towards user port).
     For Vmux:
     routing (2) - enable/disable Router
     backup  (3) - enable/disable Backup between E1/T1/Serial Link and ETH.
     uplinkLoopDetect (5) - enable/disable Loop Detection on the TDM Uplink.
     systemClock (6) - enable/disable the System Clock.
	 nps (7) - N+1 Protection Switching device physically connected to I/O
	 modules in Gmux2000.
     "
     ::= { agnFunctionEntry 1 }

agnFunctionActivation	OBJECT-TYPE
	SYNTAX  INTEGER
	{
	 disable   (2),
	 enable    (3)
	 	 }
	MAX-ACCESS  read-write
	STATUS current
	DESCRIPTION
	"This MIB object indicates the activation of the current function."
     ::= { agnFunctionEntry 2 }

agnManagerConfigPorts OBJECT-TYPE
    SYNTAX  Integer32 
    MAX-ACCESS  read-write
    STATUS  current
     DESCRIPTION
     "This variable defines from which port/s this manager can manage the device.
	  The value is a sum of 2**n, where n is a bit assigned to a certain port.
	  For RIC-E1 and ETX 102 the value will be according to the ports 
	  combination:
      Network = bit 0
      User= bit 1
  	  For Example: All = 3."
     ::= {agnt 46 }

agnEgressRateRange OBJECT-TYPE
    SYNTAX  INTEGER
    	{
	 unlimited   (1),
	 range1   (2),
	 range2   (3),
	 range3   (4),
	 range4   (5),
	 range5   (6),
     range6   (7),
     range7   (8)  
     	 	 }
    MAX-ACCESS  read-write
    STATUS  current
     DESCRIPTION
     "This variable defines the valid ranges of egress rate. 
      For example, for ETX 102:
	  range 1 (2)= 128KBPS - 8MBPS,
	  range 2 (3)= 256KBPS - 16MBPS,
	  range 3 (4)= 512KBPS - 32MBPS,
	  range 4 (5)= 1MBPS - 64MBPS,
	  range 5 (6)= 1.5MBPS - 80MBPS."
     ::= {agnt 47 }

agnNoOfCurrentConns OBJECT-TYPE
	SYNTAX  Integer32 
	MAX-ACCESS  read-only
	STATUS  current
	DESCRIPTION
	"This variable indicates the number of connections
	 currently configured for the agent."
	::= { agnt 48 }

agnIngressRateRange OBJECT-TYPE
    SYNTAX  INTEGER
    	{
	 unlimited   (1),
	 range1   (2),
	 range2   (3),
	 range3   (4),
	 range4   (5),
	 range5   (6),
     range6   (7),
     range7   (8)  
	 	 }
    MAX-ACCESS  read-write
    STATUS  current
     DESCRIPTION
     "This variable defines the valid ranges of ingress rate. 
      For example, for ETX 102:
	  range 1 (2)= 128KBPS - 8MBPS,
	  range 2 (3)= 256KBPS - 16MBPS,
	  range 3 (4)= 512KBPS - 32MBPS,
	  range 4 (5)= 1MBPS - 64MBPS,
	  range 5 (6)= 1.5MBPS - 80MBPS."
     ::= {agnt 49 }


alarmForwardingTable OBJECT-TYPE
    SYNTAX  SEQUENCE OF AlarmForwardingEntry
    MAX-ACCESS  not-accessible
    STATUS  current
    DESCRIPTION
    "The Alarm Forwarding Mechanism will be operated 
     for this table entries."
   ::= { agnt 50 }

alarmForwardingEntry OBJECT-TYPE
    SYNTAX  AlarmForwardingEntry
    MAX-ACCESS  not-accessible
    STATUS  current
    DESCRIPTION
    "Each entry in this table is a pair of ports that
    the Alarm Forwarding Mechanism is determined for."
    INDEX   { alarmForwardingFailPort, alarmForwardingToPort }
    ::= { alarmForwardingTable 1 }

AlarmForwardingEntry ::=
    SEQUENCE {
     alarmForwardingFailPort
         Integer32,
     alarmForwardingToPort
         Integer32,
     alarmForwardingRowStatus
         RowStatus,
     alarmForwardingRecoveryTime
         Integer32,
     alarmForwardingGroupConditions
     	 Integer32,
     alarmForwardingCause
     	 BITS,
     alarmForwardingRecoveryMode
     	 INTEGER,	  
     alarmForwardingRecoveryCommand
		 INTEGER,
    alarmForwardingDelay
     	 Unsigned32,
    alarmForwardingDirection
     	 INTEGER,
    alarmForwardingAction
         BITS  	  
    }

alarmForwardingFailPort OBJECT-TYPE
    SYNTAX  Integer32 (0..2147483647)
    MAX-ACCESS  not-accessible
    STATUS  current
    DESCRIPTION
    "An Index of the port on which a fail occurs."
    ::= { alarmForwardingEntry 1}

alarmForwardingToPort OBJECT-TYPE
    SYNTAX  Integer32 (0..2147483647)
    MAX-ACCESS  not-accessible
    STATUS  current
    DESCRIPTION
    "An Index of the port that will be affected 
    upon the failure of the alarmForwardingFailPort."
    ::= { alarmForwardingEntry 2}

alarmForwardingRowStatus OBJECT-TYPE
    SYNTAX  RowStatus 
    MAX-ACCESS  read-create
    STATUS  current
    DESCRIPTION
    "Creation/ Deletion of rows in the table."
    ::= { alarmForwardingEntry 3}

alarmForwardingRecoveryTime OBJECT-TYPE
     SYNTAX  Integer32 
     MAX-ACCESS  read-create
     STATUS  current
     DESCRIPTION
     "This parameter defines the maximum time (sec) 
      the affected port will hold the down state."
      ::= { alarmForwardingEntry 4 }

alarmForwardingGroupConditions OBJECT-TYPE
	 SYNTAX  Integer32
     MAX-ACCESS  read-create
     STATUS  current
     DESCRIPTION
	 "This parameter is applicable when there is a group of interfaces 
	 in which a fault may occur, and one interface to which alarm is propagated (forwarded).
	 0 = All - Forwarding will take place only when all interfaces of the 
     same group are faulty.
	 1 = Single - Forwarding will take place when at least one (single)
     interface of the same group (any of them) is faulty.
	 n - forwarding will take place only when n (n < all) 
	 interfaces of the same group fail."
	 ::= { alarmForwardingEntry 5 }

alarmForwardingCause  OBJECT-TYPE
     SYNTAX   BITS
     {
	   loss	           (0),
	   ais             (1),
	   rdi	           (2),
	   protocolDown	   (3),
	   oamSignalingEfm (4),
	   oamSignalingCfm (5)
     }
     MAX-ACCESS  read-create
     STATUS  current
     DESCRIPTION
	 "Bit map representing the cause upon which alarm forwarding will take place.
          bit 0 - LOSS (LINE DOWN)
          bit 1 - AIS 
		  bit 2 - RDI
		  bit 3 - PROTOCOL DOWN.
		  bit 4 - OAM Signaling - EFM
		  bit 5 - OAM Signaling - CFM. " 
     ::= { alarmForwardingEntry 6 }

alarmForwardingRecoveryMode OBJECT-TYPE
     SYNTAX  INTEGER 
     {
  	    manual     (1),
	    automatic  (2)
     } 
     MAX-ACCESS  read-create
     STATUS  current
     DESCRIPTION
     "This parameter determines the Recovery Mode. 
     manual - The user should stop the alarm forwarding 
     by using the alarmForwardingRecoveryCommand.
     automatic - Alarm forwarding will be automatically 
     stopped upon alarmForwardingFailPort recovery."
     ::= { alarmForwardingEntry 7 }

alarmForwardingRecoveryCommand OBJECT-TYPE
     SYNTAX  INTEGER 
     {
 	   off   (2),
	   on    (3)
     } 
     MAX-ACCESS  read-create
     STATUS  current
     DESCRIPTION
     "This parameter is a command. It is applicable when 
     alarmForwardingRecoveryMode = manual.
     on - Will stop alarm forwarding. 
     After setting to 'On', the agent will set this parameter back to 'Off'."
     ::= { alarmForwardingEntry 8 }

alarmForwardingDelay OBJECT-TYPE
     SYNTAX  Unsigned32 
     MAX-ACCESS  read-create
     STATUS  current
     DESCRIPTION
     "This parameter determines the period of time (in seconds) the 
     alarm of the alarmForwardingFailPort should exist before 
     starting alarm forwarding."
     ::= { alarmForwardingEntry 9 }

alarmForwardingDirection OBJECT-TYPE
     SYNTAX  INTEGER 
     {
  	    unidirectional (1),
	    bidirectional  (2)
     } 
     MAX-ACCESS  read-create
     STATUS  current
     DESCRIPTION
     "This parameter determines the Direction of the Alarm Forwarding. 
     unidirectional - alarmForwardingFailPort affects the
                      alarmForwardingToPort.
     bidirectional - alarmForwardingFailPort affects the
                     alarmForwardingToPort AND vice-versa.
                     For such cases, this value will be selected, instead of 
                     entering an additional unidirectional entry
                     in the table, where the indexes are swapped."
     ::= { alarmForwardingEntry 10 }

alarmForwardingAction  OBJECT-TYPE
     SYNTAX   BITS
     {
	   noAction              (0),
	   interfaceDeactivation (1),
	   oamSignaling          (2)
     }
     MAX-ACCESS  read-create
     STATUS  current
     DESCRIPTION
	 "Bit map representing the action to be performed when alarm forwarding will take place.
	      bit 0 - No Action. 
	              '1' value - device should NOT perform any action, though other bits 
	                          indicate the action to be taken. 
	              '0' value - device should perform the action/s indicated by rest of 
	                          the bits.	In this case, one of the other bits should be '1'.
          bit 1 - Interface Deactivation (of the affected Port: alarmForwardingToPort)
          bit 2 - OAM Signaling. Affected Port (alarmForwardingToPort) will send
                  special OAM Signaling to the Far-End unit about the Failure.
      This object will be used only for devices that support Deactivation per entry OR 
      can support more than one action." 
     ::= { alarmForwardingEntry 11 }


agnSwVersionSwapCmd OBJECT-TYPE
	SYNTAX  INTEGER
	{
	 off  (2),
	 mainAndBackup  (3)
	 	 }
	MAX-ACCESS  read-write
	STATUS current
	DESCRIPTION
	"SW switch command.
	 mainAndBackup (3) = Swap between Main SW and the backup one.
	 Agent will perform the required command and change automatically 
	 the value of this object to off(2)."
     ::= { agnt 51 }

agnClockSource OBJECT IDENTIFIER ::= {agnt 52} 

agnClkSrcPortTable OBJECT-TYPE
      SYNTAX SEQUENCE OF AgnClkSrcPortEntry
      MAX-ACCESS not-accessible
      STATUS  current
      DESCRIPTION
      "Pool of Ports for the Master/Fallback Clock Source
       and of Recovered IDs.
       For devices with more than one configuration:
       Set operation is valid only to the TmpCnfg entry."
       ::= { agnClockSource 1}

agnClkSrcPortEntry OBJECT-TYPE
      SYNTAX AgnClkSrcPortEntry
      MAX-ACCESS not-accessible
      STATUS current
	  DESCRIPTION  "An entry in the table."
	  INDEX {agnClkSrcPortCnfgIdx, agnClkSrcPortSrcIdx, agnClkSrcPortIdx}
      ::= { agnClkSrcPortTable 1}

AgnClkSrcPortEntry ::=
      SEQUENCE {
      agnClkSrcPortCnfgIdx      Integer32,
      agnClkSrcPortSrcIdx       INTEGER,
      agnClkSrcPortIdx          Integer32,
      agnClkSrcPort             Integer32,
      agnClkSrcPortRowStatus    RowStatus,
	  agnClkSrcPortAdminStatus	INTEGER,
	  agnClkSrcPortType			INTEGER,
	  agnClkSrcPortQuality		INTEGER,
	  agnClkSrcPortNetType		INTEGER,
	  agnClkSrcPortState		INTEGER,
	  agnClkSrcPortSrcType   	INTEGER								
	  }

agnClkSrcPortCnfgIdx OBJECT-TYPE
      SYNTAX Integer32 (1..2147483647)
      MAX-ACCESS not-accessible
      STATUS current
      DESCRIPTION
      "This object indicates the Idx of the Cnfg being 
       accessed ; Idx of 255 relates to the TmpCnfg.
       For product supporting a single configuration, the value will be 1."
      ::= { agnClkSrcPortEntry 1}

agnClkSrcPortSrcIdx OBJECT-TYPE
      SYNTAX  INTEGER 
      {
      master    (1),
      fallback  (2),
	  recovered	(3)
      }
      MAX-ACCESS  not-accessible
      STATUS  current
      DESCRIPTION
      "Clock Source Index. 
       master   	- refers to Master clock  
       fallback 	- refers to Fallback clock
       recovered	- refers to Recovered clock."
      ::= { agnClkSrcPortEntry 2}

agnClkSrcPortIdx OBJECT-TYPE
      SYNTAX Integer32 (1..2147483647)
      MAX-ACCESS not-accessible
      STATUS current
      DESCRIPTION
      "This object indicates the running Idx of the Port/Recovered ID that is 
       to be used as Clock Source, for each agnClkSrcPortSrcIdx instance."
      ::= { agnClkSrcPortEntry 3}

agnClkSrcPort OBJECT-TYPE
      SYNTAX Integer32 (1..2147483647)
      MAX-ACCESS read-create
      STATUS current
      DESCRIPTION
      "This object indicates the Port/Interface/Recovered ID # that is 
       to be used as Clock Source.
       In case of agnClkSrcPortSrcIdx=recovered	(3) - it indicates the PW number.
       When agnClkSrcPortSrcIdx=master(1) or fallback(2), this list may include  
       both External Ports and Recovered IDs (mixed). Therefore, in order to know
       which type of instance is indicated, agnClkSrcPortSrcType will be used:
       - When agnClkSrcPortSrcType=rxClock(3), this object indicates a Port index.
       - When agnClkSrcPortSrcType=recovered(12), this object indicates a Recovered ID."
      ::= { agnClkSrcPortEntry 4}

agnClkSrcPortRowStatus OBJECT-TYPE
      SYNTAX  RowStatus 
      MAX-ACCESS  read-create
      STATUS  current
      DESCRIPTION
      "This object enables Creation/ Deletion of rows in the table."
      ::= { agnClkSrcPortEntry 5}

agnClkSrcPortAdminStatus OBJECT-TYPE
      SYNTAX  INTEGER 
      {
		notApplicable	(1), 
		down			(2),
		up				(3)
      }
      MAX-ACCESS  read-create
      STATUS  current
      DESCRIPTION
      "This object indicates the Recovered Clock Administrative Status."
      ::= { agnClkSrcPortEntry 6 }

agnClkSrcPortType OBJECT-TYPE
      SYNTAX  INTEGER 
      {
		notApplicable		(1), 
		adaptive			(2),
		ieee1588v2			(3),
		commonClock			(4)
      }
      MAX-ACCESS  read-create
      STATUS  current
      DESCRIPTION
      "This object is relevant only in case of Recovery Clock.
       It indicates the Clock Type."
      ::= { agnClkSrcPortEntry 7 }

agnClkSrcPortQuality OBJECT-TYPE
      SYNTAX  INTEGER 
      {
		notApplicable		(1), 
		stratum1			(2),
		stratum2			(3),
		stratum3			(4),
		stratum3e			(5),
		stratum4			(6)
      }
      MAX-ACCESS  read-create
      STATUS  current
      DESCRIPTION
      "This object indicates the Clock Source Quality."
      ::= { agnClkSrcPortEntry 8 }

agnClkSrcPortNetType OBJECT-TYPE
      SYNTAX  INTEGER 
      {
		notApplicable		(1), 
		typeA				(2),
		typeB				(3),
		typeC				(4),
		typeD				(5),
		typeE				(6),
		typeF				(7)
      }
      MAX-ACCESS  read-create
      STATUS  current
      DESCRIPTION
      "This object is relevant only in case of Recovery Clock.
       It indicates the Clock Network Type, i.e.
       the PSN network characteristics and behavior."
      ::= { agnClkSrcPortEntry 9 }

agnClkSrcPortState OBJECT-TYPE
      SYNTAX  INTEGER 
      {
		freeRun					(1),
		frequencyAcquisition	(2),
		rapidPhaseLock			(3),
		finePhaseLock			(4),
		holdover				(5),
		notApplicable			(6)
      }
      MAX-ACCESS  read-only
      STATUS  current
      DESCRIPTION
      "This object indicates the Clock State.
       
       freeRun(1) -
       Clock recovery is not locked to any clock.
       
       frequencyAcquisition(2) -
       Adaptive clock recovery is learning the frequency.
       
       rapidPhaseLock(3) -
       Clock recovery is in training process till it reaches fine phase lock.
       
       finePhaseLock(4) -
       Clock is locked and clock recovery is qualified and stable.
       
       holdover(5) -
       Clock recovery is in holdover mode.
              
       notApplicable(6) -
       Clock recovery is not applicable."
      ::= { agnClkSrcPortEntry 10 }

agnClkSrcPortSrcType OBJECT-TYPE
      SYNTAX  INTEGER 
      {
		rxClock	  (3),
		recovered(12)
      }
      MAX-ACCESS  read-create
      STATUS  current
      DESCRIPTION
      "This object indicates the Src Type of each entry in the list of source
       instances, when agnClkSrcPortSrcIdx=master(1)or fallback(2).
       According to this type, agnClkSrcPort gets the relevant meaning (Port index 
       or Recovered ID)."
      ::= { agnClkSrcPortEntry 11 }


agnCurrClkTable OBJECT-TYPE
      SYNTAX SEQUENCE OF AgnCurrClkEntry
      MAX-ACCESS not-accessible
      STATUS  current
      DESCRIPTION
      "Current Clock Source."
       ::= { agnClockSource 2}

agnCurrClkEntry OBJECT-TYPE
      SYNTAX AgnCurrClkEntry
      MAX-ACCESS not-accessible
      STATUS current
	  DESCRIPTION  "An entry in the table."
	  INDEX {agnCurrClkObjIdx}
      ::= { agnCurrClkTable 1}

AgnCurrClkEntry ::=
      SEQUENCE {
      agnCurrClkObjIdx      	Integer32,
      agnCurrClkMode        	INTEGER,
      agnCurrClkSrc         	INTEGER,
      agnCurrClkPort        	Integer32,
	  agnCurrClkHoldover    	INTEGER,
	  agnCurrClkSsmBased    	INTEGER,
	  agnCurrClkState			INTEGER,
	  agnCurrClkQualification	INTEGER
	  }

agnCurrClkObjIdx OBJECT-TYPE
      SYNTAX Integer32 (1..2147483647)
      MAX-ACCESS not-accessible
      STATUS current
      DESCRIPTION
      "This MIB object identifies the object for which the Clock Source
       is used (System, Other System, Card)."
      ::= { agnCurrClkEntry 1}

agnCurrClkMode OBJECT-TYPE
      SYNTAX  INTEGER 
      {
      master    (1),
      fallback  (2),
	  internal  (3)
      }
      MAX-ACCESS  read-only
      STATUS  current
      DESCRIPTION
      "Current Clock Source Mode. 
       master   - refers Master clock  
       fallback - refers Fallback clock
       internal - only when both Master and Fallback Sources failed "
      ::= { agnCurrClkEntry 2}

agnCurrClkSrc OBJECT-TYPE
      SYNTAX INTEGER
      {
      none            (1),
      internal        (2),
      rxClk           (3),
      station         (4),  -- station A (for GMUX2000)
      lbt             (5),
	  ntr             (6),
	  adaptive        (7),  
	  stationB        (8),
	  automatic		 (9),
	  system         (10),
	  sSubsystem     (11),
	  recovered      (12),
      notApplicable (255)
       }
      MAX-ACCESS read-only
      STATUS current
      DESCRIPTION
      "This object indicates the Current Clock Source."
      ::= { agnCurrClkEntry 3}

agnCurrClkPort OBJECT-TYPE
      SYNTAX Integer32 (1..2147483647)
      MAX-ACCESS read-only
      STATUS current
      DESCRIPTION
      "This object indicates the Port/Interface/Recovered ID that is 
       Currently used as Clock Source.
       - When agnCurrClkSrc=rxClock(3), this object indicates a Port index.
       - When agnCurrClkSrc=recovered(12), this object indicates a Recovered ID."
      ::= { agnCurrClkEntry 4}

agnCurrClkHoldover OBJECT-TYPE
      SYNTAX  INTEGER 
      {
      notApplicable(1),
      no  (2),
	  yes (3)
      }
      MAX-ACCESS  read-only
      STATUS  current
      DESCRIPTION
      "Current Clock Holdover State. 
       As a last resort, in the absence of higher quality timing: 
       - a SONET/SDH object can enter 'holdover' state, until higher quality 
         external timing becomes available again. In this state (value=yes) 
         the SONET/SDH object uses its own timing circuits for clock of the 
         SONET/SDH signal.
       - for other objects, the 'holdover'=yes state means that the object uses
         last available clock (stored by the object) for a pre-defined time,
         until another clock source is used."
      ::= { agnCurrClkEntry 5}

agnCurrClkSsmBased    OBJECT-TYPE
      SYNTAX  INTEGER
       {
       notApplicable (1),
       no            (2),
       yes           (3)
       }
      MAX-ACCESS  read-only
      STATUS  current
      DESCRIPTION
      "This parameter indicates whether clock source 
       is selected based on receive clock quality. 
       Clock quality is indicated in S1 byte inside SONET/SDH overhead, 
       (encoded as SSM - Synchronization Status Messaging)."
      ::= { agnCurrClkEntry 6}

agnCurrClkState OBJECT-TYPE
      SYNTAX  INTEGER 
      {
		freeRun					(1),
		rapidPhaseLock			(2),
		finePhaseLock			(3),
		holdover				(4),
		frequencyAcquisition    (5)
      }
      MAX-ACCESS  read-only
      STATUS  current
      DESCRIPTION
      "This object indicates the Current Clock State.
       
       freeRun(1) -
       Current clock state machine is not locked
       and run from the internal oscillator.
       
       rapidPhaseLock(2) -
       Current clock state machine is locked.
       
       finePhaseLock(3) -
       Current clock state machine is in pre-locking.
       
       holdover(4) -
       Current clock state machine is in holdover mode
       (due to loss of event).
 
       frequencyAcquisition(5) -
       Adaptive clock recovery is learning the frequency."
      ::= { agnCurrClkEntry 7 }

agnCurrClkQualification OBJECT-TYPE
      SYNTAX  INTEGER 
      {
		notApplicable	(1),
		disqualified	(2),
		qualified		(3)
      }
      MAX-ACCESS  read-only
      STATUS  current
      DESCRIPTION
      "This object indicates the Current Clock Qualification
       and defines whether the PLL can locked according to the stratum definitions."
      ::= { agnCurrClkEntry 8 }


agnClockMonitoring	OBJECT IDENTIFIER ::= { agnClockSource 3 } 

agnClkCurrentTable OBJECT-TYPE
    SYNTAX		SEQUENCE OF AgnClkCurrentEntry
    MAX-ACCESS	not-accessible
    STATUS		current
    DESCRIPTION
		"The Clock Current table."
    ::= { agnClockMonitoring 1 }

agnClkCurrentEntry OBJECT-TYPE
    SYNTAX		AgnClkCurrentEntry
    MAX-ACCESS  not-accessible
    STATUS		current
    DESCRIPTION
		"An entry in the Clock Current table."
    INDEX		{ agnClkCurrentIndex }
    ::= { agnClkCurrentTable 1 }

AgnClkCurrentEntry ::=
    SEQUENCE {
		agnClkCurrentIndex						Unsigned32,
		agnClkCurrentRxPackets					Gauge32,
		agnClkCurrentLostPackets				Gauge32,
		agnClkCurrentOutOfOrderPackets			Gauge32,
		agnClkCurrentBufferUnderflow			Gauge32
		}

agnClkCurrentIndex OBJECT-TYPE
    SYNTAX		Unsigned32
    MAX-ACCESS	not-accessible
    STATUS		current
    DESCRIPTION
		"An Index that is uniquely represents the Clock."
    ::= { agnClkCurrentEntry 1 }

agnClkCurrentRxPackets OBJECT-TYPE
    SYNTAX      Gauge32
    MAX-ACCESS  read-only
    STATUS      current
    DESCRIPTION
    	"The counter associated with the number of Received Packets, 
         encountered by a Bridge Port in the current 15 minute interval."
    ::= { agnClkCurrentEntry 2 }

agnClkCurrentLostPackets OBJECT-TYPE
    SYNTAX      Gauge32
    MAX-ACCESS  read-only
    STATUS      current
    DESCRIPTION
    	"The counter associated with the number of Lost Packets, 
         encountered by a Bridge Port in the current 15 minute interval."
    ::= { agnClkCurrentEntry 3 }

agnClkCurrentOutOfOrderPackets OBJECT-TYPE
    SYNTAX      Gauge32
    MAX-ACCESS  read-only
    STATUS      current
    DESCRIPTION
    	"The counter associated with the number of times Out-of-Order Packets
         encountered by a Bridge Port in the current 15 minute interval."
    ::= { agnClkCurrentEntry 4 }

agnClkCurrentBufferUnderflow OBJECT-TYPE
    SYNTAX      Gauge32
    MAX-ACCESS  read-only
    STATUS      current
    DESCRIPTION
    	"The counter associated with the number of times Underflow event 
         encountered by a Bridge Port in the current 15 minute interval."
    ::= { agnClkCurrentEntry 5 }


agnClkIntervalTable OBJECT-TYPE
    SYNTAX		SEQUENCE OF AgnClkIntervalEntry
    MAX-ACCESS	not-accessible
    STATUS		current
    DESCRIPTION
		"The Clock Interval table."
    ::= { agnClockMonitoring 2 }

agnClkIntervalEntry OBJECT-TYPE
    SYNTAX		AgnClkIntervalEntry
    MAX-ACCESS  not-accessible
    STATUS		current
    DESCRIPTION
		"An entry in the Clock Interval table."
    INDEX		{ agnClkIntervalIndex, agnClkIntervalNumber }
    ::= { agnClkIntervalTable 1 }

AgnClkIntervalEntry ::=
    SEQUENCE {
		agnClkIntervalIndex						Unsigned32,
		agnClkIntervalNumber					Unsigned32,
		agnClkIntervalRxPackets					Gauge32,
		agnClkIntervalLostPackets				Gauge32,
		agnClkIntervalOutOfOrderPackets			Gauge32,
		agnClkIntervalBufferUnderflow			Gauge32
		}

agnClkIntervalIndex OBJECT-TYPE
    SYNTAX		Unsigned32
    MAX-ACCESS	not-accessible
    STATUS		current
    DESCRIPTION
		"An Index that is uniquely represents the Clock."
    ::= { agnClkIntervalEntry 1 }

agnClkIntervalNumber OBJECT-TYPE
    SYNTAX		Unsigned32
    MAX-ACCESS  not-accessible
    STATUS		current
    DESCRIPTION
    "A number between 1 and 96,
     where 1 is the most recently completed 15 minute interval
     and 96 is the least recently completed 15 minutes interval
     (assuming that all 96 intervals exist)."
    ::= { agnClkIntervalEntry 2 }

agnClkIntervalRxPackets OBJECT-TYPE
    SYNTAX      Gauge32
    MAX-ACCESS  read-only
    STATUS      current
    DESCRIPTION
    	"The counter associated with the number of Received Packets, 
    	 encountered by a Bridge Port in one of the previous 96,
    	 individual 15 minute, intervals."
    ::= { agnClkIntervalEntry 3 }

agnClkIntervalLostPackets OBJECT-TYPE
    SYNTAX      Gauge32
    MAX-ACCESS  read-only
    STATUS      current
    DESCRIPTION
    	"The counter associated with the number of Lost Packets, 
    	 encountered by a Bridge Port in one of the previous 96,
    	 individual 15 minute, intervals."
    ::= { agnClkIntervalEntry 4 }

agnClkIntervalOutOfOrderPackets OBJECT-TYPE
    SYNTAX      Gauge32
    MAX-ACCESS  read-only
    STATUS      current
    DESCRIPTION
    	"The counter associated with the number of times Out-of-Order Packets
    	 are detected, encountered by a Bridge Port in one of the previous 96,
    	 individual 15 minute, intervals."
    ::= { agnClkIntervalEntry 5 }

agnClkIntervalBufferUnderflow OBJECT-TYPE
    SYNTAX      Gauge32
    MAX-ACCESS  read-only
    STATUS      current
    DESCRIPTION
    	"The counter associated with the number of times Underflow event 
    	 is detected, encountered by a Bridge Port in one of the previous 96,
    	 individual 15 minute, intervals."
    ::= { agnClkIntervalEntry 6 }


agnMaxNoOfConns OBJECT-TYPE
	SYNTAX  Integer32 
	MAX-ACCESS  read-only
	STATUS  current
	DESCRIPTION
	"This variable indicates the maximum number of connections
	 that can be configured for the agent."
	::= { agnt 53 }
 

lag	 OBJECT IDENTIFIER  ::=  { agnt 54  }

lagTable OBJECT-TYPE
    SYNTAX  SEQUENCE OF LagEntry
    MAX-ACCESS  not-accessible
    STATUS  current
    DESCRIPTION
    "A table defining Link Aggregation Groups port association, 
     and other parameters."
::= {lag 1}

lagEntry OBJECT-TYPE
    SYNTAX  LagEntry
    MAX-ACCESS  not-accessible
    STATUS  current
    DESCRIPTION
    "An entry in the LAG table."
     INDEX  { lagCnfgIdx, lagIdx }
    ::= { lagTable 1 }

LagEntry ::=
    SEQUENCE {
     lagCnfgIdx             Unsigned32, 
	 lagIdx                 Unsigned32, 
	 lagPortMembers         PortList,
	 lagDistributionMethod  INTEGER,
	 lagRecoveryMode	    INTEGER,
	 lagWaitToRestore	    Unsigned32, 
	 lagRowStatus           RowStatus,
	 lagShutDownDurationUponFlip Unsigned32,
	 lagRdnMethod	        INTEGER,
	 lagLacpEnable          INTEGER
	}

lagCnfgIdx OBJECT-TYPE
    SYNTAX      Unsigned32	  (1..255)
    MAX-ACCESS  not-accessible
    STATUS      current
    DESCRIPTION
     "This object indicates the Idx of the Cnfg(1..255) being 
      accessed ; Idx of 255 relates to the TmpCnfg."
    ::= { lagEntry 1}

lagIdx  OBJECT-TYPE
    SYNTAX       Unsigned32 
    MAX-ACCESS   not-accessible
    STATUS       current
    DESCRIPTION
    "This object indicates LAG unique index."
    ::= { lagEntry 2}

lagPortMembers  OBJECT-TYPE
    SYNTAX      PortList
	MAX-ACCESS  read-create
    STATUS      current
    DESCRIPTION
   "The set of ports which are permanently assigned to the
    Link Aggregation Group.  
    The default value of this object is a string of zeros."
    ::= { lagEntry 3}
			
lagDistributionMethod OBJECT-TYPE
    SYNTAX    INTEGER
	{
     portBased                    (2),
     oneToOne                     (3),
     sourceMac                    (4),
     destinationMac               (5),
     sourceXorDestinationMac      (6),
     sourceAndDestinationMac      (7),
     sourceIp                     (8),
     destinationIp                (9),
     sourceAndDestinationMacAndIp (10),
	 roundRobin					  (11)
    }
    MAX-ACCESS read-create
    STATUS       current
    DESCRIPTION
    "This object defines the criteria for the 802.3ad (LAG)
     to  split the traffic between ports"
    ::= { lagEntry 4}

lagRecoveryMode OBJECT-TYPE
    SYNTAX    INTEGER
	{
     nonRevertive (2),
     revertive    (3)
    }
	MAX-ACCESS read-create
    STATUS       current
    DESCRIPTION
    "This object defines whether traffic will be returned to
     a port after its recovery. 
     This object is applicable only when 
     lagDistributionMethod= oneToOne (3)."
    ::= { lagEntry 5}

lagWaitToRestore  OBJECT-TYPE
    SYNTAX    Unsigned32 (0..720)
    MAX-ACCESS read-create
    STATUS       current
    DESCRIPTION
    "This object defines traffic recovery time (in seconds) 
     to the port after its recovery.
     This object is applicable only when 
     lagRecoveryMode= revertive (3)."
    ::= { lagEntry 6}

lagRowStatus    OBJECT-TYPE
    SYNTAX      RowStatus
    MAX-ACCESS  read-create				
    STATUS      current
    DESCRIPTION
    "This object enables user to create/delete 
     entries of this table.
     Note: 
     When using LAG standard package, this table is static,
     hence, only the values active(1), notInService(2) are used."
    ::= { lagEntry 7}

lagShutDownDurationUponFlip  OBJECT-TYPE
    SYNTAX    Unsigned32 (0..30)
    MAX-ACCESS read-create
    STATUS       current
    DESCRIPTION
    "This object defines the duration (in seconds) the active 
     port transmission is shut down after LAG Flip occurs.
	 The transmission is shut down and then opened again (after the duration
	 defined by this object), in order to cause the other side to flip 
	 to the new active port.
	 0=no shut-down.
     This object is applicable only when lagDistributionMethod=oneToOne(3)
     and mainly when each of the Links of our device is connected to a different device."
    ::= { lagEntry 8}

	lagRdnMethod    OBJECT-TYPE
    SYNTAX    INTEGER
	{
     loadSharing (1), 
     redundancy  (2) 
     }
    MAX-ACCESS read-create
    STATUS       current
    DESCRIPTION
    "This object defines the redundancy method."
    ::= { lagEntry 9}

lagLacpEnable    OBJECT-TYPE 
    SYNTAX    INTEGER
	{
        no  (2), 
        yes (3) 
     }
    MAX-ACCESS read-create
    STATUS       current
    DESCRIPTION
    "Enabling/Disabling the LACP for a LAG.
     The LACP will be enabled for all ports belonging to this LAG."
    ::= { lagEntry 10} 


lagStatTable OBJECT-TYPE
    SYNTAX  SEQUENCE OF LagStatEntry
    MAX-ACCESS  not-accessible
    STATUS  current
    DESCRIPTION
    "A table defining Link Aggregation Groups Redundancy. This table is applicable only 
     when lagDistributionMethod = oneToOne."
::= {lag 2}

lagStatEntry OBJECT-TYPE
    SYNTAX  LagStatEntry
    MAX-ACCESS  not-accessible
    STATUS  current
    DESCRIPTION
    "An entry in the LAG Status table."
     INDEX  { lagIdx }
    ::= { lagStatTable 1 }

LagStatEntry ::=
    SEQUENCE {
	 lagStatForcePort       Unsigned32,
	 lagStatActivePort     	Unsigned32
	}

lagStatForcePort	OBJECT-TYPE
   SYNTAX       Unsigned32
   MAX-ACCESS   read-write				
   STATUS       current
   DESCRIPTION
   "This object enables user to enforce the active port.
    0 = No Enforcement; Otherwise the ifIndex of the port."
    ::= { lagStatEntry 1}

lagStatActivePort	OBJECT-TYPE
   SYNTAX       Unsigned32
   MAX-ACCESS   read-only			
   STATUS       current
   DESCRIPTION
   "This object indicates the current active port. It is applicable only 
    when lagDistributionMethod = oneToOne. The value is the ifIndex of the port.
    0 = none of the ports is active."
    ::= { lagStatEntry 2}


gfp	 OBJECT IDENTIFIER  ::=  { agnt 55  }

gfpCnfgTable OBJECT-TYPE
    SYNTAX  SEQUENCE OF GfpCnfgEntry
    MAX-ACCESS  not-accessible
    STATUS  current
    DESCRIPTION
    "Configuration table for GFP (General Framing Protocol)."
::= {gfp 1}

gfpCnfgEntry OBJECT-TYPE
    SYNTAX  GfpCnfgEntry
    MAX-ACCESS  not-accessible
    STATUS  current
    DESCRIPTION
    "An entry in the GFP configuration table."
     INDEX  { ifIndex, gfpCnfgIdx }
    ::= { gfpCnfgTable 1 }

GfpCnfgEntry ::=
    SEQUENCE {
     gfpCnfgIdx             Unsigned32, 
 	 gfpPayloadFcs          INTEGER,
	 gfpRxTxScramble        INTEGER,
	 gfpVcatHeader			INTEGER
	}

gfpCnfgIdx  OBJECT-TYPE
    SYNTAX       Unsigned32 
    MAX-ACCESS   not-accessible
    STATUS       current
    DESCRIPTION
    "Index to GFP configuration table."
    ::= { gfpCnfgEntry 1 }

gfpPayloadFcs  OBJECT-TYPE
    SYNTAX     INTEGER
	{
	 disable   (2),
     enable    (3)
    }
	MAX-ACCESS read-write
    STATUS       current
    DESCRIPTION
    "This object defines whether protocol header will
    include FCS."
    ::= { gfpCnfgEntry 2 }


gfpRxTxScramble OBJECT-TYPE
    SYNTAX    INTEGER
	{
	 noScramble     (1),
     rxTxScramble   (2),
     rxOnlyScramble (3),
	 txOnlyScramble	(4)
    }
	MAX-ACCESS read-write
    STATUS       current
    DESCRIPTION
    "This object defines whether transmission will be scrambled."
    ::= { gfpCnfgEntry 3 }

gfpVcatHeader  OBJECT-TYPE
      SYNTAX INTEGER
      {
       notApplicable (1),
       disable       (2),
       enable        (3)
 	  }
      MAX-ACCESS read-write
      STATUS current
      DESCRIPTION
      "VCAT header is LCAS  CONTROL packet as described in the G-7043.
       one control packet is transmitted in a period of 16 Multi frame"   
      ::= { gfpCnfgEntry 4}

--Group Table

agnGroupTable OBJECT-TYPE
    SYNTAX  SEQUENCE OF AgnGroupEntry
    MAX-ACCESS  not-accessible
    STATUS  current
    DESCRIPTION
    "A table that enables associating components to Group/s
     (or removing components of a group).
     The Group Idx can then be used in other tables (e.g alarmForwardingTable)."
    ::= {agnt 56}

agnGroupEntry OBJECT-TYPE
    SYNTAX  AgnGroupEntry
    MAX-ACCESS  not-accessible
    STATUS  current
    DESCRIPTION
    "An entry in the agnGroupTable."
     INDEX  { agnGroupCnfgIdx, agnGroupIdx, agnGroupComponentIdx }
    ::= { agnGroupTable 1 }

AgnGroupEntry ::=
    SEQUENCE {
     agnGroupCnfgIdx        Unsigned32,
     agnGroupIdx            Unsigned32, 
	 agnGroupComponentIdx   Unsigned32, 
	 agnGroupRowStatus       RowStatus
	}

agnGroupCnfgIdx OBJECT-TYPE
    SYNTAX      Unsigned32 (1..255)	  
    MAX-ACCESS  not-accessible
    STATUS      current
    DESCRIPTION
     "This object indicates the Idx of the Cnfg(1..255) being 
      accessed ; Idx of 255 relates to the TmpCnfg."
    ::= { agnGroupEntry 1}

agnGroupIdx OBJECT-TYPE
    SYNTAX      Unsigned32	  
    MAX-ACCESS  not-accessible
    STATUS      current
    DESCRIPTION
     "This object indicates a unique Group Index."
    ::= { agnGroupEntry 2}

agnGroupComponentIdx  OBJECT-TYPE
    SYNTAX       Unsigned32 
    MAX-ACCESS   not-accessible
    STATUS       current
    DESCRIPTION
    "This object indicates a unique Component Index that belongs to the
     Group defined by agnGroupIdx."
    ::= { agnGroupEntry 3}

agnGroupRowStatus    OBJECT-TYPE
    SYNTAX      RowStatus
    MAX-ACCESS  read-create				
    STATUS      current
    DESCRIPTION
    "This object enables user to create/delete entries of this table.
     destroy - If a Group is used in another table, Agent may not allow
               destroying the entry/ies that belong to this Group Index."
    ::= { agnGroupEntry 4}

agnStatNoOfUploadedIntervals OBJECT-TYPE
	SYNTAX		Integer32
	MAX-ACCESS	read-only
	STATUS		current
	DESCRIPTION
	"This parameter indicates the Number of Intervals that were
	 successfully collected and uploaded in the last statistics collection session."        
       ::= { agnt 57 }

agnSyslog	 OBJECT IDENTIFIER  ::=  { agnt 58 }

agnSyslogDeviceUdpPort OBJECT-TYPE
    SYNTAX      Unsigned32
    MAX-ACCESS  read-write
    STATUS      current
    DESCRIPTION
    "The UDP Port of the device, from which Syslog messages are sent.
     Default=514."
    ::= { agnSyslog 1 }

agnSyslogFacility OBJECT-TYPE
    SYNTAX      INTEGER
            {
-- (0)..(15) are reserved for Standard values + (16) is reserved for Local 0.
              local1          (17),
              local2          (18),
              local3          (19),
              local4          (20),
              local5          (21),
              local6          (22),
              local7          (23)
-- (99) is reserved for  'noMap' - indicating that the appropriate facility 
--      will be provided by the application          
            }
    MAX-ACCESS  read-write
    STATUS      current
    DESCRIPTION
    "A user defined SW module, task or function, from which Syslog messages are sent
     to the remote Server."
    ::= { agnSyslog 2 }

agnSyslogSeverityLevel OBJECT-TYPE
    SYNTAX      INTEGER
            {
              critical        (1),  -- action must be taken immediately (in standard: 'alert')
              major           (2),  -- critical conditions (in standard: 'critical')
              minor           (3),  -- error conditions (in standard: 'error')
              warning         (4),  -- warning condition (in standard: 'warning')
              event           (5),  -- normal but significant condition (in standard: 'notice')
              info            (6),  -- informational messages (in standard: 'informational')
              debug           (7)   -- debug-level messages	(in standard: 'debug')
            }
    MAX-ACCESS  read-write
    STATUS      current
    DESCRIPTION
    "Device will send events equal or exceeding this severity level (configured by user)."
    ::= { agnSyslog 3 }

agnNetworkInterfaceType OBJECT-TYPE
	SYNTAX  INTEGER
	{
	 notApplicable (1),
	 t1  (2),
	 t3  (3)
    }
	MAX-ACCESS  read-write
	STATUS current
	DESCRIPTION
	"This MIB object indicates the network interface type to be used
	 by the device.
	 It is used for devices that use only one network port type."
	::= { agnt 59 }

agnTrapDelay OBJECT-TYPE
	SYNTAX  Unsigned32
	MAX-ACCESS  read-write
	STATUS current
	DESCRIPTION
	"This variable enables the user to set a delay (in seconds) before a trap is sent.
	 This delay will be used only for traps that need to be sent during device initialization.
	 It is needed because the device connected to our device starts transmitting traps later.
	 The delay starts from the end of the Boot process. The device will keep the init traps
	 in the correct order, and cancel those which clear former ones in the list.
	 After this init delay, traps will be sent without a delay."
	 	::= { agnt 60 }


trapManagement	OBJECT IDENTIFIER ::= { agnt 61 }

trapMngVars		OBJECT IDENTIFIER ::= { trapManagement 1 }

trapState	OBJECT-TYPE
	SYNTAX  INTEGER
	{
		start	(2),
		end		(3)		
	}
	MAX-ACCESS  accessible-for-notify
    STATUS     current
	DESCRIPTION
		"State of current trap (sent within a trap)."
	::= { trapMngVars 1 }

trapSeqId	OBJECT-TYPE
    SYNTAX     Unsigned32
    MAX-ACCESS accessible-for-notify
    STATUS     current
    DESCRIPTION
	    "Sequence ID of current trap (sent within a trap)."
    ::= { trapMngVars 2 }

alarmSync		OBJECT IDENTIFIER ::= { trapManagement 2 }

alarmSyncEvents	OBJECT IDENTIFIER ::= { alarmSync 0 }

hardSyncTrap  NOTIFICATION-TYPE
	OBJECTS       { trapState }
	STATUS		current
	DESCRIPTION     
		"This trap is sent whenever Hard Synchronization process starts or ends
		 (Hard Synchronization retrieves current status of Agent)."
     ::= { alarmSyncEvents 1 }

alarmSyncTable	OBJECT-TYPE
    SYNTAX      SEQUENCE OF AlarmSyncEntry
    MAX-ACCESS  not-accessible
    STATUS      current
    DESCRIPTION
		"This table includes Alarm Synchronization information
		 for each Logical Group of managers."
    ::= { alarmSync 1 }

alarmSyncEntry	OBJECT-TYPE
    SYNTAX		AlarmSyncEntry
    MAX-ACCESS	not-accessible
    STATUS		current
    DESCRIPTION
		"An entry in the table."
    INDEX		{ alarmSyncGroupId }
    ::= { alarmSyncTable 1 }

AlarmSyncEntry ::= SEQUENCE {
	alarmSyncGroupId				Unsigned32,
	alarmSyncLastSentSeqId			Counter32,
	alarmSyncCmd					INTEGER,
	alarmSyncStartSeqId				Unsigned32,
	alarmSyncEndSeqId				Unsigned32
	}

alarmSyncGroupId	OBJECT-TYPE
	SYNTAX		Unsigned32 
	MAX-ACCESS  not-accessible
	STATUS  	current
	DESCRIPTION
		"A unique Logical Group ID,
		 which represents a group of managers."
	::= { alarmSyncEntry 1 }

alarmSyncLastSentSeqId	OBJECT-TYPE
    SYNTAX		Counter32
    MAX-ACCESS 	read-only
    STATUS		current
    DESCRIPTION
		"Last Sequence ID of trap that is sent
		 to this Logical Group of managers."
    ::= { alarmSyncEntry 2 }

alarmSyncCmd	OBJECT-TYPE
	SYNTAX  INTEGER
	{
		off			(1),
		softSync 	(2),
		hardSync	(3)
	}
	MAX-ACCESS  read-write
    STATUS     current
	DESCRIPTION
		"Initates an Alarm Synchronization request
		 for this Logical Group of managers.

		 softSync(2) - sends Soft Synchronization request,
					   in order to synchronize missing traps from Agent.
		 hardSync(3) - sends Hard Synchronization request,
					   in order to synchronize current alarms of Agent.

		 After an Alarm Synchronization process is completed,
		 Agent will automatically change this value to off(2).
		 "
	::= { alarmSyncEntry 3 }

alarmSyncStartSeqId	OBJECT-TYPE
    SYNTAX     Unsigned32
    MAX-ACCESS read-write
    STATUS     current
    DESCRIPTION
	     "First Sequence ID of Soft Synchronization request
	      for this Logical Group of managers.
	      
	      Soft Synchronization request is sent for a range of Sequence IDs.
	      This object represents the first Sequence ID of this range."
    ::= { alarmSyncEntry 4 }

alarmSyncEndSeqId	OBJECT-TYPE
    SYNTAX     Unsigned32
    MAX-ACCESS read-write
    STATUS     current
    DESCRIPTION
	     "Last Sequence ID of Soft Synchronization request
	      for this Logical Group of managers.
	      
	      Soft Synchronization request is sent for a range of Sequence IDs.
	      This object represents the last Sequence ID of this range."
    ::= { alarmSyncEntry 5 }

agnStringToIndexTable OBJECT-TYPE
	SYNTAX  SEQUENCE OF AgnStringToIndexEntry
	MAX-ACCESS  not-accessible
	STATUS  current
	DESCRIPTION
	"This table holds the conversions of tables from unique String 
	 to numeric index."
	::= {agnt 62}

agnStringToIndexEntry OBJECT-TYPE
	SYNTAX  AgnStringToIndexEntry
	MAX-ACCESS  not-accessible
	STATUS  current
	DESCRIPTION
	"An entry in the table."
	INDEX   { agnStringToIndexTableId,IMPLIED agnStringToIndexUserName } 
	::= { agnStringToIndexTable 1 }

AgnStringToIndexEntry ::= SEQUENCE {
	agnStringToIndexTableId	    	  OBJECT IDENTIFIER,
	agnStringToIndexUserName          SnmpAdminString,
	agnStringToIndexTableIndex  	  Unsigned32
			}

agnStringToIndexTableId OBJECT-TYPE
	SYNTAX  OBJECT IDENTIFIER 
	MAX-ACCESS  not-accessible
	STATUS  current
	DESCRIPTION
	"The OBJECT IDENTIFIER of the Table, having as index numeric values. 
	 In this table, the value of agnStringToIndexUserName is an attribute."
	::= { agnStringToIndexEntry 1 }

agnStringToIndexUserName OBJECT-TYPE
	SYNTAX  SnmpAdminString(SIZE (1..64))  
	MAX-ACCESS  not-accessible
	STATUS  current
	DESCRIPTION
	"This object indicates a unique name used by agnStringToIndexTableId,
	 although it is not it's index."
	::= { agnStringToIndexEntry 2 }

agnStringToIndexTableIndex OBJECT-TYPE
	SYNTAX  Unsigned32
	MAX-ACCESS  read-only
	STATUS  current
	DESCRIPTION
	"The numeric Index of agnStringToIndexTableId."
	::= { agnStringToIndexEntry 3 }

agnRowPointerTable OBJECT-TYPE
	SYNTAX  SEQUENCE OF AgnRowPointerEntry
	MAX-ACCESS  not-accessible
	STATUS  current
	DESCRIPTION
	"This table holds information about a specific entry in a table.
	 For example, number of usages of this row."
	::= { agnt 63 }

agnRowPointerEntry OBJECT-TYPE
	SYNTAX  AgnRowPointerEntry
	MAX-ACCESS  not-accessible
	STATUS  current
	DESCRIPTION
	"An entry in the table."
	INDEX   {agnRowPointerIndex } 
	::= { agnRowPointerTable 1 }

AgnRowPointerEntry ::= SEQUENCE 
    {
	agnRowPointerIndex	           OBJECT IDENTIFIER,
	agnRowPointerNoOfUsages        Unsigned32
	}

agnRowPointerIndex   OBJECT-TYPE
	SYNTAX  OBJECT IDENTIFIER
	MAX-ACCESS  not-accessible
	STATUS  current
	DESCRIPTION
	"The OBJECT IDENTIFIER of an entry in a table."
	::= { agnRowPointerEntry 1 }

agnRowPointerNoOfUsages  OBJECT-TYPE
	SYNTAX  Unsigned32 
	MAX-ACCESS  read-only
	STATUS  current
	DESCRIPTION
	"The number of usages of specific entry in a table, which is
	 pointed by agnRowPointerIndex.Usually, when the value of this counter is greater
	 than 0,the entry cannot be removed."
	::= { agnRowPointerEntry 2 }


agnConfigVersion OBJECT-TYPE
	SYNTAX		SnmpAdminString
	MAX-ACCESS  read-only
	STATUS		current
	DESCRIPTION
		"ASCII string of the Configuration Version."
	::= { agnt 64 }


--services OBJECT IDENTIFIER ::= { radGen 3}  See services.txt

radTransport OBJECT IDENTIFIER ::= { radGen 4}
--RAD transport tree
radTransportDomains  OBJECT IDENTIFIER ::= { radTransport 1}

radTransportDomainSnmpEfmOam OBJECT-IDENTITY
   STATUS  current
   DESCRIPTION
   "The SNMP over EFM OAM transport domain.  The corresponding
    transport address is of type RadTransportAddressEfmOam for
    EFM OAM addresses (port)."
   ::= { radTransportDomains 1 }

RadTransportAddressType ::= TEXTUAL-CONVENTION
    STATUS      current
    DESCRIPTION
    "A value that represents a transport domain. This is the
     enumerated version of the transport domain registrations
     in this MIB module. It was added in RAD MIB due to the fact 
     that it is not defined in Standard MIB.
     The enumerated values have the	following meaning:

     unknown(0)     unknown transport address type
     efmOam (1)     radTransportDomainSnmpEfmOam

     This textual convention can be used to represent transport
     domains in situations where a syntax of TransportDomain is
     unwieldy (for example, when used as an index).

     The usage of this textual convention implies that additional
     transport domains can only be supported by updating this MIB
     module."
    SYNTAX  INTEGER {
            unknown(0),
            efmOam (1)
            }

RadTransportAddressEfmOam ::= TEXTUAL-CONVENTION
    STATUS      current
    DESCRIPTION
        "Represents a transport address consisting of an EFM OAM port number."
    SYNTAX      OCTET STRING (SIZE (4))


-- SYSTEM TRAPS

--NOTIFICATIONS

systemsEvents OBJECT-IDENTITY
     STATUS  current
     DESCRIPTION
     "The events for RAD products."
     ::= { systems 0 }

tftpStatusChangeTrap  NOTIFICATION-TYPE
     OBJECTS       { tftpStatus }
     STATUS current
     DESCRIPTION     
     "This trap is sent whenever the status of tftp changed."
     ::= { systemsEvents 1 }

agnStatusChangeTrap  NOTIFICATION-TYPE
	OBJECTS		{agnIndication }
    STATUS current
	DESCRIPTION
	"This trap is sent whenever the state of the entity the agent is
	 responsible for changed.
	 TDM devices will send agnTestStatus variable to indicate the current test status."
	::= { systemsEvents 2 }

prtStatusChangeTrap  NOTIFICATION-TYPE
    STATUS current
	DESCRIPTION
	"This trap is sent whenever the state of a port changed.
	 Attached, will be parameter/s that indicate the new port status.
	 The attached variables will be specified in the specifications
	 of the products supporting this trap."
	::= { systemsEvents 3 }

swdlStatusResult	    NOTIFICATION-TYPE
	OBJECTS			{swdlStatusFileName}
    STATUS  current
	DESCRIPTION
	"This notification is sent when Software Down Load is finished.
	 The attached object indicates the File Name."
	::= { systemsEvents 4 }

intSwdlSlotFileMismatch	    NOTIFICATION-TYPE
	OBJECTS			{intSwdlFileName}
    STATUS  current
	DESCRIPTION
	"This notification is sent when the card in the chosen slot doesn't match 
	 the chosen file.
	 The attached object indicates the File Name."
	::= { systemsEvents 5 }

agnCounterChange  NOTIFICATION-TYPE
    STATUS  current
	DESCRIPTION
	"This notification is sent when the value of a specific Counter is changed.
	 Agent can send as attached object the updated Counter.
	 For details about this Counter and attached object, see spec of the relevant
	 application."
	::= { systemsEvents 6 }

prtClkSrcChangeTrap NOTIFICATION-TYPE
      STATUS  current
      DESCRIPTION
	  "This trap is sent upon any port clock change."
    ::= { systemsEvents 7 }

moduleFailTrap NOTIFICATION-TYPE
      STATUS  current
      DESCRIPTION
	  "This trap is sent upon a module failure."
    ::= { systemsEvents 8 }
	
moduleInitFailTrap NOTIFICATION-TYPE
    STATUS current
      DESCRIPTION
	  "This trap is sent upon a module initialization failure."
	::= { systemsEvents 9 }

clkSrcChangeTrap NOTIFICATION-TYPE
      STATUS  current
      DESCRIPTION
	  "This trap is sent upon any change in Clock Source."
    ::= { systemsEvents 10 }

agnUploadDataTrap  NOTIFICATION-TYPE
     STATUS current
     DESCRIPTION     
     "This trap is sent upon an upload data session termination.
     For more details see product specification."
     ::= { systemsEvents 11 }

enrollmentTrap  NOTIFICATION-TYPE
     STATUS current
     DESCRIPTION     
     "This trap is a periodically trap, which sent to manager 
     untill Agent get any response (Get or Set) from this manager."
     ::= { systemsEvents 12 }

agnPowerFailureTrap  NOTIFICATION-TYPE
     STATUS current
     DESCRIPTION     
     "This trap is sent upon power failure. It is applicable for 
     the following devices:
     1. Devices having one PS unit, which sense the failure in advance,
        and still have time to send this trap before it goes off.
     2. Devices having 2 PS units and send this trap in order to notify a
        failure in one of the units."
     ::= { systemsEvents 13 }

agnFanFailureTrap  NOTIFICATION-TYPE
     STATUS current
     DESCRIPTION     
     "This trap is sent upon fan failure/recovery."
 	 ::= { systemsEvents 14 }

agnSystemParameterChangeTrap   NOTIFICATION-TYPE
	OBJECTS			{systemParameter}
    STATUS  current
	DESCRIPTION
	"This trap is sent upon any change of the systemParameter value."
	 ::= { systemsEvents 15 }

 
-- CONFIG DATABASE CHECKSUM ERROR  
agnConfigDBChecksumError  NOTIFICATION-TYPE
      OBJECTS			{alarmSeverity}
      STATUS  current
      DESCRIPTION
      "This trap indicates that the database currently
      stored in the non-volatile memory of the device is corrupted"	
      ::= { systemsEvents 16 }

-- ALARM BUFFER OVERFLOW
agnAlarmBufferOverflow  NOTIFICATION-TYPE		
      OBJECTS {alarmSeverity}
      STATUS  current
      DESCRIPTION
      "This trap indicates that the quantity of 
      alarm messages which have been written 
      in the alarm buffer, since the last clear command,
      exceeds predefined threshold. (Buffer size) 
      The new alarms are overwriting the oldest alarms 
      (the first alarms written in the buffer).
      For LA-110,threshold value is 200 alarms."
      ::= { systemsEvents 17 }

-- ALARM BUFFER CLEAR	
agnAlarmBufferClear NOTIFICATION-TYPE		
      OBJECTS {alarmSeverity}
      STATUS  current
      DESCRIPTION
      "This trap indicates that 
       alarm buffer has been cleared."	
      ::= { systemsEvents 18 }


-- PARAMETER CHANGES IN DB DUE TO UPGRADE PROCESS	
agnParametersValueChanged NOTIFICATION-TYPE		
      OBJECTS {alarmSeverity}
      STATUS  current
      DESCRIPTION
      "This trap indicates that due to software upgrade, 
       some of the parameters are assigned new values"	
      ::= { systemsEvents 19 }

-- (SHDSL) INTERFACE SW VERSION INCOMPATIBLE WITH HW	
agnDriverSwMismatch NOTIFICATION-TYPE		
      OBJECTS {alarmSeverity,ifAlias}
      STATUS  current
      DESCRIPTION
      "There is mismatch between the SW driver and 
       the HW of the device uplink interface."	
      ::= { systemsEvents 20 }

-- DEVICE SYNCHRONIZED ON LESS THAN CONFIGURED BANDWIDTH
agnActualLowRate NOTIFICATION-TYPE		
      OBJECTS {alarmSeverity}
      STATUS  current
      DESCRIPTION
      "The main link is synchronized 
       at a rate lower than expected."	
      ::= { systemsEvents 21 }

xModemFileTransferStatusTrap  NOTIFICATION-TYPE
     OBJECTS       { trapVal }
     STATUS current
     DESCRIPTION     
     "This trap is sent in the following cases:
      - When an xModem File Transfer Session begins. In this case,
        the trapVal.1 string sent will be: 'Start'.
      - When an xModem File Transfer Session ends. In this case,
        the trapVal.1 string sent will be one of the following,
        according to the way the session ended :
        - 'End: OK'
        - 'End: Failed'   "
     ::= { systemsEvents 22 }

agnStationClkFailureTrap  NOTIFICATION-TYPE
     STATUS current
     DESCRIPTION     
     "This trap is sent upon Station Clock failure."
     ::= { systemsEvents 23 }

successfulLogin  NOTIFICATION-TYPE
     STATUS current
     DESCRIPTION     
     "This trap is sent when a user performed successful Login via 
      Terminal/Telnet/Web. This trap is used when the device is located
      at End-User's premises while management is at Service Provider's 
      premises."
     ::= { systemsEvents 24 }

failedLogin  NOTIFICATION-TYPE
     STATUS current
     DESCRIPTION     
     "This trap is sent when a user tried to Login via Terminal/Telnet/Web
      and failed. This trap is used when the device is located
      at End-User's premises while management is at Service Provider's 
      premises."
     ::= { systemsEvents 25 }

modlChangeTrap  NOTIFICATION-TYPE
     STATUS current
     DESCRIPTION     
     "This trap is sent whenever a module is inserted or removed.
      The trap should include the new module type (e.g. modlParamType)."
     ::= { systemsEvents 26 }

licenseUpdateTrap  NOTIFICATION-TYPE
     STATUS current
     DESCRIPTION     
     "This trap is sent whenever a license is successfully downloaded
      or whenever a license's demo duration is expired."
     ::= { systemsEvents 27 }

agnClkSrcStateChangeTrap  NOTIFICATION-TYPE
     OBJECTS       { agnClkSrcPortState }
     STATUS	current
     DESCRIPTION     
	 "The trap is sent upon change in Recovery Clock State."
     ::= { systemsEvents 28 }

agnSelfTestResultChangeTrap NOTIFICATION-TYPE
	 STATUS  current
 	 DESCRIPTION
	 "The trap is sent upon each change in the result of a Self State operation."
	 ::= { systemsEvents 29 }

agnCurrClkStateChangeTrap NOTIFICATION-TYPE
     OBJECTS       { agnCurrClkState }
     STATUS	current
     DESCRIPTION     
	 "The trap is sent upon change in the state of the current (active) clock,
	  when it is a Recovery Clock." 
     ::= { systemsEvents 30 }

agnClkSrcFrequencyAlarmTrap  NOTIFICATION-TYPE
     STATUS	current
     DESCRIPTION     
	 "The trap is sent upon Recovered Clock Frequency alarm."
     ::= { systemsEvents 31 }

prtLoopDetectTrap NOTIFICATION-TYPE
	STATUS current
	DESCRIPTION
	"This trap is sent upon Loop Detect (On/Off) on a certain port."
	::= { systemsEvents 32 }

-- { systemsEvents 164 } is reserved for an internal trap.

-- 
-- file :D:\Synergy\WorkArea\545\mib_rad\txt\trgen.txt
-- 
--Version:  4.0
--Date:   16.10.94		
--By:        Orly Nicklass
--File:       TRGEN.TXT
--Last update: 05.12.95

trGen  OBJECT IDENTIFIER ::= {radTokenRing 1}

--

agnRR OBJECT IDENTIFIER ::= {trGen 1} --agent RAD ring general information

ringTR OBJECT IDENTIFIER ::= { trGen 2 } --ring general information

segTR OBJECT IDENTIFIER ::= { trGen 3} --  segment  general information

moduleTR OBJECT IDENTIFIER ::= {trGen 4}  --  Module general information

prtTR OBJECT IDENTIFIER ::= {trGen  5 } --port general information

--
-- RADRing agent  specific information
--

agnRRcoprocHwVersion OBJECT-TYPE
      SYNTAX  DisplayString
      MAX-ACCESS  read-write
      STATUS  current
      DESCRIPTION
      "ASCII string for description and display of the CML\IB hardware
       version. If the entry is not applicable, it will display the string -NOT APPLICABLE-"
      ::= { agnRR 1 }

agnRRrecMode OBJECT-TYPE
           SYNTAX  INTEGER {
         	unknown(1),
                slow(2),
                fast(3),
                notSupported(4)
                   }
           MAX-ACCESS  read-write
           STATUS  current
           DESCRIPTION
           "The manager station can assist the agent in the autorecovery
            process by setting this value to  SLOW(1). This value indicates
            the presence of old modules within the radring hub. Autorecovery 
            process will be faster for new modules. However it might fail
            if set to FAST(2) and old modules are inserted."
           ::= { agnRR 2 }

agnRRmaskIBMalrt OBJECT-TYPE
           SYNTAX  INTEGER {
                unknown(1),
                disabled(2),
                enabled(3)
                   }
           MAX-ACCESS  read-write
           STATUS  current
           DESCRIPTION
          "When this object is set to the value of Enabled(3),
           Agent-traps that are not masked will also be sent to the IBM LAN manager 
           using IBM's Alert Transport Service Protocol.
           This object is applicable only for TR agents."
      ::= { agnRR 3}

agnRRResetConfig OBJECT-TYPE
           SYNTAX  INTEGER {
                off(2),
                on(3),
                notSupported(4)
                   }
           MAX-ACCESS  read-write
           STATUS  current
           DESCRIPTION
          "Setting the value to ON(3)is interpreted as a reset command
           for the agent NV Ram. When reset process is ended, a trap
           will be issued. If the entry is not applicable, The value notSupported will be read."
           ::= { agnRR 4 }

agnRRSwReset OBJECT-TYPE
           SYNTAX  INTEGER {
                off(2),
                on(3)
                   }
           MAX-ACCESS  read-write
           STATUS  deprecated
           DESCRIPTION
          "Setting the value to ON(3)is interpreted as a  software reset command
           for the agent. When reset process is ended, a trap  will be issued. "
           ::= { agnRR 5 }

agnRRRingReportMngr OBJECT-TYPE
           SYNTAX  INTEGER {
                off(2),
                on(3)
                   }
           MAX-ACCESS  read-write
           STATUS  deprecated
           DESCRIPTION
          "Setting the value to ON(3) is interpreted as assigning the duty of  Ring Report 
	Manager on  the agent "
           ::= { agnRR 6 }

agnRRSubSysCommState  OBJECT-TYPE
           SYNTAX  INTEGER {
                failed(2),
                ok(3),
                 notSupported(4)
                   }
           MAX-ACCESS  read-only
           STATUS  current
           DESCRIPTION
          "This attribute indicates the status of communication between the two agent's
	processors.  The communication is failed when the CML/NM card is removed"
           ::= { agnRR  7 }

--
-- Ring information for the ring the agent is connected to. It is traffic information and
-- isolated error information.
--	       

ringResetStatistics OBJECT-TYPE   
      SYNTAX  INTEGER {  
           unknown(1),
           off(2), 
           on(3)
      }
      MAX-ACCESS  read-write    
      STATUS  current
      DESCRIPTION
      "Setting the value of this attribute to ON(3) resets all the inband
      statistics and error counters." 
           ::= { ringTR 1 }

ringCurrentTraffic OBJECT-TYPE 
      SYNTAX  Integer32	  
      MAX-ACCESS  read-only
      STATUS  current
      DESCRIPTION
      "Momentary traffic for the last time interval. The traffic is expressed in
      percents of the maximum Tokenring traffic ."
      ::= { ringTR 2 }

ringPeakTraffic OBJECT-TYPE 
      SYNTAX  Integer32   
      MAX-ACCESS  read-only
      STATUS  current
      DESCRIPTION
      "Maximal traffic value since last reset of Agent or statistics.
      Expressed in percents of the maximum Tokenring traffic."
      ::= { ringTR 3 }

ringTrafficTreshold OBJECT-TYPE 
      SYNTAX  Integer32		    
      MAX-ACCESS  read-write
      STATUS  current
      DESCRIPTION
      "Traffic threshold value. When reached, a trap will be sent to the management
      console. Expressed in percents of the maximum Tokenring traffic"
      ::= { ringTR 4 }

ringLineErrCnt OBJECT-TYPE
      SYNTAX  Counter32
      MAX-ACCESS  read-only
      STATUS  current
      DESCRIPTION
       "This counter is incremented when a frame
       or token is copied or repeated by any of the
       stations on the ring, the E bit is zero in the frame
       or token and one of the following
       conditions exists: 1) there is a
       non-data bit (J or K bit) between the SD
       and the ED of the frame or token, or
       2) there is an FCS error in the frame."
      ::= { ringTR 5 }

ringLineErr OBJECT-TYPE
      SYNTAX  Integer32
      MAX-ACCESS  read-only
      STATUS  current
      DESCRIPTION
       "This counter is incremented when a frame
       or token is copied or repeated by any of the
       stations on the ring, the E bit is zero in the frame
       or token and one of the following
       conditions exists: 1) there is a
       non-data bit (J or K bit) between the SD
       and the ED of the frame or token, or
       2) there is an FCS error in the frame."
      ::= { ringTR 6 }

ringBurstErrCnt OBJECT-TYPE
      SYNTAX  Counter32
      MAX-ACCESS  read-only
      STATUS  current
      DESCRIPTION
      "This counter is incremented when any of the stations
       on the ring detects the absence of transitions for five
       half-bit timers (burst-five error)."
      ::= { ringTR 7 }

ringBurstErr OBJECT-TYPE
      SYNTAX  Integer32
      MAX-ACCESS  read-only
      STATUS  current
      DESCRIPTION
      "This counter is incremented when any of the stations
       on the ring detects the absence of transitions for five
       half-bit timers (burst-five error)."
      ::= { ringTR 8 }

ringACFCErrCnt  OBJECT-TYPE
      SYNTAX  Counter32
      MAX-ACCESS  read-only
      STATUS  current
      DESCRIPTION
     "This counter is incremented when any of the stations
     on the ring receives an AMP or SMP frame in which A is
     equal to C is equal to 0, and then receives
     another SMP frame with A is equal to C is
     equal to 0 without first receiving an AMP
     frame. It denotes a station that cannot set
     the AC bits properly."
      ::= { ringTR 9 }


ringACFCErr OBJECT-TYPE
      SYNTAX  Integer32
      MAX-ACCESS  read-only
      STATUS  current
      DESCRIPTION
     "This counter is incremented when any of the stations
     on the ring receives an AMP or SMP frame in which A is
     equal to C is equal to 0, and then receives
     another SMP frame with A is equal to C is
     equal to 0 without first receiving an AMP
     frame. It denotes a station that cannot set
     the AC bits properly."
      ::= { ringTR 10 }


ringTotErrCnt OBJECT-TYPE
      SYNTAX  Counter32
      MAX-ACCESS  read-only
      STATUS  current
      DESCRIPTION
      "The total of the above described errors"
      ::= { ringTR 11 }

ringTotErr OBJECT-TYPE
      SYNTAX  Integer32
      MAX-ACCESS  read-only
      STATUS  current
      DESCRIPTION
      "The total of the above described errors"
      ::= { ringTR 12 }

ringTotErrThreshold OBJECT-TYPE
 SYNTAX  Integer32
      MAX-ACCESS  read-write
      STATUS  current
      DESCRIPTION
      "The threshold value of the total of the above described errors.When the threshold is reached 
        a trap indicating the status of the ring (SOFT ERROR)will be sent to the management station"
      ::= { ringTR 13}

ringStatus OBJECT-TYPE 
      SYNTAX  INTEGER {
        unknown(1),
        normal(2),
        softError(3),
        beacon(4)
	 }   
      MAX-ACCESS  read-only
      STATUS  current
      DESCRIPTION
      "Describes the status of the LAN segment the agent is attached to:
      Normal(2) - The LAN segment is operating normally
      SoftError(3) - The Token ring LAN segment (ring) is experiencing 
                      intermittent failures that temporarily harm the 
                      ring's performance and cause data to be transmitted
                      more than ones.
      Beaconing(4) - The ring is not operative; no data is transmitted."
      ::= { ringTR 14 }

ringConfigMsg OBJECT-TYPE   
      SYNTAX  OCTET STRING
      MAX-ACCESS  read-only
      STATUS  current
      DESCRIPTION
      "Full configuration message  coded in internal RAD application format.
      This entry describes ring information. "
      ::= { ringTR 15 }

ringCurrentTrafficCnt OBJECT-TYPE 
      SYNTAX   Counter32
      MAX-ACCESS  read-only
      STATUS  current
      DESCRIPTION
      "Momentary traffic for the last time interval. The traffic is expressed as bits per second."
      ::= { ringTR 16 }

--
-- Segments 
--
segTRTable OBJECT-TYPE
               SYNTAX SEQUENCE OF SegTREntry
               MAX-ACCESS not-accessible
               STATUS current
			   DESCRIPTION
			   "Segments."
               ::= { segTR 1}

segTREntry OBJECT-TYPE
               SYNTAX SegTREntry
               MAX-ACCESS not-accessible
               STATUS current
			   DESCRIPTION
			   "An entry in table segTRTable."
               INDEX { segTRID}
               ::= { segTRTable 1}
   
SegTREntry ::= 
            SEQUENCE {
               segTRID
                  Integer32,
               segTRLastSlot
                  Integer32,
               segTRFirstSlot
                  Integer32,
               segTRStatus
                  INTEGER
                 }

segTRID OBJECT-TYPE
           SYNTAX  Integer32  (1..20) 
           MAX-ACCESS  read-only
           STATUS  current
           DESCRIPTION
           "Segment unique identification number (internal). It is  
	        the extreme left slot, marking the beginning of the 
	        segment."
           ::= {  segTREntry 1 }

segTRLastSlot OBJECT-TYPE  
           SYNTAX  Integer32   
           MAX-ACCESS  read-only
           STATUS  current
           DESCRIPTION
           "Location of the right most slot marking the end of the 
            segment. In the RADring hub it is slot number 20 or the slot 
            where end of segment module is inserted or the slot before
            a beginning of a new segment. ( End of segment 
            module could be one with termination on or TIO, TFR, TCR etc.)"
           ::= {  segTREntry 2 }

segTRFirstSlot OBJECT-TYPE
           SYNTAX  Integer32     
           MAX-ACCESS  read-only
           STATUS  current
           DESCRIPTION
           "Location of the left most slot marking the beginning
           of the segment. In the RADring hub it is slot number 1 or 
           the slot number following the end of segment module, or where
           a repeater or TIO is inserted."
           ::= {  segTREntry 3 }

segTRStatus OBJECT-TYPE 
      SYNTAX  INTEGER {
        unknown(1),
        beaconing(2),
        normal(3)
	 }   
      MAX-ACCESS  read-only
      STATUS  current
      DESCRIPTION
      "Describes the status of the segment :
      Normal(3) - The segment is operating normally
      Beaconing(2) - The ring is not operative; no data is transmitted.
      Segment without inband module within its limit will display Unknown(1).
       This entry is specially usefull when the hub is configured with multiple segments
        and each segment is part of another net"
      ::= { segTREntry 4 }


--
-- Modules parameters structure
-- contains general information about the modules 
--

mdlTRTable  OBJECT-TYPE
      SYNTAX SEQUENCE OF MdlTREntry
      MAX-ACCESS not-accessible
      STATUS current
	  DESCRIPTION
	  "Modules parameters structure
	   contains general information about the modules."
      ::= { moduleTR 1 }

mdlTREntry OBJECT-TYPE
      SYNTAX    MdlTREntry
      MAX-ACCESS    not-accessible
      STATUS    current
	  DESCRIPTION
	  "An entry in table mdlTRTable."
      INDEX     { mdlTRID  }
      ::= { mdlTRTable 1 }
 
MdlTREntry ::=
      SEQUENCE {
          mdlTRID
              Integer32,
          mdlTRSegID
              Integer32,
          mdlTRType 
              INTEGER,
          mdlTRHwVer
              DisplayString,
          mdlTRSwVer 
             DisplayString,
          mdlTRTotalNoOfPrt 
             Integer32,
         mdlTRSpecific
             OBJECT IDENTIFIER
          }

mdlTRID  OBJECT-TYPE
      SYNTAX  Integer32 
      MAX-ACCESS  read-only
      STATUS  current
      DESCRIPTION
      "The slot number where the module is inserted. Can not be greater
       than chNoSlot"  
      ::= { mdlTREntry 1 }        

mdlTRSegID  OBJECT-TYPE
      SYNTAX  Integer32 
      MAX-ACCESS  read-only
      STATUS  current
      DESCRIPTION
      "The segment number where the module belongs to. One of the 
       segTRID values."  
      ::= {mdlTREntry 2 }        

mdlTRType OBJECT-TYPE
      SYNTAX  INTEGER {
            unknown(1),
            empty(2),
            tl4s(3),
            tl4su(4),
            tl4sd(5),
            tl4cx(6), 
            tl4u(7),
            tl2edu(8), 
            tl2eds(9),
            tl2edsu(10),
            tl2f(11),   
            tja(12),      
            tio(13),
            tfr(14),
            tfc1(15),
            tfc2(16),
            tcr(17),
            tl4au(18),
            tl4as(19),
            tl4asd(20),
            tl4asu(21),
            tre1d(22),
            tre(23),
            tre8d(24),
            stc1(25),
            stc2(26),
            ftc(27),
            cmlib(28),
            tl2fsat(29),
            nonTR(30),
            tau(31),	-- for all TAUs type
            rmu(32)	-- for all RMUs type
      }
      MAX-ACCESS  read-only
      STATUS  deprecated
      DESCRIPTION
      "Indicates the type of the module connected at the specified slot number."
      ::= { mdlTREntry 3 }

mdlTRHwVer OBJECT-TYPE
      SYNTAX  DisplayString
      MAX-ACCESS  read-write
      STATUS  current
      DESCRIPTION
      "ASCII string for description and display of the module's hardware version,
      as it is known by the module's software. A manager can record his own 
      hardware upgrade."
      ::= { mdlTREntry 4 }

mdlTRSwVer OBJECT-TYPE
      SYNTAX  DisplayString
      MAX-ACCESS  read-only
      STATUS  current
      DESCRIPTION
      "ASCII string for description and display of the module's 
       software version. A value of NOT APPLICABLE will be recorded
       for module having no independent processor."
      ::= { mdlTREntry  5 }

mdlTRTotalNoOfPrt OBJECT-TYPE
      SYNTAX  Integer32 
      MAX-ACCESS  read-only
      STATUS  current
      DESCRIPTION
      "This entry describes the number of possible ports/lobes/links
        connection in the module (not all ports hardware should be active) ." 
      ::= { mdlTREntry 6 }


mdlTRSpecific OBJECT-TYPE
      SYNTAX  OBJECT IDENTIFIER
      MAX-ACCESS  read-only
      STATUS  current
      DESCRIPTION
      " Object identifier of entity containing additional information 
      regarding this instance. This entry is type specific."
      ::= { mdlTREntry 7 }
--
-- TReral port table for any media type
--

prtTRTable OBJECT-TYPE
      SYNTAX SEQUENCE OF PrtTREntry
      MAX-ACCESS not-accessible
      STATUS current
	  DESCRIPTION
	  "TReral port table for any media type."
      ::= { prtTR 1 }

prtTREntry OBJECT-TYPE
      SYNTAX    PrtTREntry
      MAX-ACCESS    not-accessible
      STATUS    current
	  DESCRIPTION
	  "An entry in table prtTRTable."
      INDEX     {  prtTRModuleID,prtTRID  }
      ::= { prtTRTable 1 }
 
PrtTREntry ::=
      SEQUENCE {
          prtTRModuleID
             Integer32,
          prtTRID
             Integer32,
          prtTRFunctionality
             INTEGER,
          prtTRConnectorType         
             INTEGER,
          prtTRAdminCmd
	 INTEGER,
          prtTRActiveState
             INTEGER,
          prtTRTrapMaskEnable
             INTEGER,
          prtTRstatus
             INTEGER,
          prtTRCableProtectEnable
              INTEGER,
          prtTRCableState
               INTEGER,
          prtTRMACAddress
             MacAddress,
          prtTRSpecific 
              OBJECT IDENTIFIER

          }

prtTRModuleID OBJECT-TYPE  
      SYNTAX  Integer32   
      MAX-ACCESS  read-only
      STATUS  current
      DESCRIPTION
      "A unique identifier of the module(slot no.)this port is attached to."
      ::= { prtTREntry 1 }

prtTRID OBJECT-TYPE  
      SYNTAX  Integer32   
      MAX-ACCESS  read-only
      STATUS  current
      DESCRIPTION
      "A unique identifier of the port within its module."
      ::= { prtTREntry 2 }

prtTRFunctionality OBJECT-TYPE
      SYNTAX  INTEGER {
           unknown(1),		
           ringin(2) ,
           ringout(3) ,
           satellite(4),
           lobe(5),
           link(6),
           tja(7),
           none(8),		-- N.C. repeater
           smart-port(9)              -- for RR-SAT if prtRRMode is set to smart-port
      }
      MAX-ACCESS  read-only
      STATUS  current
      DESCRIPTION
      "Describes the functionality of the port in a Token ring topology or other implementations."
      ::= { prtTREntry 3 }

prtTRConnectorType OBJECT-TYPE
      SYNTAX  INTEGER {
                notApplicable(1),		
	idc(2),      
	rj45(3),
                srj45(4),
                db9(5),      
                bnc(6),
                foSt(7),
	db25(8) 
--           foSma(9),          
--           foFc(10)
      }
      MAX-ACCESS  read-only
      STATUS  current
      DESCRIPTION
      "Type of hardware connector in the port." 
      ::= { prtTREntry 4 }

prtTRAdminCmd OBJECT-TYPE 
      SYNTAX  INTEGER {
          unknown(1),
          disable(2),
          enable(3),
          short(4),
          normal(5)
      }
      MAX-ACCESS  read-write
      STATUS  current
      DESCRIPTION
      "By setting this attribute to DISABLE(2) or SHORT(4) the 
       management station can force this  lobe/port/link-connection  to be 
        removed and block any access to the  network via this lobe/port/link.
       It is not mandatory that a certain lobe/port/link will support all the 
       enumerated states. The state of the lobe/port/link is type specific and
        indicated within the specific group"
 	::= { prtTREntry 5 }

prtTRActiveState OBJECT-TYPE
      SYNTAX  INTEGER {
           unknown(1),
           off(2),
           on(3),
           standby(4)
      }
      MAX-ACCESS  read-only
      STATUS  current
      DESCRIPTION
      "This attribute describes the electrical or optical activity 
       state of  a lobe or the state of a port.  Certain values may
       not be applicable in some cases"
      ::= { prtTREntry 6 }

prtTRTrapMaskEnable OBJECT-TYPE   
      SYNTAX  INTEGER {  
	   off(2),
	   on(3)
      }
      MAX-ACCESS  read-write    
      STATUS  current
      DESCRIPTION
      "When this attribute is set to OFF by the management console the 
       agent starts sending the unmasked traps related to this port. 
       Otherwise no traps from this port are sent."
      ::= { prtTREntry 7 }

prtTRstatus OBJECT-TYPE
      SYNTAX  INTEGER {
          unknown(1),
          disabledManuall(2),
          disabledAutorec(3),
          disabledSecurity(4),
          disableAuto(5),
          disableFlip(6),
          inserted(7),
          bypass(8),
          forcedloop(9),
          trunkfail(10),
          normal(11)
      }
      MAX-ACCESS  read-only
      STATUS  current
      DESCRIPTION
      "This attribute indicates the status of this lobe/port 
       connection:
      DISABLED - (2) to  (6) indicates the reason for the disabled state.
      INSERTED - (7)indicates that the lobe hardware inserts this lobe 
                 into the ring , thus it becomes part of the ring.
      BYPASS   - (8)indicates that the ring bypasses this lobe and the 
                 lobe hardware provides loopback connection towards the 
                 station for media test purposes.
      FORCEDLOOP - (9) indicates the port is in a loopback state and the 
                 main ring is connected to the backup path.
      TRUNKFAIL - (10) indicates that the ring connection is broken for a
                 repeater, converter or a cable protector.
      NORMAL   - (11) indicates the port is in normal condition.
      It is not mandatory that a certain lobe/port will support all the 
      enumerated states."
      ::= { prtTREntry 8 }

prtTRCableProtectEnable OBJECT-TYPE
      SYNTAX  INTEGER {
           unknown(1),
           off(2),    
           on(3),
            inhibit(4)   
      }	
      MAX-ACCESS  read-only
      STATUS  current
      DESCRIPTION
      "The value of this attribute determines activation of the cable-fault
      protection mechanism of  TCR and the optical link mechanism of
      TFR and TFC ."
      ::= { prtTREntry  9 }

prtTRCableState OBJECT-TYPE
      SYNTAX  INTEGER {
           unknown(1),
           failed(2),    
           normal(3),
           remoteFailed(4)    
      }
      MAX-ACCESS  read-only
      STATUS  current
      DESCRIPTION
      "The value of this attribute determines the cable status
       of  TCR and the optical link mechanism of
       TFR and TFC ."
      ::= { prtTREntry  10}


prtTRMACAddress OBJECT-TYPE
           SYNTAX  MacAddress
           MAX-ACCESS  read-only
           STATUS  current
           DESCRIPTION
           "The value of this object is the specific MAC address 
           of this interface which uniquely identifies this Interface 
           on a ring."
           ::= { prtTREntry 11 }

prtTRSpecific OBJECT-TYPE
      SYNTAX  OBJECT IDENTIFIER 
      MAX-ACCESS  read-only
      STATUS  current
      DESCRIPTION
      " Object identifier of entity containing additional information 
      regarding this instance. This entry is type specific."
      ::= { prtTREntry 12}

prtTRMacAddressTable OBJECT-TYPE
      SYNTAX SEQUENCE OF PrtTRMacAddressEntry
      MAX-ACCESS not-accessible
      STATUS current
	  DESCRIPTION
	  "."
      ::= { prtTR 2 }

prtTRMacAddressEntry OBJECT-TYPE
      SYNTAX    PrtTRMacAddressEntry
      MAX-ACCESS    not-accessible
      STATUS    current
	  DESCRIPTION
	  "An entry in table prtTRMacAddressTable."
      INDEX     {  prtTRMacAddressModuleID,prtTRMacAddressPortID, prtTRMacAddressID}
      ::= { prtTRMacAddressTable 1 }
 
PrtTRMacAddressEntry ::=
      SEQUENCE {
          prtTRMacAddressModuleID
             Integer32,
          prtTRMacAddressPortID
             Integer32,
          prtTRMacAddressID
             Integer32,
          prtTRMACAddressValue
             MacAddress
          }

prtTRMacAddressModuleID OBJECT-TYPE  
      SYNTAX  Integer32   
      MAX-ACCESS  read-only
      STATUS  current
      DESCRIPTION
      "A unique identifier of the module(slot no.)this port is attached to."
      ::= { prtTRMacAddressEntry 1 }

prtTRMacAddressPortID OBJECT-TYPE  
      SYNTAX  Integer32   
      MAX-ACCESS  read-only
      STATUS  current
      DESCRIPTION
      "A unique identifier of the port within its module."
      ::= { prtTRMacAddressEntry 2 }

prtTRMacAddressID OBJECT-TYPE  
      SYNTAX  Integer32   (1..250)
      MAX-ACCESS  read-only
      STATUS  current
      DESCRIPTION
      "A identifier of the MAC address in the list according to the ring order"
      ::= { prtTRMacAddressEntry 3 }

prtTRMACAddressValue OBJECT-TYPE
           SYNTAX  MacAddress
           MAX-ACCESS  read-only
           STATUS  current
           DESCRIPTION
           " MAC address from the list of addresses connected to this port"
           ::= { prtTRMacAddressEntry 4 }

-- 
-- file :D:\Synergy\WorkArea\545\mib_rad\txt\radring.txt
-- 



--Version:    4.00
--Original : 30.11.93
--Last revision:  05.12.95              
--File:          radring.txt
				   
--

radRing  OBJECT IDENTIFIER ::= {radTokenRing 2}

--

chasRR OBJECT IDENTIFIER ::= {radRing 1} -- Chassis  information

segRR  OBJECT IDENTIFIER ::= { radRing 2 } --  segment information

moduleRR  OBJECT IDENTIFIER ::= { radRing 3 } --Module  information

prtRR OBJECT IDENTIFIER ::= { radRing 4 } --  Port  information


--
-- Chassis description for any object having to be surrounded by a frame
--
chType OBJECT-TYPE
      SYNTAX  DisplayString
      MAX-ACCESS  read-write
      STATUS  current
      DESCRIPTION
	" This value indicates which type of enclosure  the Rad agent is managing. The default value will be RadRing"
      ::= { chasRR 1 }

chNoSlot OBJECT-TYPE
      SYNTAX  Integer32 
      MAX-ACCESS  read-only
      STATUS  current
      DESCRIPTION
      "This value indicates the number of manageable slots in the chassis.
	   Not all slots must be occupied."
      ::= { chasRR 2 }

chPSPrimary OBJECT-TYPE
      SYNTAX  INTEGER {
	    unknown(1),        
	    off(2),
	    fault(3),
	    active(4),
	    recovered(5),
	    none(6)
      }
      MAX-ACCESS  read-only
      STATUS  current
      DESCRIPTION
      "This attribute indicates the status of the main (primary) power 
       supply  unit "
      ::= { chasRR 3 }

chPSSecondary OBJECT-TYPE
      SYNTAX  INTEGER {
	   unknown(1),        
	   off( 2),
	   fault(3),
	   active(4),
	   recovered(5),
	   none( 6)
      }
      MAX-ACCESS  read-only
      STATUS  current
      DESCRIPTION
      "This attribute indicates the status of the secondary power 
       supply  unit"
      ::= { chasRR 4 }

chTemperature OBJECT-TYPE
      SYNTAX  INTEGER {
	   ok(1),
	   exceed(2)
      }
      MAX-ACCESS  read-only
      STATUS  current
      DESCRIPTION
      "This attribute indicates if the internal hub temperature exceeded
       the permissible maximum "
      ::= { chasRR 5 }

chEtMainClock OBJECT-TYPE
      SYNTAX  INTEGER {
           unknown(1),
           ok(2),
           fault(3)
      }
      MAX-ACCESS  read-only
      STATUS  current
      DESCRIPTION
      "This attribute indicates the status of Eternet repeater main clock
      in RadRingII hub"
      ::= { chasRR 6 }

chEtSecClock OBJECT-TYPE
      SYNTAX  INTEGER {
           unknown(1),
           ok(2),
           fault(3)
      }
      MAX-ACCESS  read-only
      STATUS  current
      DESCRIPTION
      "This attribute indicates the status of Eternet repeater secondary clock
      in RadRingII hub"
      ::= { chasRR 7 }

--
-- RADRing segments' specific information
--

segRRSecurityTable OBJECT-TYPE
	       SYNTAX SEQUENCE OF SegRRSecEntry
	       MAX-ACCESS not-accessible
	       STATUS current
	       DESCRIPTION
		   "RADRing segments' specific information"
	       ::= { segRR 1}

segRRSecEntry OBJECT-TYPE
	       SYNTAX SegRRSecEntry
	       MAX-ACCESS not-accessible
	       STATUS current
	       DESCRIPTION
		   "An entry in table segRRSecurityTable."
	       INDEX { segRRID, segRRSecID}
	       ::= { segRRSecurityTable 1}
   
SegRRSecEntry ::= 
	    SEQUENCE {
	   segRRID
	      Integer32,
	   segRRSecID
	      Integer32,
	   segRRSecEnable
	      INTEGER,
	   segRRSecurityPattern
	      MacAddress,
	   segRRSecurityMask
	      MacAddress
	} 

segRRID OBJECT-TYPE
	   SYNTAX  Integer32  (1..21)
	   MAX-ACCESS  read-only
	   STATUS  current
	   DESCRIPTION
	   "Segment unique identification number (internal). It is  
	    the extreme left slot, marking the beginning of the 
	    segment.
	    TR segment no.: 1 .. 20 
	    Ethernet segment no.: 21."
      ::= { segRRSecEntry 1 }

segRRSecID OBJECT-TYPE
	   SYNTAX  Integer32  
	   MAX-ACCESS  read-only
	   STATUS  current
	   DESCRIPTION
	   "Segment's security unique identification number"
      ::= { segRRSecEntry 2 }

segRRSecEnable  OBJECT-TYPE
	   SYNTAX  INTEGER {
		off(2),
		on(3)
	}
	   MAX-ACCESS  read-write
	   STATUS  current
	   DESCRIPTION
	   "This entry indicates whether the specific segment's security is active or not"
      ::= { segRRSecEntry 3 }

segRRSecurityPattern OBJECT-TYPE
      SYNTAX  MacAddress
      MAX-ACCESS  read-write
      STATUS  current
      DESCRIPTION
      "A six-octet (48 bit) pattern, where the masked bits of segTRSecurityMask
       need to match the MAC address of each port within the segment. A Value of 
       all-zeros  indicates no security."
      ::= { segRRSecEntry 4 }

segRRSecurityMask  OBJECT-TYPE
      SYNTAX  MacAddress
      MAX-ACCESS  read-write
      STATUS  current
      DESCRIPTION
      "Mask of the allowed MAC address that can be connected through 
      the ports within  the segment"
    ::= { segRRSecEntry 5}

--
-- RADRing  specific modules' information
--

mdlRRTable OBJECT-TYPE
	       SYNTAX SEQUENCE OF MdlRREntry
	       MAX-ACCESS not-accessible
	       STATUS current
	       DESCRIPTION
		   "RADRing  specific modules' information"
	       ::= { moduleRR 1 }

mdlRREntry OBJECT-TYPE
	       SYNTAX MdlRREntry
	       MAX-ACCESS not-accessible
	       STATUS current
	       DESCRIPTION
		   "An entry in table mdlRRTable."
	       INDEX { mdlRRid}
	       ::= { mdlRRTable 1}

MdlRREntry ::= 
	    SEQUENCE {
	    mdlRRid
	  Integer32,
	     mdlRRTLRstatus
	   INTEGER,
	     mdlRRtermination
	   INTEGER,
	    mdlRRReset                     
	  INTEGER, 
	     mdlRRLed
	   OCTET STRING,
	     mdlRRSpeed
	   INTEGER,    
	     mdlRRMngAutoDis
	   INTEGER,
	     mdlRRAutodisable
	   INTEGER,             
	     mdlRRConfigMsg
	   OCTET STRING,
	     mdlRRMngState
	   INTEGER,
	     mdlRRType 
	   INTEGER,
	     mdlRRHwVer 
	   DisplayString,
	     mdlRRSwVer 
	   DisplayString,
	     mdlRRSpecific 
       OBJECT IDENTIFIER 
	   }

mdlRRid OBJECT-TYPE
	   SYNTAX  Integer32  (1..20)
	   MAX-ACCESS  read-only
	   STATUS  current
	   DESCRIPTION
	   "Unique number to identify the module. It indicates the slot
	    number the module is inserted in."
	 ::= { mdlRREntry 1}

mdlRRTLRstatus  OBJECT-TYPE   
      SYNTAX  INTEGER {
			unknown(1),
		off(2),
		on(3)
		}
      MAX-ACCESS  read-only
      STATUS  current
      DESCRIPTION
	"This entry specifies the status of the setup on the TL-2/Exx
	 modules. When the value is ON, lobe one is the only active lobe. This entry
	  will have the value UNKNOWN for all other modules   "
      ::= { mdlRREntry 2 }

mdlRRtermination  OBJECT-TYPE
      SYNTAX  INTEGER {
	   unknown(1),          
	   off(2),
	   on(3)
      }
      MAX-ACCESS  read-only
      STATUS  current
      DESCRIPTION
      "Attribute describing the termination state as set by the switches on the
       lobe modules"
      ::= { mdlRREntry 3 }


mdlRRReset  OBJECT-TYPE
      SYNTAX  INTEGER {
	   unknown(1),
	   off(2),
	   on(3)
	      }
      MAX-ACCESS  read-write
      STATUS  current
      DESCRIPTION
      "When this object is set to the value of ON(3),
       the module performs software reset. Upon completion, a trap  will
       be issued to the management station and  the value
       will be set to OFF. This entry will have the value of UNKNOWN (1) for 
       modules without independent processors. This command should be masked 
       for the agent module"
      ::= { mdlRREntry 4 }

mdlRRLed  OBJECT-TYPE   
      SYNTAX  OCTET STRING 
      MAX-ACCESS  read-only
      STATUS  current
      DESCRIPTION
	"This entry specifies  the LEDs status in the module . Each led will be represented by 4 bits
	where the first 2 bits will specify  the status (NA, OFF, ON, BLINK), and the next two bits
	will specify the color (RED, GREEN, YELLOW)"
      ::= { mdlRREntry 5}

mdlRRSpeed OBJECT-TYPE
      SYNTAX  INTEGER {
	unknown(1),        -- for WAN cards     
	fourMegabit(2),
	sixteenMegabit(3), 
	tenMegabit(4)      -- for Ethernet
      }
      MAX-ACCESS  read-only
      STATUS  current
      DESCRIPTION
      "Attribute describing the bandwidth of the media as set by the module switches."
      ::= { mdlRREntry 6 }

mdlRRMngAutoDis OBJECT-TYPE   
      SYNTAX   INTEGER {
		unknown(1),
		off(2),
		on(3)
	}
      MAX-ACCESS  read-only
      STATUS  obsolete
      DESCRIPTION
      "Attribute describing the setup of the MNG switch on the TL- Active cards. Value ON indicates 
       the ability of activating  the auto-disable mechanism of the card via management command. 
       Value   OFF indicates  that the activation of the auto-disable mechanism of the card  is according 
       to the switch setting.In this case the mdlRRAutodisable will not be available for write 
	   operation. Applicable to Token Ring cards only.
	   Replaced by mdlRRMngState."
      ::= { mdlRREntry 7}

mdlRRAutodisable  OBJECT-TYPE   
      SYNTAX   INTEGER {
		  notApplicable(1),
		  off(2),
		  on(3)
	}
      MAX-ACCESS  read-write
      STATUS  current
      DESCRIPTION
	"This attribute can be set by the manager if the value of mdlRRMngAutoDis is ON. It 
   	controls the behavior of the Active cards regarding the Auto-disable mechanism. All
	  ports will be in the same mode. Applicable to Token Ring cards only."
      ::= { mdlRREntry 8 }

 mdlRRConfigMsg OBJECT-TYPE   
      SYNTAX  OCTET STRING
      MAX-ACCESS  read-only
      STATUS  current
      DESCRIPTION
      "Full configuration message  coded in internal RAD application format.
      This entry describes  module' configuration. "
      ::= { mdlRREntry 9 }
 
mdlRRMngState OBJECT-TYPE   
      SYNTAX   INTEGER {
		unknown(1),
		disable(2),
		enable(3)
}
      MAX-ACCESS  read-only
      STATUS  current
      DESCRIPTION
      " This entry indicates  the setting of the module's switches. ENABLE means that the module 
       can accept management commands. "
      ::= { mdlRREntry 10 }


mdlRRType OBJECT-TYPE
      SYNTAX  INTEGER {
	    unknown(1),
	    empty(2),
	    tl4s(3),
	    tl4su(4),
	    tl4sd(5),
	    tl4cx(6), 
	    tl4u(7),
	    tl2edu(8), 
	    tl2eds(9),
	    tl2edsu(10),
	    tl2f(11),   
	    tja(12),      
	    tio(13),
	    tfr(14),
	    tfc1(15),
	    tfc2(16),
	    tcr(17),
	    tl4au(18),
	    tl4as(19),
	    tl4asd(20),
	    tl4asu(21),
	    tre1d(22),
	    tre(23),
	    tre8d(24),
	    stc1(25),
	    stc2(26),
	    ftc(27),
	    cmlib(28),
	    tl2fsat(29),
-- WAN
	    taV24(30),
	    taV11(31),
	    wangVs(32),
	    ta3x74(33),
	    ta3x(34),                    
-- rr-sat
	sat-asu(35),
	sat-asd(36),
	sat-su(37),
	sat-sd(38),
-- ethernet
	ep8t(39),
	ep4taui(40),
	ep4t2fl(41),
	ep4tfl(42),
	ep4fl(43),
-- epr
	epr8t(45),
	epr4taui(46),
	epr4t2fl(47),
	epr4tfl(48),
	epr4fl(49),
-- rr
	tl2fm(51),
	ftc2(53),
	mlbt(54),
	mlbtf(55),
	ftbDfo(56),
	ftbSfo(57),
	mbe8d(58),
	mbe1d(59),
	cmlibE(60)
      }
      MAX-ACCESS  read-only
      STATUS  current
      DESCRIPTION
      "Indicates the type of the module installed in the specified slot number."
      ::= { mdlRREntry 11}

mdlRRHwVer OBJECT-TYPE
      SYNTAX  DisplayString
      MAX-ACCESS  read-write
      STATUS  current
      DESCRIPTION
      "ASCII string for description and display of the module's hardware version,
      as it is known by the module's software. A manager can record his own 
      hardware upgrade."
      ::= { mdlRREntry 12 }

mdlRRSwVer OBJECT-TYPE
      SYNTAX  DisplayString
      MAX-ACCESS  read-only
      STATUS  current
      DESCRIPTION
      "ASCII string for description and display of the module's 
       software version. A value of NOT APPLICABLE will be recorded
       for a module having no independent processor."
      ::= { mdlRREntry  13 }

mdlRRSpecific OBJECT-TYPE
      SYNTAX  OBJECT IDENTIFIER
      MAX-ACCESS  read-only
      STATUS  current
      DESCRIPTION
      " Object identifier of entity containing additional information 
      regarding this instance. This entry is module type specific."
      ::= { mdlRREntry 14 }




--
-- Additional parameters that can be monitored for a segment with an inband module.
-- Module specific for Token Ring


mdlIBTable OBJECT-TYPE
	       SYNTAX SEQUENCE OF MdlIBEntry
	       MAX-ACCESS not-accessible
	       STATUS current
	       DESCRIPTION
		   "Additional parameters that can be monitored for a segment
		    with an inband module. Module specific for Token Ring"
	       ::= { moduleRR 2 }

mdlIBEntry OBJECT-TYPE
	       SYNTAX MdlIBEntry
	       MAX-ACCESS not-accessible
	       STATUS current
	       DESCRIPTION
		   "An entry in table mdlIBTable."
	       INDEX { mdlIBid}
	       ::= { mdlIBTable 1}

MdlIBEntry ::= 
	    SEQUENCE {
	       mdlIBid
		  Integer32,
	       mdlIBsegID
		  Integer32,
	       mdlIBCorrelationEnable
		  INTEGER,
	       mdlIBAutorecEnable
		  INTEGER,
	       mdlIBAutorecResult
		 INTEGER,
	       mdlIBcommand
		 INTEGER,
	       mdlIBstate
		 INTEGER,
	       mdlIBagnt
    	 INTEGER,
	       mdlIBIpAddress
		 IpAddress,
	       mdlIBLocalMacAddr
		 MacAddress,
	       mdlIBbrnInMacAddr
		 MacAddress,
	       mdlIBLocalAddrStatus
		 INTEGER,
	       mdlIBTrapMaskEnable
	 INTEGER
	 }

mdlIBid OBJECT-TYPE
	   SYNTAX  Integer32  (1..20)
	   MAX-ACCESS  read-only
	   STATUS  current
	   DESCRIPTION
	   "Unique number to identify the CML\IB module. It indicates the slot
	    number the module is inserted in"
	   ::= {  mdlIBEntry 1 }

mdlIBsegID OBJECT-TYPE
	   SYNTAX  Integer32  (1..20)
	   MAX-ACCESS  read-only
	   STATUS  current
	   DESCRIPTION
	   "Unique number to identify the segment where the CML\IB module
	    is inserted. It is one of the segTRID values."
	   ::= {  mdlIBEntry 2 }

mdlIBCorrelationEnable OBJECT-TYPE
	   SYNTAX  INTEGER {
		off(2),
		on(3)
		     }
	   MAX-ACCESS  read-write
	   STATUS  current
	   DESCRIPTION
	   "When set to ON(3), the in-band agent should perform 
	    correlation each time a station enters/leaves the segment."
	   ::= { mdlIBEntry 3 }

mdlIBAutorecEnable OBJECT-TYPE
	   SYNTAX  INTEGER {
		off(2),
		on(3)
		     }
	   MAX-ACCESS  read-write
	   STATUS  current
	   DESCRIPTION
	   "When set to ON(3), the in-band agent should perform 
	    autorecovery each time a beacon status is detected."
	   ::= { mdlIBEntry 4 }

mdlIBAutorecResult OBJECT-TYPE
	   SYNTAX  INTEGER {
		notStarted(1),
		started(2),
		segmentOk(3),
		segmentFixed(4),
		segmentClosed(5),
		failed(6),
		hubProblem(7)
		     }
	   MAX-ACCESS  read-only
	   STATUS  current
	   DESCRIPTION
	    "When autorecovery is completed the result will be reported (3)..(7).
	     While in autorecovery process, started(2) will be reported.
	     Before autorecovery process, notStarted(1) will be reported."  
	   ::= { mdlIBEntry 5 }

mdlIBcommand   OBJECT-TYPE
	 SYNTAX  INTEGER {
		       noOp(1),
		       open(2),
		       reset(3),
		       close(4)
		 }
	 MAX-ACCESS  read-write
	 STATUS  current
	 DESCRIPTION
		 "When this object is set to the value of
		  open(2), the station should go into the
		  open state.  The progress and success of
		  this command is given by the values of the
		  object mdlIBstate.
		      When this object is set to the value
		  of reset(3), then the station should do
		  a reset.  On a reset, all MIB counters
		  should retain their values, if possible.
		  Other side effects depend on the hardware chip set.
		      When this object is set to the value
		  of close(4), the station should go into
		  the closed state by removing itself
		  from the ring.
		      Setting this object to a value of
		  no-op(1) has no effect.
		      For read operation, this object has always a
		  value of no-op(1). It is not permitted to apply this 
	      command on an agent module."
	 ::= { mdlIBEntry 6 }

mdlIBstate OBJECT-TYPE
		     SYNTAX  INTEGER
		{ 
		unknown (1),
		opened(2),
		closed(3),
		opening(4),
		closing(5),
		badParam(6),
		lobeFailed(7),
		signalLoss(8),
		insertionTimeout(9),
		ringFailed(10),
		beaconning(11),
		duplicateMac(12),
		requestFailed(13),
		removeReceived(14),
		budFailure(15),
		initFailure(16)
		}                       
		     MAX-ACCESS  read-only
		     STATUS  current
		     DESCRIPTION
			     "The current adapter status, which can
			     be used to diagnose fluctuating problems."
	::= { mdlIBEntry 7 }

mdlIBagnt OBJECT-TYPE
	   SYNTAX  INTEGER  {
		off(2),
		on (3),
		standBy (4)
    	}
	   MAX-ACCESS  read-only
	   STATUS  current
	   DESCRIPTION
	" Indicates whether the specific inband module serves as:
	  - Active hub agent - (on)
	  - Ring Monitor (for TR module only) - (off)
	  - Standby agent - (standBy)"
	::= { mdlIBEntry 8 }

mdlIBIpAddress OBJECT-TYPE
      SYNTAX  IpAddress
      MAX-ACCESS  read-only
      STATUS  current
      DESCRIPTION
      "Indicates IP address of the module if the module serves as  
       an agent of itself."
      ::= {  mdlIBEntry 9}

mdlIBLocalMacAddr OBJECT-TYPE
	   SYNTAX  MacAddress
	   MAX-ACCESS  read-write
	   STATUS  current
	   DESCRIPTION
	   "The value of this object is the specific MAC address 
	   of this interface which uniquely identifies this interface 
	   on a ring.It is the address set by the management  and
           upon request it will replace the burn in address.
           Non-canonical format."
	   ::= { mdlIBEntry 10}

mdlIBLocalAddrStatus OBJECT-TYPE
	   SYNTAX  INTEGER {
		   unknown(1),
		   off(2),
		   on(3)
		}
	   MAX-ACCESS  read-write
	   STATUS  current
	   DESCRIPTION
	   "The value of this object specifies whether the specific 
	    MAC address  of this interface was set by the local 
	    management or it is the burn-in address in use."
	   ::= { mdlIBEntry 11 }

mdlIBbrnInMacAddr OBJECT-TYPE 
      SYNTAX   MacAddress
      MAX-ACCESS  read-only
      STATUS  current
      DESCRIPTION
	"The value of this object is the specific Burn-in MAC address 
	   of this interface which uniquely identifies this interface 
	   on a ring. Non-canonical format."
	   ::= { mdlIBEntry 12 }

mdlIBTrapMaskEnable OBJECT-TYPE
	   SYNTAX  INTEGER {
	    off(2),
	   on(3)
      }
      MAX-ACCESS  read-write    
      STATUS  current
      DESCRIPTION
      "When this attribute is set to OFF by the management console, the 
       agent starts sending the unmasked traps related to this module. 
       Otherwise, no traps are sent by this module."
	   ::= { mdlIBEntry 13 }

-- Special modules such as bridges/converters  that are within the hub
--

mdlBRGTable OBJECT-TYPE
	       SYNTAX SEQUENCE OF MdlBRGEntry
	       MAX-ACCESS not-accessible
	       STATUS current
	       DESCRIPTION
		   "Special modules such as bridges/converters  that are within the hub"
	       ::= { moduleRR 3 }

mdlBRGEntry OBJECT-TYPE
	       SYNTAX MdlBRGEntry
	       MAX-ACCESS not-accessible
	       STATUS current
	       DESCRIPTION
		   "An entry in table mdlBRGTable."
	       INDEX { mdlBRGid}
	       ::= { mdlBRGTable 1}

MdlBRGEntry ::= 
	    SEQUENCE {
	  mdlBRGid
	      Integer32,
	   mdlBRGReady
	      INTEGER,
	   mdlBRGStatus
	       DisplayString,
	    mdlBRGLocation
	       INTEGER,
	    mdlBRGIpAddress
	       IpAddress,
	    mdlBRGMacAddr
	       MacAddress,
		mdlBRGAdapterState
		   INTEGER,
		mdlBRGBypassSw
		   INTEGER
	 }

mdlBRGid OBJECT-TYPE
	   SYNTAX  Integer32  (1..20)
	   MAX-ACCESS  read-only
	   STATUS  current
	   DESCRIPTION
	   "Unique number to identify the module. It indicates the slot
	    number the module is inserted in."
	 ::= { mdlBRGEntry 1}

 mdlBRGReady  OBJECT-TYPE   
      SYNTAX  INTEGER {  
	   unknown(1),
	   off(2), 
	   on(3),
	    blink(4)
      }
      MAX-ACCESS  read-only    
      STATUS  current
      DESCRIPTION
       "This entry will have the value ON when packets can be transferred in the TRE module.
	 The value UNKNOWN will be used for all other modules where this characteristic is 
	not applicable"
	 ::= { mdlBRGEntry 2}

mdlBRGStatus OBJECT-TYPE   
      SYNTAX  DisplayString      
      MAX-ACCESS  read-only    
      STATUS  current
      DESCRIPTION
      "This entry specifies the status of operation of the STC or FTC modules. For other modules
	this value will read NOAP"
 ::= { mdlBRGEntry 3}

 mdlBRGLocation  OBJECT-TYPE   
      SYNTAX  INTEGER {  
	   unknown(1),
	   main(2), 
	   remote(3),
	   secondary(4)
      }
      MAX-ACCESS  read-only    
      STATUS  current
      DESCRIPTION
       "This entry indicates the configuration mode:
        - for the TRE bridge (main/remote) 
        - for MLB-T, MLBT-F (main/secondary) "
 ::= { mdlBRGEntry 4}

mdlBRGIpAddress OBJECT-TYPE
      SYNTAX  IpAddress
      MAX-ACCESS  read-only
      STATUS  current
      DESCRIPTION
      "Indicates IP address of the module if the module serves as  an agent of itself. For 
       all other modules the IP value will be 0.0.0.0"
      ::= {  mdlBRGEntry 5}


mdlBRGMacAddr OBJECT-TYPE 
      SYNTAX   MacAddress
      MAX-ACCESS  read-only
      STATUS  current
      DESCRIPTION
	"The value of this object is the specific MAC address 
	   of this interface which uniquely identifies this interface 
	   on a ring."
	   ::= { mdlBRGEntry 6}

mdlBRGAdapterState OBJECT-TYPE
		     SYNTAX  INTEGER
		{ 
		unknown (1),
		opened(2),
		closed(3),
		opening(4),					  
		closing(5),
		badParam(6),
		lobeFailed(7),
		signalLoss(8),
		insertionTimeout(9),
		ringFailed(10),
		beaconning(11),
		duplicateMac(12),
		requestFailed(13),
		removeReceived(14),
		budFailure(15),
		initFailure(16)
		}                       
		     MAX-ACCESS  read-only
		     STATUS  current
		     DESCRIPTION
			     "The current adapter status, which can
			      be used to diagnose fluctuating problems.
			      This object is applicable only for TR bridges
			      with adapter.
			      The value 'unknown' will be used for other 
			      module types."
	::= { mdlBRGEntry 7 }

mdlBRGBypassSw  OBJECT-TYPE   
      SYNTAX  INTEGER {  
	   unknown(1),
	   off(2), 
	   on(3)
      }
      MAX-ACCESS  read-only    
      STATUS  current
      DESCRIPTION
       "This entry is applicable only for FTB-D/FO module.
        It describes the status of the Bypass Switch. 
        The value UNKNOWN will be used for all other modules where 
        this characteristic is not applicable"
	 ::= { mdlBRGEntry 8}



-- Special "WAN" modules that are within the RadRing hub
--

mdlMMTable OBJECT-TYPE
	       SYNTAX SEQUENCE OF MdlMMEntry
	       MAX-ACCESS not-accessible
	       STATUS current
	       DESCRIPTION
		   "Special 'WAN' modules that are within the RadRing hub"
	       ::= { moduleRR 4 }

mdlMMEntry OBJECT-TYPE
	       SYNTAX MdlMMEntry
	       MAX-ACCESS not-accessible
	       STATUS current
	       DESCRIPTION
		   "An entry in table mdlMMTable."
	       INDEX { mdlMMid}
	       ::= { mdlMMTable 1}

MdlMMEntry ::= 
	    SEQUENCE {
	  mdlMMid
	      Integer32,
	   mdlMMBertCmd
	      INTEGER
	 }

mdlMMid OBJECT-TYPE
	   SYNTAX  Integer32  (1..20)
	   MAX-ACCESS  read-only
	   STATUS  current
	   DESCRIPTION
	   "Unique number to identify the module. It indicates the slot
	    number the module is inserted in."
	 ::= { mdlMMEntry 1}

mdlMMBertCmd OBJECT-TYPE
	   SYNTAX  INTEGER {
	     unknown(1),
		 off(2),
		 on(3)
		     }
	   MAX-ACCESS  read-write
	   STATUS  current
	   DESCRIPTION
	   "Setting this Object to ON, will start BERT test on all the channels that are currently in               
	     Remote Loop. If the value of mdlRRMngState is disabled, this parameter is read-only
		     and  reflects the module jumper setting. "
	   ::= { mdlMMEntry 2}

-- "Ethernet" modules that are within the hub
--

mdlETTable OBJECT-TYPE
	       SYNTAX SEQUENCE OF MdlETEntry
	       MAX-ACCESS not-accessible
	       STATUS current
		   DESCRIPTION
		   "'Ethernet' modules that are within the hub"
	       ::= { moduleRR 5 }

mdlETEntry OBJECT-TYPE
	       SYNTAX MdlETEntry
	       MAX-ACCESS not-accessible
	       STATUS current
		   DESCRIPTION
		   "An entry in table mdlETTable."
	       INDEX { mdlMMid }
	       ::= { mdlETTable 1}

MdlETEntry ::= 
	    SEQUENCE {
       mdlETid
	      Integer32,
	   mdlETSAmode
	      INTEGER
	 }

mdlETid OBJECT-TYPE
	   SYNTAX  Integer32  (1..20)
	   MAX-ACCESS  read-only
	   STATUS  current
	   DESCRIPTION
	   "Unique number to identify the module. It indicates the slot
	    number the module is inserted in. It is the same
		as rptrGroupIndex in the Repeater MIB"
	 ::= { mdlETEntry 1}

mdlETSAmode       OBJECT-TYPE
      SYNTAX   INTEGER {
	       unknown(1),
	       off(2),
	       on(3)
}
      MAX-ACCESS  read-write
      STATUS  current
      DESCRIPTION
      "Setting this Object to ON, will change the mode of operation 
       of the Ethernet card to a stand alone operation mode. It will 
       disconnect the card from the repeater bus. The rptrGroupOperStatus 
	   parameter in the Repeater MIB is changed to other(1). 
	   The parameter is read-only when the value of  mdlRRMngState 
	   is disabled"
	 ::= { mdlETEntry 2 }

--
--RADRing specific port information
--

prtRRTable OBJECT-TYPE
      SYNTAX SEQUENCE OF PrtRREntry
      MAX-ACCESS not-accessible
      STATUS current
      DESCRIPTION
	  "RADRing specific port information"
      ::= { prtRR 1 }

prtRREntry OBJECT-TYPE
      SYNTAX    PrtRREntry
      MAX-ACCESS    not-accessible
      STATUS    current
      DESCRIPTION
	  "An entry in table prtRRTable."
      INDEX     { prtRRmdlID, prtRRID }
      ::= { prtRRTable 1 }
 
PrtRREntry ::=
      SEQUENCE {
	  prtRRmdlID
	     Integer32,
	  prtRRID
	     Integer32,
	  prtRRSecurityState
	      INTEGER,
	  prtRRSecurityEnable
	      INTEGER,
	  prtRRSecurityMask  
	     MacAddress,
	  prtRRSecurityPattern
	     MacAddress,
	  prtRRJitterAttenEnable 
	     INTEGER,
	  prtRRConfigMsg
	      OCTET STRING,
	  prtRRFlipAutoDisable
	     INTEGER,
	  prtRRSecurityMask2
	     MacAddress,
	  prtRRSecurityPattern2
	     MacAddress,
	  prtRRMode
	      INTEGER,
	   prtRRAttachment
	      INTEGER
		 }

prtRRmdlID OBJECT-TYPE  
      SYNTAX  Integer32   
      MAX-ACCESS  read-only
      STATUS  current
      DESCRIPTION
      "A unique identifier of the module,(slot no.),this port is attached to."
      ::= { prtRREntry 1 }

prtRRID OBJECT-TYPE  
      SYNTAX  Integer32   
      MAX-ACCESS  read-only
      STATUS  current
      DESCRIPTION
      "A unique identifier of the port within its module."
      ::= { prtRREntry 2 }

prtRRSecurityState OBJECT-TYPE
	   SYNTAX  INTEGER {
		 notactive(1),
		 active(2)
		     }
	   MAX-ACCESS  read-only
	   STATUS  current
	   DESCRIPTION
	   "This entry indicates whether a security check can be performed on 
	    the specific port. This value is directly related to the
	    presence of an inband module in the segment where the port
	    belongs to and to activation of the correlation process."
	   ::= {  prtRREntry 3 }

prtRRSecurityEnable OBJECT-TYPE
      SYNTAX  INTEGER 
	{
	    off(2),
	    on(3)
	}
      MAX-ACCESS  read-write
      STATUS  current
      DESCRIPTION
      "This value indicates whether a security check should be performed.
       Setting this value to ON(3) will activate the security mechanism
       if and only if, the value of  prtRRSecurityState is ACTIVE."
      ::= { prtRREntry 4 }


prtRRSecurityMask OBJECT-TYPE
      SYNTAX  MacAddress
      MAX-ACCESS  read-write
      STATUS  current
      DESCRIPTION
      "Mask of the allowed MAC address that can be connected through 
      this port. The security of the individual port overwrites  the
       security of the segment where the port belongs to"
      ::= { prtRREntry 5 }

prtRRSecurityPattern   OBJECT-TYPE
      SYNTAX  MacAddress
      MAX-ACCESS  read-write
      STATUS  current
      DESCRIPTION
      "A six-octet(48 bit) pattern, where the masked bits of prtRRSecurityMask
       should match the MAC address."
      ::= { prtRREntry 6}

prtRRJitterAttenEnable OBJECT-TYPE
      SYNTAX  INTEGER {
	   unknown(1),
	   off(2),    
	   on(3)    
      }
      MAX-ACCESS  read-write
      STATUS  current
      DESCRIPTION
      "The value of this attribute determines activation of the
      jitters Attenuation mechanism of  repeater's port ."
      ::= { prtRREntry 7 }

 prtRRConfigMsg OBJECT-TYPE   
      SYNTAX  OCTET STRING
      MAX-ACCESS  read-only
      STATUS  current
      DESCRIPTION
      "Full configuration message  coded in internal RAD application format.
      This entry describes  port' configuration. "
      ::= { prtRREntry  8 }

prtRRFlipAutoDisable OBJECT-TYPE   
      SYNTAX   INTEGER {
		noApplicable(1),
		off(2),
		on(3)
	}
      MAX-ACCESS  read-write
      STATUS  current
      DESCRIPTION
      "Attribute describing the control on the flipping mechanism of a lobe . 
	Value ON indicates  the ability of the lobe to  auto disable itself when flipping occur. 
	Value   OFF indicates  that  the auto disable mechanism should not be activated and the 
	lobe should stay in a flipping state. 
       This attribute applies on selected lobes (tl-2/f, or tl-2/fsat)"
      ::= { prtRREntry  9 }

prtRRSecurityMask2 OBJECT-TYPE
      SYNTAX  MacAddress
      MAX-ACCESS  read-write
      STATUS  current
      DESCRIPTION
      "Mask of the allowed MAC address that can be connected through 
      this port. The security of the individual port overwrites  the
       security of the segment where the port belongs to"
      ::= { prtRREntry 10 }

prtRRSecurityPattern2   OBJECT-TYPE
      SYNTAX  MacAddress
      MAX-ACCESS  read-write
      STATUS  current
      DESCRIPTION
      "A six-octet(48 bit) pattern: where the masked bits of prtRRSecurityMask2
       should match the MAC address."
      ::= { prtRREntry 11 }

prtRRMode  OBJECT-TYPE
      SYNTAX  INTEGER
{
		noApplicable (1),
		smart-port   (2),
		port         (3),
		interRptrPort(4),
		multiConnPort(5)
}
      MAX-ACCESS  read-write
      STATUS  current
      DESCRIPTION
     "Indicates the port status of rr-sat card after the communication
      is broken. When configured to smart-port, the port disables itself
      when there is no management communication with attachment.
      interRptrPort - this port is used to connect an external 
                      repeater. No security can be set for this port.
                      MAC Address is set to 0. No traps 'MAC Address changed'
                      are generated.
      multiConnPort - this port is used for connection of external
                      4 port repeater. 8 securities per port exist.
                      MAC Address is set to 0. No traps 'MAC Address changed'
                      are generated. "
      ::= { prtRREntry 12 }

prtRRAttachment  OBJECT-TYPE
      SYNTAX  INTEGER
{
		none(1),
		station(2),
		sLau2(3),
		sLau4(4)
}
      MAX-ACCESS  read-only
      STATUS  current
      DESCRIPTION
     "Indicates the type of the port attachment. Smart attachment types
      are applicable for rr-sat card only"
      ::= { prtRREntry 13 }
    
--
--RADRing specific WAN modules port information 
--

prtMMTable OBJECT-TYPE
      SYNTAX SEQUENCE OF PrtMMEntry
      MAX-ACCESS not-accessible
      STATUS current
      DESCRIPTION
	  "RADRing specific WAN modules port information."
      ::= { prtRR 2 }

prtMMEntry OBJECT-TYPE
      SYNTAX    PrtMMEntry
      MAX-ACCESS    not-accessible
      STATUS    current
      DESCRIPTION
	  "An entry in table prtMMTable."
      INDEX     { prtMMmdlID, prtMMID  }
      ::= { prtMMTable 1 }
 
PrtMMEntry ::=
      SEQUENCE {
	  prtMMmdlID
	     Integer32,
	  prtMMID
	     Integer32,
      prtMMAdminCmd
	     INTEGER,
      prtMMOperStatus
	     INTEGER,
      prtMMTestStatus
	     INTEGER,
      prtMMBertResult
	     INTEGER,
      prtMMTrapMaskEnable
	     INTEGER
      }

prtMMmdlID OBJECT-TYPE  
      SYNTAX  Integer32   
      MAX-ACCESS  read-only
      STATUS  current
      DESCRIPTION
      "A unique identifier of the module(slot no.)this port is attached to."
      ::= { prtMMEntry 1 }

prtMMID OBJECT-TYPE  
      SYNTAX  Integer32   
      MAX-ACCESS  read-only
      STATUS  current
      DESCRIPTION
      "A unique identifier of the port (link) within its module."
      ::= { prtMMEntry 2 }

prtMMAdminCmd  OBJECT-TYPE
      SYNTAX  INTEGER {
	   normal(1),
	   locLoop(2),    
	   remLoop(3)    
}            
      MAX-ACCESS  read-write
      STATUS  current
      DESCRIPTION
      "Setting the object to locLoop(2) or remLoop(3) will activate the corresponding test.
	  Value remLoop(3) activates the BERT test on the related link if mdlMMBertCmd
	  is set to on(3). Setting parameter to normal(1), restores the normal operation
	  of the link. The parameter is read-only when value of mdlRRMngState is disable"
      ::= { prtMMEntry 3 }

prtMMOperStatus OBJECT-TYPE
      SYNTAX  INTEGER {
	   operational(1),
	   locSyncLoss(2),    
	   remSyncLoss(3)
}            
      MAX-ACCESS  read-only
      STATUS  current
      DESCRIPTION
	  "Reflects the Synchronization status. "
      ::= { prtMMEntry 4 }

prtMMTestStatus OBJECT-TYPE
      SYNTAX  INTEGER {
	   normal(1),
	   locLoop(2),    
	   remLoop(3),
	   bert(4)    
}            
      MAX-ACCESS  read-only
      STATUS  current
      DESCRIPTION
	  "Reflects the link status. When the object is set to the value of bert(4),
      it means that the remote loopback is active too. "
      ::= { prtMMEntry 5 }

prtMMBertResult  OBJECT-TYPE
      SYNTAX  INTEGER {
	   unknown(1),
	   fault(2),    
	   ok(3)    
}            
      MAX-ACCESS  read-only
      STATUS  current
      DESCRIPTION
	  "The value of this object indicates the status of the last BERT test."
      ::= { prtMMEntry 6 }

prtMMTrapMaskEnable OBJECT-TYPE
	   SYNTAX  INTEGER {
	   off(2),
	   on(3)
      }
      MAX-ACCESS  read-write    
      STATUS  current
      DESCRIPTION
      "When this object is set to OFF by the management console, the 
       agent starts sending the unmasked traps related to this module. 
       Otherwise, no traps are sent by this module."
	   ::= { prtMMEntry 7 }



--
--RADRing specific Ethernet port information
--

prtETTable OBJECT-TYPE
      SYNTAX SEQUENCE OF PrtETEntry
      MAX-ACCESS not-accessible
      STATUS current
      DESCRIPTION
	  "RADRing specific Ethernet port information"
      ::= { prtRR 3 }

prtETEntry OBJECT-TYPE
      SYNTAX    PrtETEntry
      MAX-ACCESS    not-accessible
      STATUS    current
      DESCRIPTION
	  "An entry in table prtETTable."
      INDEX     { prtETmdlID, prtETID }
      ::= { prtETTable 1 }
 
PrtETEntry ::=
      SEQUENCE {
	  prtETmdlID
	     Integer32,
	  prtETID
	     Integer32,
	  prtETTrapMaskEnable
	      INTEGER
		}

prtETmdlID OBJECT-TYPE
      SYNTAX  Integer32   
      MAX-ACCESS  read-only
      STATUS  current
      DESCRIPTION
      "A unique identifier of the module, (slot no.), this port is attached to."
      ::= { prtETEntry 1 }

prtETID OBJECT-TYPE
      SYNTAX  Integer32   
      MAX-ACCESS  read-only
      STATUS  current
      DESCRIPTION
      "A unique identifier of the port within its module."
      ::= { prtETEntry 2 }

prtETTrapMaskEnable OBJECT-TYPE
      SYNTAX  INTEGER {  
	   off(2),
	   on(3)
      }
      MAX-ACCESS  read-write    
      STATUS  current
      DESCRIPTION
      "When this attribute is set to OFF by the management console, the 
       agent starts sending the unmasked traps related to this port. 
       Otherwise, no traps are sent by this port."
      ::= { prtETEntry 3 }

--
-- RR Port Security Table (10.08.95)
--
prtRRSecTable OBJECT-TYPE
      SYNTAX SEQUENCE OF PrtRRSecEntry
      MAX-ACCESS not-accessible
      STATUS current
      DESCRIPTION
	  "RR Port Security Table (10.08.95)"
      ::= { prtRR 4 }

prtRRSecEntry OBJECT-TYPE
      SYNTAX    PrtRRSecEntry
      MAX-ACCESS    not-accessible
      STATUS    current
      DESCRIPTION
	  "An entry in table prtRRSecTable."
      INDEX     { prtRRSecmdlID, prtRRSecPrtID, prtRRSecID }
      ::= { prtRRSecTable 1 }
 
PrtRRSecEntry ::=
      SEQUENCE {
	  prtRRSecmdlID
	     Integer32,
	  prtRRSecPrtID
	     Integer32,
	  prtRRSecID
	     Integer32,
	  prtRRSecMask  
	     MacAddress,
	  prtRRSecPattern
	     MacAddress
	  }

prtRRSecmdlID OBJECT-TYPE  
      SYNTAX  Integer32   
      MAX-ACCESS  read-only
      STATUS  current
      DESCRIPTION
      "A unique identifier of the module,(slot no.),this port is 
       attached to."
      ::= { prtRRSecEntry 1 }

prtRRSecPrtID OBJECT-TYPE  
      SYNTAX  Integer32   
      MAX-ACCESS  read-only
      STATUS  current
      DESCRIPTION
      "A unique identifier of the port within its module."
      ::= { prtRRSecEntry 2 }

prtRRSecID OBJECT-TYPE  
      SYNTAX  Integer32   
      MAX-ACCESS  read-only
      STATUS  current
      DESCRIPTION
      "A unique identifier of the security number within the port."
      ::= { prtRRSecEntry 3 }

prtRRSecMask OBJECT-TYPE
      SYNTAX  MacAddress
      MAX-ACCESS  read-write
      STATUS  current
      DESCRIPTION
      "Mask of the allowed MAC address that can be connected through 
       this port. The security of the individual port overwrites the
       security of the segment,  the port belongs to"
      ::= { prtRRSecEntry 4 }

prtRRSecPattern   OBJECT-TYPE
      SYNTAX  MacAddress
      MAX-ACCESS  read-write
      STATUS  current
      DESCRIPTION
      "A six-octet(48 bit) pattern, where the masked bits of 
       prtRRSecMask	should match the MAC address."
      ::= { prtRRSecEntry 5}
	









































-- 
-- file :D:\Synergy\WorkArea\545\mib_rad\txt\fdx.txt
-- 


--Title:    FDX   MIB
--Version:   2.1...
--Date:   16.10.94              
--By:        Dan.R.
--File:       FDX.TXT

--Comments: The FDX agent also supports the following Public MIBs:
--              MIB-II (RFC1213)
--              FDDI MIB (RFC  1285)
--       relevant parts of Lannet-60 MIB.

-- the RAD Station Group
-- Implementation of the Station group is current
-- for all manageable systems which support RAD Stations


radFddiStation OBJECT IDENTIFIER ::= { radFddi 1 }

radFddiStationsNumber  OBJECT-TYPE
      SYNTAX  Integer32 (0..65535)      
      MAX-ACCESS  read-only
      STATUS  current
      DESCRIPTION
      "The number of manageable Stations implemented in the box."
      ::= { radFddiStation 1 }
      
-- the FDDI concentrator table

radFddiStationTable OBJECT-TYPE
      SYNTAX  SEQUENCE OF RadFddiStationEntry
      MAX-ACCESS  not-accessible
      STATUS current
      DESCRIPTION
      "A list of FddiStation entries. The number of entries is 
      given by the value of radFddiStationsNumber. "
      ::= { radFddiStation 2 }

radFddiStationEntry OBJECT-TYPE
      SYNTAX  RadFddiStationEntry
      MAX-ACCESS  not-accessible
      STATUS  current
      DESCRIPTION
	  "An entry in table radFddiStationTable."
      INDEX   { radFddiStationIndex }
      ::= { radFddiStationTable 1 }

RadFddiStationEntry ::=
   SEQUENCE {
      radFddiStationIndex
	 Integer32,
      radFddiStationType
	 INTEGER,
      radFddiStationBus1TestResult
	 INTEGER,
      radFddiStationBus2TestResult
	 INTEGER,
      radFddiStationTempDeInsertAction
	 Integer32,
      radFddiStationPerformTest
	 INTEGER,
      radFddiStationOpticalSwitchStatus  -- was radFddiStationOpticalSwitchBypass
	 INTEGER
 }
 
radFddiStationIndex OBJECT-TYPE  
      SYNTAX  Integer32 (1..65535)
      MAX-ACCESS  read-only 
      STATUS  current
      DESCRIPTION
      "A unique value for each Station. Its value ranges 
      between 1 and the value ofradFddiStationNumber."
      ::= { radFddiStationEntry 1 }

radFddiStationType OBJECT-TYPE  
      SYNTAX  INTEGER {
	other(1),
	singleAttachedStation(2),
	dualAttachedStation(3),
	singleAttachedConcentrator(4),
	dualAttachedConcentrator(5),
	nullAttachedConcentrator(6)
      }
      MAX-ACCESS  read-only
      STATUS  current
      DESCRIPTION
      " Indicates the type of the station." 
      ::= { radFddiStationEntry 2 }

radFddiStationBus1TestResult OBJECT-TYPE  
      SYNTAX  INTEGER {
	ok(1),
	faulty(2)
      }
      MAX-ACCESS  read-only
      STATUS  current
      DESCRIPTION
      " Indicates the result of a test performed on Bus1." 
      ::= { radFddiStationEntry 3 }

radFddiStationBus2TestResult OBJECT-TYPE  
      SYNTAX  INTEGER {
	ok(1),
	faulty(2)
      }
      MAX-ACCESS  read-only
      STATUS  current
      DESCRIPTION
      " Indicates the result of a test performed on Bus2." 
      ::= { radFddiStationEntry 4 }

radFddiStationTempDeInsertAction OBJECT-TYPE  
      SYNTAX  Integer32 
      MAX-ACCESS  read-write
      STATUS  current
      DESCRIPTION
      "This action provides temporary deinsertion of the root
      station from the ring. Expressed in milliseconds."
      ::= { radFddiStationEntry 5 }

radFddiStationPerformTest OBJECT-TYPE  
      SYNTAX  INTEGER {
	on(1),
	off(2) 
      }
      MAX-ACCESS  read-write
      STATUS  current
      DESCRIPTION
      "A value ON of this attribute indicates that a test should be 
      performed upon the Station." 
      ::= { radFddiStationEntry 6 }

radFddiStationOpticalSwitchStatus OBJECT-TYPE
      SYNTAX  INTEGER {
	on(1),
	off(2),
	notSupported(255) 
      }
      MAX-ACCESS  read-only
      STATUS  current
      DESCRIPTION
      "A value ON of this attribute indicates that the Station 
      is in bypass mode." 
      ::= { radFddiStationEntry 7 }



-- the RAD FDDI SMT table



radFddiSMTTable OBJECT-TYPE
      SYNTAX  SEQUENCE OF RadFddiSMTEntry
      MAX-ACCESS  not-accessible
      STATUS current
      DESCRIPTION
      "A list of FddiSMT entries. The number of entries is 
      given by the value of snmpFddiSMTNumber. "
      ::= { radFddi 2 }


radFddiSMTEntry OBJECT-TYPE
      SYNTAX  RadFddiSMTEntry
      MAX-ACCESS  not-accessible
      STATUS  current
      DESCRIPTION
	  "An entry in table radFddiSMTTable."
      INDEX   { radFddiSMTIndex }
      ::= { radFddiSMTTable 1 }


RadFddiSMTEntry ::=
   SEQUENCE {
      radFddiSMTIndex
	 Integer32,
      radFddiSMTStation
	 Integer32,
      radFddiSMTCFState
	 INTEGER,
      radFddiSMTLeftSlot
	 Integer32,
      radFddiSMTRightSlot
	 Integer32
      }
	
radFddiSMTIndex OBJECT-TYPE  
      SYNTAX  Integer32 (1..65535)
      MAX-ACCESS  read-only 
      STATUS  current
      DESCRIPTION
      "A unique value for each SMT. Its value ranges 
      between 1 and the value of snmpFddiSMTNumber."
      ::= { radFddiSMTEntry 1 }



radFddiSMTStation OBJECT-TYPE  
      SYNTAX  Integer32 (1..65535)
      MAX-ACCESS  read-only 
      STATUS  current
      DESCRIPTION
      "Indicates the Station inside the box to which the
      current SMT belongs. Its value ranges 
      between 1 and the value of radFddiStationNumber."
      ::= { radFddiSMTEntry 2 }



radFddiSMTCFState OBJECT-TYPE  
      SYNTAX  INTEGER {
	isolated(1),
	localA(2),
	localB(3),
	localAB(4),
	localS(5),
	wrapA(6),
	wrapB(7),
	wrapAB(8),
	wrapS(9),
	cWrapA(10),
	cWrapB(11),
	cWrapS(12),
	thru(13)
      }      
      MAX-ACCESS  read-only 
      STATUS  obsolete
      DESCRIPTION
      "The attachement configuration for the Station. Extends the
      range of values provided by the SNMP variable snmpFddiSMTCFState
      from the SNMP FDDI MIB."
      ::= { radFddiSMTEntry 3 }



radFddiSMTLeftSlot OBJECT-TYPE
	SYNTAX  Integer32
	MAX-ACCESS  read-only
	STATUS  current
	DESCRIPTION
	"Indicates the slot number of the leftmost card on the concentrator
	implemented inside the box and managed by the agent MAC."
	::= { radFddiSMTEntry 4 }



radFddiSMTRightSlot OBJECT-TYPE
	SYNTAX  Integer32
	MAX-ACCESS  read-only
	STATUS  current
	DESCRIPTION
	"Indicates the slot number of the rightmost card on the concentrator
	implemented inside the box and managed by the agent MAC. Note that
	the MAC-agent card itself is not taken into consideration."
	::= { radFddiSMTEntry 5 }



-- the RAD FDDI MAC table



radFddiMACTable OBJECT-TYPE
      SYNTAX  SEQUENCE OF RadFddiMACEntry
      MAX-ACCESS  not-accessible
      STATUS current
      DESCRIPTION
      "A list of FddiMAC entries. The number of entries is 
      given by the value of snmpFddiMACNumber. "
      ::= { radFddi 3 }



radFddiMACEntry OBJECT-TYPE
      SYNTAX  RadFddiMACEntry
      MAX-ACCESS  not-accessible
      STATUS  current
      DESCRIPTION
	  "An entry in table radFddiMACTable."
      INDEX   { radFddiMACSMTIndex, radFddiMACIndex }
      ::= { radFddiMACTable 1 }


RadFddiMACEntry ::=
   SEQUENCE {
      radFddiMACSMTIndex
	 Integer32,
      radFddiMACIndex
	 Integer32,
      radFddiMACStation
	 Integer32,
      radFddiMACTestResult
	 Integer32,
      radFddiMACTokenCt
	 Counter32,
      radFddiMACRingLoad
	 Integer32,            
      radFddiMACRingLoadBuffer
	 OCTET STRING,            
      radFddiMACRingLoadTrsh 
	 Integer32,
      radFddiMACRingLoadPeak 
	 Integer32,
      radFddiMACDownstreamNbr
	 OCTET STRING,
      radFddiMACRingStatus
	 INTEGER,
      radFddiMACRingUtilization
	 Integer32,
      radFddiMACRingPeakUtilization
	 Integer32
      }

 

radFddiMACSMTIndex OBJECT-TYPE  
      SYNTAX  Integer32 (1..65535)
      MAX-ACCESS  read-only 
      STATUS  current
      DESCRIPTION
      "The value of the SMT index associated with this MAC."
      ::= { radFddiMACEntry 1 }



radFddiMACIndex OBJECT-TYPE  
      SYNTAX  Integer32 (1..65535)
      MAX-ACCESS  read-only 
      STATUS  current
      DESCRIPTION
      "A unique value for each MAC. Its value ranges 
      between 1 and the value of snmpFddiMACNumber."
      ::= { radFddiMACEntry 2 }


radFddiMACStation OBJECT-TYPE  
      SYNTAX  Integer32 (1..65535)
      MAX-ACCESS  read-only 
      STATUS  current
      DESCRIPTION
      "Indicates the Station inside the box to which the
      current MAC belongs. Its value ranges 
      between 1 and the value of radFddiStationNumber."
      ::= { radFddiMACEntry 3 }

radFddiMACTestResult OBJECT-TYPE  
      SYNTAX  Integer32 
      MAX-ACCESS  read-only
      STATUS  current
      DESCRIPTION
      " Indicates the result of a test performed on MAC.
      The value is a sum. It takes the value 0 if the result of the
      test is OK and if faults occur, 2 raised to a power is added 
      to the sum. The powers are according to the following table:
	     Fault       Power
      cardConfigError     0
      GeneralError        1
      MACError            2 "
      ::= { radFddiMACEntry 4 }

radFddiMACTokenCt OBJECT-TYPE
      SYNTAX Counter32
      MAX-ACCESS read-only
      STATUS current
      DESCRIPTION
      "Token Counts - Refer to ANSI MAC {73}."
      ::= { radFddiMACEntry 5 }
      
radFddiMACRingLoad OBJECT-TYPE 
      SYNTAX  Integer32             
      MAX-ACCESS  read-only
      STATUS  current
      DESCRIPTION
      "Current traffic value. The
       traffic is expressed in percents of the maximum FDDI traffic 
       in the range 1..20, expressed on a log(10) 
      scale ( value = 10*log10(percent) )."
      ::= { radFddiMACEntry 6 }

radFddiMACRingLoadBuffer OBJECT-TYPE
      SYNTAX  OCTET STRING
      MAX-ACCESS  read-only
      STATUS  current
      DESCRIPTION
      "Record of traffic for the last second with a resolution of 100 msec. The
       traffic is expressed in percents of the maximum FDDI traffic and each
      record contains 10 readings, in the range 1..20, expressed on a log(10) 
      scale ( value = 10*log10(percent) )."
      ::= { radFddiMACEntry 7 }

radFddiMACRingLoadTrsh OBJECT-TYPE 
      SYNTAX  Integer32               
      MAX-ACCESS  read-write
      STATUS  current
      DESCRIPTION
      "Traffic threshold value. When exceeded, a trap is send to the management
      console. Expressed in percents of the maximum FDDI traffic, in the 
      range 1..20, expressed on a log(10) scale."
      ::= { radFddiMACEntry 8 }

radFddiMACRingLoadPeak OBJECT-TYPE 
      SYNTAX  Integer32              
      MAX-ACCESS  read-only
      STATUS  current
      DESCRIPTION
      "Maximal traffic value since last reset of hub or relay. Expressed in per-
      cents of the maximum FDDI traffic, in the range 1..20, 
      expressed on log(10) scale."
      ::= { radFddiMACEntry 9 }

radFddiMACDownstreamNbr OBJECT-TYPE 
      SYNTAX  OCTET STRING  (SIZE (6))             
      MAX-ACCESS  read-only
      STATUS  current
      DESCRIPTION
      "The MAC's downstream neighbor's long individual MAC address. The value
      shall be reported as '00 00 00 00 00 00' if it is unknown."
      ::= { radFddiMACEntry 10 }

radFddiMACRingStatus OBJECT-TYPE 
      SYNTAX  INTEGER {
	ringUp(1),
	ringDown(2)
      }      
      MAX-ACCESS  read-only
      STATUS  current
      DESCRIPTION
      "Attribute which summs the status of the ring controlled by the current
      MAC."
      ::= { radFddiMACEntry 11 }

radFddiMACRingUtilization OBJECT-TYPE
     SYNTAX  Integer32
     MAX-ACCESS  read-only
     STATUS  current
     DESCRIPTION
     "Current traffic value. The traffic is expressed in percents of the maximum FDDI traffic." 
      ::= { radFddiMACEntry 12 }

radFddiMACRingPeakUtilization OBJECT-TYPE
     SYNTAX  Integer32
     MAX-ACCESS  read-only
     STATUS  current
     DESCRIPTION
     "Peak traffic value since las reset of the hub or relay. The traffic is expressed
     in percents of the maximum FDDI traffic." 
      ::= { radFddiMACEntry 13 }

-- the RAD FDDI Group table

radFddiGroupTable OBJECT-TYPE
      SYNTAX  SEQUENCE OF RadFddiGroupEntry
      MAX-ACCESS  not-accessible
      STATUS current
      DESCRIPTION
      "A list of FddiGroup entries. The number of entries is 
      given by the value of snmpFddiGroupNumber. "
      ::= { radFddi 4 }

radFddiGroupEntry OBJECT-TYPE
      SYNTAX  RadFddiGroupEntry
      MAX-ACCESS  not-accessible
      STATUS  current
      DESCRIPTION
	  "An entry in table radFddiGroupTable."
      INDEX   { radFddiGroupId }
      ::= { radFddiGroupTable 1 }

RadFddiGroupEntry ::=
   SEQUENCE {
      radFddiGroupId                    
	 Integer32,
      radFddiGroupRedundancy
	 INTEGER,
      radFddiGroupTopologyMode
	 INTEGER,
      radFddiGroupTestResult
	 INTEGER,
      radFddiGroupConfigStatus
	 INTEGER,
      radFddiGroupAutoRightLoop
	 INTEGER,
      radFddiGroupAutoLeftLoop
	 INTEGER,
      radFddiGroupManRightLoop
	 INTEGER,
      radFddiGroupManLeftLoop
	 INTEGER,
      radFddiGroupOpticalSwitchStatus
	 INTEGER
      }
      
radFddiGroupId OBJECT-TYPE  
      SYNTAX  Integer32         
      MAX-ACCESS  read-only
      STATUS  current
      DESCRIPTION
      "Unique ID of the group in radFddiGroupTable. Equivalent to slot number 
      in enclosures."
      ::= { radFddiGroupEntry 1 }

radFddiGroupRedundancy OBJECT-TYPE
      SYNTAX  INTEGER {
	none(1),
	double-bandwidth(2),
	backup(3)
	}
      MAX-ACCESS  read-write
      STATUS  current
      DESCRIPTION
      "This attribute shows the usage of the A/B pair of ports in Tree mode.
      If the redundancy conditions are not fulfilled, value none(1) will be
      returned.
      If backup mode port A is a standby backup of port B, otherwise each of
      them is connected to a separate bus."
      ::= { radFddiGroupEntry 2 }

radFddiGroupTopologyMode OBJECT-TYPE
      SYNTAX  INTEGER {
	none(1), 
	tree(2),
	ring(3)
	}
      MAX-ACCESS  read-only
      STATUS  current
      DESCRIPTION
      "Defines the topology mode of the FDDI PHY card."
      ::= { radFddiGroupEntry 3 }

radFddiGroupTestResult OBJECT-TYPE  
      SYNTAX  INTEGER {
	ok(1),
	faulty(2)
      }
      MAX-ACCESS  read-only
      STATUS  current
      DESCRIPTION
      "Result of test performed upon an FDDI group. A value of faulty (1)
      indicates a CPU or communication at module level."
      ::= { radFddiGroupEntry 4 }

radFddiGroupConfigStatus OBJECT-TYPE  
      SYNTAX  INTEGER {
	ok(1),
	cardConfigErrorAB(2),
	cardConfigErrorS(3),
	switchTopologyError(4)
      } 
      MAX-ACCESS  read-only
      STATUS  current
      DESCRIPTION
      " Indicates the configuration status of the module (group)."
      ::= { radFddiGroupEntry 5 }

radFddiGroupAutoRightLoop OBJECT-TYPE 
      SYNTAX  INTEGER {
	on(1),
	off(2) 
      }
      MAX-ACCESS  read-only
      STATUS  current
     DESCRIPTION
     "Value ON of this attribute signifies that a hardware loop was 
      automatically created on a FDDI module which does not sense 
      the existence of another FDDI group on the right hand side."
      ::= { radFddiGroupEntry 6 }

radFddiGroupAutoLeftLoop OBJECT-TYPE 
      SYNTAX  INTEGER {
	on(1),
	off(2) 
      }
      MAX-ACCESS  read-only
      STATUS  current
     DESCRIPTION
     "Value ON of this attribute signifies that a hardware loop was 
      automatically created on a FDDI module which does not sense 
      the existence of another FDDI group on the left hand side."
      ::= { radFddiGroupEntry 7 }


radFddiGroupManRightLoop OBJECT-TYPE 
      SYNTAX  INTEGER {
	on(1),
	off(2) 
      }
      MAX-ACCESS  read-write
      STATUS  current
     DESCRIPTION
     "Setting this attribute to ON signifies a command to the hardware 
     to create a loop on the FDDI module which isolates the ring
     from the right hand side."
      ::= { radFddiGroupEntry 8 }

radFddiGroupManLeftLoop OBJECT-TYPE 
      SYNTAX  INTEGER {
	on(1),
	off(2) 
      }
      MAX-ACCESS  read-write
      STATUS  current
     DESCRIPTION
     "Setting this attribute to ON signifies a command to the hardware 
     to create a loop on the FDDI module which isolates the ring
     from the left hand side."
      ::= { radFddiGroupEntry 9 }


radFddiGroupOpticalSwitchStatus OBJECT-TYPE  
      SYNTAX  INTEGER {
	not-present(1),
	inserted(2),
	not-inserted(3),
	present(4)
      }
      MAX-ACCESS  read-only
      STATUS  current
      DESCRIPTION
      "This attribute describes the presence of the optical switch
      and for existing optical switches describes the possibility of 
      auto-reconfiguration of path resources (MACs and
      M-ports) in the case of bus fault or connection
      disabling. If merge(2), resources will try to move 
      to another bus, if non-merge(1) resources are left
      on their dedicated bus."
      ::= { radFddiGroupEntry 10 }




radFddiPortTable OBJECT-TYPE
      SYNTAX SEQUENCE OF RadFddiPortEntry
      MAX-ACCESS not-accessible
      STATUS current 
	  DESCRIPTION
	  "."
      ::= { radFddi 5 }


radFddiPortEntry OBJECT-TYPE
      SYNTAX  RadFddiPortEntry
      MAX-ACCESS  not-accessible
      STATUS  current
      DESCRIPTION
	  "An entry in table radFddiPortTable."
      INDEX   { radFddiPortGroupID, radFddiPortID }
      ::= { radFddiPortTable 1 }

RadFddiPortEntry ::= SEQUENCE {
      radFddiPortGroupID
	 Integer32,
      radFddiPortID  
	 Integer32,
      radFddiPortTestResult
	 INTEGER,
      radFddiPortNumberOfConnectedStations
	 Integer32,
      radFddiPortConnectedStations
	 OCTET STRING,
      radFddiPortCurrentPath
	 INTEGER,
      radFddiPortFunctionalStatus
	 INTEGER
      }

radFddiPortGroupID OBJECT-TYPE
      SYNTAX  Integer32
      MAX-ACCESS  read-only
      STATUS  current
      DESCRIPTION
      "ID of group to which the FDDI card belongs."
      ::= { radFddiPortEntry 1 }

radFddiPortID OBJECT-TYPE   
      SYNTAX  Integer32
      MAX-ACCESS  read-only
      STATUS  current
      DESCRIPTION
      "Unique Id of the port in the radFddiPortEntry."
      ::= { radFddiPortEntry 2 }

radFddiPortTestResult OBJECT-TYPE  
      SYNTAX  INTEGER {
	ok(1),
	faulty(2)
      }
      MAX-ACCESS  read-only
      STATUS  current
      DESCRIPTION
      "Indicates the result of a test performed on a port." 
      ::= { radFddiPortEntry 4 }

radFddiPortNumberOfConnectedStations OBJECT-TYPE  
      SYNTAX  Integer32 
      MAX-ACCESS  read-only
      STATUS  current
      DESCRIPTION
      "Number of stations connected to the port." 
      ::= { radFddiPortEntry 5 }

radFddiPortConnectedStations OBJECT-TYPE  
      SYNTAX  OCTET STRING 
      MAX-ACCESS  read-only
      STATUS  current
      DESCRIPTION
      "This attribute displays the configuration of the stations connected 
      to the port.The FDDI addresses of the stations are displayed in ring 
      order, starting with the address of the first station connected to the
      port. The length of the string is equal to the value of
      radFddiPortNumberOfConnectedStations multiplied by 8 (length of
      FddiSMTStationIdType)." 
      ::= { radFddiPortEntry 6 }

radFddiPortCurrentPath OBJECT-TYPE
      SYNTAX INTEGER{
	isolated(1),
	local(2),
	secondary(3),
	primary(4),
	concatenated(5),
	thru(6)
	}
      MAX-ACCESS read-write
      STATUS obsolete 
      DESCRIPTION
      "Current Path in FDDI port on PHY cards."
      ::= { radFddiPortEntry 8 }
      
radFddiPortFunctionalStatus OBJECT-TYPE
      SYNTAX INTEGER{
	ok(1),
	lerAlarm(2),
	lerCutoff(3)
	}
      MAX-ACCESS read-write
      STATUS current
      DESCRIPTION
      "Fubctional status of the port according to value of link error
      estimate relative to thresholds of alarm and cutoff."
      ::= { radFddiPortEntry 9 }
      

radFddiAgn OBJECT IDENTIFIER ::= { radFddi 6 }

-- the RAD Agent Group
-- Implementation of the Agent group is current
-- for all manageable systems which support RAD Stations     
      
radFddiAgnPriSwDesc  OBJECT-TYPE    
      SYNTAX  DisplayString
      MAX-ACCESS  read-only
      STATUS  current
      DESCRIPTION
      "ASCII string for description and display of the Fddi agent software version."
      ::= { radFddiAgn 1 }



















-- 
-- file :D:\Synergy\WorkArea\545\mib_rad\txt\brggen.txt
-- 
--version 5.35
--Initial Version:   4.0
--Date:   16.10.94              
--By:       Debby Koren &  Orly Nicklass
--File:       brggen.txt

--Last update: 16-Jun-2008 By Eran Cohen
-- ----------------------------------------------------------------------------------


genBridge      OBJECT IDENTIFIER ::= {radBridges 1 }

-- At the end of the MIB there is a definition of all RAD general traps for bridges. 


radBridgeAction OBJECT-TYPE
    SYNTAX  INTEGER {
       reset(1),
       sendNetworkTab(2),
       deleteNetworkTab(3),
       sendRoutingTab(4),    -- Level II
       deleteRoutinTab(5),
       sendLanTab(6),
       deleteLanTab(7),
       deleteArpTab(8),
       sendArpTab(9),
       deleteRouteTab(10),   -- Level III
       sendRouteTab(11),
       deactivateAllMasks(12),
       saveAllActiveMasks(13),
       loadAndActivateAllMasksFromNVRAM(14),
       clearAllMasksFromNVRAM(15),
	   defaultConfig(16),
	   resetNVRAM(17),
	   clearIPNVRAM(18),
	noOp(255)
     }
    MAX-ACCESS  read-write
    STATUS  current
    DESCRIPTION
	"This variable enables the operator to perform one of the
	specified actions on the tables maintained by the network device.
	Send actions are not currently implemented.  Not all actions can 
	be performed on all bridges."
   ::= { genBridge 1  }

radBridgeInactiveArpTimeOut OBJECT-TYPE
    SYNTAX Integer32
    MAX-ACCESS  read-write
    STATUS  current
    DESCRIPTION
	"This variable defines the maximum time period that can pass
	between ARP requests concerning an entry in the ARP table.
	After this time period, the entry is deleted from the table."
    ::= { genBridge 2  }


-- radBridgeMaskTab defines the format of  RAD Bridge OLD masking tables

radBridgeMaskTable    OBJECT-TYPE
    SYNTAX  SEQUENCE  OF RadBridgeMaskEntry
    MAX-ACCESS  not-accessible
    STATUS  current
    DESCRIPTION
	"Mask tables enable definition of forwarding restrictions and 
	control of message flow in the internetwork. Each entry
	in this table defines a mask statement consisting of up to 
	three mask definitions and an action defined by 
	radBridgeMaskOper. Different types of mask entries are supported, 
	as defined by radBridgeMaskType."
    ::=  { genBridge 3 }

radBridgeMaskEntry OBJECT-TYPE
    SYNTAX  RadBridgeMaskEntry
    MAX-ACCESS  not-accessible
    STATUS  current
    DESCRIPTION
    "An entry in table radBridgeMaskTable."
    INDEX   { radBridgeMaskType, radBridgeMaskIfIndex, radBridgeMaskNum  }
    ::=  { radBridgeMaskTable 1  }

RadBridgeMaskEntry ::= SEQUENCE {
    radBridgeMaskType
     INTEGER,
    radBridgeMaskIfIndex
     Integer32,   
    radBridgeMaskNum
     Integer32,
    radBridgeMaskDest
     INTEGER,
    radBridgeMaskPat1
     OCTET STRING,
    radBridgeMaskActiveBit1
     OCTET STRING,
    radBridgeMaskFrom1
     INTEGER,
    radBridgeMaskOffset1
     Integer32,
    radBridgeMaskCond1
     INTEGER,
    radBridgeMaskPat2
     OCTET STRING,
    radBridgeMaskActiveBit2
     OCTET STRING,
    radBridgeMaskFrom2
     INTEGER,
    radBridgeMaskOffset2
     Integer32,
    radBridgeMaskCond2
     INTEGER,
    radBridgeMaskPat3
     OCTET STRING,
    radBridgeMaskActiveBit3
     OCTET STRING,
    radBridgeMaskFrom3
     INTEGER,
    radBridgeMaskOffset3
     Integer32,
    radBridgeMaskCond3
     INTEGER,
    radBridgeMaskOper
     INTEGER
    }

radBridgeMaskType  OBJECT-TYPE
    SYNTAX INTEGER {
       tx(1),
       rx(2),
       compress(3),
       priority(4),
       loadSharing(5),
       facs(6),
       codConnect(7),
	   codDisconnect(8)
      }
    MAX-ACCESS  read-only
    STATUS  current
    DESCRIPTION
	"Defines the type of mask entry."
    ::= { radBridgeMaskEntry 1  }

radBridgeMaskIfIndex  OBJECT-TYPE
    SYNTAX Integer32
    MAX-ACCESS  read-only
    STATUS  current
    DESCRIPTION 
	"Specifies the if Index of the interface to which the mask is applied."
   ::= { radBridgeMaskEntry 2  }

radBridgeMaskNum  OBJECT-TYPE
    SYNTAX Integer32
    MAX-ACCESS  read-only
    STATUS  current
    DESCRIPTION
	"The Mask entry number, defined by its line number in the mask
	table."
   ::= {  radBridgeMaskEntry 3  }

radBridgeMaskDest  OBJECT-TYPE
    SYNTAX INTEGER {
       unassigned-cond (1),
       broadcast-msge (2),
       multicast-msge (3),
       all-msge(4),
   none(5)
    }

    MAX-ACCESS  read-write
    STATUS  current
    DESCRIPTION 
	"Specifies the type of destination address carried by the frame
	to which the mask will be applied. Unassigned-condition 
	deactivates the mask entry."
    ::= {  radBridgeMaskEntry 4   }


radBridgeMaskPat1 OBJECT-TYPE
    SYNTAX OCTET STRING  -- (SIZE (2))
    MAX-ACCESS  read-write
    STATUS  current
    DESCRIPTION
	"Describes the mask field which is either a 16 bit binary pattern,
	or four digit hexadecimal pattern."
    ::= { radBridgeMaskEntry 5  }

radBridgeMaskActiveBit1  OBJECT-TYPE
    SYNTAX OCTET STRING  -- (SIZE (2))
    MAX-ACCESS  read-write
    STATUS  current
    DESCRIPTION
	"Specifies the positions of the wild card characters (*) 
	in the radBridgeMaskPat1 field."
    ::= { radBridgeMaskEntry 6  }

radBridgeMaskFrom1  OBJECT-TYPE
    SYNTAX INTEGER {
       mac(1),
       llc(2),
	   net(3)
    }
    MAX-ACCESS  read-write
    STATUS  current
    DESCRIPTION
	"Offset base of radBridgeMaskPat1 within the frame.
	 Net can be in some cases the data start point."
    ::= { radBridgeMaskEntry 7  }

radBridgeMaskOffset1  OBJECT-TYPE
    SYNTAX Integer32
    MAX-ACCESS  read-write
    STATUS  current
    DESCRIPTION
	"Specifies the radBridgeMaskPat1 offset within the frame (in bytes) from 
	the base defined in by radBridgeMaskForm1.The mask offset is an even
	decimal number in the range of 0 to 1518." 
    ::= { radBridgeMaskEntry 8  }

radBridgeMaskCond1 OBJECT-TYPE
    SYNTAX INTEGER {
       false (1),
       true (2)
    }
    MAX-ACCESS  read-write
    STATUS  current
    DESCRIPTION
	"Specifies the logical condition of the mask pattern:

	true  - Condition is valid if at the position specified by 
		radBridgeMaskOffset1 the packet contains data that matches
		the content of radBridgeMaskPat1.

	false - Condition is valid if at the position specified by 
		radBridgeMaskOffset1 the packet contains data that does not
		match the content of radBridgeMaskPat1."
    ::= {  radBridgeMaskEntry 9  }

radBridgeMaskPat2  OBJECT-TYPE
    SYNTAX OCTET STRING  --   (SIZE (2))
    MAX-ACCESS  read-write
    STATUS  current
    DESCRIPTION
	"Describes the mask field which is either a 16 bit binary pattern,
	 or four digit hexadecimal pattern."
    ::= {  radBridgeMaskEntry 10  }

radBridgeMaskActiveBit2  OBJECT-TYPE
    SYNTAX OCTET STRING  --   (SIZE (2))
    MAX-ACCESS  read-write
    STATUS  current
    DESCRIPTION
	"Specifies the positions of the wild card characters (*) 
	in the radBridgeMaskPat2 field."
    ::= {  radBridgeMaskEntry 11  }

radBridgeMaskFrom2  OBJECT-TYPE
    SYNTAX INTEGER { 
       mac (1),
       llc (2),
	   net(3)
    }
    MAX-ACCESS  read-write
    STATUS  current
    DESCRIPTION
	"Offset base of radBridgeMaskPat2 within the frame.
	 Net can be in some cases the data start point."
    ::= {  radBridgeMaskEntry 12  }

radBridgeMaskOffset2  OBJECT-TYPE
    SYNTAX Integer32
    MAX-ACCESS  read-write
    STATUS  current
    DESCRIPTION
	"Specifies the radBridgeMaskPat2 offset within the frame (in bytes) from 
	the base defined in by radBridgeMaskForm2.The mask offset is an even
	decimal number in the range of 0 to 1518." 
    ::= {  radBridgeMaskEntry 13  }

radBridgeMaskCond2 OBJECT-TYPE
    SYNTAX INTEGER { 
       false (1),
       true (2)
    }
    MAX-ACCESS  read-write
    STATUS  current
    DESCRIPTION
	"Specifies the logical condition of the mask pattern:

	true  - Condition is valid if at the position specified by 
		radBridgeMaskOffset2 the packet contains data that matches
		the content of radBridgeMaskPat2.

	false - Condition is valid if at the position specified by 
		radBridgeMaskOffset2 the packet contains data that does not
		match the content of radBridgeMaskPat2."
    ::= {  radBridgeMaskEntry 14  }

radBridgeMaskPat3 OBJECT-TYPE
    SYNTAX OCTET STRING  --   (SIZE (2))
    MAX-ACCESS  read-write
    STATUS  current
    DESCRIPTION
	"Describes the mask field which is either a 16 bit binary pattern,
	or four digit hexadecimal pattern."
    ::= {  radBridgeMaskEntry 15  }

radBridgeMaskActiveBit3 OBJECT-TYPE
    SYNTAX OCTET STRING  --   (SIZE (2))
    MAX-ACCESS  read-write
    STATUS  current
    DESCRIPTION
	"Specifies the positions of the wild card characters (*) 
	in the radBridgeMaskPat3 field."
    ::= {  radBridgeMaskEntry 16  }

radBridgeMaskFrom3 OBJECT-TYPE
    SYNTAX INTEGER { 
       mac (1),
       llc (2),
	   net (3)
    }
    MAX-ACCESS  read-write
    STATUS  current
    DESCRIPTION
	"Offset base of radBridgeMaskPat3 within the frame.
	 Net can be in some cases the data start point."
    ::= {  radBridgeMaskEntry 17  }

radBridgeMaskOffset3 OBJECT-TYPE
    SYNTAX Integer32
    MAX-ACCESS  read-write
    STATUS  current
    DESCRIPTION
	"Specifies the radBridgeMaskPat3 offset within the frame (in bytes) from 
	the base defined in by radBridgeMaskForm3. The mask offset is an even
	decimal number in the range of 0 to 1518." 
    ::= {  radBridgeMaskEntry 18  }

radBridgeMaskCond3 OBJECT-TYPE
   SYNTAX INTEGER { 
       false (1),
       true (2)
    }
    MAX-ACCESS  read-write
    STATUS  current
    DESCRIPTION
	"Specifies the logical condition of the mask pattern:

	true  - Condition is valid if at the position specified by 
		radBridgeMaskOffset3 the packet contains data that matches
		the content of radBridgeMaskPat3

	false - Condition is valid if at the position specified by 
		radBridgeMaskOffset3 the packet contains data that does not
		match the content of radBridgeMaskPat3."
    ::= {  radBridgeMaskEntry 19  }

radBridgeMaskOper OBJECT-TYPE
    SYNTAX INTEGER { 
       block (1),
       forward (2),
       route (3),
       forward-route (4),
       high-priority (5),
       noOp(6),
       delete(7)
     }
   
   
    MAX-ACCESS read-write
    STATUS current
    DESCRIPTION
	"The type of action to be taken if the frame meets the 
     conditions of the mask.
     noOp = disabled (mask remains on list, but is not active) 
	 delete = mask is removed from the list. "
    ::= {  radBridgeMaskEntry 20 }

radBridgeCOD      OBJECT IDENTIFIER ::= {genBridge 4 }

radBridgeCODParamTable OBJECT-TYPE
	SYNTAX  SEQUENCE OF RadBridgeCODEntry
	MAX-ACCESS  not-accessible
	STATUS  current
	DESCRIPTION
	       "The table of COD parameters "
	::= { radBridgeCOD 1}


radBridgeCODEntry OBJECT-TYPE
	SYNTAX RadBridgeCODEntry
	MAX-ACCESS  not-accessible
	STATUS  current
	DESCRIPTION
	       "Each radBridgeCODEntry consists of the following parameters"
	INDEX   {radBridgeCODIfIndex}
	::= { radBridgeCODParamTable 1 }


RadBridgeCODEntry ::= SEQUENCE {
	  radBridgeCODIfIndex
		Integer32,
	  radBridgeCODManualConnect
		INTEGER,
	  radBridgeCODMode
		INTEGER,
	  radBridgeCODConnectDelay
		Integer32,
	  radBridgeCODisConnectDelay
		Integer32,
	  radBridgeCODImplicitSwitch
		INTEGER,
	  radBridgeCODNumAccess
		Counter32,
	  radBridgeCODTotalConnecTime
		Integer32
 }

radBridgeCODIfIndex OBJECT-TYPE
	SYNTAX  Integer32 
	MAX-ACCESS  read-only
	STATUS  current
	DESCRIPTION
	       "The interface to which this COD entry is applicable."
	::= { radBridgeCODEntry 1 }

radBridgeCODManualConnect OBJECT-TYPE
	SYNTAX  INTEGER {
		connect(1),
		disconnect(2)
	     }
	MAX-ACCESS  read-write
	STATUS  current
	DESCRIPTION
	       "The management station can start connection manually
		by setting this parameter"
	::= { radBridgeCODEntry 2 }


radBridgeCODMode OBJECT-TYPE
	SYNTAX  INTEGER {
		answer(1),
		originate(2),
		disable(3),
	    answerAndOriginate(4)
	     }
	MAX-ACCESS  read-write
	STATUS  current
	DESCRIPTION
	     "In answer mode only one incoming call may be accepted at a time. Other nodes
	      attempting to access the local modem will receive a busy signal until the
	      connection is terminated. (Answer mode has no difficulty supporting multiple
	      remote connections to one local port, as blocking multiple incoming calls is
	      just a modem function. Originate mode, on the other
	      hand will only support a single local port to remote port connection).
	      The disable parameter disables the COD utility for this interface. 
	      Choosing any other mode will enable the COD utility."
	::= { radBridgeCODEntry 3 }

radBridgeCODConnectDelay OBJECT-TYPE
	SYNTAX  Integer32
	MAX-ACCESS  read-write
	STATUS  current
	DESCRIPTION
     "The connect delay defines the minimum time period that 
      the link must stay disconnected, between 2 succesive 
      connections (in seconds)."
	::= { radBridgeCODEntry 4 }

radBridgeCODisConnectDelay OBJECT-TYPE
	SYNTAX  Integer32
	MAX-ACCESS  read-write
	STATUS  current
	DESCRIPTION
		"The disconnect delay defines the minimum time period
		 the link must stay connected, between 2 succesive
		 disconnections (in seconds)."
	::= { radBridgeCODEntry 5 }


radBridgeCODImplicitSwitch  OBJECT-TYPE
	SYNTAX  INTEGER  {
	      enable(1),
	      disable(2)
	}
	MAX-ACCESS  read-write
	STATUS  current
	DESCRIPTION
	     "The inplicit switch allows the user to ignore implicit triggers  provided 
	      by the COD software."
--      DEFVAL  { 1 }
	::= { radBridgeCODEntry 6 }


radBridgeCODNumAccess  OBJECT-TYPE
	SYNTAX Counter32
	MAX-ACCESS read-only
	STATUS  current
	DESCRIPTION
	     "The number of successful connections that have been established since 
	      the COD has been reset."
	::= { radBridgeCODEntry 7}

radBridgeCODTotalConnecTime  OBJECT-TYPE
	SYNTAX Integer32
	MAX-ACCESS read-only
	STATUS  current
	DESCRIPTION
	     "The sum of all the connect time intervals since the COD was reset."
	::= { radBridgeCODEntry 8}




 
radBridgeCODTimeTriggerTable OBJECT-TYPE
	SYNTAX  SEQUENCE OF RadBridgeCODTimeTriggerEntry
	MAX-ACCESS  not-accessible
	STATUS  current
	DESCRIPTION
		     "The table of COD parameters "
	::= { radBridgeCOD 2 }

radBridgeCODTimeTriggerEntry  OBJECT-TYPE
	SYNTAX RadBridgeCODTimeTriggerEntry
	MAX-ACCESS not-accessible
	STATUS current
	DESCRIPTION
	      "Each radBridgeCODTimeTriggerEntry consists of the following parameters"
	INDEX   { radBridgeCODTimeIfIndex, radBridgeCODDay, radBridgeCODTimeTriggerNum }
	::= { radBridgeCODTimeTriggerTable 1 }

RadBridgeCODTimeTriggerEntry ::= SEQUENCE {
	radBridgeCODTimeIfIndex
	      Integer32,
	radBridgeCODDay
	      INTEGER,
	radBridgeCODTimeTriggerNum
	      Integer32,
	radBridgeCODTimeTriggerFrom
	      DisplayString,
	radBridgeCODTimeTriggerTo
	      DisplayString,
	radBridgeCODTimeTriggerStatus
	      INTEGER
	}

radBridgeCODTimeIfIndex OBJECT-TYPE
    SYNTAX Integer32
    MAX-ACCESS read-only
    STATUS current
    DESCRIPTION
	       "The interface to which this COD  Time Trigger  entry is applicable."
	    ::= { radBridgeCODTimeTriggerEntry 1}

radBridgeCODDay  OBJECT-TYPE
    SYNTAX  INTEGER {
	  mon(1),
	  tue(2),
	  wed(3),
	  thu(4),
	  fri(5),
	  sat(6),
	  sun(7)
	 }
    MAX-ACCESS read-only
    STATUS current
    DESCRIPTION
       " The  day of the week in which  the dial up connection operates."
    ::= { radBridgeCODTimeTriggerEntry 2 }

radBridgeCODTimeTriggerNum  OBJECT-TYPE
    SYNTAX  Integer32  (1..3)
    MAX-ACCESS read-only
    STATUS current
    DESCRIPTION
       " Every day of the week the user can configure 3 dial up connections."
   ::= { radBridgeCODTimeTriggerEntry 3 }

radBridgeCODTimeTriggerFrom  OBJECT-TYPE
    SYNTAX DisplayString
    MAX-ACCESS read-write
    STATUS current
    DESCRIPTION
       "Time to start Dial Up connection, in format hh:mm."
    ::= {radBridgeCODTimeTriggerEntry 4 }

radBridgeCODTimeTriggerTo  OBJECT-TYPE
    SYNTAX DisplayString
    MAX-ACCESS read-write
    STATUS current
    DESCRIPTION
       "Time to terminate Dial Up connection, in format HH:MM."
 ::= {radBridgeCODTimeTriggerEntry 5 }

radBridgeCODTimeTriggerStatus OBJECT-TYPE
	     SYNTAX  INTEGER {
		  valid(1),
		  invalid(2)           
	    }
	     MAX-ACCESS  read-write
	     STATUS  current
	     DESCRIPTION
	       "The status of a table entry."
   ::= { radBridgeCODTimeTriggerEntry  6 }

radBridgeCODTraffic  OBJECT IDENTIFIER ::= { radBridgeCOD 3}

radBridgeCODTrafficTable OBJECT-TYPE
	SYNTAX  SEQUENCE OF RadBridgeCODTrafficEntry
	MAX-ACCESS  not-accessible
	STATUS  current
	DESCRIPTION
	       "The table of COD Traffic trigger "
	::= { radBridgeCODTraffic 1 }

radBridgeCODTrafficEntry OBJECT-TYPE
	SYNTAX RadBridgeCODTrafficEntry
	MAX-ACCESS  not-accessible
	STATUS  current
	DESCRIPTION
	       "Each radBridgeCODTrafficEntry consists of the following parameters."
	INDEX {radBridgeCODProtocolType}
	::= { radBridgeCODTrafficTable 1}


RadBridgeCODTrafficEntry ::= SEQUENCE {
	  radBridgeCODProtocolType
		INTEGER,
	  radBridgeCODTrafficTriggerStatus
		INTEGER }


radBridgeCODProtocolType OBJECT-TYPE
	SYNTAX INTEGER {
		ip(1),
		ipx(2),
		other(3)
}                                   
 
	MAX-ACCESS  read-only
	STATUS  current
	DESCRIPTION
		"The Protocol Type of the Traffic Table"
	::= { radBridgeCODTrafficEntry 1 }


radBridgeCODTrafficTriggerStatus OBJECT-TYPE
	SYNTAX INTEGER {
		enable(1),
		disable(2) 
}
	MAX-ACCESS  read-write
	STATUS  current
	DESCRIPTION
		"Command of Status of the Protocol Traffic Trigger"
	::= { radBridgeCODTrafficEntry 2 }


radBridgeCODRemoteIPAddr  OBJECT-TYPE
	SYNTAX IpAddress
	MAX-ACCESS  read-write
	STATUS  current
	DESCRIPTION
		" This is the Remote IP Address"
	::= { radBridgeCODTraffic 2 }


radBridgeCODIPMask  OBJECT-TYPE
	SYNTAX IpAddress
	MAX-ACCESS  read-write
	STATUS  current
	DESCRIPTION
		" This is the Mask of the Remote IP Address"
	::= { radBridgeCODTraffic 3 }

radBridgeCODTrafficTriggerProtType OBJECT-TYPE
	SYNTAX  OCTET STRING
	MAX-ACCESS  read-write
	STATUS  current
	DESCRIPTION
		"Protocol Type for the User Defined Protocol Traffic Trigger (3)."
	::= { radBridgeCODTraffic 4 }


--COD Condition table

radBridgeCODCondTable OBJECT-TYPE
	SYNTAX  SEQUENCE OF RadBridgeCODCondEntry
	MAX-ACCESS  not-accessible
	STATUS  current
	DESCRIPTION
	       "The table of COD Condition parameters "
	::= { radBridgeCOD 4}


radBridgeCODCondEntry OBJECT-TYPE
	SYNTAX RadBridgeCODCondEntry
	MAX-ACCESS  not-accessible
	STATUS  current
	DESCRIPTION
	       "Each radBridgeCODCondEntry consists of the following parameters"
	INDEX   {radBridgeCODCondIfIndex}
	::= { radBridgeCODCondTable 1 }


RadBridgeCODCondEntry ::= SEQUENCE {
	  radBridgeCODCondIfIndex 
	  	Integer32, 
	  radBridgeCODOriginateConnectCondition 
	  	INTEGER, 
	  radBridgeCODOriginateDisConnectCondition
	  	INTEGER,
	  radBridgeCODOriginateDisConnectDelay
	  	Integer32, 
	  radBridgeCODAnswerConnectCondition
	  	INTEGER, 
      radBridgeCODSpecificOnTrafficOIDCondition
        OBJECT IDENTIFIER, 
      radBridgeCODDisConnectMinimunFramesNumber
        Integer32 



  }


radBridgeCODCondIfIndex OBJECT-TYPE
	SYNTAX  Integer32 
	MAX-ACCESS  read-only
	STATUS  current
	DESCRIPTION
	"The interface, this COD entry is applicable to."
	::= { radBridgeCODCondEntry 1 }
   
radBridgeCODOriginateConnectCondition OBJECT-TYPE
	SYNTAX  INTEGER {
               onPowerOn           (1),
               whenAnyStationOnLan (2),
               onTraffic           (3),
               onManualConnect     (4)
               }
	MAX-ACCESS  read-write
	STATUS  current
	DESCRIPTION
	     " This condition, allows the user to specify the 
	       condition under which the link is connected.
           The options are
                  onPowerOn           - On power on.
                  whenAnyStationOnLan - When any station on lan.
                  onTraffic           - On traffic. The user can specify the 
                                        condition/s for connection.
                                        The connection will be defined in
                                        CODSpecificOnTrafficConditionOID .
                  onManualConnect     - depends on radBridgeCODManualConnect 
                                        OBJECT-TYPE (=connect).
                  "
	::= { radBridgeCODCondEntry 2 }
   
radBridgeCODOriginateDisConnectCondition OBJECT-TYPE
	SYNTAX  INTEGER {
               noStationOnLan                 (1),
               onTraffic                      (2),
               onDelayFromConnectionOnRequest (3),
               onManualDisConnect             (4)
               }
	MAX-ACCESS  read-write
	STATUS  current
	DESCRIPTION
	     "This condition allows the user to specify the 
	      condition under which the link is disconnected.
          The options are: 
                  noStationOnLan - When there is no station on lan.
                                   Counts 15 minutes from the point the last 
                                   frame from lan has been received. If no 
                                   frame have been transmitted on lan by the 
                                   end of this period, disconnect the connection.
                  onTraffic      - On traffic. The user can specify the 
                                   condition/s for disconnection.
                                   The disconnection will be defined in
                                   CODSpecificOnTrafficConditionOID .
                  onDelayFromConnectionOnRequest - 
                                   On Delay From Connection On Request .
                                   The delay time period will be defined in
                                   CODOriginateDisConnectDelay . 
                  onManualDisConnect - depends on radBridgeCODManualConnect 
                                    OBJECT-TYPE (=disconnect).
                  "
	::= { radBridgeCODCondEntry 3 }

radBridgeCODOriginateDisConnectDelay OBJECT-TYPE
	SYNTAX  Integer32 
	MAX-ACCESS  read-write
	STATUS  current
	DESCRIPTION
             "Delay time in seconds. "
	::= { radBridgeCODCondEntry 4 }

radBridgeCODAnswerConnectCondition OBJECT-TYPE
	SYNTAX  INTEGER {
               onPowerOn           (1),
               whenAnyStationOnLan (2),
               onTraffic           (3),
               onManualConnect     (4)
               }
	MAX-ACCESS  read-write
	STATUS  current
	DESCRIPTION
	     "CODCondAnswerConnect allows the user to specify 
	      the condition under which the link is connected.
          The options are: 
                  onPowerOn           - On power on.
                  whenAnyStationOnLan - When any station on lan.
                  onTraffic           - On traffic. The user can specify the 
                                        condition/s for connection.
                                        The connection will be defined in
                                        CODSpecificOnTrafficConditionOID .
                  onManualConnect     - depends on radBridgeCODManualConnect 
                                        OBJECT-TYPE .
             "     
	::= { radBridgeCODCondEntry 5 }


radBridgeCODSpecificOnTrafficOIDCondition OBJECT-TYPE
        SYNTAX  OBJECT IDENTIFIER
        MAX-ACCESS  read-only
        STATUS  current
        DESCRIPTION
             "A reference to a specific entry in the
			  radBridgeMaskTable, which describes the 
              particular COD condition .
              If Connect or Disconnect Conditions are not 
              onTraffic, its value should be set to the 
              OBJECT IDENTIFIER { 0 0 }. "
	::= { radBridgeCODCondEntry 6 }


radBridgeCODDisConnectMinimunFramesNumber OBJECT-TYPE
        SYNTAX Integer32
        MAX-ACCESS  read-write
        STATUS  current
        DESCRIPTION
             "Frames rate."
	::= { radBridgeCODCondEntry 7 }

--The IPX following objects define the Spoofing 

radBridgeIPX      OBJECT IDENTIFIER ::= {genBridge 5 }


radBridgeIPXdriver      OBJECT IDENTIFIER ::=  {radBridgeIPX 1 }
radBridgeIPXRip          OBJECT IDENTIFIER ::=  {radBridgeIPX 2 }
radBridgeIPXSap         OBJECT IDENTIFIER ::=  {radBridgeIPX 3 }

radBridgeIPXForwarding OBJECT-TYPE
    SYNTAX  INTEGER {
	forwarding(1),
       not-forwarding(2)
       }
    MAX-ACCESS  read-write      
    STATUS  current
    DESCRIPTION
       "The indication of whether this entity is acting as an IPX
       gateway in respect to the forwarding of datagrams received by,
       but not addressed to, this entity.  IPX gateways forward
       datagrams.  IPX hosts do not.  Note that changing this parameter 
       requiers RESET of the router."
--      DEFVAL  { 1 }
    ::= { radBridgeIPXdriver 1 }

radBridgeIPXRipOutPackets OBJECT-TYPE
    SYNTAX  Counter32
    MAX-ACCESS  read-only
    STATUS  current
    DESCRIPTION
       "The total number of packets transmitted by RIP."
    ::= { radBridgeIPXRip 1 }
    
radBridgeIPXRipInPackets OBJECT-TYPE
    SYNTAX  Counter32
    MAX-ACCESS  read-only
    STATUS  current
    DESCRIPTION
       "The total number of packets received by RIP.  This will include
       any packets that are subsequently discarded."
    ::= { radBridgeIPXRip 2 }
    
radBridgeIPXRipInDiscards OBJECT-TYPE
    SYNTAX  Counter32
    MAX-ACCESS  read-only
    STATUS  current
    DESCRIPTION
       "The number of received packets discarded by RIP."
    ::= { radBridgeIPXRip 3 }
    
radBridgeIPXRipTblNoOfEntries OBJECT-TYPE
    SYNTAX  Integer32
    MAX-ACCESS  read-only
    STATUS  current
    DESCRIPTION
       "The max number of entries that exist in the RIP routing table."
    ::= { radBridgeIPXRip 4 }
    
radBridgeIPXRipTblBcastTrigUpdateInterval OBJECT-TYPE
    SYNTAX  Integer32
    MAX-ACCESS  read-write
    STATUS  current
    DESCRIPTION
       "The default time interval (in seconds)between triggered RIP updates on 
       a broadcast type interface.  A triggered update occurs when a change is 
       detected in the routing database.  This time interval delays the 
       broadcasting of these updates so that changes on the network will 
       not result in a lot of triggered updates."
    ::= { radBridgeIPXRip 5 }
  

 
radBridgeIPXRipTable OBJECT-TYPE
    SYNTAX  SEQUENCE OF RadBridgeIPXRipTableEntry
    MAX-ACCESS  not-accessible
    STATUS  current
    DESCRIPTION
       "The routing table used by RIP to calculate routes to remote
       desination networks."
    ::= { radBridgeIPXRip 6 }
    
radBridgeIPXRipTableEntry OBJECT-TYPE
    SYNTAX  RadBridgeIPXRipTableEntry
    MAX-ACCESS  not-accessible
    STATUS  current
    DESCRIPTION
       "The routing information for one of this entity's destination networks."
    INDEX   { radBridgeIPXRipDestNetwork, 
	      radBridgeIPXRipPolicy }
    ::= { radBridgeIPXRipTable 1 }
    
RadBridgeIPXRipTableEntry ::= SEQUENCE {
radBridgeIPXRipDestNetwork
     OCTET STRING,
radBridgeIPXRipPolicy
     INTEGER,
radBridgeIPXRipForwardingRouter
     OCTET STRING,
radBridgeIPXRipNIC
     Integer32,
radBridgeIPXRipTickMetric
     Integer32,
radBridgeIPXRipHopMetric
     Integer32,
radBridgeIPXRipAgingTime
     TimeTicks,
radBridgeIPXRipValueStatus
     INTEGER,
radBridgeIPXRipForwardType
     INTEGER
}

radBridgeIPXRipDestNetwork OBJECT-TYPE
    SYNTAX  OCTET STRING (SIZE(4))
    MAX-ACCESS  read-only
    STATUS  current
    DESCRIPTION
	 "The destination network address to which this entry's
	  routing information pertains."
    ::= {radBridgeIPXRipTableEntry 1 }
    
radBridgeIPXRipPolicy OBJECT-TYPE
    SYNTAX  INTEGER  {
	main(1),
	alternate(2)
    }
    MAX-ACCESS  read-only
    STATUS  current
    DESCRIPTION
       "A value specifying the precidence of the route.  A value of
       zero means that the route is the best route, a value of one
       means that the route is the second best route and so on."
    ::= { radBridgeIPXRipTableEntry 2 }
    
radBridgeIPXRipForwardingRouter OBJECT-TYPE
    SYNTAX  OCTET STRING (SIZE(6))
    MAX-ACCESS  read-write
    STATUS  current
    DESCRIPTION
       "The IPX node address of the next hop (router) for the
       entry's associated destination network."
    ::= { radBridgeIPXRipTableEntry 3 }
    
radBridgeIPXRipNIC OBJECT-TYPE
    SYNTAX  Integer32 
    MAX-ACCESS  read-write
    STATUS  current
    DESCRIPTION
       "An interface identifier specifying what IPX interface the
       next hop can be found on."
    ::= { radBridgeIPXRipTableEntry 4 }
    
radBridgeIPXRipTickMetric OBJECT-TYPE
    SYNTAX  Integer32
    MAX-ACCESS  read-write
    STATUS  current
    DESCRIPTION
       "The metric, in terms of transit time, associated with the route
       given by the entry.  This time is in terms of 1/18ths of a
       second."
    ::= { radBridgeIPXRipTableEntry 5 }
    
radBridgeIPXRipHopMetric OBJECT-TYPE
    SYNTAX  Integer32
    MAX-ACCESS  read-write
    STATUS  current
    DESCRIPTION
       "The metric, in terms of distance , associated with the route
	given by the entry."
    ::= { radBridgeIPXRipTableEntry 6 }
    
    
radBridgeIPXRipAgingTime OBJECT-TYPE
    SYNTAX  TimeTicks
    MAX-ACCESS  read-only
    STATUS  current
    DESCRIPTION
      "The last time that the entry was updated.  The time will be
       provided in terms of the MIB-I object sysUpTime."
    ::= {radBridgeIPXRipTableEntry 7 }
    
radBridgeIPXRipValueStatus OBJECT-TYPE
    SYNTAX  INTEGER {
	static(1),
	dynamic(2),
	invalid(3),
	semiDynamic(4)
    }
    MAX-ACCESS  read-write
    STATUS  current
    DESCRIPTION
       "The entry status value; whether the entry is permanent (added
	statically), reachable or unreachable.  In the latter two cases
       it would be added by RIP. A semiDynamic entry is an entry
       enterd manualy by the user and can be updated by the router."
    ::= { radBridgeIPXRipTableEntry 8 }
    
radBridgeIPXRipForwardType  OBJECT-TYPE
    SYNTAX  INTEGER {
	 other    (1), -- not specified by this MIB
	 local    (2), -- local interface
	 remote   (3)  -- remote destination
     }
     MAX-ACCESS   read-write
     STATUS   current
     DESCRIPTION
	"The type of route. Note that local(2) refers to a route for which the 
	 next hop is the final destination; remote(3) refers to  a  route  
	 for which  the next  hop is not the final destination."
    ::= {radBridgeIPXRipTableEntry 9 }
    
	  
    
radBridgeIPXRipInfTable OBJECT-TYPE
     SYNTAX  SEQUENCE OF RadBridgeIPXRipInfEntry
     MAX-ACCESS  not-accessible
     STATUS  current
     DESCRIPTION
     "The RIP interface table."
     ::= { radBridgeIPXRip 7 }
    
radBridgeIPXRipInfEntry OBJECT-TYPE
     SYNTAX  RadBridgeIPXRipInfEntry
     MAX-ACCESS  not-accessible
     STATUS  current
     DESCRIPTION
	  "Each entry corresponds to one ifindex."
     INDEX   { radBridgeIPXRipInfIfIndex}
     ::= { radBridgeIPXRipInfTable 1 }
    
RadBridgeIPXRipInfEntry ::= SEQUENCE {
     radBridgeIPXRipInfIfIndex
     Integer32,
     radBridgeIPXRipInfBcastUpdate
     Integer32,
     radBridgeIPXRipInfAgeMultiplier
     Integer32
     }
    
radBridgeIPXRipInfIfIndex OBJECT-TYPE
     SYNTAX  Integer32
     MAX-ACCESS  read-only
     STATUS  current
     DESCRIPTION
	  "This value of Ifindex is same as radBridgeIPXIfIndex in the
	   IPX Interface Table."
     ::= { radBridgeIPXRipInfEntry 1 }
    
radBridgeIPXRipInfBcastUpdate OBJECT-TYPE
     SYNTAX  Integer32
     MAX-ACCESS  read-write
     STATUS  current
     DESCRIPTION
	    "The RIP periodic update interval, in seconds. Zero value
	     corresponds to infinite interval."
--     DEFVAL {60}
     ::= { radBridgeIPXRipInfEntry 2 }
    
radBridgeIPXRipInfAgeMultiplier OBJECT-TYPE
     SYNTAX  Integer32
     MAX-ACCESS  read-write
     STATUS  current
     DESCRIPTION
       "The holding multiplier for information received in RIP
       periodic updates. Zero value corresponds to infinite aging time."
--     DEFVAL {3}
     ::= { radBridgeIPXRipInfEntry 3 }

radBridgeIPXSapOutPackets OBJECT-TYPE
    SYNTAX  Counter32
    MAX-ACCESS  read-only
    STATUS  current
    DESCRIPTION
	   "The total number of packets transmitted by SAP."
    ::= { radBridgeIPXSap 1 }
    
radBridgeIPXSapInPackets OBJECT-TYPE
    SYNTAX  Counter32
    MAX-ACCESS  read-only
    STATUS  current
    DESCRIPTION
      "The total number of packets received by SAP.  This will include
       any packets that are subsequently discarded."
    ::= { radBridgeIPXSap 2 }
    
radBridgeIPXSapInDiscards OBJECT-TYPE
    SYNTAX  Counter32
    MAX-ACCESS  read-only
    STATUS  current
    DESCRIPTION
	   "The number of received packets discarded by SAP."
    ::= { radBridgeIPXSap 3 }
    
    
radBridgeIPXSapTblNoOfEntries OBJECT-TYPE
    SYNTAX  Integer32
    MAX-ACCESS  read-only
    STATUS  current
    DESCRIPTION
	   "The max number of entries that exist in the SAP Server
    Information table."
    ::= { radBridgeIPXSap 4 }
    
radBridgeIPXSapTblBcastTrigUpdateInterval OBJECT-TYPE
    SYNTAX  Integer32
    MAX-ACCESS  read-write
    STATUS  current
    DESCRIPTION
       "The default time interval (in seconds) between triggered SAP updates on a
	broadcast style interface.  A triggered update occurs when a
	change is detected in the service database.  This time interval
	delays the transmission of these updates so that changes on the
	network will not result in a lot of triggered updates."
    ::= { radBridgeIPXSap 5 }
        
    
   
radBridgeIPXSapTable OBJECT-TYPE
    SYNTAX  SEQUENCE OF RadBridgeIPXSapTableEntry
    MAX-ACCESS  not-accessible
    STATUS  current
    DESCRIPTION
	   "The Server Information table is used by SAP to store information
	   of services which are available on the internetwork."
    ::= { radBridgeIPXSap 6 }
    
radBridgeIPXSapTableEntry OBJECT-TYPE
    SYNTAX  RadBridgeIPXSapTableEntry
    MAX-ACCESS  not-accessible
    STATUS  current
    DESCRIPTION
       "The server information for one of this entity's server entries."
    INDEX   { radBridgeIPXSapServerType,
	  radBridgeIPXSapName }
    ::= { radBridgeIPXSapTable 1 }

RadBridgeIPXSapTableEntry ::= SEQUENCE {
    radBridgeIPXSapServerType
	Integer32,
    radBridgeIPXSapName
	DisplayString,
    radBridgeIPXSapNetwork
	OCTET STRING,
    radBridgeIPXSapNode
	OCTET STRING,
    radBridgeIPXSapSocket
	Integer32,
    radBridgeIPXSapHopsToServer
	Integer32,
    radBridgeIPXSapNIC
	Integer32,
    radBridgeIPXSapAgingTime
	TimeTicks,
   radBridgeIPXSapStatus
	INTEGER 
    }
    
radBridgeIPXSapServerType OBJECT-TYPE
    SYNTAX  Integer32
    MAX-ACCESS  read-only
    STATUS  current
    DESCRIPTION
	   "The type of the server for which this entry pertains."
    ::= { radBridgeIPXSapTableEntry 1 }
    
radBridgeIPXSapName OBJECT-TYPE
    SYNTAX  DisplayString (SIZE(48))
    MAX-ACCESS  read-only
    STATUS  current
    DESCRIPTION
	   "The name of the server for which this entry pertains."
    ::= { radBridgeIPXSapTableEntry 2 }
    
radBridgeIPXSapNetwork OBJECT-TYPE
    SYNTAX  OCTET STRING (SIZE(4))
    MAX-ACCESS  read-write
    STATUS  current
    DESCRIPTION
	   "The IPX network address of the host on which this server exists."
    ::= { radBridgeIPXSapTableEntry 3 }
    
radBridgeIPXSapNode OBJECT-TYPE
    SYNTAX  OCTET STRING (SIZE(6))
    MAX-ACCESS  read-write
    STATUS  current
    DESCRIPTION
	   "The IPX node address of the host on which this server exists."
    ::= { radBridgeIPXSapTableEntry 4 }
    
radBridgeIPXSapSocket OBJECT-TYPE
    SYNTAX  Integer32
    MAX-ACCESS  read-write
    STATUS  current
    DESCRIPTION
	   "The IPX socket number that is being used by the server to
	   which this entry pertains."
    ::= { radBridgeIPXSapTableEntry 5 }
    
radBridgeIPXSapHopsToServer OBJECT-TYPE
    SYNTAX  Integer32 (1..16)
    MAX-ACCESS  read-write
    STATUS  current
    DESCRIPTION
       "The number of hops to the entity on which this server exists."
    ::= { radBridgeIPXSapTableEntry 6 }
    
radBridgeIPXSapNIC OBJECT-TYPE
    SYNTAX  Integer32 
    MAX-ACCESS  read-write
    STATUS  current
    DESCRIPTION
       "An Network Interface Card identifier specifying what IPX 
	interface the next hop can be found on."
    ::= { radBridgeIPXSapTableEntry 7 }
    
radBridgeIPXSapAgingTime OBJECT-TYPE
    SYNTAX  TimeTicks
    MAX-ACCESS  read-only
    STATUS  current
    DESCRIPTION
       "The last time that the entry was updated.  The time will be
	provided in terms of the MIB-I object sysUpTime."
    ::= { radBridgeIPXSapTableEntry 8 }
    
radBridgeIPXSapStatus OBJECT-TYPE
    SYNTAX  INTEGER {
    permanent(1),
    dynamic(2),
    invalid(3),
    semiDynamic(4)
    }
    MAX-ACCESS  read-write
    STATUS  current
    DESCRIPTION
       "The status of the entry."
    ::= { radBridgeIPXSapTableEntry 9 }
   
  

radBridgeIPXSapInfTable OBJECT-TYPE
    SYNTAX  SEQUENCE OF RadBridgeIPXSapInfEntry
    MAX-ACCESS  not-accessible
    STATUS  current
    DESCRIPTION
    "The Sap interface table."
    ::= { radBridgeIPXSap 7 }
    
radBridgeIPXSapInfEntry OBJECT-TYPE
    SYNTAX  RadBridgeIPXSapInfEntry
    MAX-ACCESS  not-accessible
    STATUS  current
    DESCRIPTION
	 "Each entry corresponds to one ifindex."
    INDEX   {radBridgeIPXSapInfIfIndex}
    ::= { radBridgeIPXSapInfTable 1 }
    
RadBridgeIPXSapInfEntry ::= SEQUENCE {
    radBridgeIPXSapInfIfIndex
    Integer32,
    radBridgeIPXSapInfBcastUpdate
    Integer32,
    radBridgeIPXSapInfAgeMultiplier
    Integer32
    }
    
radBridgeIPXSapInfIfIndex OBJECT-TYPE
    SYNTAX  Integer32
    MAX-ACCESS  read-only
    STATUS  current
    DESCRIPTION
	 "This value of Ifindex is same as radBridgeIPXIfIndex in the
	  IPX Interface Table."
    ::= { radBridgeIPXSapInfEntry 1 }
    
radBridgeIPXSapInfBcastUpdate OBJECT-TYPE
    SYNTAX  Integer32
    MAX-ACCESS  read-write
    STATUS  current
    DESCRIPTION
       "The SAP periodic update interval, in seconds. Zero value
       corresponds to infinite interval."
--    DEFVAL {60}
    ::= { radBridgeIPXSapInfEntry 2 }
    
radBridgeIPXSapInfAgeMultiplier OBJECT-TYPE
    SYNTAX  Integer32
    MAX-ACCESS  read-write
    STATUS  current
    DESCRIPTION
       "The holding multiplier for information received in SAP
       periodic updates. Zero value corresponds to infinite aging time."
--    DEFVAL {3}
    ::= { radBridgeIPXSapInfEntry 3 }


-- radMaskingTab defines the new format of RAD Bridge masking tables


GenAddress ::= OCTET STRING (SIZE(12))

newMasking     OBJECT IDENTIFIER ::= {genBridge 6 }

maskingMaxEntries OBJECT-TYPE
    SYNTAX  Integer32
    MAX-ACCESS  read-only
    STATUS  current
    DESCRIPTION
        "The maximum number of entries in the masking table."
    ::=  { newMasking 1 }


maskingCurrentEntries OBJECT-TYPE
    SYNTAX  Integer32
    MAX-ACCESS  read-only
    STATUS  current
    DESCRIPTION
        "The number of entries in the mask table."
    ::=  { newMasking 2 }

maskingTable    OBJECT-TYPE
    SYNTAX  SEQUENCE  OF MaskingEntry
    MAX-ACCESS  not-accessible
    STATUS  current
    DESCRIPTION
	    "This is the new masking scheme. 
	    Mask tables enable definition of forwarding restrictions and 
	    control of message flow in the internetwork. Each entry
	    in this table defines a mask statement and an action defined by 
	    maskingOperation."
    ::=  { newMasking 3 }
    
maskingEntry OBJECT-TYPE
    SYNTAX  MaskingEntry
    MAX-ACCESS  not-accessible
    STATUS  current
    DESCRIPTION
	    "Defines the contents of each line in the mask table."
    INDEX  { maskingType, maskingIfIndex, maskingIndex }
    ::=  { maskingTable 1 }

MaskingEntry ::= SEQUENCE {
                     maskingType
					  INTEGER,
                     maskingIfIndex
                      Integer32,
                     maskingIndex
                      Integer32,
                     maskingProtocolType
                      INTEGER,
					 maskingSmartMaskOID
					  OBJECT IDENTIFIER,
                     maskingFrameType
                      INTEGER,
                     maskingFrameTypeCondition
                      INTEGER,
                     maskingSourceAddress
                      GenAddress,
                     maskingSourceActiveBits
                      GenAddress,
                     maskingSourceMacOrNet
                        INTEGER,
                     maskingSourceCondition
                      INTEGER,
                     maskingDestAddress
                      GenAddress,
                     maskingDestActiveBits
                      GenAddress,
                     maskingDestMacOrNet
                        INTEGER,
                     maskingDestCondition
                      INTEGER,
                     maskingLowLevelProt
                      INTEGER,
                     maskingLowLevelProtCondition
                      INTEGER,
                     maskingHighLevelProt
                      Integer32,
                     maskingHighLevelProtCondition
                      INTEGER,
                     maskingPortNum
                      Integer32,
                     maskingPortNumCondition
                      INTEGER,
                     maskingOperation
                      INTEGER,
                     maskingSrcPortNum 
                      Integer32,
                     maskingSrcPortNumCondition 
                      INTEGER
                       }

   maskingType OBJECT-TYPE
    SYNTAX  INTEGER {
	  tx            (1),
	  rx            (2),
      compress(3),
      priority(4),
      loadSharing(5),
      facs(6),
      codConnect(7),
      codDisconnect(8)
     }
    MAX-ACCESS  read-only
    STATUS  current
    DESCRIPTION
        "Defines the type of mask entry. "
    ::= {    maskingEntry 1  }


   maskingIfIndex  OBJECT-TYPE
    SYNTAX Integer32
    MAX-ACCESS  read-only
    STATUS  current
    DESCRIPTION 
	"Specifies the ifIndex of the interface to which the mask is applied."
	::= {    maskingEntry 2  }
   

                  
   maskingIndex OBJECT-TYPE
    SYNTAX  Integer32
    MAX-ACCESS  read-only
    STATUS  current
    DESCRIPTION
        "An index to the masking table. This number should not be greater than maskingMaxEntries"
    ::= {    maskingEntry 3  }
                  
            
                
        
   maskingProtocolType OBJECT-TYPE
    SYNTAX  INTEGER {
    unknown     (1),
    ip          (2),
	ipx         (3),
	sna         (4),
	netbios     (5),
              apple      (6),
              dec         (7),
    all         (255)
    }			
    MAX-ACCESS  read-write
    STATUS  current
    DESCRIPTION
         "The base protocol for masking. IPX, IP, others."
    ::= {    maskingEntry 4  }


    maskingSmartMaskOID OBJECT-TYPE
	 SYNTAX  OBJECT IDENTIFIER
	 MAX-ACCESS  read-only
	 STATUS  current
	 DESCRIPTION
	      "A reference to a specific Smart mask table (old radBridgeMaskTable)
	       which enables a more specific mask type.
		   If this information is not available, its value 
		   should be set to the OBJECT IDENTIFIER { 0 0 }. "
     ::= {  maskingEntry 5  }		    

         
    maskingFrameType OBJECT-TYPE
    SYNTAX  INTEGER {
    unknown     (1),
    all         (2),
    broadcast   (3),
    multicast   (4)
    }
    MAX-ACCESS  read-write
    STATUS  current
    DESCRIPTION
        "Enables the user to decide about frame type 
          * all frame 
          * just broadcast 
          * just multicast."
    ::= {    maskingEntry 6  }

   maskingFrameTypeCondition OBJECT-TYPE
    SYNTAX  INTEGER {
    false      (1),
    true       (2)
    }
    MAX-ACCESS  read-write
    STATUS  current
    DESCRIPTION
	"Specifies the logical condition of the mask pattern:

	true  - Condition is valid if at the position specified by 
   		   maskingFrameType the packet contains data that matches
  	the content of maskingFrameType.

	fa    lse - Condition is valid if at the position specified by 
		   maskingFrameType the packet contains data that does not
    		match the content of maskingFrameType."
    ::= {    maskingEntry 7  }

   maskingSourceAddress OBJECT-TYPE
    SYNTAX  GenAddress
    MAX-ACCESS  read-write
    STATUS  current
    DESCRIPTION
       "The source address is according to the maskingMacOrNet and 
        maskingProtocolType variables. 
        In case of 'MAC' enter 6 bytes (48 bit) of source address.
        In case of 'NET' 
            if the    maskingProtocolType is IP, this is the IP address
            if the    maskingProtocolType is IPX, this is the IPX address 
                 (nnnnmmmmmmss)
                                nnnn   - IPX net address
                                mmmmmm - Node address (Mac)
                                ss     - IPX socket
        In case of 'Apple' 
                                nn - net address (4 nibbles) 
                                ss - socket (4 nibbles)."   
    ::= {    maskingEntry 8  }

   maskingSourceActiveBits OBJECT-TYPE
    SYNTAX  GenAddress
    MAX-ACCESS  read-write
    STATUS  current
    DESCRIPTION
	   "Specifies the positions of the wild card characters (*) 
	    in the    maskingSourceAddress field. Only the 1's bit will be taken in 
        considerations."
    ::= {    maskingEntry 9  }

   maskingSourceMacOrNet OBJECT-TYPE
    SYNTAX  INTEGER {
    macAddress  (1),
    netAddress  (2),
    ipRange     (3),
    appleAddress(4)
    }
    MAX-ACCESS  read-write
    STATUS  current
    DESCRIPTION
	"The variable maskingSourceAddress and maskingSourceActiveBits 
	 will be treated as MAC, or NET address.
	 -  If maskingProtocolType = 'all', 'sna', 'netbios', dec or 
		'unknown', the maskingSourceMacOrNet can be macAddress only!
	 -  If maskingProtocolType = 'ip' the 
		maskingSourceMacOrNet can be  macAddress or netAddress or 
		appleAddress. 
	 -  If maskingProtocolType = 'ipx', the 
		maskingSourceMacOrNet can be either macAddress or netAddress. 
	 -  If maskingProtocolType = 'apple', the 
		maskingSourceMacOrNet can be either macAddress or appleAddress." 
    ::= {    maskingEntry 10  }
    
   maskingSourceCondition OBJECT-TYPE
    SYNTAX  INTEGER {
    false (1),
    true (2)
    }
    MAX-ACCESS  read-write
    STATUS  current
    DESCRIPTION
	"Specifies the logical condition of the mask pattern:

	true  - Condition is valid if at the position specified by 
	           maskingSourceAddress (in conjunction with maskingSourceActiveBits) 
	        the packet contains data that matches the content of maskingSourceAddress.

	false - Condition is valid if at the position specified by 
		   maskingSourceAddress (in conjunction with maskingSourceActiveBits) 
	    	the packet contains data that does not match the content of
	        maskingSourceAddress."
    ::= {    maskingEntry 11 }
    
   maskingDestAddress OBJECT-TYPE
    SYNTAX  GenAddress
    MAX-ACCESS  read-write
    STATUS  current
    DESCRIPTION
       "If maskingFrameType = broadcast or multicast, this object
	    is NOT APPLICABLE.
	    If maskingFrameType = all or unknown, this object is 
	    applicable.
        The destination address is according to the maskingMacOrNet and maskingProtocolType variables. 
        In case of 'MAC' enter 6 bytes (48 bit) of source address.
        In case of 'NET' 
            if the    maskingProtocolType is IP, this is the IP address
            if the    maskingProtocolType is IPX, this is the IPX address 
                 (nnnnmmmmmmss)
                                nnnn   - IPX net address
                                mmmmmm - Node address (Mac)
                                ss     - IPX socket.
        In case of 'Apple' 
                                nn - net address (4 nibbles) 
                                ss - socket (4 nibbles).
        The IPX socket entered here has priority over the value of
        maskingLowLevelProt, when it is ipxRip, ipxSap or ipxSpx, 
        unless the entered IPX socket is don't care. "   
    ::= {    maskingEntry 12  }

   maskingDestActiveBits OBJECT-TYPE
    SYNTAX  GenAddress
    MAX-ACCESS  read-write
    STATUS  current
    DESCRIPTION
	   "If maskingFrameType = broadcast or multicast, this object
	    is NOT APPLICABLE.
	    If maskingFrameType = all or unknown, this object is 
	    applicable.
	    Specifies the positions of the wild card characters (*) 
	    in the    maskingDestAddress field. Only the 1's bit will be taken in 
        considerations."
    ::= {    maskingEntry 13   }

   maskingDestMacOrNet OBJECT-TYPE
    SYNTAX  INTEGER {
    macAddress  (1),
    netAddress  (2),
    ipRange     (3),
    appleAddress(4)
    }
    MAX-ACCESS  read-write
    STATUS  current
    DESCRIPTION
	"If maskingFrameType = broadcast or multicast, this object
	 is NOT APPLICABLE.
	 If maskingFrameType = all or unknown, this object is 
	 applicable.
	 -  If maskingProtocolType = 'all', 'sna', 'netbios', dec or 
		'unknown', the maskingDestMacOrNet can be macAddress only!
	 -  If maskingProtocolType = 'ip' the 
		maskingDestMacOrNet can be  macAddress or netAddress or 
		appleAddress. 
	 -  If maskingProtocolType = 'ipx', the 
		maskingDestMacOrNet can be either macAddress or netAddress. 
	 -  If maskingProtocolType = 'apple', the 
		maskingDestMacOrNet can be either macAddress or appleAddress. 
     The variable maskingDestAddress and maskingDestActiveBits will 
	 be treated as MAC, or NET address.	"
    ::= {    maskingEntry 14  }

   maskingDestCondition OBJECT-TYPE
    SYNTAX  INTEGER {
    false (1),
    true (2)
    }
    MAX-ACCESS  read-write
    STATUS  current
    DESCRIPTION
	"If maskingFrameType = broadcast or multicast, this object
	 is NOT APPLICABLE.
	 If maskingFrameType = all or unknown, this object is 
	 applicable.
	Specifies the logical condition of the mask pattern:

	true  - Condition is valid if at the position specified by 
	           maskingDestAddress (in conjunction with maskingDestActiveBits) 
	        the packet contains data that matches the content of maskingDestAddress.

	false - Condition is valid if at the position specified by 
		   maskingDestAddress (in conjunction with maskingDestActiveBits) 
		the packet contains data that does not match the content of maskingDestAddress."
    ::= {    maskingEntry 15  }

   maskingLowLevelProt OBJECT-TYPE
    SYNTAX  INTEGER {
      unknown (1), -- don't care
      ipxRip  (2), -- 0x51
      ipxSap  (3), -- 0x52
      ipxSpx  (4), -- 0x53
      ipUdp   (5), -- 0x54
      ipTcp   (6), -- 0x55
      ipIcmp  (7), -- 0x56
	ipxNcp  (8), -- 0x57
	ipxWan  (9), -- 0x58
	ipxEco (10), -- 0x59
	ipxErr (11), -- 0x5a
	ipxPep (12)  -- 0x5b 
    }
    MAX-ACCESS  read-write
    STATUS  current
    DESCRIPTION
         "This field is set in conjunction with the maskingProtocolType variable.
          This variable specifies the low level protocol.
          The IPX socket entered in maskingDestAddress has priority 
          over the value of maskingLowLevelProt, when it is ipxRip, 
          ipxSap or ipxSpx, unless the entered IPX socket is don't 
          care."
    ::= {    maskingEntry 16  }

   maskingLowLevelProtCondition OBJECT-TYPE
    SYNTAX  INTEGER {
    false  (1),
    true (2)
    }
    MAX-ACCESS  read-write
    STATUS  current
    DESCRIPTION
	"Specifies the logical condition of the mask pattern:

	true  - Condition is valid if at the position specified by 
    	   maskingLowLevelProt the packet contains data that matches
		the content of maskingLowLevelProt.

	false - Condition is valid if at the position specified by 
		   maskingLowLevelProt the packet contains data that does not
		match the content of maskingLowLevelProt."
    ::= {    maskingEntry 17  }

   maskingHighLevelProt OBJECT-TYPE
    SYNTAX  Integer32 
    MAX-ACCESS  read-write
    STATUS  current
    DESCRIPTION
         "This field is set in connection to the maskingProtocolType variable.
          This variable specifies the high level protocols (application).
          As for today it supports just IP protocol stack.
          The object's value is a sum of the following instances values 
          (selected by user):  
                     none     (0), -- don't care
    			   ftp      (1), 
    			   ftpC     (2), 
    			   telnet   (4), 
    			   smtp     (8),
    			   tftp     (16),
    			   snmp     (32),
    			   snmpTrap (64),
			       ipRip    (128),
			       www      (256),
			       email    (512),
			       dns      (1024),
                     
                     For Apple Protocol only:
                     rtmp     (2048), 
                     nbp      (4096), 
                     atp      (8192), 
                     aep      (16384), 
                     zip      (32768), 
                     adsp     (65536),
					 pap      (131072),
					 asp      (262144)
 
          Example: if ftp(1), snmp(32) and snmpTrap(64) instances 
                   were selected, the value should be 97 (=1+32+64)."
    ::= {    maskingEntry 18  }

   maskingHighLevelProtCondition OBJECT-TYPE
    SYNTAX  INTEGER {
    false  (1),
    true (2)
    }
    MAX-ACCESS  read-write
    STATUS  current
    DESCRIPTION
	"Specifies the logical condition of the mask pattern:

	true  - Condition is valid if at the position specified by 
		   maskingHighLevelProt the packet contains data that matches
		the content of    maskingHighLevelProt.

	false - Condition is valid if at the position specified by 
		   maskingHighLevelProt the packet contains data that does not
		match the content of    maskingHighLevelProt."
    ::= {    maskingEntry 19  }

   maskingPortNum OBJECT-TYPE
    SYNTAX  Integer32
    MAX-ACCESS  read-write
    STATUS  current
    DESCRIPTION
        "The port number is the same as in high level protocol. It 
         specifies the dest. port in IP case or the dest. socket 
         in case of IPX & apple protocols.
		 IP  -  This object is applicable only if none (0) value was selected in
		        maskingHighLevelProt.
         IPX -  This object is applicable only if the socket 
                entered in maskingDestAddress is 'don't care'(00) AND
			    maskingLowLevelProt is NOT ipxRip or ipxSap.
	     Apple - This option is applicable only if the socket 
                entered in maskingDestAddress is 'don't care'(00)."
    ::= {    maskingEntry 20  }

   maskingPortNumCondition OBJECT-TYPE
    SYNTAX  INTEGER  {
    false  (1),
    true (2)
    }
    MAX-ACCESS  read-write
    STATUS  current
    DESCRIPTION
	"Specifies the logical condition of the mask pattern:

	true  - Condition is valid if at the position specified by 
		   maskingPortNum the packet contains data that matches
		the content of    maskingPortNum.

	false - Condition is valid if at the position specified by 
		   maskingPortNum the packet contains data that does not
		match the content of    maskingPortNum.
	 This object is applicable only when maskingPortNum is applicable."
    ::= {    maskingEntry 21  }

 
maskingOperation OBJECT-TYPE
    SYNTAX INTEGER { 
       block         (1),
       forward       (2),
       route         (3),
       forward-route (4),
       high-priority (5),
       noOp          (6),
       delete        (7),
       smartMask     (8)
}
    MAX-ACCESS read-write
    STATUS current
    DESCRIPTION
	"The type of action to be taken if the frame meets the 
     conditions of the mask.
       noOp = disabled (mask remains on list, but is not active) 
	 delete = mask is removed from the list.
	 smartMask = the operation and destination of the mask will
	             be determined by the objects of the Smart Table 
	             (old masking table: radBridgeMaskTable). 
     If maskingType is codConnect, the 'block' value is NOT 
     allowed. 
     If maskingType is codDisconnect, the 'forward' value is NOT 
     allowed."     
     ::= {  maskingEntry 22 }    

maskingSrcPortNum OBJECT-TYPE
    SYNTAX  Integer32
    MAX-ACCESS  read-write
    STATUS  current
    DESCRIPTION
        "The source port number.
         For IP:   No Condition.
         For IPX:  This object is applicable only if the socket entered in
                   maskingSourceAddress is don't care (00) and maskingLowLevelProt
                   is NOT ipxRip or ipxSap.
         For Apple:This object is applicable only if the socket entered in
                   maskingSourceAddress is don't care (00). "
    ::= {    maskingEntry 23  }

maskingSrcPortNumCondition OBJECT-TYPE
    SYNTAX  INTEGER  {
    false  (1),
    true (2)
    }
    MAX-ACCESS  read-write
    STATUS  current
    DESCRIPTION
	"The same as 'maskingPortNumCondition'.
       Relates to source port."
    ::= {  maskingEntry 24  }
 

radBridgePerformance      OBJECT IDENTIFIER ::= {genBridge 7 }

 -- The RAD Bridge current table contains statistics being
 -- collected for the current 15 minute interval.

 radBridgeCurrentTable OBJECT-TYPE
     SYNTAX  SEQUENCE OF RadBridgeCurrentEntry
     MAX-ACCESS  not-accessible
     STATUS  current
     DESCRIPTION
             "The RAD Bridge Current table."
     ::= { radBridgePerformance 1 }

 radBridgeCurrentEntry OBJECT-TYPE
     SYNTAX  RadBridgeCurrentEntry
     MAX-ACCESS  not-accessible
     STATUS  current
     DESCRIPTION
             "An entry in the RAD Bridge Current table."
     INDEX   { radBridgeCurrentIndex }
     ::= { radBridgeCurrentTable 1 }

 RadBridgeCurrentEntry ::=
     SEQUENCE {
		radBridgeCurrentIndex								Integer32,
		radBridgeCurrentIngressFilteringDiscardedFrames		Gauge32,
		radBridgeCurrentFrameTypeDiscardedFrames			Gauge32,
		radBridgeCurrentRxCorrectFrames						Gauge32,
		radBridgeCurrentRxCorrectBytes						Gauge32,
		radBridgeCurrentRxCorrectBytesHCOverflow			Gauge32,
		radBridgeCurrentRxBcastFrames						Gauge32,
		radBridgeCurrentRxMcastFrames						Gauge32,
		radBridgeCurrentTxCorrectFrames						Gauge32,
		radBridgeCurrentTxCorrectBytes						Gauge32,
		radBridgeCurrentTxCorrectBytesHCOverflow			Gauge32,
		radBridgeCurrentTxBcastFrames						Gauge32,
		radBridgeCurrentTxMcastFrames						Gauge32,
		radBridgeCurrentTxDropFrames						Gauge32
		}

radBridgeCurrentIndex OBJECT-TYPE
    SYNTAX      Integer32
    MAX-ACCESS  read-only
    STATUS      current
    DESCRIPTION
        "The index of the Bridge interface or Bridge Port. 
        It may be ifIndex."
    ::= { radBridgeCurrentEntry 1 }

radBridgeCurrentIngressFilteringDiscardedFrames OBJECT-TYPE
    SYNTAX      Gauge32
    MAX-ACCESS  read-only
    STATUS      current
    DESCRIPTION
        "The counter associated with the number of Discarded 
        Frames upon Ingress Filtering, encountered by a Bridge
        interface in the current 15 minute interval."
    ::= { radBridgeCurrentEntry 2 }

radBridgeCurrentFrameTypeDiscardedFrames OBJECT-TYPE
    SYNTAX      Gauge32
    MAX-ACCESS  read-only
    STATUS      current
    DESCRIPTION
        "The counter associated with the number of Discarded 
        Frames upon Frame Type and Tagging Mismatch, encountered 
        by a Bridge interface in the current 15 minute interval."
    ::= { radBridgeCurrentEntry 3 }

radBridgeCurrentRxCorrectFrames OBJECT-TYPE
    SYNTAX      Gauge32
    MAX-ACCESS  read-only
    STATUS      current
    DESCRIPTION
        "The counter associated with the number of Received Correct Frames, 
         encountered by a Bridge Port in the current 15 minute interval."
    ::= { radBridgeCurrentEntry 4 }

radBridgeCurrentRxCorrectBytes OBJECT-TYPE
    SYNTAX      Gauge32
    MAX-ACCESS  read-only
    STATUS      current
    DESCRIPTION
        "The counter associated with the number of Received Correct Bytes, 
         encountered by a Bridge Port in the current 15 minute interval."
    ::= { radBridgeCurrentEntry 5 }

radBridgeCurrentRxCorrectBytesHCOverflow OBJECT-TYPE
    SYNTAX      Gauge32
    MAX-ACCESS  read-only
    STATUS      current
    DESCRIPTION
        "The counter associated with the number of times the associated
         radBridgeCurrentRxCorrectBytes counter has overflowed."
    ::= { radBridgeCurrentEntry 6 }

radBridgeCurrentRxBcastFrames OBJECT-TYPE
    SYNTAX      Gauge32
    MAX-ACCESS  read-only
    STATUS      current
    DESCRIPTION
        "The counter associated with the number of Received Broadcast Frames, 
         encountered by a Bridge Port in the current 15 minute interval."
    ::= { radBridgeCurrentEntry 7 }

radBridgeCurrentRxMcastFrames OBJECT-TYPE
    SYNTAX      Gauge32
    MAX-ACCESS  read-only
    STATUS      current
    DESCRIPTION
        "The counter associated with the number of Received Multicast Frames, 
         encountered by a Bridge Port in the current 15 minute interval."
    ::= { radBridgeCurrentEntry 8 }

radBridgeCurrentTxCorrectFrames OBJECT-TYPE
    SYNTAX      Gauge32
    MAX-ACCESS  read-only
    STATUS      current
    DESCRIPTION
        "The counter associated with the number of Transmitted Correct Frames, 
         encountered by a Bridge Port in the current 15 minute interval."
    ::= { radBridgeCurrentEntry 9 }

radBridgeCurrentTxCorrectBytes OBJECT-TYPE
    SYNTAX      Gauge32
    MAX-ACCESS  read-only
    STATUS      current
    DESCRIPTION
        "The counter associated with the number of Transmitted Correct Bytes, 
         encountered by a Bridge Port in the current 15 minute interval."
    ::= { radBridgeCurrentEntry 10 }

radBridgeCurrentTxCorrectBytesHCOverflow OBJECT-TYPE
    SYNTAX      Gauge32
    MAX-ACCESS  read-only
    STATUS      current
    DESCRIPTION
        "The counter associated with the number of times the associated
         radBridgeCurrentTxCorrectBytes counter has overflowed."
    ::= { radBridgeCurrentEntry 11 }

radBridgeCurrentTxBcastFrames OBJECT-TYPE
    SYNTAX      Gauge32
    MAX-ACCESS  read-only
    STATUS      current
    DESCRIPTION
        "The counter associated with the number of Transmitted Broadcast Frames, 
         encountered by a Bridge Port in the current 15 minute interval."
    ::= { radBridgeCurrentEntry 12 }

radBridgeCurrentTxMcastFrames OBJECT-TYPE
    SYNTAX      Gauge32
    MAX-ACCESS  read-only
    STATUS      current
    DESCRIPTION
        "The counter associated with the number of Transmitted Multicast Frames, 
         encountered by a Bridge Port in the current 15 minute interval."
    ::= { radBridgeCurrentEntry 13 }

radBridgeCurrentTxDropFrames OBJECT-TYPE
    SYNTAX      Gauge32
    MAX-ACCESS  read-only
    STATUS      current
    DESCRIPTION
        "The counter associated with the number of Transmitted Dropped Frames, 
         encountered by a Bridge Port in the current 15 minute interval."
    ::= { radBridgeCurrentEntry 14 }


--Interval Table

-- The RAD Bridge Interval table contains statistics being
-- collected by each Interface over the previous 24
-- hours of operation.  The past 24 hours are broken into 96
-- completed 15 minute intervals.

radBridgeIntervalTable OBJECT-TYPE
    SYNTAX  SEQUENCE OF RadBridgeIntervalEntry
    MAX-ACCESS  not-accessible
    STATUS  current
    DESCRIPTION
            "The RAD Bridge Interval table."
    ::= { radBridgePerformance 2 }

radBridgeIntervalEntry OBJECT-TYPE
    SYNTAX  RadBridgeIntervalEntry
    MAX-ACCESS  not-accessible
    STATUS  current
    DESCRIPTION
            "An entry in the RAD Bridge Interval table."
    INDEX   { radBridgeIntervalIndex, radBridgeIntervalNumber }
    ::= { radBridgeIntervalTable 1 }

RadBridgeIntervalEntry ::=
    SEQUENCE {
		radBridgeIntervalIndex								Integer32,
		radBridgeIntervalNumber								Integer32,
		radBridgeIntervalIngressFilteringDiscardedFrames	Gauge32,
		radBridgeIntervalFrameTypeDiscardedFrames			Gauge32,
		radBridgeIntervalRxCorrectFrames					Gauge32,
		radBridgeIntervalRxCorrectBytes						Gauge32,
		radBridgeIntervalRxCorrectBytesHCOverflow			Gauge32,
		radBridgeIntervalRxBcastFrames						Gauge32,
		radBridgeIntervalRxMcastFrames						Gauge32,
		radBridgeIntervalTxCorrectFrames					Gauge32,
		radBridgeIntervalTxCorrectBytes						Gauge32,
		radBridgeIntervalTxCorrectBytesHCOverflow			Gauge32,
		radBridgeIntervalTxBcastFrames						Gauge32,
		radBridgeIntervalTxMcastFrames						Gauge32,
		radBridgeIntervalTxDropFrames						Gauge32
		}

radBridgeIntervalIndex OBJECT-TYPE
    SYNTAX      Integer32
    MAX-ACCESS  read-only
    STATUS      current
    DESCRIPTION
    "The index of the bridge interface or Bridge Port. 
    It may be ifIndex."
    ::= { radBridgeIntervalEntry 1 }

radBridgeIntervalNumber OBJECT-TYPE
    SYNTAX  Integer32 (1..96)
    MAX-ACCESS  read-only
    STATUS  current
    DESCRIPTION
    "A number between 1 and 96, where 1 is the most
     recently completed 15 minute interval and 96 is
     the least recently completed 15 minutes interval
     (assuming that all 96 intervals exist)."
    ::= { radBridgeIntervalEntry 2 }

radBridgeIntervalIngressFilteringDiscardedFrames OBJECT-TYPE
    SYNTAX      Gauge32
    MAX-ACCESS  read-only
    STATUS      current
    DESCRIPTION
    "The counter associated with the number of Discarded 
    Frames upon Ingress Filtering, encountered by a 
    Bridge interface in one of the previous 96, individual 
    15 minute, intervals."
    ::= { radBridgeIntervalEntry 3 }

radBridgeIntervalFrameTypeDiscardedFrames OBJECT-TYPE
    SYNTAX      Gauge32
    MAX-ACCESS  read-only
    STATUS      current
    DESCRIPTION
    "The counter associated with the number of Discarded 
    Frames upon Frame Type and Tagging Mismatch, encountered 
    by a Bridge interface in one of the previous 96, individual 
    15 minute, intervals."
    ::= { radBridgeIntervalEntry 4 }

radBridgeIntervalRxCorrectFrames OBJECT-TYPE
    SYNTAX      Gauge32
    MAX-ACCESS  read-only
    STATUS      current
    DESCRIPTION
    	"The counter associated with the number of Received Correct Frames, 
    	 encountered by a Bridge Port in one of the previous 96,
    	 individual 15 minute, intervals."
    ::= { radBridgeIntervalEntry 5 }

radBridgeIntervalRxCorrectBytes OBJECT-TYPE
    SYNTAX      Gauge32
    MAX-ACCESS  read-only
    STATUS      current
    DESCRIPTION
    	"The counter associated with the number of Received Correct Bytes, 
     	 encountered by a Bridge Port in one of the previous 96,
    	 individual 15 minute, intervals."
    ::= { radBridgeIntervalEntry 6 }

radBridgeIntervalRxCorrectBytesHCOverflow OBJECT-TYPE
    SYNTAX      Gauge32
    MAX-ACCESS  read-only
    STATUS      current
    DESCRIPTION
        "The counter associated with the number of times the associated
         radBridgeIntervalRxCorrectBytes counter has overflowed."
    ::= { radBridgeIntervalEntry 7 }

radBridgeIntervalRxBcastFrames OBJECT-TYPE
    SYNTAX      Gauge32
    MAX-ACCESS  read-only
    STATUS      current
    DESCRIPTION
    	"The counter associated with the number of Received Broadcast Frames, 
     	 encountered by a Bridge Port in one of the previous 96,
    	 individual 15 minute, intervals."
    ::= { radBridgeIntervalEntry 8 }

radBridgeIntervalRxMcastFrames OBJECT-TYPE
    SYNTAX      Gauge32
    MAX-ACCESS  read-only
    STATUS      current
    DESCRIPTION
    	"The counter associated with the number of Received Multicast Frames, 
     	 encountered by a Bridge Port in one of the previous 96,
    	 individual 15 minute, intervals."
    ::= { radBridgeIntervalEntry 9 }

radBridgeIntervalTxCorrectFrames OBJECT-TYPE
    SYNTAX      Gauge32
    MAX-ACCESS  read-only
    STATUS      current
    DESCRIPTION
    	"The counter associated with the number of Transmitted Correct Frames, 
     	 encountered by a Bridge Port in one of the previous 96,
     	 individual 15 minute, intervals."
    ::= { radBridgeIntervalEntry 10 }

radBridgeIntervalTxCorrectBytes OBJECT-TYPE
    SYNTAX      Gauge32
    MAX-ACCESS  read-only
    STATUS      current
    DESCRIPTION
    	"The counter associated with the number of Transmitted Correct Bytes, 
     	 encountered by a Bridge Port in one of the previous 96,
     	 individual 15 minute, intervals."
    ::= { radBridgeIntervalEntry 11 }

radBridgeIntervalTxCorrectBytesHCOverflow OBJECT-TYPE
    SYNTAX      Gauge32
    MAX-ACCESS  read-only
    STATUS      current
    DESCRIPTION
        "The counter associated with the number of times the associated
         radBridgeIntervalTxCorrectBytes counter has overflowed."
    ::= { radBridgeIntervalEntry 12 }

radBridgeIntervalTxBcastFrames OBJECT-TYPE
    SYNTAX      Gauge32
    MAX-ACCESS  read-only
    STATUS      current
    DESCRIPTION
    	"The counter associated with the number of Transmitted Broadcast Frames, 
     	 encountered by a Bridge Port in one of the previous 96,
    	 individual 15 minute, intervals."
    ::= { radBridgeIntervalEntry 13 }

radBridgeIntervalTxMcastFrames OBJECT-TYPE
    SYNTAX      Gauge32
    MAX-ACCESS  read-only
    STATUS      current
    DESCRIPTION
    	"The counter associated with the number of Transmitted Multicast Frames, 
     	 encountered by a Bridge Port in one of the previous 96,
    	 individual 15 minute, intervals."
    ::= { radBridgeIntervalEntry 14 }

radBridgeIntervalTxDropFrames OBJECT-TYPE
    SYNTAX      Gauge32
    MAX-ACCESS  read-only
    STATUS      current
    DESCRIPTION
    	"The counter associated with the number of Transmitted Dropped Frames, 
     	 encountered by a Bridge Port in one of the previous 96,
    	 individual 15 minute, intervals."
    ::= { radBridgeIntervalEntry 15 }


radBridgePortBaseVlan      OBJECT IDENTIFIER ::= {genBridge 8 }

radBridgePortBaseVlanTable OBJECT-TYPE
    SYNTAX      SEQUENCE OF RadBridgePortBaseVlanEntry
    MAX-ACCESS  not-accessible
    STATUS      current
    DESCRIPTION
    "A table containing static configuration information for
     each VLAN configured into the device by  management.
     All entries are permanent and will
     be restored after the device is reset."
    ::= { radBridgePortBaseVlan 1 }

radBridgePortBaseVlanEntry  OBJECT-TYPE
    SYNTAX      RadBridgePortBaseVlanEntry
    MAX-ACCESS  not-accessible
    STATUS      current
    DESCRIPTION
    "Static information for a VLAN configured into the
    device by (local or network) management."
    INDEX   { radBridgePortBaseVlanCnfgIdx,radBridgePortBaseVlanIdx }
    ::= { radBridgePortBaseVlanTable 1 }

RadBridgePortBaseVlanEntry ::=
    SEQUENCE {
        radBridgePortBaseVlanCnfgIdx       Integer32,
        radBridgePortBaseVlanIdx           Integer32,
        radBridgePortBaseVlanName          SnmpAdminString,
        radBridgePortBaseVlanEgressPorts   PortList,
        radBridgePortBaseVlanVirtualGroups PortList,
        radBridgePortBaseVlanRowStatus     RowStatus,
		radBridgePortBaseVlanMng		   INTEGER
    }

radBridgePortBaseVlanCnfgIdx OBJECT-TYPE
    SYNTAX  Integer32 (1..255)
    MAX-ACCESS  not-accessible
    STATUS  current
    DESCRIPTION
    "This object indicates the Idx of the Agent Cnfg the following 
     objects refer.
     255=Temporary Cnfg (when relevant, 
     Set is done only to this configuration).
     For Agents that support only one configuration, 
     this object will be  constant=1. "
    ::= { radBridgePortBaseVlanEntry 1 }

radBridgePortBaseVlanIdx OBJECT-TYPE
    SYNTAX      Integer32
    MAX-ACCESS  not-accessible
    STATUS      current
    DESCRIPTION
    "Index of the port based VLAN."
    ::= { radBridgePortBaseVlanEntry 2 }

radBridgePortBaseVlanName OBJECT-TYPE
    SYNTAX      SnmpAdminString (SIZE (0..32))
    MAX-ACCESS  read-create
    STATUS      current
    DESCRIPTION
    "An administratively assigned string, which may be used
     to identify the the port based VLAN."
    ::= { radBridgePortBaseVlanEntry 3 }

radBridgePortBaseVlanEgressPorts OBJECT-TYPE
    SYNTAX      PortList
    MAX-ACCESS  read-create
    STATUS      current
    DESCRIPTION
    "The set of ports which are permanently assigned to the
    egress list for this port based VLAN by management.  
    The default value of this object is a string of zeros."
    ::= { radBridgePortBaseVlanEntry 4 }


radBridgePortBaseVlanVirtualGroups OBJECT-TYPE
    SYNTAX      PortList
    MAX-ACCESS  read-create
    STATUS      current
    DESCRIPTION
    "The set of Virtual Groups which are permanently assigned to
     this port based VLAN by management. 
     (read Virtual Group instead of port in PortList Textual Convention)
     The default value of this object is a string of zeros."
    ::= { radBridgePortBaseVlanEntry 5 }


radBridgePortBaseVlanRowStatus OBJECT-TYPE
    SYNTAX      RowStatus
    MAX-ACCESS  read-create
    STATUS      current
    DESCRIPTION
    "This object enable user to 
     create/delete entries in this table."
    ::= { radBridgePortBaseVlanEntry 6 }
 
radBridgePortBaseVlanMng  OBJECT-TYPE		   
   SYNTAX         INTEGER
      {
      notApplicable  (1),
	  disable		 (2),
	  enable		 (3)
   	  }
    MAX-ACCESS     read-create
    STATUS         current
    DESCRIPTION
    "This object allows user to enable/disable 
    management traffic on this VLAN.
    disable - only non-management data is allowed.
    enable  - mixture of management traffic 0with other 
              types of data is allowed."
    ::= { radBridgePortBaseVlanEntry 7 }


-- The Bridge's Ports-VLANs Memebership Table

radBridgePortVlanMemberTable OBJECT-TYPE
	SYNTAX  SEQUENCE OF RadBridgePortVlanMemberEntry
    MAX-ACCESS  not-accessible
    STATUS  current
    DESCRIPTION
	"The Bridge Ports-VLAN Membership table.
	 This table enables the user to assign:
	 - Several VLANs to a Port.
	 - Several Ports to a VLAN."
    ::= { radBridgePortBaseVlan 2 }

radBridgePortVlanMemberEntry OBJECT-TYPE
    SYNTAX  RadBridgePortVlanMemberEntry
    MAX-ACCESS  not-accessible
    STATUS  current
    DESCRIPTION
    "An entry in the Bridge Ports-VLANs Memebership table."
    INDEX   { radBridgePortVlanMemberBridgeIdx, 
    		  radBridgePortVlanMemberPortIdx, 
    		  radBridgePortVlanMemberVlanId }
    ::= { radBridgePortVlanMemberTable 1 }

RadBridgePortVlanMemberEntry ::=
    SEQUENCE {
		radBridgePortVlanMemberBridgeIdx	Integer32,
		radBridgePortVlanMemberPortIdx		Integer32,
		radBridgePortVlanMemberVlanId		Integer32,
		radBridgePortVlanMemberRowStatus	RowStatus
    }

radBridgePortVlanMemberBridgeIdx OBJECT-TYPE
    SYNTAX  Integer32
    MAX-ACCESS  read-only
    STATUS  current
    DESCRIPTION
    "This object indicates the Bridge Index."
    ::= { radBridgePortVlanMemberEntry 1 }

radBridgePortVlanMemberPortIdx OBJECT-TYPE
    SYNTAX  Integer32
    MAX-ACCESS  read-only
    STATUS  current
    DESCRIPTION
    "This object indicates the Bridge's Port Index.
     For some cases, it can be used as the Port ofIndex."
    ::= { radBridgePortVlanMemberEntry 2 }

radBridgePortVlanMemberVlanId OBJECT-TYPE
    SYNTAX  Integer32
    MAX-ACCESS  read-only
    STATUS  current
    DESCRIPTION
    "This object indicates the VLAN ID."
    ::= { radBridgePortVlanMemberEntry 3 }
	
radBridgePortVlanMemberRowStatus OBJECT-TYPE
    SYNTAX      RowStatus
    MAX-ACCESS  read-create
    STATUS      current
    DESCRIPTION
    "This object enables the user to 
     create/delete entries in this table."
    ::= { radBridgePortVlanMemberEntry 4 }

radBridgeGenCnfg      OBJECT IDENTIFIER ::= {genBridge 9 }


radBridgeGenFlowTable OBJECT-TYPE
    SYNTAX      SEQUENCE OF RadBridgeGenFlowEntry
    MAX-ACCESS  not-accessible
    STATUS      current
    DESCRIPTION
    "A table containing static configuration information for
    Bridge configured into the device by (local or
    network) management.  All entries are permanent and will
    be restored after the device is reset."
    ::= {  radBridgeGenCnfg 1 }

radBridgeGenFlowEntry  OBJECT-TYPE
    SYNTAX      RadBridgeGenFlowEntry
    MAX-ACCESS  not-accessible
    STATUS      current
    DESCRIPTION
    "Static information for a Bridge configured into the
    device by  management."
    INDEX   { radBridgeGenFlowCnfgIdx,radBridgeGenFlowIdx }
    ::= { radBridgeGenFlowTable 1 }

RadBridgeGenFlowEntry ::=
SEQUENCE
    { 
    radBridgeGenFlowCnfgIdx                    Integer32,
    radBridgeGenFlowIdx                        Integer32,
    radBridgeGenFlowRowStatus                  RowStatus,
    radBridgeGenFlowFloodOrBcastMaxRate 	   Integer32,
    radBridgeGenFlowQosMode                    INTEGER,
    radBridgeGenFlowSchedulingMode             INTEGER,
    radBridgeGenFlowBasicClassification        INTEGER,
    radBridgeGenFlowMulticastTrafficClass	   Integer32,
    radBridgeGenFlowBroadcastTrafficClass	   Integer32,
    radBridgeGenFlowUnkownUnicastTrafficClass  Integer32 
    }

radBridgeGenFlowCnfgIdx OBJECT-TYPE
    SYNTAX  Integer32 (1..2147483647)
    MAX-ACCESS  not-accessible
    STATUS  current
    DESCRIPTION
    "This object indicates the Idx of the 
     Agent Cnfg the following objects refer.
     255=Temporary Cnfg (when relevant Set is done 
     only to this configuration).
     For Agents that support only one configuration, 
     this object will be  constant=1. 
     This object can be used to carry additional indexing 
     (e.g port index) when needed."
    ::= { radBridgeGenFlowEntry 1 }

radBridgeGenFlowIdx OBJECT-TYPE
    SYNTAX      Integer32
    MAX-ACCESS  not-accessible
    STATUS      current
    DESCRIPTION
    "For Agent having more than one bridge, 
     this index may be used as bridge index "
    ::= { radBridgeGenFlowEntry 2 }

radBridgeGenFlowRowStatus OBJECT-TYPE
    SYNTAX      RowStatus
    MAX-ACCESS  read-create
    STATUS      current
    DESCRIPTION
    "This object enable user to 
     create/delete entries in this table."
    ::= { radBridgeGenFlowEntry 3 }


radBridgeGenFlowFloodOrBcastMaxRate OBJECT-TYPE
    SYNTAX      Integer32
    MAX-ACCESS  read-create
    STATUS      current
    DESCRIPTION
    "This object controls maximum Flooding or Broadcast Rate:
     Max number of multicast along with unknown 
     or flooded unicast frames allowed to enter 
     any port. 
     The number can be presented either as percentage of bandwidth, or bandwidth in Kbps.        
     Once the limit is exceeded, any multicast or flooded 
     frame entering from the port is discarded
     For RIC-155, and FCD-155 valid values are 3% , 6%, 12% 
     and 100% = No Limit"
    ::= { radBridgeGenFlowEntry 4 }


radBridgeGenFlowQosMode OBJECT-TYPE
    SYNTAX      INTEGER
    {
     notApplicable   (1),
     vlanTag         (2), -- 802.1p
     dscp            (3),
     dscpAndVlanTag  (4),
     vlanTagAndDscp  (5),
	 none			 (6),
	 tos			 (7),
	 perPort		 (8),
	 ipPrecedence    (9),
	 dsField        (10),
	 vlanTagAndTos  (11),
	 tosAndVlanTag  (12),
	 vlanTagAndIpPrecedence(13),
	 ipPrecedenceAndVlanTag(14),
	 vlanTagAndDsField     (15),
	 dsFieldAndVlanTag     (16)	  
          }
    MAX-ACCESS  read-create
    STATUS      current
    DESCRIPTION
    "This object controls Quality of Service mode.
    User may select which field(s) 
    (in case of fields -  which one has precedence) 
    will affect prioritization of data between egress queues."
    ::= { radBridgeGenFlowEntry 5 }

radBridgeGenFlowSchedulingMode  OBJECT-TYPE
    SYNTAX      INTEGER
    {
     notApplicable (1),
     wfq           (2), -- Weighted Fair Queuing
     sp            (3), -- Strict Priority
	 atmCos        (4)  --  ATM Class of Service
          }
    MAX-ACCESS  read-create
    STATUS      current
    DESCRIPTION
    "This object controls which scheduling mode is used:
     Weighted Fair Queuing (WFQ) scheme,
     Strict Priority (SP)
     or ATM CoS"
    ::= { radBridgeGenFlowEntry 6 }

radBridgeGenFlowBasicClassification  OBJECT-TYPE
    SYNTAX      INTEGER
    {
     none (2), 
     port (3)  
    }
    MAX-ACCESS  read-create
    STATUS      current
    DESCRIPTION
    "This object defines whether Classification based on Port should be
     taken into account (either as default, or in addition to other 
     classifications)."
    ::= { radBridgeGenFlowEntry 7 }

radBridgeGenFlowMulticastTrafficClass OBJECT-TYPE
    SYNTAX      Integer32
    MAX-ACCESS  read-create
    STATUS      current
    DESCRIPTION
    "The Traffic Class the received Multicast frame is mapped to."
    ::= { radBridgeGenFlowEntry 8 }

radBridgeGenFlowBroadcastTrafficClass OBJECT-TYPE
    SYNTAX      Integer32
    MAX-ACCESS  read-create
    STATUS      current
    DESCRIPTION
    "The Traffic Class the received Broadcast frame is mapped to."
    ::= { radBridgeGenFlowEntry 9 }

radBridgeGenFlowUnkownUnicastTrafficClass OBJECT-TYPE
    SYNTAX      Integer32
    MAX-ACCESS  read-create
    STATUS      current
    DESCRIPTION
    "The Traffic Class the received
     Unkonwn Unicast frame is mapped to."
    ::= { radBridgeGenFlowEntry 10 }


radBridgeDot1qVlanStaticTable OBJECT-TYPE
    SYNTAX      SEQUENCE OF RadBridgeDot1qVlanStaticEntry
    MAX-ACCESS  not-accessible
    STATUS      current
    DESCRIPTION
        "A table containing static configuration information for
        each VLAN configured into the device by (local or
        network) management.  All entries are permanent and will
        be restored after the device is reset."
    ::= { radBridgeGenCnfg 2 }

radBridgeDot1qVlanStaticEntry OBJECT-TYPE
    SYNTAX      RadBridgeDot1qVlanStaticEntry
    MAX-ACCESS  not-accessible
    STATUS      current
    DESCRIPTION
        "Static information for a VLAN configured into the
        device by (local or network) management."
    AUGMENTS   { dot1qVlanStaticEntry }
    ::= { radBridgeDot1qVlanStaticTable 1 }

RadBridgeDot1qVlanStaticEntry ::=
    SEQUENCE {
        radBridgeDot1qVlanTaggedPorts
            PortList,
        radBridgeDot1qVlanUnmodifiedPorts
            PortList,
		 radBridgeDot1qVlanSplitHorizon
		    INTEGER
            }

radBridgeDot1qVlanTaggedPorts OBJECT-TYPE
    SYNTAX      PortList
    MAX-ACCESS  read-create
    STATUS      current
    DESCRIPTION
         "The set of ports which should transmit egress packets
         for this VLAN as tagged."
    ::= { radBridgeDot1qVlanStaticEntry 1 }

radBridgeDot1qVlanUnmodifiedPorts OBJECT-TYPE
    SYNTAX      PortList
    MAX-ACCESS  read-create
    STATUS      current
    DESCRIPTION
        "The set of ports which should transmit egress packets
         for this VLAN as unmodified."
    ::= { radBridgeDot1qVlanStaticEntry 2 }

radBridgeDot1qVlanSplitHorizon OBJECT-TYPE
    SYNTAX      INTEGER
	{
	notApplicable (1),
	disable       (2),
	enable        (3) 
	}
    MAX-ACCESS  read-create
    STATUS      current
    DESCRIPTION
        "When 'enable (3)', packets having this VLAN will 
         not be switched back to other bridge ports which are 
         members of this VLAN."
    ::= { radBridgeDot1qVlanStaticEntry 3 }
     

radBridgeStatus      OBJECT IDENTIFIER ::= {genBridge 10 }

radBridgeInvBasePortTable OBJECT-TYPE
    SYNTAX  SEQUENCE OF RadBridgeInvBasePortEntry
    MAX-ACCESS  not-accessible
    STATUS  current
    DESCRIPTION
    "An inversed table to dot1dBasePortTable 
     from RFC1493 with reduced information.
     This table index is known to the NMS and 
     this way the needed information can be received
     by just one Get command, instead of searching 
     the entire dot1dBasePortTable (where it is an 
     attribute). "
    ::= { radBridgeStatus 1 }

radBridgeInvBasePortEntry OBJECT-TYPE
    SYNTAX  RadBridgeInvBasePortEntry
    MAX-ACCESS  not-accessible
    STATUS  current
    DESCRIPTION
    "The bridge port number for each bridge port 
     interface index."
     INDEX  { radBridgeInvBasePortIfIndex }
    ::= { radBridgeInvBasePortTable 1 }

RadBridgeInvBasePortEntry ::=
    SEQUENCE {
    radBridgeInvBasePortIfIndex	Integer32,
    radBridgeInvBasePort		Integer32
              }

radBridgeInvBasePortIfIndex OBJECT-TYPE
    SYNTAX  Integer32
    MAX-ACCESS  read-only
    STATUS  current
    DESCRIPTION
    "The value of the instance of the ifIndex object,
     defined in MIB-II, for the interface corresponding
     to this Bridge port."
    ::= { radBridgeInvBasePortEntry 1 }

radBridgeInvBasePort OBJECT-TYPE
    SYNTAX  Integer32
    MAX-ACCESS  read-only
    STATUS  current
    DESCRIPTION
    "The Bridge port number."
    ::= { radBridgeInvBasePortEntry 2 }

--Spanning Tree Protocol (STP)

radBridgeStp OBJECT IDENTIFIER ::= {genBridge 11 }

--Configuration Table

radBridgeStpCnfgTable OBJECT-TYPE
    SYNTAX  SEQUENCE OF RadBridgeStpCnfgEntry
    MAX-ACCESS  not-accessible
    STATUS  current
    DESCRIPTION
    "STP Configuration table. STP=Spanning Tree Protocol.  
     It includes STP configurable parameters that in BRIDGE-MIB 
     are scalars, while we need them per card/bridge/interface
	 and per different configurations."
    ::= { radBridgeStp 1 }

radBridgeStpCnfgEntry OBJECT-TYPE
    SYNTAX  RadBridgeStpCnfgEntry
    MAX-ACCESS  not-accessible
    STATUS  current
    DESCRIPTION
    "An entry in the radBridgeStpCnfgTable."
     INDEX  {radBridgeStpCnfgIdx1, radBridgeStpCnfgIdx2}
    ::= { radBridgeStpCnfgTable 1 }

RadBridgeStpCnfgEntry ::=
    SEQUENCE {
    radBridgeStpCnfgIdx1         Integer32,
    radBridgeStpCnfgIdx2         Integer32,
	radBridgeStpCnfgForwardDelay Timeout,
	radBridgeStpCnfgMaxAge       Timeout,
	radBridgeStpCnfgHelloTime	 Timeout,
	radBridgeStpCnfgPriority	 Integer32,
	radBridgeStpCnfgStpVersion   INTEGER
    }

radBridgeStpCnfgIdx1 OBJECT-TYPE
    SYNTAX  Integer32 (1..255)
    MAX-ACCESS  not-accessible
    STATUS  current
    DESCRIPTION
    "This object indicates the Index of the Agent Configuration 
     the following objects refer to.
     For Agents that support more than one configuration:
         255=Temporary Cnfg ; Set can be done only to this configuration.
     For Agents that support only one configuration, this object will be  
     constant=1."
    ::= { radBridgeStpCnfgEntry 1 }

radBridgeStpCnfgIdx2 OBJECT-TYPE
    SYNTAX      Integer32
    MAX-ACCESS  not-accessible
    STATUS      current
    DESCRIPTION
    "For Agents having the table objects per Card/Bridge/Interface
     this will be the index of the Card/Bridge/Interface used."
    ::= { radBridgeStpCnfgEntry 2 }

radBridgeStpCnfgForwardDelay OBJECT-TYPE
    SYNTAX  Timeout (400..3000)
    MAX-ACCESS  read-write 
    STATUS  current
    DESCRIPTION
    "The value that the bridge of radBridgeStpCnfgIdx2 uses for 
     Forward Delay when this bridge is acting as the root.  Note that
     the range for this parameter is related to the value of
     radBridgeStpCnfgMaxAge (according to 802.1D-1990 for the similar
     scalars of BRIDGE-MIB).  The granularity of this timer is specified 
     by 802.1D-1990 to be 1 second.
     An agent may return a badValue error if a set is attempted to a value 
     which is not a whole number of seconds."
    ::= { radBridgeStpCnfgEntry 3 }

radBridgeStpCnfgMaxAge OBJECT-TYPE
    SYNTAX  Timeout (600..4000)
    MAX-ACCESS  read-write
    STATUS  current
    DESCRIPTION
    "The value that the bridge of radBridgeStpCnfgIdx2 uses for 
     MaxAge when this bridge is acting as the root.  Note that
     the range for this	parameter is related to the value of
     radBridgeStpCnfgHelloTime (according to 802.1D-1990 for the similar
     scalars of BRIDGE-MIB). The granularity of this timer is specified 
     by 802.1D-1990 to be 1 second.
     An agent may return a badValue error if a set is attempted to a value 
     which is not a whole number of seconds."
    ::= { radBridgeStpCnfgEntry 4 }

radBridgeStpCnfgHelloTime OBJECT-TYPE
    SYNTAX  Timeout (100..1000)
    MAX-ACCESS  read-write
    STATUS  current
    DESCRIPTION
    "The value that the bridge of radBridgeStpCnfgIdx2 uses for 
     Hello Time when this bridge is acting as the root. The	granularity 
     of this timer is specified by 802.1D-1990 to be 1 second.  An agent 
     may return a badValue error if a set is attempted to a value
     which is not a whole number of seconds."
    ::= { radBridgeStpCnfgEntry 5 }

radBridgeStpCnfgPriority OBJECT-TYPE
    SYNTAX  Integer32 (0..65535)
    MAX-ACCESS  read-write
    STATUS  current
    DESCRIPTION
    "The value of the write-able portion of the Bridge ID, i.e., the first 
     two octets of the (8 octet	long) Bridge ID, per radBridgeStpCnfgIdx2
     instance."
    ::= { radBridgeStpCnfgEntry 6 }

radBridgeStpCnfgStpVersion OBJECT-TYPE
    SYNTAX      INTEGER
    {
     notApplicable (1),
     stp           (2), 
     rstp          (3)  
    }
    MAX-ACCESS  read-write
    STATUS      current
    DESCRIPTION
    "This object determines the STP version used:
     stp  - usual Spanning Tree Protocol.
     rstp - Rapid Spanning Tree Protocol."
    ::= { radBridgeStpCnfgEntry 7 }

--Status Table

radBridgeStpStatTable OBJECT-TYPE
    SYNTAX  SEQUENCE OF RadBridgeStpStatEntry
    MAX-ACCESS  not-accessible
    STATUS  current
    DESCRIPTION
    "STP Status table. STP=Spanning Tree Protocol.
     It includes STP status parameters that in BRIDGE-MIB 
     are scalars, while we need them per card/bridge/interface.
     For devices that have several configurations, this table is for Status
     of the Active configuration."
    ::= { radBridgeStp 2 }

radBridgeStpStatEntry OBJECT-TYPE
    SYNTAX  RadBridgeStpStatEntry
    MAX-ACCESS  not-accessible
    STATUS  current
    DESCRIPTION
    "An entry in the radBridgeStpStatTable."
     INDEX  {radBridgeStpStatIdx}
    ::= { radBridgeStpStatTable 1 }

RadBridgeStpStatEntry ::=
    SEQUENCE {
    radBridgeStpStatIdx            Integer32,
	radBridgeStpStatForwardDelay   Timeout,
	radBridgeStpStatMaxAge         Timeout,
	radBridgeStpStatHelloTime	   Timeout,
	radBridgeStpStatDesignatedRoot BridgeId,
	radBridgeStpStatRootCost       Integer32
    }

radBridgeStpStatIdx OBJECT-TYPE
    SYNTAX      Integer32
    MAX-ACCESS  not-accessible
    STATUS      current
    DESCRIPTION
    "For Agents having the table objects per Card/Bridge/Interface
     this will be the index of the Card/Bridge/Interface used."
    ::= { radBridgeStpStatEntry 1 }

radBridgeStpStatForwardDelay OBJECT-TYPE
    SYNTAX  Timeout
    MAX-ACCESS read-only
    STATUS  current
    DESCRIPTION
    "This time value, measured in units of hundredths of a second, 
     controls how fast a port changes its spanning state when moving 
     towards the Forwarding	state.  The value determines how long the port
     stays in each of the Listening and Learning states, which precede 
     the Forwarding state.  This value is also used, when a topology 
     change has	been detected and is underway, to age all dynamic
     entries in the Forwarding Database.  [Note that this value is 
     the one that this bridge is currently using, in contrast to
     radBridgeStpCnfgForwardDelay which is the value that this bridge 
     would start using if/when this bridge were to become the root.]"
    ::= { radBridgeStpStatEntry 2 }

radBridgeStpStatMaxAge OBJECT-TYPE
    SYNTAX  Timeout
    MAX-ACCESS  read-only
    STATUS  current
    DESCRIPTION
    "The maximum age of Spanning Tree Protocol information learned 
     from the network on any port before it is discarded, in units 
     of hundredths of a second.  This is the actual value that this
     bridge is currently using."
    ::= { radBridgeStpStatEntry 3 }

radBridgeStpStatHelloTime OBJECT-TYPE
    SYNTAX  Timeout
    MAX-ACCESS  read-only
    STATUS  current
    DESCRIPTION
    "The amount of time between the transmission of	Configuration 
     bridge PDUs by this node on any port when it is the root of 
     the spanning tree or trying to become so, in units of hundredths 
     of a second. This is the actual value that this bridge is
     currently using."
    ::= { radBridgeStpStatEntry 4 }

radBridgeStpStatDesignatedRoot OBJECT-TYPE
    SYNTAX  BridgeId
    MAX-ACCESS  read-only
    STATUS  current
    DESCRIPTION
    "The bridge identifier of the root of the spanning tree as determined 
     by the Spanning Tree Protocol as executed by this node.  This value 
     is used as	the Root Identifier parameter in all Configuration
     Bridge PDUs originated by this node."
    ::= { radBridgeStpStatEntry 5 }

radBridgeStpStatRootCost OBJECT-TYPE
    SYNTAX  Integer32
    MAX-ACCESS  read-only
    STATUS  current
    DESCRIPTION
    "The cost of the path to the root as seen from this bridge."
    ::= { radBridgeStpStatEntry 6 }


radBridgeForwardingMode OBJECT-TYPE
    SYNTAX      INTEGER
    {
     notApplicable (1),
     transparent   (2), 
     filter        (3),
	 filterTagged  (4),
	 transparentTagged  (5)
    }
    MAX-ACCESS  read-write
    STATUS      current
    DESCRIPTION
    "This object determines the Bridge Forwarding Mode:
     transparent  - Forward all frames received (not dependent on VLAN).
     filter - Filter frames received according to MAC Address.
     filterTagged = Filter frames received according to VLAN.
     transparentTagged = VLAN aware + Transparent."
    ::= {genBridge 12 }


radBridgePort      OBJECT IDENTIFIER ::= { genBridge 13 }

radBridgePortCnfgTable OBJECT-TYPE
    SYNTAX  SEQUENCE OF RadBridgePortCnfgEntry
    MAX-ACCESS  not-accessible
    STATUS  current
    DESCRIPTION
    "The Bridge Port Configuration Table."
    ::= { radBridgePort 1 }

radBridgePortCnfgEntry OBJECT-TYPE
    SYNTAX  RadBridgePortCnfgEntry
    MAX-ACCESS  not-accessible
    STATUS  current
    DESCRIPTION
    "An entry in the table."
     INDEX  { radBridgePortCnfgIdx, radBridgePortCnfgPrtIdx }
    ::= { radBridgePortCnfgTable 1 }

RadBridgePortCnfgEntry ::=
    SEQUENCE {
    radBridgePortCnfgIdx				Integer32,
	radBridgePortCnfgPrtIdx				Integer32,
	radBridgePortCnfgMaxMacAddr			Integer32,
	radBridgePortCnfgMngFlow			INTEGER,
	radBridgePortCnfgMcastMode			INTEGER,
	radBridgePortCnfgDefaultVpi			Integer32,
	radBridgePortCnfgDefaultVci		   	Integer32,
	radBridgePortCnfgStatVlanId  		Integer32,
	radBridgePortCnfgIngressMtu  		Integer32,
	radBridgePortCnfgEgressMtu  		Integer32,
	radBridgePortCnfgDot1x    		    INTEGER,	    -- Not in use. Moved to ethIftable
	radBridgePortCnfgMappingProfile		Integer32
    }

radBridgePortCnfgIdx OBJECT-TYPE
    SYNTAX      Integer32
    MAX-ACCESS  not-accessible
    STATUS      current
    DESCRIPTION
    "The first index of the table.
     It can serve for Configuration index, Bridge index or other."
    ::= { radBridgePortCnfgEntry 1 }

radBridgePortCnfgPrtIdx OBJECT-TYPE
    SYNTAX      Integer32
    MAX-ACCESS  not-accessible
    STATUS      current
    DESCRIPTION
    "This object indicates the Bridge Port index."
    ::= { radBridgePortCnfgEntry 2 }

radBridgePortCnfgMaxMacAddr OBJECT-TYPE
    SYNTAX      Integer32
    MAX-ACCESS  read-write
    STATUS      current
    DESCRIPTION
    "This object indicates the maximum number of total MAC Addresses
	 (static and learned) supported by this Bridge Port."
    ::= { radBridgePortCnfgEntry 3 }

radBridgePortCnfgMngFlow OBJECT-TYPE    
    SYNTAX  INTEGER {
		disable  (2),
		enable   (3) 
            }
    MAX-ACCESS  read-write
    STATUS      current
    DESCRIPTION
    "This object indicates whether this Bridge Port
     is dedicated for management flow."
    ::= { radBridgePortCnfgEntry 4 }

radBridgePortCnfgMcastMode OBJECT-TYPE    
    SYNTAX  INTEGER {
		flooding	(1),
		forwarding	(2) 
            }
    MAX-ACCESS  read-write
    STATUS      current
    DESCRIPTION
    "This object indicates this Bridge Port's Multicast Mode:
     flooding	(1) - flood multicast MAC addresses
	 forwarding	(2) - forward multicast MAC addresses to the subnet indicated."
    ::= { radBridgePortCnfgEntry 5 }

radBridgePortCnfgDefaultVpi OBJECT-TYPE
    SYNTAX      Integer32
    MAX-ACCESS  read-write
    STATUS      current
    DESCRIPTION
    "This object indicates the VPI of this Bridge Port's Default VCL.
     An incoming frame with priority that is not assigned to any VCL
     will be transferred to the Default VCL."
    ::= { radBridgePortCnfgEntry 6 }

radBridgePortCnfgDefaultVci OBJECT-TYPE
    SYNTAX      Integer32
    MAX-ACCESS  read-write
    STATUS      current
    DESCRIPTION
    "This object indicates the VCI of this Bridge Port's Default VCL.
     An incoming frame with priority that is not assigned to any VCL
     will be transferred to the Default VCL."
    ::= { radBridgePortCnfgEntry 7 }

radBridgePortCnfgStatVlanId OBJECT-TYPE
    SYNTAX      Integer32
    MAX-ACCESS  read-write
    STATUS      current
    DESCRIPTION
    "This object indicates the selected VlanId of the bridge port 
    on which statistics are being collected.
    0=no Statistics collected for VLAN on this bridge port."
    ::= { radBridgePortCnfgEntry 8 }

radBridgePortCnfgIngressMtu  OBJECT-TYPE
    SYNTAX     	Integer32
    MAX-ACCESS  read-write
    STATUS      current
    DESCRIPTION
    "The size of the largest packet which can be received
     on the interface, specified in octets."
    ::= { radBridgePortCnfgEntry 9 }


radBridgePortCnfgEgressMtu   OBJECT-TYPE
    SYNTAX     	Integer32
    MAX-ACCESS  read-write
    STATUS      current
    DESCRIPTION
    "The size of the largest packet which can be sent
     on the interface, specified in octets."
    ::= { radBridgePortCnfgEntry 10 }


radBridgePortCnfgDot1x       OBJECT-TYPE
    SYNTAX      INTEGER
	{
	  disabled (2),
	  enabled  (3)
	}
    MAX-ACCESS  read-write
    STATUS      current
    DESCRIPTION
    "This feature is currently supported via the variable ethIfTable.ethDot1xEnable.
    Determnines if the Port-Based Network Access Protocol
    (IEEE-802.1x)is enabled for the bridge Port."
    ::= { radBridgePortCnfgEntry 11 }

radBridgePortCnfgMappingProfile   OBJECT-TYPE
    SYNTAX       Integer32
    MAX-ACCESS   read-write
    STATUS       current
    DESCRIPTION
	"This attribute defines the Queue Mapping Profile ID(cosProfileTable) assigned 
	 to this Bridge Port."
     ::= { radBridgePortCnfgEntry 12 }


radDot1qPortVlanTable OBJECT-TYPE
    SYNTAX      SEQUENCE OF RadDot1qPortVlanEntry
    MAX-ACCESS  not-accessible
    STATUS      current
    DESCRIPTION
    "A table containing control and status
     information for VLAN configuration per port."
    ::= { radBridgeGenCnfg 3 }

radDot1qPortVlanEntry OBJECT-TYPE
    SYNTAX      RadDot1qPortVlanEntry
    MAX-ACCESS  not-accessible
    STATUS      current
    DESCRIPTION
    "Information controlling VLAN configuration for a port.  
    This is indexed by dot1dBasePort."
    AUGMENTS { dot1dBasePortEntry }
    ::= { radDot1qPortVlanTable 1 }

RadDot1qPortVlanEntry ::=
    SEQUENCE {
        radDot1qPortStacking
            INTEGER,
        radDot1qPortCopyOriginVlanPriority
            INTEGER,
		radDot1qPortDefaultVlanPriority
            Integer32,
		radDot1qPortTagStripping
            INTEGER,
		radDot1qPortEgressTagHandling
		    INTEGER,
		radDot1qPortIngressTagHandling
		    INTEGER,
		radDot1qPortReplaceVlanPriority
		    INTEGER,
		radDot1qPortVlanEthType
		    Unsigned32,
		radDot1qPortVlanCnodeLevel1Agent
			INTEGER
    }

radDot1qPortStacking OBJECT-TYPE
SYNTAX  INTEGER
	{
       notApplicable (1),
       unmodify  	 (2),
       tag        	 (3),
	   stack		 (4)
    }
    MAX-ACCESS  read-write
    STATUS  current
    DESCRIPTION
    "This object indicates the port stacking operation:
    unmodify  	 (2) = Do not add Tag.
    tag        	 (3) = Add Tag to Untagged Frames.
    stack		 (4) = Add Tag to all Frames."
    ::= { radDot1qPortVlanEntry 1 }

radDot1qPortCopyOriginVlanPriority OBJECT-TYPE
SYNTAX  INTEGER
	{
       notApplicable (1),
       no       	 (2),
       yes        	 (3) 
    }
    MAX-ACCESS  read-write
    STATUS  current
    DESCRIPTION
    "This object indicates whether use the original VLAN Priority of the frame, 
    as the priority of the VLAN added by this port."
    ::= { radDot1qPortVlanEntry 2 }

radDot1qPortDefaultVlanPriority OBJECT-TYPE
     SYNTAX  Integer32 
     MAX-ACCESS  read-write
     STATUS  current
     DESCRIPTION
     "Default VLAN Frame priority of the VLAN added by this port."
    ::= { radDot1qPortVlanEntry 3 }

radDot1qPortTagStripping OBJECT-TYPE
SYNTAX  INTEGER
	{
       notApplicable (1),
       no       	 (2),
       yes        	 (3) 
    }
    MAX-ACCESS  read-write
    STATUS  current
    DESCRIPTION
    "This object indicates whether remove a tag from the frame on this port,
     frame with double tag will remain with one tag and frame with 
     one tag will remain untagged."
    ::= { radDot1qPortVlanEntry 4 }

radDot1qPortEgressTagHandling OBJECT-TYPE
SYNTAX  INTEGER
	{
       none       	 (2),
       stacking   	 (3),
       stripping     (4) 
    }
    MAX-ACCESS  read-write
    STATUS  current
    DESCRIPTION
    "This object indicates how is the Egress VLAN Tag processed.
     It is mainly for use with Double Tagging."
    ::= { radDot1qPortVlanEntry 5 }

radDot1qPortIngressTagHandling OBJECT-TYPE
SYNTAX  INTEGER
	{
       none       	 (2),
       stacking   	 (3),
       stripping     (4) 
    }
    MAX-ACCESS  read-write
    STATUS  current
    DESCRIPTION
    "This object indicates how is the Ingress VLAN Tag processed.
     It is mainly for use with Double Tagging."
    ::= { radDot1qPortVlanEntry 6 }

radDot1qPortReplaceVlanPriority OBJECT-TYPE
	SYNTAX  INTEGER
	{
       notApplicable (1),
       no       	 (2),
       yes        	 (3) 
    }
    MAX-ACCESS  read-write
    STATUS  current
    DESCRIPTION
    "This object indicates whether for each received tagged frame on this Bridge Port -
     VLAN Priority will be replaced by another Priority.
	 no(2)  = no repacement
	 yes(3) = VLAN Priority will be replaced

     For Egate-100:
     When value is 'yes', the original Priority is replaced by the Default Priority."
    ::= { radDot1qPortVlanEntry 7 }

radDot1qPortVlanEthType OBJECT-TYPE
	SYNTAX  Unsigned32
    MAX-ACCESS  read-write
    STATUS  current
    DESCRIPTION
    "This object indicates the Ethernet Type. 
	 For some devices, it is applicable only when radDot1qPortStacking = stack."
    ::= { radDot1qPortVlanEntry 8 }

radDot1qPortVlanCnodeLevel1Agent	 OBJECT-TYPE
 	SYNTAX	INTEGER
 	{
 	   disable (2),
 	   enable  (3)
 	}
     MAX-ACCESS  read-write
     STATUS  current
     DESCRIPTION
     "Specify if a Level 1 cNode agent is enabled or not for the bridge port."
     ::= { radDot1qPortVlanEntry 9 }


radBridgeGenCfgTable OBJECT-TYPE
    SYNTAX      SEQUENCE OF RadBridgeGenCfgEntry
    MAX-ACCESS  not-accessible
    STATUS      current
    DESCRIPTION
    "A table containing Bridge configuration parameters."
    ::= {  radBridgeGenCnfg 4 }

radBridgeGenCfgEntry  OBJECT-TYPE
    SYNTAX      RadBridgeGenCfgEntry
    MAX-ACCESS  not-accessible
    STATUS      current
    DESCRIPTION
    "Describes an entry in the radBridgeGenCfgTable."
    INDEX   { radBridgeGenCfgIdx, radBridgeGenCfgIdx2 }
    ::= { radBridgeGenCfgTable 1 }

RadBridgeGenCfgEntry ::=
SEQUENCE
    { 
    radBridgeGenCfgIdx						Integer32,
    radBridgeGenCfgIdx2						Integer32,
    radBridgeGenCfgBridgeAction				INTEGER,
    radBridgeAgingTimeSec					INTEGER,
    radBridgeMngVlanId						Unsigned32,
	radBridgeLoopDetectVlanId               Unsigned32,
	radBridgeSplitHorizon					INTEGER,
	radBridgeEthType						Unsigned32
    }

radBridgeGenCfgIdx OBJECT-TYPE
    SYNTAX  Integer32 (1..255)
    MAX-ACCESS  not-accessible
    STATUS  current
    DESCRIPTION
    "This object indicates the Idx of the 
     Agent Cnfg the following objects refer.
     255=Temporary Cnfg.
     For Agents that support only one Configuration, 
     this object will be  constant=1. "
    ::= { radBridgeGenCfgEntry 1 }

radBridgeGenCfgIdx2 OBJECT-TYPE
    SYNTAX      Integer32
    MAX-ACCESS  not-accessible
    STATUS      current
    DESCRIPTION
    "For Agents having more than one bridge, 
     this index may be used as bridge index "
    ::= { radBridgeGenCfgEntry 2 }

radBridgeGenCfgBridgeAction OBJECT-TYPE
    SYNTAX  INTEGER {
       deleteLanTab(7),
	   noOp(255)
     }
    MAX-ACCESS  read-write
    STATUS  current
    DESCRIPTION
	"This variable enables the operator to perform one of the
	specified actions on the tables maintained by the Bridge.
	After performing the action, Agent will automatically 
	Set the value of this variable to noOp(255)."
    ::= { radBridgeGenCfgEntry 3 }

radBridgeAgingTimeSec OBJECT-TYPE
     SYNTAX   INTEGER (10..1000000)
     MAX-ACCESS   read-write
     STATUS   current
     DESCRIPTION
     "This variable duplicates scalar object 
     dot1dTpAgingTimeThe of BRIDGE-MIB with configuration index
     and Bridge index. 
	  
     It defines the timeout period in seconds for aging out
     dynamically learned forwarding information.
     802.1D-1990 recommends a default of 300 seconds."
     REFERENCE
     "IEEE 802.1D-1990: Section 6.7.1.1.3"
   ::= { radBridgeGenCfgEntry 4 }

radBridgeMngVlanId OBJECT-TYPE
     SYNTAX			Unsigned32
     MAX-ACCESS		read-write
     STATUS			current
     DESCRIPTION
     "This variable indicates the VLAN ID
      used for remote management traffic.
      0 = Not Applicable."
   ::= { radBridgeGenCfgEntry 5 }

radBridgeLoopDetectVlanId OBJECT-TYPE
     SYNTAX			Unsigned32
     MAX-ACCESS		read-write
     STATUS			current
     DESCRIPTION
     "This variable indicates the VLAN ID used for Loop Detection packets.
      Valid values:
      1 - 4095: VLAN ID
      0 - Means that the Loop Detection is Disabled."
   ::= { radBridgeGenCfgEntry 6 }

radBridgeSplitHorizon OBJECT-TYPE
    SYNTAX  INTEGER {
       notApplicable (1),
       disable       (2),
       enabled       (3),
	   vlanBased     (4)
            }
    MAX-ACCESS  read-write
    STATUS  current
    DESCRIPTION
	"This object configure 'split horizon' switching between bridge Ports.
	  - disable - normal (VLAN aware) bridge behavior.
	  - enable - all packets, regardless their VLAN, coming from user side
	    are blocked from being switched back to other user side bridge ports.
	  -	vlanBased  - split horizon behavior is applicable only for specific VLANs,
	    according to radBridgeDot1qVlanSplitHorizon."
   ::= { radBridgeGenCfgEntry 7 }

radBridgeEthType	 OBJECT-TYPE
	SYNTAX      Unsigned32
    MAX-ACCESS  read-write
    STATUS  current
    DESCRIPTION
    "Value of Ethertype field in Ethernet frame. 
     This field indicates which protocol is being transported 
     in an ethernet frame."
   ::= { radBridgeGenCfgEntry 8 }				  

radBridgeAgingTime OBJECT-TYPE
    SYNTAX  INTEGER {
       notApplicable (1),
       infinite(2),
       finite  (3)
            }
    MAX-ACCESS  read-write
    STATUS  current
    DESCRIPTION
	"This variable defines whether the Aging Time will be finite or infinite.
	 When selecting the finite (3) value, the exact time will be determined 
	 by another variable of the standard MIB (ex. 1493.dot1dTpAgingTime).
	 or by radBridgeAgingTime below."
   ::= { radBridgeGenCnfg 5 }


radBridgeMngFlow OBJECT-TYPE
    SYNTAX  INTEGER {
		disable  (2),
		enable   (3) 
            }
    MAX-ACCESS  read-write
    STATUS  current
    DESCRIPTION
	"This variable defines whether the Management Flow is passed
	 through the bridge (enable) or not (disable)."
   ::= { radBridgeGenCnfg 6 }

-- 
-- file :D:\Synergy\WorkArea\545\mib_rad\txt\trim.txt
-- 
--Title:         TrimBridge MIB
--Version:   3.0
--Last revision: 9.10.94
--By:            Debby Koren & Orly Nicklass
--File:          trim.txt                                    
											 

  
-- Objects in this section are arranged into groups:
--   trimInterface  -  Interface table and RS232 interface parameters
--   trimBackup     -  Backup feature, Dial-up parameters.
--   trimTR - Token Ring interface management
--   trimTrapInfo - parameters that provide information on traps sent


--Comments: The Trimbridge-16 agent also supports the following Public MIBs:
--              MIB-II (RFC1213)
--              dot5 ( RFC1231-MIB, updated by RFC1239 ) except for the optional Timers-table
--	 bridge (RFC 1493)
--Comments: The Trimbridge-10 agent also supports the following Public MIBs:
--              MIB-II (RFC1213)
--	 bridge (RFC 1493)


-- the trimInterface group defines the Trimbridge interface table and parameters for 
-- RS232 interface


trim OBJECT IDENTIFIER ::= {radBridges 3 }
trimInterface OBJECT IDENTIFIER ::= { trim 1  }

trimIfTable  OBJECT-TYPE
    SYNTAX SEQUENCE OF  TrimIfEntry 
    MAX-ACCESS  not-accessible
    STATUS  current
    DESCRIPTION
	"RAD-specific interface table. "
    ::= {  trimInterface 1  }
		   
trimIfEntry  OBJECT-TYPE
    SYNTAX TrimIfEntry 
    MAX-ACCESS  not-accessible
    STATUS  current
	DESCRIPTION
	"An entry in table trimIfTable."
    INDEX   { trimIfIndex  }
    ::= {  trimIfTable 1  }


TrimIfEntry ::= SEQUENCE { 
  trimIfIndex  
     Integer32,
  trimIfBoardNum  
     Integer32,
  trimIfNetAddress
     IpAddress,
  trimIfStatus    
     INTEGER,
  trimIfClockType  
     INTEGER,
  trimIfBaudRate
     Integer32,
  trimIfCost
     Integer32,
  trimIfCompression
     INTEGER,
  trimIfCompressionStatus
     INTEGER,
  trimIfCompressionRate
     Integer32,
  trimIfLATCompression
     INTEGER,
  trimIfCompressionType
     INTEGER,
  trimIfFilterMode
     INTEGER,
  trimIfConType
     INTEGER,
  trimIfRemAddress
     DisplayString,
  trimIfLocSubAddress
     DisplayString,
  trimIfRemSubAddress
     DisplayString,
  trimIfCLIVerification
     INTEGER

  }


trimIfIndex OBJECT-TYPE
    SYNTAX   Integer32  
    MAX-ACCESS  read-only
    STATUS  current
    DESCRIPTION
	"Index to the Trimbridge Interface Table. The interface defined by a 
	particular value of this index is the same interface as 
	identified by the same value of ifIndex (MIB II)."
    ::= {  trimIfEntry 1  }


trimIfBoardNum OBJECT-TYPE
    SYNTAX   Integer32  
    MAX-ACCESS  read-only
    STATUS  current
    DESCRIPTION
	"Reserved for possible future use.  Not currently applicable to Trimbridge."
    ::= {  trimIfEntry 2  }


trimIfNetAddress OBJECT-TYPE
    SYNTAX   IpAddress  
    MAX-ACCESS  read-only
    STATUS  current
    DESCRIPTION
	"The IP address of the interface defined by the particular value of 
	trimIfIndex."
    ::= {  trimIfEntry 3  }


trimIfStatus  OBJECT-TYPE
    SYNTAX   INTEGER  {
       ok (1),
       okSingleBrg(2),
       okMultiBrg(3),
       connctFault(4),
       rxFault(5),
       txFault(6),
       channelLoopback(7),
       rxClockFault(8),
       t1Alarm(9)
    }
    MAX-ACCESS  read-only
    STATUS  current
    DESCRIPTION
	"The current status of the interface.  Some of these status values are not applicable to Trimbridge."
     ::= {  trimIfEntry 4  }


trimIfClockType   OBJECT-TYPE 
    SYNTAX  INTEGER { 
       external(1),
       internal(2),
       t1(3),
       g703(4)
    }
    MAX-ACCESS  read-write
    STATUS  current
    DESCRIPTION
	"trimIfClockType defines the type of clock each interface
	uses: internal or external."
    ::= {  trimIfEntry 5  }


trimIfBaudRate    OBJECT-TYPE          -- Level II routing
    SYNTAX   Integer32   -- word
    MAX-ACCESS  read-write
    STATUS  current
    DESCRIPTION
	" Defines the baud rate in use by the interface. The valid
	 rates are determined by the type of the media for which this
	 baud rate is defined."
    ::= { trimIfEntry 6  }


trimIfCost    OBJECT-TYPE          -- Level II routing
    SYNTAX   Integer32   -- word 
    MAX-ACCESS  read-write
    STATUS  current
    DESCRIPTION
	"This object is inapplicable to Trimbridge."
    ::= { trimIfEntry 7  }


trimIfCompression   OBJECT-TYPE
    SYNTAX  INTEGER {
       enable(1),
       disable(2)
    }
    MAX-ACCESS  read-write
    STATUS  current
    DESCRIPTION
       "Defines whether data compression is enabled or disabled for the 
       interface."
    ::= {  trimIfEntry 8  }


  trimIfCompressionStatus  OBJECT-TYPE
  SYNTAX  INTEGER {
       not-inserted(1),
       active(2),
       not-active(3),
       disable(4)
    }
    MAX-ACCESS  read-only
    STATUS  current
    DESCRIPTION
	  "Defines the status of the compression component: 
	  not-inserted - compression component is not in the device
	  active - compression is enabled and operates correctly
	  not-active - compression is enables but does not operate. 
		       The reason may be that there is no 
		       compression component on the device connected 
		       to this interface.
	  disabled - compression was disabled by management, using 
		       variable trimCompression."
    ::= {  trimIfEntry 9  }
  

  trimIfCompressionRate  OBJECT-TYPE
    SYNTAX  Integer32
    MAX-ACCESS  read-only
    STATUS  current
    DESCRIPTION
	  "Percentage of compression. This variable applies only 
	  if trimCompressionStatus is active."
    ::= {  trimIfEntry 10  }


  trimIfLATCompression  OBJECT-TYPE
    SYNTAX  INTEGER {
       enable(1),
       disable(2)
    }
    MAX-ACCESS  read-write
    STATUS  current
    DESCRIPTION
	  "Enable/Disable the LAT Compression." 
    ::= {  trimIfEntry 11  }


  trimIfCompressionType  OBJECT-TYPE
    SYNTAX  INTEGER {
       none(1),
       lowSpeed(2),
       highSpeed(3)
    }
    MAX-ACCESS  read-only
    STATUS  current
    DESCRIPTION
	  "This parameter indicates the type of compression option available in
	   the device. 
	     `None(1)           - indicates that there is no compression option in the device
	      lowSpeed(2)   - indicates a compression option which is  operational up 
					 to line speed sof 64 kbps.
	      highSpeed(3) - indicates a compression option which is  operational up
					 to line speeds of 2 Mbps."
    ::= {  trimIfEntry 12  }



trimIfFilterMode  OBJECT-TYPE
    SYNTAX  INTEGER {
       destinationOnly(1),
       sourceAndDestination(2)
    }
    MAX-ACCESS  read-write
    STATUS  current
    DESCRIPTION
	"This parameter indicates the type of filtering in the device. "
    ::= {  trimIfEntry 13 }

trimIfConType  OBJECT-TYPE
    SYNTAX  INTEGER {
       unknown(1),
	   none(2),
       x21Old(3),
	   x21(4),
	   v35Old(5),
	   v35(6),
	   rs530Old(7),
	   rs530(8),
	   rs232Old(9),
	   rs232(10),
	   spsV35(11),
	   spsRS530(12),
	   spsRS232(13),
	   spsX21(14),
	   isdn(15)
    }
    MAX-ACCESS  read-only
    STATUS  current
    DESCRIPTION
	"This parameter indicates the connector type of an interface. "
    ::= {  trimIfEntry 14 }



trimIfRemAddress OBJECT-TYPE
    SYNTAX   DisplayString (SIZE(1..17))
    MAX-ACCESS  read-write
    STATUS  current
    DESCRIPTION
	"         "
    ::= {  trimIfEntry 15  }



trimIfLocSubAddress OBJECT-TYPE
    SYNTAX   DisplayString (SIZE(1..6))
    MAX-ACCESS  read-write
    STATUS  current
    DESCRIPTION
	"Space is not valid. If the string includes a space,
	 the whole entry is considered not valid."
    ::= {  trimIfEntry 16  }



trimIfRemSubAddress OBJECT-TYPE
    SYNTAX   DisplayString (SIZE(1..6))
    MAX-ACCESS  read-write
    STATUS  current
    DESCRIPTION
	"Space is not valid. If the string includes a space,
	 the whole entry is considered not valid."
    ::= {  trimIfEntry 17  }



trimIfCLIVerification OBJECT-TYPE
    SYNTAX  INTEGER {
	enable(1),
	disable(2)
	}
	MAX-ACCESS  read-write
	STATUS  current
	DESCRIPTION
	"Enables/Disables verification of Control Line Identification (CLI)"
	::= {  trimIfEntry 18  }


--    The variables in this group define the RS232 management interface 


trimRS232Conf        OBJECT IDENTIFIER ::= { trimInterface 2  }

trimBaudRate OBJECT-TYPE
    SYNTAX INTEGER { 
       br300(1),
       br1200(2),
       br2400(5),
       br4800(7),
       br9600(9),
       br19200(10)
    }
    MAX-ACCESS  read-write
    STATUS  current
    DESCRIPTION
	"Selects the baud rate used by the RS232 management interface. The 
	default selection is 1200 bits/second."
    ::= { trimRS232Conf 1  }


trimParity OBJECT-TYPE
    SYNTAX INTEGER { 
       noParity(1),
       oddParity(2),
       evenParity(3)
    }
    MAX-ACCESS  read-write
    STATUS  current
    DESCRIPTION
	"Determines whether the parity bit will be used and determines 
	its type."
    ::= { trimRS232Conf 2  }


trimStopBit OBJECT-TYPE
    SYNTAX INTEGER {
       oneStopBit(1),
       twoStopBit(2)
    }
    MAX-ACCESS  read-write
    STATUS  current
    DESCRIPTION
	"Selects the number of stop bits appended to the end of 
	each data word."
    ::= { trimRS232Conf 3  }


trimThresholdRep    OBJECT IDENTIFIER ::= { trimInterface 3}
trimIfThresholdRepTable   OBJECT-TYPE
    SYNTAX  SEQUENCE  OF TrimIfThresholdRepEntry
    MAX-ACCESS  not-accessible
    STATUS  current
    DESCRIPTION
	"    ....."
    ::=  {trimThresholdRep 1}


trimIfThresholdRepEntry  OBJECT-TYPE
    SYNTAX TrimIfThresholdRepEntry
    MAX-ACCESS  not-accessible
    STATUS  current
	DESCRIPTION
	"An entry in table trimIfThresholdRepTable."
    INDEX  { trimIfThreRepId,trimIfThreRepCounterId }
    ::=  { trimIfThresholdRepTable 1}



TrimIfThresholdRepEntry  ::= SEQUENCE {
     trimIfThreRepId
	  Integer32,
     trimIfThreRepCounterId
	  INTEGER,
     trimThresholdValue
	  Integer32,
     trimIfThreRepSampleRate
	  Integer32,
     trimIfThreRepTrapRate
	  Integer32
      }
trimIfThreRepId OBJECT-TYPE
    SYNTAX   Integer32
    MAX-ACCESS  read-only
    STATUS  current
    DESCRIPTION
	"The Interface number serves as an index to the Threshold Reoprt Table."
     ::= { trimIfThresholdRepEntry 1  }


trimIfThreRepCounterId OBJECT-TYPE
    SYNTAX   INTEGER{
	  vot(1)
	}
    MAX-ACCESS  read-only
    STATUS  current
    DESCRIPTION
	"The Counter ID  serves as an index to the Threshold Reoprt Table, and identify the counter for which 
	 to pot the threshold."
     ::= {  trimIfThresholdRepEntry 2  }



trimThresholdValue OBJECT-TYPE
    SYNTAX   Integer32
    MAX-ACCESS  read-write
    STATUS  current
    DESCRIPTION
	"The Threshold value , this is the maximum rate of counter increments  before the element issue trap."  
     ::= {  trimIfThresholdRepEntry 3  }


trimIfThreRepSampleRate OBJECT-TYPE
    SYNTAX   Integer32
    MAX-ACCESS  read-write
    STATUS  current
    DESCRIPTION
	   "The network object  will sample the counter atthis  interval. When this  parameter 
	    is set to 0, the treshold comparison is disable."
--      DEFVAL  { 10 }
     ::= {  trimIfThresholdRepEntry 4}
   

trimIfThreRepTrapRate  OBJECT-TYPE
    SYNTAX   Integer32
    MAX-ACCESS  read-write
    STATUS  current
    DESCRIPTION
	  " The network object  will issue a trap according to this interval. Note that the trape 
	    interval nust be equal or larger then trimIfThreRepSampleRate."
--      DEFVAL  { 30 }
     ::= {  trimIfThresholdRepEntry 5}

-- trimBackup group defines the parameters for the backup feature

trimBackup    OBJECT IDENTIFIER ::= { trim 2 }

trimBackupState OBJECT-TYPE
    SYNTAX  INTEGER {
      main(1),
      backup(2)
    }
    MAX-ACCESS  read-only
    STATUS current 
    DESCRIPTION
	"If main - the bridge is connected via the main physical link. 
	If backup - the automatic backup feature was enabled 
	and the bridge is connected via the backup physical link."
    ::= { trimBackup 1 }

   trimDialUpStatus  OBJECT-TYPE
    SYNTAX  INTEGER {
      enable(1),
      disable(2)
      }
    MAX-ACCESS  read-write
    STATUS  current
    DESCRIPTION
	"This parameter controls the operation of dial-up backup function.
	  If status is disable(2), dial-up backup will not be initiated when the 
	  main link fails or exceeds the specified error limit.
	   If status is enable(1), the dial-up backup will be initiated if the main
	  link fails or if the error rate on the main link exceeds the limit specified
	  by variable trimDialUp ErrorThreshold."
    ::= { trimBackup 2 }

trimBackLinkType  OBJECT-TYPE
    SYNTAX  INTEGER {
	dialUp(1),
	leased (2)
	}
    MAX-ACCESS  read-write
    STATUS  current
    DESCRIPTION
	"This variable specifies the type of the backup link. If the type is leased(2), 
	  Trimbridge will reroute traffic to the backup link, when main link fails.
	  If the value is dialUp(1), then the backup dial-up procedure is initiated
	  when the main link fails."
    ::= { trimBackup 3 }



trimDialUpMode  OBJECT-TYPE
    SYNTAX  INTEGER {
      originate(1),
      answer(2)
      }
    MAX-ACCESS  read-write
    STATUS  current
    DESCRIPTION
	"If the mode is originate(1), Trimbridge initiates the backup procedure when the
	  main link fails. if the mode is answer(2), it expects that the bridge on the 
	 other end of the link will initiate the backup procedure. Note that only one 
	 bridge in a pair should be set to mode originate(1). "
    ::= { trimBackup 4 }

trimDialUpErrorThreshold  OBJECT-TYPE
    SYNTAX  INTEGER {
	none(1),
	low(2),
	medium(3),
	high(4)
	    }
    MAX-ACCESS   read-write
     STATUS  current
    DESCRIPTION
	"Error rate on main link at which Backup will be enabled.
	    low    - 1*10-5
	    medium - 5*10-4
	    high   - 1*10-3 
	  If none(1) is selected, then backup is not invoked when there are errors
	  on the main link, but only when the main link is down."
    ::= { trimBackup 5 }

trimDialUpRedialTimeout  OBJECT-TYPE
    SYNTAX  Integer32
    MAX-ACCESS  read-write
    STATUS  current
    DESCRIPTION
	  "If an attempt to dial up failed for the specified time, a new redial attempt
	    will be initiated."
       ::= { trimBackup 6}

trimDialUpRedialNum   OBJECT-TYPE
    SYNTAX  Integer32
    MAX-ACCESS   read-write
    STATUS  current
    DESCRIPTION
	"This variable specifies the number of times to initiate the dial-up procedure.
	  If the number of redials is set to zero (0), then the number of redials will be 
	  unlimited. Any other value will cause the dial-up procedure to terminate after 
	 the specified number of re-dial attempts fail. Resetting this variable to any value
	  will re-initiate the dial-up procedure."
       ::= { trimBackup 7 }

trimBackUpConnectDelay OBJECT-TYPE
	SYNTAX  Integer32
	MAX-ACCESS  read-write
	STATUS  current
	DESCRIPTION
     "The connect delay defines the minimum time period that the link must be disconnected."
	::= { trimBackup 8 }

trimBackUpDisConnectDelay OBJECT-TYPE
	SYNTAX  Integer32
	MAX-ACCESS  read-write
	STATUS  current
	DESCRIPTION
		"The disconnect delay defines the delay between the last valid traffic trigger
		  and link disconnection."
	::= { trimBackup 9 }


trimBackUpScheduleTable OBJECT-TYPE
		SYNTAX  SEQUENCE  OF TrimBackUpEntry
		MAX-ACCESS  not-accessible
		STATUS  current
		DESCRIPTION
		       "This is a table that contains the reroute shedule for the backup link.  The index 
			is the day of the week, starting with 1 for Sunday, ending with 7 for 
			Saturday."
	       ::=  { trimBackup 10 }

trimBackUpEntry    OBJECT-TYPE
		SYNTAX  TrimBackUpEntry
		MAX-ACCESS  not-accessible
		STATUS  current
		DESCRIPTION
		"An entry in table trimBackUpScheduleTable."
		INDEX  { trimBackUpDay }
		::=  { trimBackUpScheduleTable 1 }

TrimBackUpEntry ::= SEQUENCE {
		 trimBackUpDay
		 Integer32,
		 trimBackUpFromTo
		 DisplayString
				      }

trimBackUpDay OBJECT-TYPE
		SYNTAX   Integer32
		MAX-ACCESS  read-only
		STATUS  current
		DESCRIPTION
		       "The day of the week for which the entry applies.  The days are numbered from 
		1 to  7, representing Monday through Sunday."
		::= {  trimBackUpEntry 1  }

trimBackUpFromTo OBJECT-TYPE
		SYNTAX  DisplayString
		MAX-ACCESS  read-write
		STATUS  current
		DESCRIPTION
			"This is the time  during which backup should be disabled, expressed
			 as xx:xx-yy:yy, where x's reflect the time from and y's reflect the time 
			to.  The first two digits, in x and in y, are the hour and the second two 
			digits are the minutes.  The pairs of digits are separated by a colon, and the 
			x is separated from the y by a dash."
		::= {  trimBackUpEntry 2  }



trimBackUpDelayAfterFailure OBJECT-TYPE
	SYNTAX  Integer32
	MAX-ACCESS  read-write
	STATUS  current
	DESCRIPTION
		"This entry defines the delay between the last @@@@"
	::= { trimBackup 11 }

-- The trimTR group defines parameters for Token Ring interface management, in addition to parameters
-- defined in the Public Token Ring MIB (RFC 1231).

trimTR    OBJECT IDENTIFIER ::= { trim 3 }

trimTRIfTable  OBJECT-TYPE
    SYNTAX  SEQUENCE  OF TrimTRIfEntry
    MAX-ACCESS  not-accessible
    STATUS  current
    DESCRIPTION
	"This table defines configuration parameters for Token Ring interfaces in the Trimbridge-16."
      ::=  { trimTR 1  }

trimTRIfEntry    OBJECT-TYPE
    SYNTAX  TrimTRIfEntry
    MAX-ACCESS  not-accessible
    STATUS  current
	DESCRIPTION
	"An entry in table trimTRIfTable."
    INDEX  { trimTRIfIndex }
    ::=  { trimTRIfTable 1  }

TrimTRIfEntry ::= SEQUENCE {
    trimTRIfIndex
     Integer32,
    trimTREarlyTokenRelease
     INTEGER,
    trimTRLocalAdminAddress
     MacAddress,
    trimTRLocalAdminAddressStatus
      INTEGER
	  }


trimTRIfIndex OBJECT-TYPE
    SYNTAX   Integer32
    MAX-ACCESS  read-only
    STATUS  current
    DESCRIPTION
	"Index to the Token Ring  Interface Table. The interface defined by a
	particular value of this index is the same interface as
	identified by the same value of ifIndex (MIBII)."
    ::= {  trimTRIfEntry 1  }

trimTREarlyTokenRelease OBJECT-TYPE
    SYNTAX  INTEGER {
       enable(1),
       disable(2)
    }
    MAX-ACCESS  read-write
    STATUS  current
    DESCRIPTION
	 "This parameter controls the early token release. This paramenter
	  is applicable only to 16 Mbps rings."
    ::= {  trimTRIfEntry 2  }

trimTRLocalAdminAddress  OBJECT-TYPE
    SYNTAX MacAddress
    MAX-ACCESS  read-write
    STATUS  current
    DESCRIPTION
	"A locally administered MAC Address of this interface."
    ::= {  trimTRIfEntry 3  }

trimTRLocalAdminAddressStatus OBJECT-TYPE
    SYNTAX  INTEGER {
       enable(1),
       disable(2)
    }
    MAX-ACCESS  read-write
    STATUS  current
    DESCRIPTION
	 "This parameter controls whether the bridge uses the locally administered MAC 
	 Address defined for this interface, when enable(1),  or not ,  when disable(2)."
    ::= {  trimTRIfEntry 4  }
	 
-- The trimTrapInfo group provides information on traps sent from Trimbridge

trimTrapInfo OBJECT IDENTIFIER ::= {trim 4}

trimErrorDesc OBJECT-TYPE
    SYNTAX DisplayString
    MAX-ACCESS  read-only
    STATUS  current
    DESCRIPTION
	"A textual description of the enterprise-specific trap sent
	to the Network Management Station by Trimbridge."
    ::= { trimTrapInfo 1  }

trimErrorSeverity OBJECT-TYPE
    SYNTAX INTEGER {
		  information(1),
		  warning(2),
		  error(3),
		  fatal(4)}
    MAX-ACCESS  read-only
    STATUS  current
    DESCRIPTION
	"The severity type of the enterprise-specific trap sent to the
	Network Management Station by Trimbridge."
    ::= { trimTrapInfo  2  }



-- 
-- file :D:\Synergy\WorkArea\545\mib_rad\txt\lanrger4.txt
-- 
--Version:   1.0
--Date:   16.10.94              
--By:       Debby Koren & Orly Nicklass
--File:      v:\doc\rdv\mib\ver540\Lanrger4.txt
--

--Last Update: 27-Feb-2008 by Smadar Tauber

-- Comments:  The LANRANger also supports the following Public MIBs:
--              - MIB-II  ( RFC1213 )
--              - Token Ring MIB (RFC 1231) or Ethernet MIB (RFC 1398), according to the LAN 
--                 interface
--      - RS-232 MIB (RFC 1317)

 lanranger     OBJECT IDENTIFIER ::= {radBridges 2 }
--   Objects in this MIB are arranged into groups:
--   lanrangerConfig - LANRANger-specific configurable parameters
--   lanrangerInterface  -  LANRANger-specific interface table 
--   lanrangerStation - Tables containing the list of remote workstations and related information
-- and static entries

-- At the end of the MIB there is a definition of all LANRANger-specific traps. 

-- the lanrangerConfig group defines configurable parameters that are specific to the LANRANger
-- product line

lanrangerConfig OBJECT IDENTIFIER ::= { lanranger 1 }

lanrangerLoc   OBJECT-TYPE 
    SYNTAX  INTEGER { 
       main(1),
       remote(2)
    }
    MAX-ACCESS  read-only
    STATUS  current
    DESCRIPTION
	"lanrangerLoc is set to main if the LANRANger is located on the main LAN and it is set to
		 remote if it is located on a LAN at a remote site."
    ::= {  lanrangerConfig 1  }

lanrangerBurnAddress   OBJECT-TYPE 
    SYNTAX  MacAddress 
    MAX-ACCESS  read-only
    STATUS  current
    DESCRIPTION
	"This is the burned-in MacAddress on the LANRANger."
    ::= {  lanrangerConfig 2  }

lanrangerLocAddress   OBJECT-TYPE 
    SYNTAX  MacAddress 
    MAX-ACCESS  read-write
    STATUS  current
    DESCRIPTION
	"This is a locally administered address.  If a zero value appears, the network administrator 
	did  not set a locally administered address."
    ::= {  lanrangerConfig 3 }

lanrangerActiveAddress OBJECT-TYPE
     SYNTAX INTEGER {burnedIn(1), locallyAdministered(2) }
     MAX-ACCESS read-write
     STATUS current
     DESCRIPTION
	 "The MAC address that is in use on the LANRANger. 
	  The address selected will appear in ifPhysAddress."
     ::= { lanrangerConfig 4 }


lanrangerLearningStationTopology OBJECT-TYPE
     SYNTAX INTEGER { dynamic             (1),
                      permanent           (2),
                      permanentAndDynamic (3)
                    }
     MAX-ACCESS read-write
     STATUS current
     DESCRIPTION
         "The Learning station topology defines for the 
          LANRANger which type of station will be inserted 
          in the station list. 
          The default value is permanentAndDynamic(3).
 
             dynamic(1)   - Learning lan station only. 
             permanent(2) - 
             permanentAndDynamic(3)-
             
          Setting this parameter will reset the LANRANger . 
                                      -----                "
     ::= { lanrangerConfig 5 }


lanrangerIpRouterInfo OBJECT IDENTIFIER
     ::= { lanrangerConfig 6 }

  lanrangerIpDefaultLink  OBJECT-TYPE
       SYNTAX Integer32 
       MAX-ACCESS read-write
       STATUS current
       DESCRIPTION
        "The default selected link, having the numbering system of ifIndex. 
         The valid values range is: 1..ifIndex.
         The value must remain constant at least from one
         re-initialization of the network management agent to
         the next.
         notSupported = 255 "
       ::= { lanrangerIpRouterInfo 1 }

  lanrangerIpFastReTxLevel  OBJECT-TYPE
       SYNTAX Integer32 
       MAX-ACCESS read-write
       STATUS current
       DESCRIPTION
         " The maximum buffer depth (queue length) for which lanranger 
           will accept retransmission (for each station; the level
           is the same for all the stations).
           The valid values range is: 1..255 .    "
       ::= { lanrangerIpRouterInfo 2 }

  lanrangerIpAgingTimeout OBJECT-TYPE
      SYNTAX  Integer32
      MAX-ACCESS  read-write
      STATUS  current
      DESCRIPTION
         " Ip aging time for a station - in min. "
       ::= { lanrangerIpRouterInfo 3 }

--BOOT-P parameters; are relevant only for routers 

   lanrangerIpBootP OBJECT IDENTIFIER
       ::= { lanrangerIpRouterInfo 4 }

    lanrangerBootPAction  OBJECT-TYPE
       SYNTAX INTEGER { 
       disable (2),
       enable (3)
       }
       MAX-ACCESS read-write
       STATUS current
       DESCRIPTION
           "Activating (disable/enable) the BootP operation."
       ::= { lanrangerIpBootP 1 }

    lanrangerBootPAvailableEntries OBJECT-TYPE
       SYNTAX  Integer32
       MAX-ACCESS  read-only
       STATUS  current
       DESCRIPTION
         "The number of available entries in the BootP table."
       ::= { lanrangerIpBootP 2 }

    lanrangerBootPCurrentEntries OBJECT-TYPE
       SYNTAX  Integer32
       MAX-ACCESS  read-only
       STATUS  current
       DESCRIPTION
         "The current number of BootP entries in the BootP table."
       ::= { lanrangerIpBootP 3 }

    lanrangerBootPTable OBJECT-TYPE
       SYNTAX SEQUENCE OF LanrangerBootPEntry
       MAX-ACCESS not-accessible
       STATUS current
       DESCRIPTION
          "A list of BootP entries.  The number of entries is up to
           BootP current entries, according to the LANRANger model."
       ::= { lanrangerIpBootP 4 }

    lanrangerBootPEntry OBJECT-TYPE
       SYNTAX  LanrangerBootPEntry
       MAX-ACCESS  not-accessible
       STATUS  current
       DESCRIPTION
           "BootP parameters per entry of the BootP table."
       INDEX   { lanrangerBootPIpAddress }
       ::= { lanrangerBootPTable 1 }

    LanrangerBootPEntry ::=
       SEQUENCE {
              lanrangerBootPIpAddress
                 IpAddress,
              lanrangerBootPIfIndex
                 INTEGER,
              lanrangerBootPOperation
                 INTEGER
          }

    lanrangerBootPIpAddress OBJECT-TYPE
        SYNTAX  IpAddress
        MAX-ACCESS  read-only
        STATUS  current
        DESCRIPTION
             "BootP Ip Address."
        ::= { lanrangerBootPEntry 1 }

    lanrangerBootPIfIndex OBJECT-TYPE
        SYNTAX  INTEGER	 {notAllocated (255)}
        MAX-ACCESS  read-only
        STATUS  current
        DESCRIPTION
             "The number is the same as the ifIndex of the link."
        ::= { lanrangerBootPEntry 2 }

   lanrangerBootPOperation OBJECT-TYPE
      SYNTAX  INTEGER {
                     active (1),
                     delete (2)
             }
      MAX-ACCESS  read-write
      STATUS  current
      DESCRIPTION
             "This object indicates the status of this entry.
                active(1) - this entry is currently in use
                            and will remain so even after the next
                            reset of the LANRANger.
                delete(2) - writing this value to the object,
                            removes the corresponding entry from the
                            table. "
      ::= { lanrangerBootPEntry 3 }


lanrangerSpoofingInfo OBJECT IDENTIFIER
     ::= { lanrangerConfig 7 }

  lanrangerSpoofingAction  OBJECT-TYPE
       SYNTAX Integer32 
       MAX-ACCESS read-write
       STATUS current
       DESCRIPTION
	"Spoofing action is applied by bit code:
         enable        :  bit 0 set (disable: bit 0 is 0)
         keepAlive     :  bit 1
            ...        :  bit 2
         and so on.
         For the above example, to set spoofing to keepAlive action,
         the object's value will be 3 = [ 2**0 + 2**1 ] 
         Only the Remote LANRANger will accept this object !
                  -------                                  "
       ::= { lanrangerSpoofingInfo 1 }

  lanrangerSpoofingAgingStation  OBJECT-TYPE
       SYNTAX Integer32 
       MAX-ACCESS read-write
       STATUS current
       DESCRIPTION
         " Aging time of stations list, in min. The agent 'translates'
           the time entered in minutes, to 10 min. resolution, as
		   follows: 
		   1..10  min - 10 min
		   11..20 min - 20 min
		   and so on...
		   0 is not a valid value.
           Only the Remote LANRANger will accept this object !
                    ----------------                          "
       ::= { lanrangerSpoofingInfo 2 }



--    The variables in the lanrangerInterface group define LANRANger-specific and other 
--    link parameters and information

lanrangerInterface OBJECT IDENTIFIER ::= { lanranger 2 }

lanrangerLinkTable OBJECT-TYPE
      SYNTAX SEQUENCE OF LanrangerLinkEntry
      MAX-ACCESS not-accessible
      STATUS current
      DESCRIPTION
	  "A list of link entries.  The number of entries is
	   up to 8, according to the LANRANger model."
      ::= { lanrangerInterface 1 }

lanrangerLinkEntry OBJECT-TYPE
    SYNTAX LanrangerLinkEntry
    MAX-ACCESS not-accessible
    STATUS current
    DESCRIPTION
	"LANRANger-specific parameter values for a link."
    INDEX {lanrangerLinkIndex }
    ::= { lanrangerLinkTable 1 }

LanrangerLinkEntry ::=
    SEQUENCE {
	lanrangerLinkIndex
	    Integer32,
	lanrangerLinkType
	    INTEGER ,
	lanrangerLinkState
	    INTEGER,
	lanrangerLinkDTRMode
	    INTEGER,
	lanrangerLinkStatus
	    INTEGER,
	lanrangerLinkConnectionStatus
	    INTEGER,
	lanrangerLinkNumOfLogLinks
	    Integer32,
	lanrangerLinkReset
	    INTEGER,
    lanrangerLinkRxMaskedFrames
	    Counter32,
    lanrangerLinkLayer2Type
        INTEGER,
    lanrangerLinkLayer3Type
        INTEGER,
	lanrangerBackupLink
	    Integer32,
    wrWanThrottle
        Integer32,
	wrIpTransparentMode
		INTEGER,
	wrIpTransparentGateway
		IpAddress,
	lanrangerLinkProtocolType
        INTEGER
    }

lanrangerLinkIndex OBJECT-TYPE
    SYNTAX Integer32
    MAX-ACCESS read-only
    STATUS current
    DESCRIPTION
	"A unique value for each link, equal to the value of ifIndex. 
	 The value for each link must remain constant at least 
	 from one re-initialization of the network management agent to
	 the next."
    ::= { lanrangerLinkEntry 1 }

lanrangerLinkType OBJECT-TYPE
     SYNTAX INTEGER { 
         synchronous    (1),
         asynchronous   (2),
         x25FRconfig    (3),
         x25FRchannel   (4),
         isdn           (5),
         frameRelay     (6),
         pcmcia         (7),
         dm2wire        (8),
         notExist       (254),
		 unknown        (255)
         }
     MAX-ACCESS read-write
     STATUS current
     DESCRIPTION
	 "The link type ."
     ::= { lanrangerLinkEntry 2 }

lanrangerLinkState OBJECT-TYPE
     SYNTAX INTEGER {      
     disable(2),
     enable (3),
	 backup (4)
      }
     MAX-ACCESS read-write
     STATUS current
     DESCRIPTION
	 "The link is  disabled, enabled or backup."
     ::= { lanrangerLinkEntry 3 }

lanrangerLinkDTRMode OBJECT-TYPE
     SYNTAX INTEGER {  off(2), on(3), unknown(255)  }
     MAX-ACCESS read-only
     STATUS current
     DESCRIPTION
	 "The link DTR mode."
     ::= { lanrangerLinkEntry 4 }

lanrangerLinkStatus OBJECT-TYPE
     SYNTAX INTEGER { 
     ok         (1), 
     fail       (2), 
     rxNoClock  (3), 
     txProblem  (4),
     noCarrierD (5),
	 unknown    (255)
      }
     MAX-ACCESS read-only
     STATUS current
     DESCRIPTION
	 "The link  physical status ."
     ::= { lanrangerLinkEntry 5 }

lanrangerLinkConnectionStatus OBJECT-TYPE
     SYNTAX INTEGER { 
     fail      (1), 
     disconnect(2), 
     connect   (3),
     wait      (4),
     down      (5),
	 trying    (6),
	 testing   (7),
	 unknown   (255)
     }
     MAX-ACCESS read-only
     STATUS current
     DESCRIPTION
	 "The link connection status."
     ::= { lanrangerLinkEntry 6 }

lanrangerLinkNumOfLogLinks OBJECT-TYPE
     SYNTAX Integer32	
     MAX-ACCESS read-only
     STATUS current
     DESCRIPTION
	 "The number of logical links on this physical link.
	  0 = noLogicalLink "
     ::= { lanrangerLinkEntry 7 }

lanrangerLinkReset OBJECT-TYPE
     SYNTAX   INTEGER {     
     off(2),
     on (3)  
     }
     MAX-ACCESS read-write
     STATUS current
     DESCRIPTION
	 "Setting this attribute to ON will reset the link . Upon completion the value will be set to OFF"
     ::= { lanrangerLinkEntry 8 }

lanrangerLinkRxMaskedFrames OBJECT-TYPE
     SYNTAX  Counter32
     MAX-ACCESS read-only
     STATUS current
     DESCRIPTION
	 "The number of masked frames received on this physical link."
     ::= { lanrangerLinkEntry 9 }

lanrangerLinkLayer2Type OBJECT-TYPE
     SYNTAX INTEGER {
              unknown         (1),
              bridge          (2),
              ipRouter        (3),
              ipxRouter       (4),
              ipAndIpxRouter  (5),
              bRouter         (6),
			  ipBrouter       (7),
			  ipxBrouter      (8),
			  ipAndIpxBrouter (9),
			  bridgeAndStp    (10)
              }
     MAX-ACCESS read-write
     STATUS current
     DESCRIPTION
         "The link layer 2 type indicates whether the link is Bridge 
          or Router	and specifies the Router's type."
     ::= { lanrangerLinkEntry 10 }

lanrangerLinkLayer3Type OBJECT-TYPE
     SYNTAX INTEGER {
              unknown        (1),
              proprietary    (2),
			  terminalServer (3),
              slip          (30),
              cSlip         (31),
              ppp           (40),
			  rfc1490       (41),
			  hdlcFraming   (42),
			  mlPpp         (43)
              }
     MAX-ACCESS read-write
     STATUS current
     DESCRIPTION
         "The link layer 3 type indicates the protocol type."
     ::= { lanrangerLinkEntry 11 }

lanrangerBackupLink OBJECT-TYPE
     SYNTAX   Integer32
     MAX-ACCESS read-write
     STATUS current
     DESCRIPTION
	 "The backup link interface index located in the two LSB bytes. 
	  If the link is FR type, the two MSB will contain a DLCi number. 
	  For other link types the two MSB will equal to 0."
     ::= { lanrangerLinkEntry 12 }

wrWanThrottle OBJECT-TYPE
     SYNTAX   Integer32
     MAX-ACCESS read-write
     STATUS current
     DESCRIPTION
	 "Throttle controls the baud rate of the WAN.
      For example if we have a WAN rate of 2M but we want only 1/2 M as 
      the baud rate we set the Wan Throttle to 512k.
      
      These are the values:
      Full (2),
      1M (3),
      512k (4),
      128k (5),
      64k (6)
      
      Full throttle option (2) means  the LAN rate."
     ::= { lanrangerLinkEntry 13 }

wrIpTransparentMode OBJECT-TYPE
     SYNTAX INTEGER {
     notApplicable  (1),
     disable        (2),
	 enableAll      (3)
     }
     MAX-ACCESS read-write
     STATUS current
     DESCRIPTION
     "This parameter shows whether the IP Transparent mode is enabled.
      When this mode is enabled, all frames (including broadcast and multicast frames)
      are forwarded from E1/T1 to LAN and from LAN to E1/T1."
     ::= { lanrangerLinkEntry 14 }

wrIpTransparentGateway OBJECT-TYPE
     SYNTAX  IpAddress
     MAX-ACCESS  read-write
     STATUS  current
     DESCRIPTION
     "The gateway used for transparent IP."
     ::= { lanrangerLinkEntry 15 }

lanrangerLinkProtocolType OBJECT-TYPE
     SYNTAX INTEGER {
     notApplicable  	(1),
     noRoutingProtocol  (2),
	 rip1      			(3),
	 rip2				(4),
	 rip1OrRip2 		(5),
	 ospf				(6)
     }
     MAX-ACCESS read-write
     STATUS current
     DESCRIPTION
     "This parameter indicates the routing protocol running on this Interface."
     ::= { lanrangerLinkEntry 16}


--Link Connections

lanrangerLinkConnection OBJECT IDENTIFIER
     ::= { lanrangerInterface 2 }

   lanrangerConnMaxEntries OBJECT-TYPE
      SYNTAX  Integer32
      MAX-ACCESS  read-only
      STATUS  current
      DESCRIPTION
        "The maximum number of entries in the Connection table."
      ::= { lanrangerLinkConnection 1 }

   lanrangerConnCurrentEntries OBJECT-TYPE
      SYNTAX  Integer32
      MAX-ACCESS  read-only
      STATUS  current
      DESCRIPTION
        "The current number of entries in the Connection table."
      ::= { lanrangerLinkConnection 2 }

   lanrangerLinkConnTable OBJECT-TYPE
      SYNTAX SEQUENCE OF LanrangerLinkConnEntry
      MAX-ACCESS not-accessible
      STATUS current
      DESCRIPTION
         "A list of Connection entries.  The number of entries is
          up to Max entries, according to the LANRANger model."
      ::= { lanrangerLinkConnection 3 }

   lanrangerLinkConnEntry OBJECT-TYPE
     SYNTAX LanrangerLinkConnEntry
     MAX-ACCESS not-accessible
     STATUS current
     DESCRIPTION
        "Information about LANRANger Connection."
     INDEX {lanrangerLinkConnPhysLink, lanrangerLinkConnAid,
            lanrangerLinkConnMacAddr }
     ::= { lanrangerLinkConnTable 1 }

   LanrangerLinkConnEntry ::=
       SEQUENCE {
           lanrangerLinkConnPhysLink
               Integer32 ,
           lanrangerLinkConnAid
               Integer32,
           lanrangerLinkConnMacAddr
               MacAddress,  
           lanrangerLinkConnStatus
               INTEGER,
           lanrangerLinkConnDeviceType
               INTEGER,
           lanrangerLinkConnDeviceName
               DisplayString,
           lanrangerLinkConnDeviceSWVer
               DisplayString,
           lanrangerLinkConnNumLanStation
               Integer32,
           lanrangerLinkSyncStatus
               INTEGER
   	}
   
   lanrangerLinkConnPhysLink OBJECT-TYPE
        SYNTAX Integer32  
        MAX-ACCESS read-only
        STATUS current
        DESCRIPTION
            "The lanrangerLinkIndex for the physical link with which this logical link is associated."
         ::= { lanrangerLinkConnEntry 1 }
           
   lanrangerLinkConnAid OBJECT-TYPE
       SYNTAX Integer32 
       MAX-ACCESS read-only
       STATUS current
       DESCRIPTION
           "A unique value for each logical link.  The maximum number 
            of logical links is 256, according to the LANRANger model.  
            The value for each logical link must remain constant at least 
            from one re-initialization of the network management agent to
            the next.  This index is the SPS address of the logical link.
            noLogicLink = 65535"
       ::= { lanrangerLinkConnEntry 2 }
   
   lanrangerLinkConnMacAddr OBJECT-TYPE
       SYNTAX  MacAddress
       MAX-ACCESS  read-only
       STATUS  current
       DESCRIPTION
           "The MAC address of the device that the logical link is connected to
            on the remote LAN."
     ::= { lanrangerLinkConnEntry 3 }
   
   lanrangerLinkConnStatus OBJECT-TYPE
     SYNTAX INTEGER { 
              unknown        (1), -- for router link
              none           (2), -- no connection
              fail           (3),
              connect        (4),
              wait           (5),
              down           (6)
             }
     MAX-ACCESS read-only
     STATUS current
     DESCRIPTION
         "The link connection status."
     ::= { lanrangerLinkConnEntry 4 }
   
   lanrangerLinkConnDeviceType OBJECT-TYPE
        SYNTAX  INTEGER {
                      tre1      (1),
                      tre8      (2),
                      tre1D     (3),
                      tre8D     (4),
                      tre8M     (5),
                      rrTre     (6),
                      rrTre1D   (7),
                      rrTre8D   (8),
                      iTre1     (9),
                      iTre2     (10),
                      mpTre8    (11),
                      kTre8     (12),
                      treRasA   (13),
                      treRasS   (14),
                      trePCAsync(15),
                      trePCSync (16),
                      mbe1      (17),
                      mbe8      (18),
                      mbe1D     (19),
                      mbe8D     (20),
                      ete8M     (21),
                      iEre1     (22),
                      iEe2      (23),
                      mpMbe8    (24),
                      kMbe8     (25),
                      mbePCAsync(26),
                      mbePCSync (27),
                      mbeRasA   (28),
                      mbeRasS   (29),
   	        other(255)  
                   }
       MAX-ACCESS  read-only
       STATUS  current
       DESCRIPTION
               "The type of device that the logical link is connected to on the remote LAN."
       ::= { lanrangerLinkConnEntry 5 }
   
   lanrangerLinkConnDeviceName  OBJECT-TYPE
       SYNTAX  DisplayString  
       MAX-ACCESS  read-only
       STATUS  current
       DESCRIPTION
            "The logical name of the device that the logical link is connected to on the remote LAN."
       ::= { lanrangerLinkConnEntry 6 }

   lanrangerLinkConnDeviceSWVer  OBJECT-TYPE
       SYNTAX  DisplayString  
       MAX-ACCESS  read-only
       STATUS  current
       DESCRIPTION
            "SW Version of the device that the logical link is 
             connected to, on the remote LAN."
       ::= { lanrangerLinkConnEntry 7 }

   lanrangerLinkConnNumLanStation OBJECT-TYPE
     SYNTAX Integer32 
     MAX-ACCESS read-only
     STATUS current
     DESCRIPTION
         "The number of stations of the remote LAN."
     ::= { lanrangerLinkConnEntry 8 }

lanrangerLinkSyncStatus OBJECT-TYPE
     SYNTAX INTEGER { 
              synchronized        (1), 
              syncNotObtained     (2), 
              waitForSync         (3),
              codDisconnected     (4),
              lcp                 (5),
              ip                  (6),
              ipvj                (7),
              ipx                 (8),
              ipIpx               (9),
              ipvj-ipx            (10),
              mlPpp               (11),
              mlPpp-ip            (12),
              mlPpp-ip-ipvj       (13),
              mlPpp-ip-ipx        (14),
              mlPpp-ipvj-ipx      (15),
              mlPpp-ipx           (16),
              frUp                (17),
              frDown              (18),
              dlciUp              (19),
              dlciDown            (20),
              extLoop             (21),
              ipcp                (22),
              lcpIpcp             (23),
			  redAlarm            (24),
			  yellowAlarm         (26),
			  localSyncLoss       (27),
			  remoteSyncLoss      (28),
			  networkLoop         (29),
			  networkLoopRedAlarm (30),
			  networkLoopYelAlarm (31),
			  networkLocSyncLoss  (32),
			  networkRemSyncLoss  (33),
			  fdlLoop             (34),
			  fdlLoopRedAlarm     (35),
			  fdlLoopYellowAlarm  (36),
			  fdlLoopLocSyncLoss  (37),
			  fdlLoopRemSyncLoss  (38),
			  loopback            (39),  -- User Loop
			  loopbackLocSyncLoss (40),
			  loopbackRemSyncLoss (41)			  
             }
     MAX-ACCESS read-only
     STATUS current
     DESCRIPTION
         "The Sync link status."
     ::= { lanrangerLinkConnEntry 9 }


--Modem Table

lanrangerModemTable OBJECT-TYPE
      SYNTAX SEQUENCE OF LanrangerModemEntry
      MAX-ACCESS not-accessible
      STATUS current
      DESCRIPTION
          "A list of Modem entries.  The number of entries is
           up to ifIndex."
      ::= { lanrangerInterface 3 }

lanrangerModemEntry OBJECT-TYPE
    SYNTAX LanrangerModemEntry
    MAX-ACCESS not-accessible
    STATUS current
    DESCRIPTION
        "LANRANger-specific parameter values for a Modem."
    INDEX {lanrangerModemLinkIndex }
    ::= { lanrangerModemTable 1 }

LanrangerModemEntry ::=
    SEQUENCE {
        lanrangerModemLinkIndex
            Integer32,
        lanrangerModemName
            DisplayString,
        lanrangerModemSettingString
            DisplayString,
        lanrangerModemAutobaudingSpeed
            INTEGER,
        lanrangerModemResetBeforeSetup
            INTEGER,
        lanrangerModemAnalyzeAnswers
            INTEGER,
        lanrangerModemSpeaker
            INTEGER,
        lanrangerModemDialingNumber
            DisplayString,
        lanrangerModemDialRetries             
            Integer32,
        wrLocalDialBackNumber
            DisplayString,
        wrRingsBeforeAnswer
            Integer32
   }

lanrangerModemLinkIndex OBJECT-TYPE
    SYNTAX Integer32
    MAX-ACCESS read-only
    STATUS current
    DESCRIPTION
        "A list of asynchronous ports of the link, according to 
         ifIndex. 
         Synchronous ports will not appear in this table. Their
         port number will be skipped."
    ::= { lanrangerModemEntry 1 }


lanrangerModemName OBJECT-TYPE
    SYNTAX DisplayString
    MAX-ACCESS read-write
    STATUS current
    DESCRIPTION
        "The Modem Name identifier for MBE/TRE.
         Up to 50 characters."
    ::= { lanrangerModemEntry 2 }

lanrangerModemSettingString OBJECT-TYPE
    SYNTAX DisplayString
    MAX-ACCESS read-write
    STATUS current
    DESCRIPTION
        "Modem setting String.
         Up to 80 characters."
    ::= { lanrangerModemEntry 3 }


lanrangerModemAutobaudingSpeed OBJECT-TYPE
     SYNTAX  INTEGER {
                 disable(2),
                 enable (3)
             }
     MAX-ACCESS  read-write
     STATUS  current
     DESCRIPTION
         "Enable or disable autobauding.
          When the Autobauding feature is enabled, the MBE/TRE 
          automatically ranges over various Baud rates, starting 
          with 115.2 Kbps, until the correct Baud rate of the modem 
          is detected. "
    ::= { lanrangerModemEntry 4 }


lanrangerModemResetBeforeSetup OBJECT-TYPE
     SYNTAX  INTEGER {
                 no (2),
                 yes(3)
             }
     MAX-ACCESS  read-write
     STATUS  current
     DESCRIPTION
         "Reset the modem before setup is performed.
          It is recommended to reset the modem before  modem setup 
          session.     "
    ::= { lanrangerModemEntry 5 }


lanrangerModemAnalyzeAnswers OBJECT-TYPE
     SYNTAX  INTEGER {
                 disable(2),
                 enable (3)
             }
     MAX-ACCESS  read-write
     STATUS  current
     DESCRIPTION
         "Enable this option if a modem using non-standard answering is used.
          When this mode is enabled, the MBE/TRE awaits modem answers
          'CONNECT', 'CARRIER', or 'OK', after it transmits a modem command.
          Modem answers acknowledge, that a specific command has been executed.
          If this option is not enabled, the MBE/TRE waits for a modem answer
          for three seconds. If no answer has been received during this period,
          the MBE/TRE continues functioning as if the modem command was successfully
          executed. However, when dialing out, the MBE/TRE waits for one minute 
          for connection."
    ::= { lanrangerModemEntry 6 }

lanrangerModemSpeaker OBJECT-TYPE
     SYNTAX  INTEGER {
                 off (2),
                 on  (3)
             }
     MAX-ACCESS  read-write
     STATUS  current
     DESCRIPTION
         "Toggle the Modem Speaker On or Off . "
    ::= { lanrangerModemEntry 7 }


lanrangerModemDialingNumber OBJECT-TYPE
    SYNTAX DisplayString
    MAX-ACCESS read-write
    STATUS current
    DESCRIPTION
        " Various command switches listed in Modem Dialing Number Menu
          allows selection of tone, pulse-dialing, or various wait states.
          P - Set Pulse dialing number .
          T - Set Tone  dialing number .
          W - Wait for dialing tone before proceeding.
          ' - Pause for 2 seconds .
          @ - Wait for silence, one ring, followed by 5 sec. of silence .

          The Dialing Number will include both digits and letter/s 
          of the command switches. The order and validity will be 
          on user's responsibility.   
          The DisplayString can have up to 40 characters."
    ::= { lanrangerModemEntry 8 }


wrLocalDialBackNumber OBJECT-TYPE
    SYNTAX DisplayString
    MAX-ACCESS read-write
    STATUS current
    DESCRIPTION
        " This is the number that the Remote Modem will use to call the local
          Modem at Dial Back.

          Various command switches listed in Modem Dialing Number Menu
          allows selection of tone, pulse-dialing, or various wait states.
          P - Set Pulse dialing number .
          T - Set Tone  dialing number .
          W - Wait for dialing tone before proceeding.
          ' - Pause for 2 seconds .
          @ - Wait for silence, one ring, followed by 5 sec. of silence .

          The Dialing Number will include both digits and letter/s 
          of the command switches. The order and validity will be 
          on user's responsibility.   
          The DisplayString can have up to 40 characters."
    ::= { lanrangerModemEntry 9 }


wrRingsBeforeAnswer  OBJECT-TYPE
     SYNTAX  Integer32 
     MAX-ACCESS  read-write
     STATUS  current
     DESCRIPTION
            "Determines which ring the modem will wait to answer the
            phone on."
    ::= { lanrangerModemEntry 10 }          
                  


lanrangerModemDialRetries OBJECT-TYPE
      SYNTAX  Integer32  (0..8)
      MAX-ACCESS  read-write
      STATUS  current
      DESCRIPTION
           "The number of dialing retries requested.
            Default = 0"
      ::= { lanrangerModemEntry 11}

--Packet Switch Table

lanrangerLinkPktSwTable OBJECT-TYPE
      SYNTAX SEQUENCE OF LanrangerLinkPktSwEntry
      MAX-ACCESS not-accessible
      STATUS current
      DESCRIPTION
          "A list of X.25/FR modules entries.  The number of entries is
           up to ifIndex."
      ::= { lanrangerInterface 4 }

lanrangerLinkPktSwEntry OBJECT-TYPE
    SYNTAX LanrangerLinkPktSwEntry
    MAX-ACCESS not-accessible
    STATUS current
    DESCRIPTION
        "LANRANger-specific parameter values for  X.25/FR modules."
    INDEX {lanrangerLinkPktSwIndex }
    ::= { lanrangerLinkPktSwTable 1 }

LanrangerLinkPktSwEntry ::=
    SEQUENCE {
        lanrangerLinkPktSwIndex
            Integer32,
        lanrangerLinkPktSwType
            INTEGER,
        lanrangerLinkPktSwControlSignal
            INTEGER,
        lanrangerLinkPktSwSpeed
            Integer32,
        lanrangerLinkPktSwConfigParity
            INTEGER,
        lanrangerLinkPktSwConfigStopBit
            INTEGER,
        lanrangerLinkPktSwResetModule
            INTEGER
       }

lanrangerLinkPktSwIndex OBJECT-TYPE
    SYNTAX Integer32
    MAX-ACCESS read-only
    STATUS current
    DESCRIPTION
        "A unique value for each X.25/FR of the link, according to 
         numbering system of ifIndex. The maximum number of links is 
         ifIndex. The value for each link must remain constant at 
         least from one re-initialization of the network management 
         agent to the next."
    ::= { lanrangerLinkPktSwEntry 1 }

lanrangerLinkPktSwType OBJECT-TYPE
    SYNTAX INTEGER {
            x25FRChannel (1),
            x25FRConfig  (2)
            }
    MAX-ACCESS read-only
    STATUS current
    DESCRIPTION
        "Packet Switch Type."
    ::= { lanrangerLinkPktSwEntry 2 }

lanrangerLinkPktSwControlSignal OBJECT-TYPE
    SYNTAX INTEGER {
            off(2),
            on (3)
            }
    MAX-ACCESS read-write
    STATUS current
    DESCRIPTION
        "Packet Switch control command. "
    ::= { lanrangerLinkPktSwEntry 3 }

lanrangerLinkPktSwSpeed OBJECT-TYPE
    SYNTAX Integer32
    MAX-ACCESS read-write
    STATUS current
    DESCRIPTION
        "The Pkt Switch  port's speed in bits per second.
         Range: 1200bps .. 1544000bps"
    ::= { lanrangerLinkPktSwEntry 4 }

lanrangerLinkPktSwConfigParity OBJECT-TYPE
    SYNTAX INTEGER { none(1), odd(2), even(3), notApplicable(255)}
    MAX-ACCESS read-write
    STATUS current
    DESCRIPTION
        "The Pkt Switch Config port's character parity bit.
         Applicable only for x25FRConfigChannel. For x25FRChannel
         the value notApplicable applies."
    ::= { lanrangerLinkPktSwEntry 5 }

lanrangerLinkPktSwConfigStopBit OBJECT-TYPE
    SYNTAX INTEGER { one(1), two(2), notApplicable(255) }
    MAX-ACCESS read-write
    STATUS current
    DESCRIPTION
        "The Pkt Switch Config port's number of stop bits.
         Applicable only for x25FRConfigChannel. For x25FRChannel
         the value notApplicable applies."
    ::= { lanrangerLinkPktSwEntry 6 }

lanrangerLinkPktSwResetModule OBJECT-TYPE
    SYNTAX INTEGER { 
    off(2),
    on (3) 
    }
    MAX-ACCESS read-write
    STATUS current
    DESCRIPTION
        "Reset command to Pkt Switch module. 
         Applicable only for x25FRChannel.
         The command will have no effect on x25FRConfigChannel."
    ::= { lanrangerLinkPktSwEntry 7 }



-- lanrangerStation group contains a list of remote workstations and related information

lanrangerStation OBJECT IDENTIFIER ::= {lanranger 3}

lanrangerStationTable OBJECT-TYPE
      SYNTAX  SEQUENCE OF LanrangerStationEntry
      MAX-ACCESS  not-accessible
      STATUS  current
      DESCRIPTION
		      "A table that contains information about the stations 
		       on the remote LAN(s).
		       A remote LANRANger contains a list of stations on its 
		       LAN, while a main LANRANger contains a list of 
		       stations at all the remote sites it is connected to."
      ::= { lanrangerStation 1 }

lanrangerStationEntry OBJECT-TYPE
     SYNTAX LanrangerStationEntry
    MAX-ACCESS  not-accessible
    STATUS  current
    DESCRIPTION
	      "Information about a specific station, that the LANRANger 
	       lists as being on a remote LAN."
 INDEX { lanrangerStationPhysLink, lanrangerStationLogLink,	lanrangerStationAddress}
    ::= { lanrangerStationTable 1 }

LanrangerStationEntry ::=
      SEQUENCE {
	lanrangerStationPhysLink
	      Integer32,
	lanrangerStationLogLink
	      Integer32,
	lanrangerStationAddress
	      MacAddress,
	lanrangerStationStatus
	      INTEGER,
	lanrangerStationSpoofingStatus
	      INTEGER
      }

lanrangerStationPhysLink OBJECT-TYPE
     SYNTAX  Integer32
    MAX-ACCESS  read-only
    STATUS  current
    DESCRIPTION
	    "The number of the physical link that is connected to the 
	     remote LAN on which the station with the associated 
	     instance of lanrangerStationAddress is located. The number 
	     is the same as the ifIndex of the link. The value will be 
	     zero on a remote LANRANger"
    ::= { lanrangerStationEntry 1 }

lanrangerStationLogLink OBJECT-TYPE
     SYNTAX  Integer32 
     MAX-ACCESS  read-only
     STATUS  current
     DESCRIPTION
	   "The number of the logical link that is connected
	    to the remote LAN on which the station with the associated 
	    instance of lanrangerStationAddress	is located.  The value 
	    will be zero on a remote LANRANger.
	    noLogicLink = 65535"
     ::= { lanrangerStationEntry 2 }

lanrangerStationAddress OBJECT-TYPE
     SYNTAX  MacAddress
     MAX-ACCESS  read-only
     STATUS  current
     DESCRIPTION
	     "The unicast MAC address  of a station that the LANRANger 
	     lists as being on a remote LAN."
     ::= { lanrangerStationEntry 3 }

lanrangerStationStatus OBJECT-TYPE
     SYNTAX  INTEGER {
		 unknown(1),
		 learned(2),
		 self   (3),
		 static (4)
	     }
     MAX-ACCESS  read-only
     STATUS  current
     DESCRIPTION
	 "The status of this entry.  The meanings of the
      values are:
		unknown(1) : 
	    learned(2) : the value of the corresponding 
		       	   instance of lanrangerStationAddress was
			       learned and is being used.

		self(3)    : the value of the corresponding
			         instance of lanrangerStationAddress
			         represents the LANRANger's address.
			           

		static(4)  : the value of the corresponding
			         instance of lanrangerStationAddress is
			         also the value of an existing
			         instance of lanrangerStaticAddress."
      ::= { lanrangerStationEntry 4 }

lanrangerStationSpoofingStatus OBJECT-TYPE
   SYNTAX  INTEGER { 
   off(2),
   on (3) 
   }
   MAX-ACCESS  read-only
   STATUS  current
   DESCRIPTION
     "The spoofing status of this entry."
     ::= { lanrangerStationEntry 5 }



lanrangerLanMaxStations OBJECT-TYPE
   SYNTAX  Integer32
   MAX-ACCESS  read-only
   STATUS  current
   DESCRIPTION
     "The maximum number of stations in the station table."
     ::= { lanrangerStation 2 }

lanrangerLanCurrentStations OBJECT-TYPE
   SYNTAX  Integer32
   MAX-ACCESS  read-only
   STATUS  current
   DESCRIPTION
     "The current number of stations in the station table."
     ::= { lanrangerStation 3 }

--Permanent Stations


lanrangerPermanentStation OBJECT IDENTIFIER
     ::= { lanrangerStation 4 }

   lanrangerPermanentMaxEntries OBJECT-TYPE
      SYNTAX  Integer32
      MAX-ACCESS  read-only
      STATUS  current
      DESCRIPTION
        "The maximum number of entries in the permanent stations table."
      ::= { lanrangerPermanentStation 1 }

   lanrangerPermanentCurrentEntries OBJECT-TYPE
      SYNTAX  Integer32
      MAX-ACCESS  read-only
      STATUS  current
      DESCRIPTION
        "The current number of entries in the permanent stations table."
      ::= { lanrangerPermanentStation 2 }


   lanrangerPermanentTable OBJECT-TYPE
      SYNTAX  SEQUENCE OF LanrangerPermanentEntry
      MAX-ACCESS  not-accessible
      STATUS  current
      DESCRIPTION
          "A table containing address information
           configured into the LANRANger by (local or network)
           management, specifying addresses on a remote LAN. 
           This table objects can be set only on a Remote LANRANger."
      ::= { lanrangerPermanentStation 3 }

   lanrangerPermanentEntry OBJECT-TYPE
      SYNTAX  LanrangerPermanentEntry
      MAX-ACCESS  not-accessible
      STATUS  current
      DESCRIPTION
            "Address information configured into the remote LANRANger
             by (local or network) management specifying addresses 
             on a remote LAN."
      INDEX   { lanrangerPermanentIfIndex, lanrangerPermanentLogLink, 
                lanrangerPermanentAddress }
      ::= { lanrangerPermanentTable 1 }

   LanrangerPermanentEntry ::=
      SEQUENCE {
        lanrangerPermanentIfIndex 
   	  	Integer32,
        lanrangerPermanentLogLink 
		Integer32,
        lanrangerPermanentAddress
        MacAddress,
        lanrangerPermanentOperation
        INTEGER
         }
   lanrangerPermanentIfIndex OBJECT-TYPE
      SYNTAX  Integer32
      MAX-ACCESS  read-only
      STATUS  current
      DESCRIPTION
            "The number of the physical link that is connected to 
             the remote LAN, on which the station with the 
             associated instance of lanrangerStationAddress is 
             located.
             The number is the same as the ifIndex of the link.
             This data is interesting for main LANRANger only."
      ::= { lanrangerPermanentEntry 1 }

   lanrangerPermanentLogLink OBJECT-TYPE
      SYNTAX  Integer32 
      MAX-ACCESS  read-only
      STATUS  current
      DESCRIPTION
           "The number of the logical link that is connected to the
            remote LAN, on which the station with the associated 
            instance of lanrangerPermanentAddress is located.
            The value will be noLogicLink on a remote LANRANger.
            This data is interesting for main LANRANger only.
            noLogicLink = 65535"
      ::= { lanrangerPermanentEntry 2 }

   lanrangerPermanentAddress OBJECT-TYPE
      SYNTAX  MacAddress
      MAX-ACCESS  read-only
      STATUS  current
      DESCRIPTION
             "The  MAC address  entered by management to this entry. 
              Only the remote LANRANger will accept Set for this object !
                       ----------------                          "
      ::= { lanrangerPermanentEntry 3 }

   lanrangerPermanentOperation OBJECT-TYPE
      SYNTAX  INTEGER {
                     active (1),
                     delete (2)
             }
      MAX-ACCESS  read-write
      STATUS  current
      DESCRIPTION
             "This object indicates the status of this entry.
                active(1) - this entry is currently in use
                            and will remain so even after the next
                            reset of the LANRANger.
                delete(2) - writing this value to the object
                            removes the corresponding entry. 
              Only the remote LANRANger will accept Set for this object !
                       ----------------               "
      ::= { lanrangerPermanentEntry 4 }


--IP Stations

lanrangerIpStation OBJECT IDENTIFIER
     ::= { lanrangerStation 5 }

   lanrangerIpPermanentAvailableEntries OBJECT-TYPE
      SYNTAX  Integer32
      MAX-ACCESS  read-only
      STATUS  current
      DESCRIPTION
        "The available number of entries in the IP permanent stations 
         table."
      ::= { lanrangerIpStation 1 }

   lanrangerIpPermanentCurrentEntries OBJECT-TYPE
      SYNTAX  Integer32
      MAX-ACCESS  read-only
      STATUS  current
      DESCRIPTION
        "The current number of entries in the IP permanent station table."
      ::= { lanrangerIpStation 2 }


-- The IP Permanent Stations table will be supported via the 
-- IP Forward table of RFC1354.MIB.


  lanrangerSpoofingStation  OBJECT IDENTIFIER
       ::= {lanrangerStation 6}

  lanrangerSpoofingMaxEntries OBJECT-TYPE
	   SYNTAX Integer32
	   MAX-ACCESS read-only
	   STATUS current
	   DESCRIPTION
	      "The maximum number of entries in the Spoofing station
		   table."
	   ::= {lanrangerSpoofingStation 1}

  lanrangerSpoofingCurrentEntries OBJECT-TYPE
	   SYNTAX Integer32
	   MAX-ACCESS read-only
	   STATUS current
	   DESCRIPTION
	      "The current number of entries in the Spoofing station
		   table."
	   ::= {lanrangerSpoofingStation 2}

  lanrangerSpoofingTable OBJECT-TYPE
       SYNTAX SEQUENCE OF LanrangerSpoofingEntry
       MAX-ACCESS not-accessible
       STATUS current
       DESCRIPTION
          "A list of Spoofing entries. The number of entries is 
           up to the current number of entries, according to the 
           LANRANger model. 
           Only the LOCAL LANRANger will show this table !
                    ---------------                          "

       ::= { lanrangerSpoofingStation 3 }

    lanrangerSpoofingEntry OBJECT-TYPE
       SYNTAX  LanrangerSpoofingEntry
       MAX-ACCESS  not-accessible
       STATUS  current
       DESCRIPTION
           "Spoofing parameters per entry of the Spoofing table."
       INDEX   {lanrangerSpoofingGroup,  lanrangerSpoofingMacAddress }
       ::= { lanrangerSpoofingTable 1 }

    LanrangerSpoofingEntry ::=
       SEQUENCE {
              lanrangerSpoofingGroup
			  Integer32,
              lanrangerSpoofingMacAddress
               MacAddress ,
              lanrangerSpoofingAging
               Integer32,
			  lanrangerSpoofingTimeLeft
			   Integer32
          }

      lanrangerSpoofingGroup   OBJECT-TYPE 
          SYNTAX  Integer32 
          MAX-ACCESS  read-only
          STATUS  current
          DESCRIPTION
             " 	The spoofing group.
                Only the LOCAL Lanranger will show this table !   "
          ::= {  lanrangerSpoofingEntry 1 }


      lanrangerSpoofingMacAddress   OBJECT-TYPE 
          SYNTAX  MacAddress 
          MAX-ACCESS  read-only
          STATUS  current
          DESCRIPTION
             " 	MAC Address of the Remote Lanrangers.
                Only the LOCAL Lanranger will show this table !   "
          ::= {  lanrangerSpoofingEntry 2 }

      lanrangerSpoofingAging OBJECT-TYPE
           SYNTAX Integer32 
           MAX-ACCESS read-only
           STATUS current
           DESCRIPTION
              " Aging time defined for a whole group, in minutes.      
                Only the LOCAL Lanranger will show this table !   "
           ::= { lanrangerSpoofingEntry 3 }

      lanrangerSpoofingTimeLeft OBJECT-TYPE
           SYNTAX Integer32 
           MAX-ACCESS read-only
           STATUS current
           DESCRIPTION
              " Time until aging expires, per station, in minutes.      
                Only the LOCAL Lanranger will show this table !   "
           ::= { lanrangerSpoofingEntry 4 }


--PPP Table for the WebRanger

wrPPPTable OBJECT-TYPE
      SYNTAX SEQUENCE OF WrPPPEntry
      MAX-ACCESS not-accessible
      STATUS current
      DESCRIPTION
          "This table contains only parameters that do not exist in the PPP
           standard MIBS.
           The table contains a list of PPP entries.  
           The number of entries is up to ifIndex."
      ::= { lanrangerInterface 5 }
      
wrPPPEntry OBJECT-TYPE
    SYNTAX WrPPPEntry
    MAX-ACCESS not-accessible
    STATUS current
    DESCRIPTION
        "LANRANger-specific parameter values for a PPP."
    INDEX {ifIndex }
    ::= { wrPPPTable 1 }

WrPPPEntry ::=
    SEQUENCE {
        wrPPPCompressionHeaderField				INTEGER,
        wrPPPCompressionProtocolFields			INTEGER,
        wrPPPSTACCompressionType				INTEGER,
	    wrPPPAuthProtocol						INTEGER,
	    wrPPPSecurityType						INTEGER,
	    wrPPPUserName							SnmpAdminString,
	    wrPPPPassword							SnmpAdminString,
	    wrPPPLinkActiveTime						Integer32,
        wrPPPIPCPSubnetMaskNegotiation			InterfaceIndexOrZero,
		wrPPPLinkControlProtocolStatus			INTEGER,
		wrPPPAuthenticationStatus				INTEGER,
		wrPPPIpcpStatus							INTEGER,
		wrPPPAssignedIPAddress					IpAddress,
	    wrPPPActualAuthProtocol					INTEGER,
		wrPPPIpTranslationMode					INTEGER,
		wrPPPTranslatedIpAddr					IpAddress
         }

wrPPPCompressionHeaderField OBJECT-TYPE
    SYNTAX INTEGER
	    { compressionOff (2),
		  compressionOn (3) }
    MAX-ACCESS read-write
    STATUS current
    DESCRIPTION "This configuration option provides a method to negotiate the
                 compression of the Data Link Layer Address and Control fields.
                 This configuration option is sent to inform the peer that the
                 implementation can receive compressed Address and Control fields."
    ::= { wrPPPEntry 1 }

wrPPPCompressionProtocolFields OBJECT-TYPE
    SYNTAX INTEGER
	    { compressionOff (2),
		  compressionOn (3) }
    MAX-ACCESS read-write
    STATUS current
    DESCRIPTION "This configuration option provides a method to negotiate the
                 compression of the PPP Protocol field. This configuration option
                 is sent to inform the peer that the implementation can receive
                 such single octet Protocol fields. "
    ::= { wrPPPEntry 2 }

wrPPPSTACCompressionType OBJECT-TYPE
    SYNTAX INTEGER
	    { disable (1),
		  noHistory (2),
		  lCB (3),
		  sequence (4),
		  extended (5) }
    MAX-ACCESS read-write
    STATUS current
    DESCRIPTION "The PPP compression control protocol provides a method to negotiate
                 and utilize compression protocol over PPP encapsulated links. 
                 These are Different types of data compression algorithm for PPP
                 encapsulated packets. "
    ::= { wrPPPEntry 3 }

wrPPPAuthProtocol OBJECT-TYPE
    SYNTAX INTEGER
            { 
		noneNone (1), 
		chapNone (2), 
		chapPap (3), 
		chapChap (4), 
		papNone (5), 
		papPap (6)
		 }
    MAX-ACCESS read-write
    STATUS current
    DESCRIPTION 
	"The type of authentication protocol being used. The left parameter
         is the maximum authentication, the right parameter is minimum authentication."
    ::= { wrPPPEntry 4 }

wrPPPSecurityType OBJECT-TYPE
    SYNTAX INTEGER
            { 
		host (1),
		guest (2) 
		}
    MAX-ACCESS read-write
    STATUS current
    DESCRIPTION 
	"Type of unit."
    ::= { wrPPPEntry 5 }


wrPPPUserName OBJECT-TYPE
    SYNTAX SnmpAdminString (SIZE (0..36))
    MAX-ACCESS read-write
    STATUS current
    DESCRIPTION 
	"PPP User name."
    ::= { wrPPPEntry 6 }

wrPPPPassword OBJECT-TYPE
    SYNTAX SnmpAdminString (SIZE (0..36))
    MAX-ACCESS read-write
    STATUS current
    DESCRIPTION 
	"PPP Password ."
    ::= { wrPPPEntry 7 }

wrPPPLinkActiveTime OBJECT-TYPE
    SYNTAX Integer32 
    MAX-ACCESS read-write
    STATUS current
    DESCRIPTION 
	"PPP link active time in seconds 
	Values range: 2 - 900.
	Default value = 2     "
    ::= { wrPPPEntry 8 }

wrPPPIPCPSubnetMaskNegotiation OBJECT-TYPE
    SYNTAX InterfaceIndexOrZero
    MAX-ACCESS read-write
    STATUS current
    DESCRIPTION 
	"This object indicates the ifIndex of the link (LAN port)
	 through which IPCP Subnet Mask negotiation is allowed.
	 The distinguished value of zero may be used if no link
	 is enabled for IPCP Subnet Mask negotiation.
	   
	 For LA-110, IPCP Subnet Mask support allows Customer Premises 
	 Equipment (CPE) to connect to a Broadband Access Server (BAS)
	 and obtain an IP address and subnet range that the CPE can
	 use to populate the DHCP server database. The IP address
     is also used to configure an IP interface over the LAN port.
     The IP Address is dynamically allocated by the DHCP Server,
     using the DHCP Pool that was allocated over the PPP connection.
     In order to connect one of the LANs to Subnet Mask Negotiation, 
     its IP Address should be 0.0.0.0. When the IP Address is allocated
     from the PPP, the 0.0.0.0 IP Address is replaced in the data base 
     by the allocated IP Address. Only one Subnet Mask Negotiation on WAN
     interface can be enabled at the same time in order to avoid 
     allocating the LAN IP address according to a few WAN
     interfaces (a one-on-one connection). 
     The linked LAN interface can be deleted only after disabling the
     Subnet Mask Negotiation on the PPP connection."
    ::= { wrPPPEntry 9 }

 wrPPPLinkControlProtocolStatus   OBJECT-TYPE
    SYNTAX INTEGER
            { 
		notApplicable (1),
		close         (2),
		open          (3) 
		}
    MAX-ACCESS read-only
    STATUS current
    DESCRIPTION 
	"PPP Link Control Protocol(LCP) Status"
    ::= { wrPPPEntry 10 }	
    	
wrPPPAuthenticationStatus   OBJECT-TYPE
    SYNTAX INTEGER
        { 
		notApplicable (1),
		failed        (2),
		passed        (3) 
		}
    MAX-ACCESS read-only
    STATUS current
    DESCRIPTION 
	"PPP Authentication status."
    ::= { wrPPPEntry 11 }

wrPPPIpcpStatus       OBJECT-TYPE
    SYNTAX INTEGER
        { 
		notApplicable (1),
		close         (2),
		open          (3) 
		}
    MAX-ACCESS read-only
    STATUS current
    DESCRIPTION 
	"IPCP (IP Control Protocol) status."
    ::= { wrPPPEntry 12}

wrPPPAssignedIPAddress       OBJECT-TYPE
    SYNTAX IpAddress
    MAX-ACCESS read-only
    STATUS current
    DESCRIPTION 
	"IP Address assigned by PPP."
    ::= { wrPPPEntry 13} 

wrPPPActualAuthProtocol OBJECT-TYPE
    SYNTAX INTEGER
	{ 
		none		(1), 
		pap			(2), 
		chap		(3)
	}
    MAX-ACCESS read-only
    STATUS current
    DESCRIPTION 
	"The Actual type of Authentication Protocol that is used."
    ::= { wrPPPEntry 14 }

wrPPPIpTranslationMode OBJECT-TYPE
	SYNTAX		INTEGER
	{ 
		disable		(2),
		enable 		(3)
	}
	MAX-ACCESS	read-write
    STATUS		current
    DESCRIPTION
   	"This object enables the IP Translation Mode."
    ::= { wrPPPEntry 15 }

wrPPPTranslatedIpAddr OBJECT-TYPE
	SYNTAX		IpAddress
	MAX-ACCESS	read-write
    STATUS		current
    DESCRIPTION
   	"This object represents the Translated IP Address.
   	 It is relevant only when IP Translation Mode is 'enable'."
    ::= { wrPPPEntry 16 }


-- ML-PPP (Multilink PPP) Table

wrMLPPPTable OBJECT-TYPE
      SYNTAX SEQUENCE OF WrMLPPPEntry
      MAX-ACCESS not-accessible
      STATUS current
      DESCRIPTION
          "This table contains a list of ML-PPP entries."
      ::= { lanrangerInterface 6 }
      
wrMLPPPEntry OBJECT-TYPE
    SYNTAX WrMLPPPEntry
    MAX-ACCESS not-accessible
    STATUS current
    DESCRIPTION
        "Specific parameter values for a ML-PPP."
    INDEX {ifIndex }
    ::= { wrMLPPPTable 1 }

WrMLPPPEntry ::=
    SEQUENCE {
        wrMLPPPEpDiscriminatorEnable  INTEGER,
		wrMLPPPReorderingEnable       INTEGER,
		wrMLPPPTxQueueSize            Unsigned32
         }

wrMLPPPEpDiscriminatorEnable OBJECT-TYPE
	SYNTAX INTEGER {
    	no	(2),
    	yes	(3)
	}
	MAX-ACCESS read-write
	STATUS current
	DESCRIPTION
    	"Indicates whether the Endpoint Discriminator Option is enabled.
    	 
    	 The Endpoint Discriminator Option represents identification of the
		 system transmitting the packet.  This option advises a system that
		 the peer on this link could be the same as the peer on another
		 existing link.  If the option distinguishes this peer from all
		 others, a new bundle MUST be established from the link being
		 negotiated.  If this option matches the class and address of some
		 other peer of an existing link, the new link MUST be joined to the
		 bundle containing the link to the matching peer or MUST establish a
		 new bundle.
		 
		 For more information about the Endpoint Discriminator Option -
		 see RFC-1990 (The PPP Multilink Protocol)."
	::= { wrMLPPPEntry 1 }

wrMLPPPReorderingEnable OBJECT-TYPE
	SYNTAX INTEGER {
		notApplicable (1),
    	no            (2),
    	yes           (3)
                    }
	MAX-ACCESS read-write
	STATUS current
	DESCRIPTION
	"Indicates whether packets reordering option is enabled.
    	 yes - packets received from MLPPP not in order are 
    	       reordered, according to sequence number, 
    	       before being transmitted to egress port.
    	 no -  received packets are transmitted in the 
    	       same order as they arrived."
	::= { wrMLPPPEntry 2 }

wrMLPPPTxQueueSize OBJECT-TYPE
	SYNTAX Unsigned32
	MAX-ACCESS read-write
	STATUS current
	DESCRIPTION
	"Indicates the number of frames in the Tx Queue."
	::= { wrMLPPPEntry 3 }

-- PPPoE (Point-to-Point Protocol over Ethernet)

pPPoE		OBJECT IDENTIFIER ::= { lanrangerInterface 7 }

pPPoETable OBJECT-TYPE
	SYNTAX SEQUENCE OF PPPoEEntry
	MAX-ACCESS	not-accessible
	STATUS		current
	DESCRIPTION
		"The PPPoE (Point-to-Point Protocol over Ethernet) Table."
	::= { pPPoE 1 }
      
pPPoEEntry OBJECT-TYPE
	SYNTAX		PPPoEEntry
	MAX-ACCESS	not-accessible
	STATUS		current
	DESCRIPTION
		"An entry in the PPPoE Table."
	INDEX { pPPoECnfgIdx, pPPoEID }
	::= { pPPoETable 1 }

PPPoEEntry ::=
    SEQUENCE {
        pPPoECnfgIdx			   			Unsigned32,
        pPPoEID					  			Unsigned32,
        pPPoERowStatus			   			RowStatus,
        pPPoEACName				   			SnmpAdminString,
	    pPPoEServiceName			 		SnmpAdminString,
		pPPoEEntityPointer					RowPointer,
	    pPPoESessionStatus			 		INTEGER,
	    pPPoESessionID				 		Unsigned32,
	    pPPoERemoteMacAddr			 		MacAddress,
        pPPoENoOfUsages		   				Unsigned32,
	    pPPoESchedRestartMode		 		INTEGER,
	    pPPoESchedRestartTime		 		DisplayString,
        pPPoESchedRestartRandomRange		Unsigned32,
	    pPPoESchedRestartActualTime	 		DisplayString,
		pPPoEInitDelayRandomRange			Unsigned32,
		pPPoEInitActualDelay				Unsigned32,
		pPPoEVlanTagging					INTEGER,
		pPPoEVlanId							Unsigned32,
		pPPoEVlanPriority					Unsigned32
		}

pPPoECnfgIdx OBJECT-TYPE
	SYNTAX		Unsigned32
	MAX-ACCESS	not-accessible
    STATUS		current
    DESCRIPTION
    	"This object represents the first index of the table.
    	 It can serve for Configuration index or other."
    ::= { pPPoEEntry 1 }

pPPoEID OBJECT-TYPE
	SYNTAX		Unsigned32
	MAX-ACCESS	not-accessible
    STATUS		current
    DESCRIPTION
    	"This object represents the PPPoE unique Identifier."
    ::= { pPPoEEntry 2 }

pPPoERowStatus OBJECT-TYPE
    SYNTAX      RowStatus
    MAX-ACCESS  read-create
    STATUS      current
    DESCRIPTION
    "This object enables the user to create/delete entries in this table."
    ::= { pPPoEEntry 3 }

pPPoEACName OBJECT-TYPE
	SYNTAX		SnmpAdminString
	MAX-ACCESS	read-create
    STATUS		current
    DESCRIPTION
    	"This object represents the Name of the Access Concentrator,
    	 with which the PPPoE session should be established."
    ::= { pPPoEEntry 4 }

pPPoEServiceName OBJECT-TYPE
	SYNTAX		SnmpAdminString
	MAX-ACCESS	read-create
    STATUS		current
    DESCRIPTION
    	"This object represents the Name of a specific Service
    	 that will be requested on this PPPoE session."
    ::= { pPPoEEntry 5 }

pPPoEEntityPointer OBJECT-TYPE
    SYNTAX      RowPointer
    MAX-ACCESS  read-create
    STATUS      current
    DESCRIPTION
    "This parameter represents the entity (interface/port etc)
     that is connected to this PPPoE.

	 The value of this parameter is a pointer to an existing row of a table,
	 where the entity connected to this PPPoE is defined.
		
	 Example:

	 In case of an interface (from 2863.ifTable):
		points to 'ifEntry' of corresponding row
		= <ifEntry OID>.<ifIndex>
     ."
    ::= { pPPoEEntry 6 }

pPPoESessionStatus OBJECT-TYPE
	SYNTAX		INTEGER
		{ 
			notApplicable	(1),
			down			(2),
			up				(3) 
		}
	MAX-ACCESS	read-only
    STATUS		current
    DESCRIPTION
    	"This object represents the Status of the PPPoE session."
    ::= { pPPoEEntry 7 }

pPPoESessionID OBJECT-TYPE
	SYNTAX		Unsigned32
	MAX-ACCESS	read-only
    STATUS		current
    DESCRIPTION
    	"This object represents PPPoE Session ID."
    ::= { pPPoEEntry 8 }

pPPoERemoteMacAddr OBJECT-TYPE
	SYNTAX		MacAddress
	MAX-ACCESS	read-only
    STATUS		current
    DESCRIPTION
    	"This object represents the MAC Address of the Access Concentrator,
    	 with which the PPPoE session is established."
    ::= { pPPoEEntry 9 }

pPPoENoOfUsages OBJECT-TYPE
	SYNTAX		Unsigned32
	MAX-ACCESS	read-only
    STATUS		current
    DESCRIPTION
    	"This object represents the number of times this PPPoE is used."
    ::= { pPPoEEntry 10 }

pPPoESchedRestartMode OBJECT-TYPE
	SYNTAX		INTEGER
		{ 
			notApplicable	(1),
			disable			(2),
			enable			(3) 
		}
	MAX-ACCESS	read-create
    STATUS		current
    DESCRIPTION
    	"This object represents Scheduled Restart Mode."
    ::= { pPPoEEntry 11 }

pPPoESchedRestartTime OBJECT-TYPE
	SYNTAX		DisplayString
	MAX-ACCESS	read-create
    STATUS		current
    DESCRIPTION
    	"This object represents Scheduled Restart Time.
    	 It is relevant only when Scheduled Restart Mode is 'enable'."
    ::= { pPPoEEntry 12 }

pPPoESchedRestartRandomRange OBJECT-TYPE
	SYNTAX		Unsigned32
	MAX-ACCESS	read-create
    STATUS		current
    DESCRIPTION
    	"This object represents Scheduled Restart Random Range (in seconds).
		 It is relevant only when Scheduled Restart Mode is 'enable'.

		 A scheduled restart Random VALUE (number of seconds) is selected
		 within this Random Range.
		 
		 This VALUE is added to configured Scheduled Restart Time, so that
		 Actual Restart Time = Configured Restart Time + VALUE,
		 in order to create a differentiation between all PPPoE entities
		 with the same configured Scheduled Restart Time.

		 Note:
		 When Random Range is 0 -->
		 Random VALUE must be 0 -->
		 Actual Restart Time = Configured Restart Time."
    ::= { pPPoEEntry 13 }

pPPoESchedRestartActualTime OBJECT-TYPE
	SYNTAX		DisplayString
	MAX-ACCESS	read-only
    STATUS		current
    DESCRIPTION
    	"This object represents Scheduled Restart Actual Time.
		 It is relevant only when Scheduled Restart Mode is 'enable'.
		 For calculation of this time - see pPPoESchedRestartRandomRange."
    ::= { pPPoEEntry 14 }

pPPoEInitDelayRandomRange  OBJECT-TYPE
	SYNTAX		Unsigned32
	MAX-ACCESS	read-create
    STATUS		current
    DESCRIPTION
    	"This object represents the Initialization Delay Random Range (in seconds).
		 An initialization DELAY (number of seconds) is selected within this Random Range.
		 
		 This DELAY is used to delay the initialization of every PPPoE session,
		 meaning that whenever a PPPoE session is reestablished,
		 the device will send the first PPPoE initialization packet (PADI)
		 only after this DELAY (in seconds).
		 
		 Note:
		 When Random Range = 0 -->
		 there will be no delay in the initialization process."
    ::= { pPPoEEntry 15 }

pPPoEInitActualDelay OBJECT-TYPE
	SYNTAX		Unsigned32
	MAX-ACCESS	read-only
    STATUS		current
    DESCRIPTION
    	"This object represents Initialization Delay (in seconds),
		 as selected within Initialization Delay Random Range (pPPoEInitDelayRandomRange)."
    ::= { pPPoEEntry 16 }

pPPoEVlanTagging OBJECT-TYPE
	SYNTAX		INTEGER
		{ 
			notApplicable	(1),
			untag			(2),
			tag				(3)
		}
	MAX-ACCESS	read-create
    STATUS		current
    DESCRIPTION
    	"This object represents the VLAN Tagging."
    ::= { pPPoEEntry 17 }

pPPoEVlanId OBJECT-TYPE
	SYNTAX		Unsigned32
	MAX-ACCESS	read-create
    STATUS		current
    DESCRIPTION
    	"This object represents the VLAN ID."
    ::= { pPPoEEntry 18 }

pPPoEVlanPriority OBJECT-TYPE
	SYNTAX		Unsigned32
	MAX-ACCESS	read-create
    STATUS		current
    DESCRIPTION
    	"This object represents the VLAN Priority."
    ::= { pPPoEEntry 19 }


-- Traps for use by the LANRANger

--NOTIFICATIONS

lanrangerEvents OBJECT-IDENTITY
    STATUS  current
	DESCRIPTION
	"The events for the LANRANger."
	::= { lanranger 0 }

lanrangerLogLinkUp NOTIFICATION-TYPE
    OBJECTS  { lanrangerLinkConnPhysLink, lanrangerLinkConnAid }
    STATUS  current
    DESCRIPTION
            "The lanrangerLogLinkUp trap indicates that the indicated logical link is connected."
	::= { lanrangerEvents 1 }

lanrangerLogLinkDown NOTIFICATION-TYPE
    OBJECTS  { lanrangerLinkConnPhysLink, lanrangerLinkConnAid }
    STATUS  current
    DESCRIPTION
            "The lanrangerLogLinkDown trap indicates that the indicated logical link is disconnected."
	::= { lanrangerEvents 2 }

lanrangerLanTableOverflow NOTIFICATION-TYPE
    STATUS  current
    DESCRIPTION
            "The station table has the maximum number of addresses for the LANRANger."
	::= { lanrangerEvents 3 }

lanrangerStatusChanged NOTIFICATION-TYPE
    OBJECTS  { agnLed }
    STATUS  current
    DESCRIPTION
            "The trap indicates changes in the device status ."
	::= { lanrangerEvents 4 }
-- 
-- file :D:\Synergy\WorkArea\545\mib_rad\txt\febftb.txt
-- 


-- Title:  FEB MIB   
-- Version:   1.0
-- Date:    29 August 94
-- By:       Orly Nicklass
--File:       febftb.txt
-- Comments:  This MIB is for FEBs and FTBs.  These bridges also support the following MIBs:
--              - MIB-II  ( RFC1213 )
--              - BRIDGE - MIB  ( RFC1493)
--	- FDDI MIB (RFC  1512)
-- The FDDI bridges also support the RAD General Bridge Branch, 164.4.1

--  Objects in this MIB are arranged into groups:
--   febFtbTranslation  -  Defines parameters for translation of Ethernet and Token-Ring to/from FDDI 
--   febFtbStatus    
-- At the end of the MIB there is a definition of all FDDI bridge-specific traps. 

febFtb  OBJECT IDENTIFIER ::= { radBridges 4 }
febFtbTranslation    OBJECT IDENTIFIER ::= { febFtb 1 }
febFtbStatus    OBJECT IDENTIFIER ::= { febFtb 2 }


febFtbTranslIfTable OBJECT-TYPE
    SYNTAX   SEQUENCE OF FebFtbTranslIfEntry
    MAX-ACCESS   not-accessible
    STATUS   current
    DESCRIPTION
       "The translation table defines which type of translation is required for each device interface. This is
       particularly important for WAN links, as the translating device does not have a knowledge of the 
       target LAN type."
    ::= { febFtbTranslation 1 }

febFtbTranslIfEntry  OBJECT-TYPE
    SYNTAX   FebFtbTranslIfEntry
    MAX-ACCESS   not-accessible
    STATUS   current
    DESCRIPTION
        "Entry in the translation table."
    INDEX { febFtbTranslIfIndex}
    ::= { febFtbTranslIfTable 1 }


FebFtbTranslIfEntry ::=
     SEQUENCE {
febFtbTranslIfIndex
        Integer32,
febFtbTunnelProtocol 
        OCTET STRING,
febFtbTranslIPXRawEthernet
        INTEGER
}
febFtbTranslIfIndex OBJECT-TYPE
    SYNTAX Integer32 
    MAX-ACCESS  read-only
    STATUS  current
    DESCRIPTION
          "Index to the Translation Table. The interface defined by a  particular value of this index is the 
          same interface as identified by the same value of ifIndex (MIBII)."
    ::= { febFtbTranslIfEntry 1 }

febFtbTunnelProtocol OBJECT-TYPE
    SYNTAX OCTET STRING (SIZE (2))
    MAX-ACCESS  read-write
    STATUS  current
    DESCRIPTION
          "IEEE 802.1h standard defines the tunneling for Appletalk I. This parameter enables the user
           to specify Ethertype of an additional protocol to tunnel (e.g. IPX). For IPX, Enter 8137 to
           translate Token Ring SNAP frames to Ethernet_SNAP frames (instead of Ethernet II).
           Valid range of values: 05DC to FFFF (hex)
           0000 (hex) - disables this function. "
    ::= { febFtbTranslIfEntry 2 }

febFtbTranslIPXRawEthernet OBJECT-TYPE
    SYNTAX INTEGER {
          ethernetRaw8023(1),
          ethernet8022(2)
   }
    MAX-ACCESS  read-write
    STATUS  current
    DESCRIPTION
	"This variable defines the translation mode for IPX frames in standrad Token Ring format. It is 
                applicable to Ethernet interfaces (i.e. febFtbTranslSwitch variable has value Ethernet (2). ).
                ethernetRaw8023:   translate to Raw Ethernet frames (default)
               ethernet8022:   translate to Ethernet 802.2 frames."
     ::= { febFtbTranslIfEntry 3 }

febFtbLanTable OBJECT-TYPE
    SYNTAX   SEQUENCE OF FebFtbLanTabEntry
    MAX-ACCESS   not-accessible
    STATUS   current
    DESCRIPTION
       "."
    ::= { febFtbStatus    1 }

febFtbLanTabEntry  OBJECT-TYPE
    SYNTAX   FebFtbLanTabEntry
    MAX-ACCESS   not-accessible
    STATUS   current
    DESCRIPTION
        "Entry in the LanTab table."
    INDEX { febFtbLanTabIfIndex}
    ::= { febFtbLanTable 1 }

FebFtbLanTabEntry ::=
     SEQUENCE {
febFtbLanTabIfIndex
        Integer32,
febFtbLanTabEntNumber    
        Integer32 
}


febFtbLanTabIfIndex  OBJECT-TYPE
    SYNTAX Integer32 
    MAX-ACCESS  read-only
    STATUS  current
    DESCRIPTION
	"This variable defines the related interface"
     ::= { febFtbLanTabEntry  1 }

febFtbLanTabEntNumber    OBJECT-TYPE
    SYNTAX Integer32 
    MAX-ACCESS  read-only
    STATUS  current
    DESCRIPTION
	"This variable defines the number of entries in the LAN table reletaed to the specific interface"
     ::= { febFtbLanTabEntry   2 }

febFtbFaults    OBJECT-TYPE
    SYNTAX Integer32 
    MAX-ACCESS  read-only
    STATUS  current
    DESCRIPTION
	"This variable defines the current device faults. It is a 32 bits variable, where each bit represents
	a unique fault"
     ::= { febFtbStatus    2 }

--NOTIFICATIONS

febFtbEvents OBJECT-IDENTITY
    STATUS  current
	DESCRIPTION
	"The events for FEBs and FTBs."
	::= { febFtb 0 }

lanTableOverflow NOTIFICATION-TYPE
	STATUS  current
    DESCRIPTION
            "The station table has the maximum number of addresses for the device."
	  ::= { febFtbEvents 1 }

statusChanged NOTIFICATION-TYPE
    OBJECTS  {agnLed, agnIndication }
	STATUS  current
    DESCRIPTION
            "A change occured in agent status or leds."
	  ::= { febFtbEvents 2 }

portFddiStatusChanged NOTIFICATION-TYPE
    OBJECTS {fddimibPORTPCMState, agnLed }
	STATUS  current
    DESCRIPTION
            "The Fddi port status changed. fddimibPORTPCMState
             value has become off, maint, active, connect, or exited 
             one of these states."
	  ::= { febFtbEvents 3 }


-- 
-- file :D:\Synergy\WorkArea\545\mib_rad\txt\mlb.txt
-- 

-- Title:   RAD MLB MIB
--             
--             
-- Version: 1.0  
-- Date:    November, 20, 1994
-- By:      Ricky Yaffe
-- File:    mlb.txt

 mlb            OBJECT IDENTIFIER ::= { radBridges 5 }


--   Objects in this MIB are arranged into groups:
--   mlbConfig  -  MLB - specific configurable parameters
--   mlbAddress -  MLB - Table containing the list of ports address  .

--  At the end of the MIB there is a definition of all MLB - specific traps. 

mlbConfig OBJECT IDENTIFIER ::= { mlb 1 }

mlbMibVersion  OBJECT-TYPE 
    SYNTAX   OCTET STRING
    MAX-ACCESS   read-only
    STATUS   current
    DESCRIPTION
       "mlb private mib version ."
    ::= {  mlbConfig 1  }

mlbPanelMedia  OBJECT-TYPE 
    SYNTAX   INTEGER {
        unknown(1),
        copper(2),
        fiberOptic(3),
        notSupported (4)
        }
    MAX-ACCESS   read-only
    STATUS   current
    DESCRIPTION
       "The panel media. It can be fiber optic connector or STP+UTP
        in case of copper"
    ::= {  mlbConfig 2  }

mlbRRFrontPanelPort  OBJECT-TYPE 
    SYNTAX   INTEGER {
        unknown(1),
        secondary(2),
        main(3),
        notSupported (4)
        }
    MAX-ACCESS   read-only
    STATUS   current
    DESCRIPTION
       "Front panel port function : MainPort / Sec.Port (case of RADring card) ."
    ::= {  mlbConfig 3  }

mlbRRTermination  OBJECT-TYPE 
    SYNTAX   INTEGER {
        unknown(1),
        on(2),
        off(3),
        notSupported (4)
        }
    MAX-ACCESS   read-only
    STATUS   current
    DESCRIPTION
       "Temination switch - Split back lan and Terminate it. (case of RADring card) ."
    ::= {  mlbConfig 4  }

mlbAddress OBJECT IDENTIFIER ::= {mlb 2}

mlbAddressTable OBJECT-TYPE
      SYNTAX  SEQUENCE OF MlbAddressEntry
      MAX-ACCESS  not-accessible
      STATUS  current
      DESCRIPTION
       "A table that contains information about the MLB ports address ."
      ::= { mlbAddress 1 }

mlbAddressEntry OBJECT-TYPE
    SYNTAX  MlbAddressEntry
    MAX-ACCESS  not-accessible
    STATUS  current
    DESCRIPTION
       "Information about a specific port that the MLB lists define."
    INDEX {mlbPortIndex }
    ::= { mlbAddressTable 1 }

    MlbAddressEntry ::=
        SEQUENCE {
            mlbPortIndex
                Integer32,
            mlbBurnAddress
                MacAddress,
            mlbLocAddress
                MacAddress,
            mlbActiveAddress
                INTEGER
              }


mlbPortIndex OBJECT-TYPE
    SYNTAX Integer32
    MAX-ACCESS read-only
    STATUS current
    DESCRIPTION
        "A unique value for each port, equal to the value of ifIndex for the port. 
        The maximum number of ports for mlb is 2 . "
    ::= { mlbAddressEntry  1  }


mlbBurnAddress   OBJECT-TYPE 
    SYNTAX  MacAddress 
    MAX-ACCESS  read-only
    STATUS  current
    DESCRIPTION
	"This is the burned-in MacAddress on the LANRANger."
    ::= { mlbAddressEntry  2  }

mlbLocAddress   OBJECT-TYPE 
    SYNTAX  MacAddress 
    MAX-ACCESS  read-write
    STATUS  current
    DESCRIPTION
	"This is a locally administered address.  If a zero value appears, the network administrator 
	did  not set a locally administered address."
    ::= { mlbAddressEntry  3 }

mlbActiveAddress OBJECT-TYPE
     SYNTAX INTEGER {burnedIn(1), locallyAdministered(2) }
     MAX-ACCESS read-write
     STATUS current
     DESCRIPTION
         "The MAC address that is in use on the LANRANger. 
          The address selected will appear in ifPhysAddress."
     ::= { mlbAddressEntry  4 }


--NOTIFICATIONS

mlbEvents OBJECT-IDENTITY
    STATUS  current
	DESCRIPTION
	"The events for the MLB."
	::= { mlb 0 }

mlbLanTableOverflow NOTIFICATION-TYPE
    STATUS  current
    DESCRIPTION
         "The station table has the maximum number of addresses for the LANRANger."
	::= { mlbEvents 1 }

mlbStatusChanged NOTIFICATION-TYPE
    OBJECTS  { agnLed }
    STATUS  current
    DESCRIPTION
         "The trap indicates changes in the device status ."
	::= { mlbEvents 2 }

-- 
-- file :D:\Synergy\WorkArea\545\mib_rad\txt\cvt.txt
-- 


--Version:   1.0
--Date:   16.10.94              
--By:      RADLINX  &  Orly Nicklass
--File:       cvt.txt
--

genSnar OBJECT IDENTIFIER ::= { radConverters 1 } 
 --                SNAR - SNA conversion software
	--                STC, FTC - Token to SDLC conversion devices
	--                SEC, FEC - Ether to SDLC conversion devices
	--                XTC - X.25/QLLC conversion device
	--    
	--                Definitions apply to all products,
	--                  unless otherwise specified. 
	--                The devices are generally referred
	--                  as 'device'. 
	--    
       Sap         ::= OCTET STRING (SIZE (1))
       SdlcAddr    ::= OCTET STRING (SIZE (1))
--    OctetRange  ::= Integer32      (1..255)

	 --Active ::= INTEGER { inactive(1) , active(2) }
	 --Side   ::= INTEGER { sideA(1) , sideB(2) }
	 --Enable ::= INTEGER { disable(1) , enable(2) }


    --** THE SNAR TREE **--
     
    snarState OBJECT IDENTIFIER ::= { genSnar   1 } 
    snarNva   OBJECT IDENTIFIER ::= { genSnar    3 } 
    snarSna   OBJECT IDENTIFIER ::= { genSnar    5 } 
       
     -- 
     --    SNAR state group
     -- General state information
     --

  snarStatus   OBJECT-TYPE
	   SYNTAX  INTEGER {
	    up   (1),
	    down (2),
	    test (3)
	   }
	   MAX-ACCESS  read-write
	   STATUS  current
	   DESCRIPTION
	  " The status of the whole SNAR process
	      1 -up
	      2 -down
	      3 -test (After setting one of the previous states, the 
		status will be test until the changes will be done).
	   "
	::= { snarState 1 }

	snarBufferUsage   OBJECT-TYPE
	   SYNTAX  Integer32 (0..100)
	   MAX-ACCESS  read-only
	   STATUS  current
	   DESCRIPTION
	   " The buffer usage of the SNAR (in percentage).
	   "
	::= { snarState 2 }

	snarMaxSnaSession   OBJECT-TYPE
	   SYNTAX  Integer32 
	   MAX-ACCESS  read-only
	   STATUS  current
	   DESCRIPTION
	   " Max number of sessions supported in this SNAR implementation
	   "
	::= { snarState 3 }

      snarSaveChanges  OBJECT-TYPE
	 SYNTAX INTEGER{
	    noSave       (1),
	    save         (2),    
	    saveAndReset (3),
	    undoAllChanges (4)
	 }
	 MAX-ACCESS read-write
	 STATUS current
	 DESCRIPTION
	 "N/A to SNAR, only for devices. When changes are made to any 
	 configuration parameters (SNA, NVA or others) it should be 
	 stored in the device's NVRAM and then the device is restarted.
	 Using this variable the manager can:
	 2 - Just save into NVRAM all configuration changes
	 3 - Save into NVRAM the configuration changes and restart the
	     Device, to reflect the changes.
	 4 - Undo all  changes  since  last reset or
	     save, (without resetting the device).
	     Load the original configuration from the NVRAM. 
	 "
	::= { snarState 5 }   


	-- 
	-- snarNVA group    
	-- 
	-- Defines the NetView agent configuration and internal
	-- statistics,  applicable to SNAR and all devices
	-- 


	nvaAgentsNumber OBJECT-TYPE
	   SYNTAX  Counter32 
	   MAX-ACCESS  read-only
	   STATUS  current
	   DESCRIPTION
	   " The number of configured NetView agents
	   "
	::= { snarNva   2 }

      --*********
	nvaAgentTable  OBJECT-TYPE
	   SYNTAX SEQUENCE OF NvaAgentEntry
	   MAX-ACCESS not-accessible
	   STATUS current
	   DESCRIPTION
	  "
	  "
	::= { snarNva 3 }

	nvaAgentEntry  OBJECT-TYPE
	   SYNTAX NvaAgentEntry
	   MAX-ACCESS not-accessible
	   STATUS current
       DESCRIPTION
	   "An entry in table nvaAgentTable."
	   INDEX  { nvaAgIndex }
	::= { nvaAgentTable 1 }

	NvaAgentEntry ::=
	   SEQUENCE {
	      nvaAgIndex
		 Integer32,
	      nvaAgAdminStatus
		 INTEGER,
	      nvaAgOperState
		 INTEGER,
	      nvaAgFilter
		 OCTET STRING,
	      nvaAgAllowRunCmd
		 INTEGER,
	   --****CFG******
	      nvaAgAccessType
		 INTEGER,
	      nvaAgIfIndex
		 Integer32,
	      nvaAgXidBlockId
		 OCTET STRING,
	      nvaAgXidBlockNum
		 OCTET STRING,
	      nvaAgSSap
		 Sap,
	      nvaAgDSap
		 Sap,
	      nvaAgRemMacAddr
		 MacAddress,
	      nvaAgSdlcAddr
		 SdlcAddr,
	      nvaAgResourceName
		 DisplayString
	  }
	

	nvaAgIndex  OBJECT-TYPE
	   SYNTAX Integer32
	   MAX-ACCESS read-only
	   STATUS current
	   DESCRIPTION
	  "Agent number .
	   Range (1 - nvaAgentsNumber)
	  "
	::= { nvaAgentEntry 1 }

	nvaAgAdminStatus  OBJECT-TYPE
	   SYNTAX  INTEGER { disable(1) , enable(2) }
	   MAX-ACCESS read-write
	   STATUS current
	   DESCRIPTION
	  " The admin. status of NV AGENT. Value of 'disable'
	    will prevent the NetView agent from trying to 
	    connect to the NetView management system
	  "
	::= { nvaAgentEntry 3 }

	nvaAgOperState  OBJECT-TYPE
	   SYNTAX INTEGER { inactive(1) , active(2) }
	   MAX-ACCESS read-only
	   STATUS current
	   DESCRIPTION
	  " Current Operation state of the NetView agent. Active
	    state means that the NetView agent is in session
	    with the NetView management system
	  "
	::= { nvaAgentEntry 4 }

	nvaAgFilter  OBJECT-TYPE
	   SYNTAX OCTET STRING
	   MAX-ACCESS read-only
	   STATUS current
	   DESCRIPTION
	  "Alert filter bit mask. Each bit corresponds to a specific alert
	   sent by the NetView agent.
	  "
	::= { nvaAgentEntry 5 }

	nvaAgAllowRunCmd  OBJECT-TYPE
	   SYNTAX   INTEGER { disable(1) , enable(2) }
	   MAX-ACCESS read-write
	   STATUS current
	   DESCRIPTION
	  "Defines whether the NetView agent is allowed to handle
	   operational commands, received by the RUNCMD facility 
	  "
	::= { nvaAgentEntry 6 }

	nvaAgAccessType OBJECT-TYPE
	   SYNTAX INTEGER{
	     llcCsmacd     (1), 
	     llcTokenRing (3),    
	     sdlc           (6),
	     qllcX25       (10)
	    }
	   MAX-ACCESS read-write
	   STATUS current
	   DESCRIPTION
	  " Defines the method in which the agent tries to
	    connect to the NetView management system(the SNA host)
	  "
	::= { nvaAgentEntry 7 }

	nvaAgIfIndex OBJECT-TYPE
	   SYNTAX Integer32
	   MAX-ACCESS read-write
	   STATUS current
	   DESCRIPTION
	  " The port number of the interface in which the 
	    NetView agent connects to the SNA host
	  "
	::= { nvaAgentEntry 8 }

	nvaAgXidBlockId  OBJECT-TYPE
	   SYNTAX OCTET STRING (SIZE (2))
	   MAX-ACCESS read-write
	   STATUS current
	   DESCRIPTION
	  " The BLOCKID part of the XID information which the NetView agent
	    should use to connect to the NetView management system
	    (The SNA host)
	  "
	::= { nvaAgentEntry 9 }

	nvaAgXidBlockNum  OBJECT-TYPE
	   SYNTAX OCTET STRING (SIZE (3))
	   MAX-ACCESS read-write
	   STATUS current
	   DESCRIPTION
	  " The BLOCKNUM part of the XID information which the NetView agent
	    should use to connect to the NetView management system
	    (The SNA host)
	  "
	::= { nvaAgentEntry 10 }

	nvaAgSSap  OBJECT-TYPE
	   SYNTAX Sap
	   MAX-ACCESS read-write
	   STATUS current
	   DESCRIPTION
	  " Local SAP, used for the NetView session - for LLC
	    access type session only.
	  "
	::= { nvaAgentEntry 11 }

	nvaAgDSap  OBJECT-TYPE
	   SYNTAX Sap
	   MAX-ACCESS read-write
	   STATUS current
	   DESCRIPTION
	  " Remote(host) Sap used by the NetView agent for the
	    SNA host connection - for LLC access session type
	    only.
	  "
	::= { nvaAgentEntry 12 }

	nvaAgRemMacAddr  OBJECT-TYPE
	   SYNTAX MacAddress
	   MAX-ACCESS read-write
	   STATUS current
	   DESCRIPTION
	  " Remote(host) MAC address used by the NetView agent
	    for the SNA host connection - for LLC access session
	    type only.
	  "
	::= { nvaAgentEntry 13 }

	nvaAgSdlcAddr  OBJECT-TYPE
	   SYNTAX SdlcAddr
	   MAX-ACCESS read-write
	   STATUS current
	   DESCRIPTION
	  " SDLC address used by the NetView agent for the SNA 
	    host connection - for SDLC access session type only.
	  "
	::= { nvaAgentEntry 14 }

	nvaAgResourceName  OBJECT-TYPE
	   SYNTAX DisplayString
	   MAX-ACCESS read-write
	   STATUS current
	   DESCRIPTION
	  " A 4 character name that is appended to the resource
	    name in the NetView alerts sent by the NetView agent
	  "
	::= { nvaAgentEntry 15 }


	nvaAgentStatTable  OBJECT-TYPE
	   SYNTAX SEQUENCE OF NvaAgentStatEntry
	   MAX-ACCESS not-accessible
	   STATUS current
	   DESCRIPTION
	  "
	  "
	::= { snarNva 4 }

	nvaAgentStatEntry  OBJECT-TYPE
	   SYNTAX NvaAgentStatEntry
	   MAX-ACCESS not-accessible
	   STATUS current
       DESCRIPTION
	   "An entry in table nvaAgentStatTable."
	   INDEX  { nvaAgStatIndex }
	::= { nvaAgentStatTable 1 }

	NvaAgentStatEntry ::=
	   SEQUENCE {
	      nvaAgStatIndex
		 Integer32,

	   --*****STATISTICS****
	      nvaAgStatTime
		 TimeTicks,
	      nvaAgActPu
		 Counter32,
	      nvaAgDactPu
		 Counter32,
	      nvaAgRpNmvt
		 Counter32,
	      nvaAgRnNmvt
		 Counter32,
	      nvaAgSpNmvt
		 Counter32,
	      nvaAgSAlerts
		 Counter32,
	      nvaAgRRunCmd
		 Counter32,
	      nvaAgSRunCmd
		 Counter32,
	      nvaAgSPdstat
		 Counter32
	   }

	nvaAgStatIndex  OBJECT-TYPE
	   SYNTAX Integer32
	   MAX-ACCESS read-only
	   STATUS current
	   DESCRIPTION
	  "Agent number .
	   Range (1 - nvaAgentsNumber)
	  "
	::= { nvaAgentStatEntry 1 }

      
	 nvaAgStatTime  OBJECT-TYPE
	   SYNTAX TimeTicks
	   MAX-ACCESS read-write
	   STATUS current
	   DESCRIPTION
	  " Time since last reset of the NV agent statistics.
	    Setting to a value of  0 will clear all  Agents'
	       statistics.
	  "
	::= { nvaAgentStatEntry 2 }

	nvaAgActPu  OBJECT-TYPE
	   SYNTAX Counter32
	   MAX-ACCESS read-only
	   STATUS current
	   DESCRIPTION
	  " Number of session initiation (ACTPU) requests received from
	    the SNA host
	  "
	::= { nvaAgentStatEntry 3 }

	nvaAgDactPu  OBJECT-TYPE
	   SYNTAX Counter32
	   MAX-ACCESS read-only
	   STATUS current
	   DESCRIPTION
	  " Number of session disconnection (DACTPU) requests received
	    from the SNA host 
	  "
	   ::= { nvaAgentStatEntry 4 }

	nvaAgRpNmvt  OBJECT-TYPE
	   SYNTAX Counter32
	   MAX-ACCESS read-only
	   STATUS current
	   DESCRIPTION
	  " Number of NMVTs received from the SNA host, and responded
	    with a positive response.
	  "
	::= { nvaAgentStatEntry 5 }

	nvaAgRnNmvt  OBJECT-TYPE
	   SYNTAX Counter32
	   MAX-ACCESS read-only
	   STATUS current
	   DESCRIPTION
	  " Number of NMVTs received from the SNA host, and
	    respond with a negative response.
	  "
	  ::= { nvaAgentStatEntry 6 }

	nvaAgSpNmvt  OBJECT-TYPE
	   SYNTAX Counter32
	   MAX-ACCESS read-only
	   STATUS current
	   DESCRIPTION
	  " Number of NMVTs (of any type) sent to the SNA host.
	  "
	::= { nvaAgentStatEntry 7 }

	nvaAgSAlerts  OBJECT-TYPE
	   SYNTAX Counter32
	   MAX-ACCESS read-only
	   STATUS current
	   DESCRIPTION
	  " Number of alert NMVTs sent by the NetView agent.
	  "
	::= { nvaAgentStatEntry 9 }

	nvaAgRRunCmd  OBJECT-TYPE
	   SYNTAX Counter32
	   MAX-ACCESS read-only
	   STATUS current
	   DESCRIPTION
	  " Number of RUNCMD (execute-command NMVTs) received by the 
	    NetView agent.
	  "
	::= { nvaAgentStatEntry 10 }

	nvaAgSRunCmd  OBJECT-TYPE
	   SYNTAX Counter32
	   MAX-ACCESS read-only
	   STATUS current
	   DESCRIPTION
	  "Number of RUNCMD replies sent to the NetView host.
	  "
	::= { nvaAgentStatEntry 11 }

	nvaAgSPdstat  OBJECT-TYPE
	   SYNTAX Counter32
	   MAX-ACCESS read-only
	   STATUS current
	   DESCRIPTION
	  "Number of PDSTAT NMVTs sent by the NetView agent.
	  "
	::= { nvaAgentStatEntry 12 }


	-- 
	-- snaSNA group    
	-- 
	-- Defines the sessions' parameters  to be converted
	--


     --*********
	snaSessTable  OBJECT-TYPE
	   SYNTAX SEQUENCE OF SnaSessEntry
	   MAX-ACCESS not-accessible
	   STATUS current
	   DESCRIPTION
	  " Holding SNA session's parameters for each side of a
	    specific session, indexed by session_id
	  "
	::= { snarSna 3 }

	snaSessEntry  OBJECT-TYPE
	   SYNTAX SnaSessEntry
	   MAX-ACCESS not-accessible
	   STATUS current
       DESCRIPTION
	   "An entry in table snaSessTable."
	   INDEX  { sessIfIndex, sessId, sessSide }
	::= { snaSessTable 1 }

	SnaSessEntry ::=
	   SEQUENCE {
	   sessIfIndex   
	      Integer32,
	   sessId
	      Integer32,
	   sessSide
	      INTEGER,
	   sessDev
	      Integer32,
	   sessAdminStatus
	      INTEGER,
	   sessOperState
	      INTEGER,
	   sessAccessType
	      INTEGER,
	   sessSXidBlockId
	      OCTET STRING,
	   sessSXidBlockNum
	      OCTET STRING,

	   --** LLC/SDLC **
	   sessSSap
	      Sap,
	   sessDSap
	      Sap,
	   sessRemMacAddr
	      MacAddress,

	   --** SDLC     **
	   sessSdlcAddr
	      SdlcAddr,
	   sessGroupPoll
	      SdlcAddr,
	   sessRole
	      INTEGER,
	   --** LLC/IP    **
	   sessIpEncapsulated
	      INTEGER,
	   sessDestIpAddr
	      IpAddress,

	   --** QLLC  x25  **
	   sessRemX25Addr
	      OCTET STRING
	 }
     


	sessIfIndex  OBJECT-TYPE
	   SYNTAX Integer32
	   MAX-ACCESS read-only
	   STATUS current
	   DESCRIPTION
	  "Interface used by this SNA session       
	  "
	::= { snaSessEntry 1 }

	sessId  OBJECT-TYPE
	   SYNTAX Integer32
	   MAX-ACCESS read-only
	   STATUS current
	   DESCRIPTION
	  " The unique identifier of the converted SNA session id
	  "
	 ::= { snaSessEntry 2 }

	sessSide  OBJECT-TYPE
	   SYNTAX INTEGER { sideA(1) , sideB(2) }
	   MAX-ACCESS read-only
	   STATUS current
	   DESCRIPTION
	  " The SNA session side. Each session handled by SNAR/device,
	    creates 2 SNA sessions, hereafter called 'side A' and 'side B'
	    Configuration parameters, and Statistics are defined for each 
	    side separately.
	  "
	::= { snaSessEntry 3 }

	sessDev OBJECT-TYPE
	   SYNTAX Integer32
	   MAX-ACCESS read-only
	   STATUS current
	   DESCRIPTION
	  " The device number, used in devices setup. N/A to SNAR. 
	  "
	::= { snaSessEntry 4 }

	sessAdminStatus  OBJECT-TYPE
	   SYNTAX INTEGER {
	    disable (1),  
	    enable  (2),   
	    underCreation (3),
	    stop    (4),
	    start   (5),      
	    invalid (10)
	   }
			
	   MAX-ACCESS read-write
	   STATUS current
	   DESCRIPTION
	  " Admin. status of this session, as requested by the manager.
	    10 - Session is invalid, and not handled by SNAR 
	       devices.
	    1 - Session is disabled. SNAR/Device will not try to start
	       this session.
	    2-  Session is enabled. SNAR/Device will try to start this
	       session.
	    3-  Under_creation - This session parameters are under creation,
	       manipulated by a manager.
	    4 - stop: stop an enabled session  immediately - no need
	       to save change.
	    5 - start :start a stopped sessions  immediately - no need to 
	       save change.
	  "
	::= { snaSessEntry 5 }

	sessOperState  OBJECT-TYPE
	   SYNTAX INTEGER {
	     stopped     (1),
	     disabled    (2),
	     sdlcProb03  (3),
	     llcProb04   (4),
	     ifProb30    (30),
	     ifProb80    (80),
	     ifProb81    (81),
	     ifProb87    (87),
	     ifProb88    (88),
	     ok          (99)
	   }
	   MAX-ACCESS read-only
	   STATUS current
	   DESCRIPTION
	  " Current operating state.
	    See Manual reference for more information.
	  "
	::= { snaSessEntry 6 }

	sessAccessType  OBJECT-TYPE
	  SYNTAX INTEGER{
	     llcCsmacd     (1), 
	     llcTokenRing (3),    
	     sdlc           (6),
	     qllcX25       (10)
	    }
	   MAX-ACCESS read-write
	   STATUS current
	   DESCRIPTION
	  "The access type  used by this side of the converted 
	   session.
	  "
	::= { snaSessEntry 7 }

	sessSXidBlockId  OBJECT-TYPE
	   SYNTAX OCTET STRING (SIZE (2))
	   MAX-ACCESS read-write
	   STATUS current
	   DESCRIPTION
	  "The BLOCKID part of the XID information sent by this side for the 
	   SNA session initiation
	  "
	::= { snaSessEntry 8 }

	sessSXidBlockNum  OBJECT-TYPE
	   SYNTAX OCTET STRING (SIZE (3))
	   MAX-ACCESS read-write
	   STATUS current
	   DESCRIPTION
	  "The BLOCKNUM part of the XID information sent by this side for the 
	   SNA session initiation
	  "
	::= { snaSessEntry 9 }


	sessSSap  OBJECT-TYPE
	   SYNTAX Sap
	   MAX-ACCESS read-write
	   STATUS current
	   DESCRIPTION
	  "The Local SAP used by SNAR for this session's side (LLC 
	   sessions only)
	  "
	::= { snaSessEntry 10 }

	sessDSap  OBJECT-TYPE
	   SYNTAX Sap
	   MAX-ACCESS read-write
	   STATUS current
	   DESCRIPTION
	  "The remote SAP used by SNAR for this session's side
	   (LLC sessions only)
	  "
	::= { snaSessEntry 11 }

	sessRemMacAddr  OBJECT-TYPE
	   SYNTAX MacAddress
	   MAX-ACCESS read-write
	   STATUS current
	   DESCRIPTION
	  "The remote MAC address used by this session's side
	   (LLC  sessions only)
	  "
	  ::= { snaSessEntry 12 }

	sessSdlcAddr  OBJECT-TYPE
	   SYNTAX SdlcAddr
	   MAX-ACCESS read-write
	   STATUS current
	   DESCRIPTION
	  "The SDLC address used by this session's side
	   (SDLC sessions only, both primary and secondary)
	  "
	::= { snaSessEntry 13 }

	sessGroupPoll  OBJECT-TYPE
	   SYNTAX  SdlcAddr
	   MAX-ACCESS read-write
	   STATUS current
	   DESCRIPTION
	  "The address of the group poll in which this session's side
		    participates (SLDC secondary only).
	   A value of 0 indicates that it doesn't participate 
	   in any group. Only one group is supported for each
	   SDLC line (same port)
	  "
	::= { snaSessEntry 14 }

	sessRole  OBJECT-TYPE
	   SYNTAX INTEGER{
	     primary   (1),
	     secondary (2)
	   }
	   MAX-ACCESS read-write
	   STATUS current
	   DESCRIPTION
	  "The type of SDLC session for this side. 
	  "
	::= { snaSessEntry 15 }

	sessIpEncapsulated  OBJECT-TYPE
	   SYNTAX  INTEGER { disable(1) , enable(2) }
	   MAX-ACCESS read-write
	   STATUS current
	   DESCRIPTION
	  "Specified whether this session data is encapsulated within 
	   UDP/IP
	  "
	::= { snaSessEntry 16 }  

	sessDestIpAddr  OBJECT-TYPE
	   SYNTAX IpAddress
	   MAX-ACCESS read-write
	   STATUS current
	   DESCRIPTION
	  "The destination IP address (IP encapsulated sessions only).
	  "
	::= { snaSessEntry 17 }  

	sessRemX25Addr  OBJECT-TYPE
	   SYNTAX OCTET STRING
	   MAX-ACCESS read-write
	   STATUS current
	   DESCRIPTION
	  "The remote X25 address (QLLC only) .
	  "
	::= { snaSessEntry 18 }

	   
      --*********
      snaSessTuneTable  OBJECT-TYPE
	   SYNTAX SEQUENCE OF SnaSessTuneEntry
	   MAX-ACCESS not-accessible
	   STATUS current
	   DESCRIPTION
	  " Holding SNA session parameters for each side of a
	    specific session, indexed by session_id
	  "
	::= { snarSna 4 }

       snaSessTuneEntry  OBJECT-TYPE
	   SYNTAX SnaSessTuneEntry
	   MAX-ACCESS not-accessible
	   STATUS current
       DESCRIPTION
	   "An entry in table snaSessTuneTable."
	   INDEX  { sessTuneIfIndex, sessTuneId, sessTuneSide}
	::= { snaSessTuneTable 1 }

	SnaSessTuneEntry ::=
	   SEQUENCE {
	   sessTuneIfIndex
	      Integer32,
	   sessTuneId
	      Integer32,
	   sessTuneSide 
	      INTEGER,

	   --** TUNNING   **
	   sessBufferSize
	      Integer32,
	   sessSegmentation
	      INTEGER,
	   sessFirstSide
	      INTEGER,
	   sessWindow
	      Integer32,
	   sessDuplex
	      INTEGER,
	   sessRXidBlockId
	      OCTET STRING,
	   sessRXidBlockNum
	      OCTET STRING,
	   sessCheckXid
	      INTEGER,
	   sessT1
	      Integer32,
	   sessTi
	      Integer32,
	   sessT2
	      Integer32,
	   sessN2
	      Integer32,
	   sessUdpPort
	      Integer32
	 }


	sessTuneIfIndex  OBJECT-TYPE
	   SYNTAX Integer32
	   MAX-ACCESS read-only
	   STATUS current
	   DESCRIPTION
	  " The SNA session side.
	  "
	::= { snaSessTuneEntry 1 }

	sessTuneId  OBJECT-TYPE
	   SYNTAX Integer32
	   MAX-ACCESS read-only
	   STATUS current
	   DESCRIPTION
	  " The unique identifier of the converted SNA session.
	  "
	 ::= { snaSessTuneEntry 2 }

	sessTuneSide  OBJECT-TYPE
	   SYNTAX INTEGER { sideA(1) , sideB(2) }
	   MAX-ACCESS read-only
	   STATUS current
	   DESCRIPTION
	  " The SNA session's side.
	  "
	::= { snaSessTuneEntry 3 }

	sessBufferSize  OBJECT-TYPE
	   SYNTAX Integer32
	   MAX-ACCESS read-write
	   STATUS current
	   DESCRIPTION
	  " The max. buffer size of remote device (All sessions).
	  "
	::= { snaSessTuneEntry 4 }

	sessSegmentation  OBJECT-TYPE
	   SYNTAX  INTEGER { disable(1) , enable(2) }
	   MAX-ACCESS read-write
	   STATUS current
	   DESCRIPTION
	  " Specifies whether the SNAR should perform
	    segmentation when incoming frame on one side is
	    longer then the sessSideBufferSize of the other size
	    
	    1 - disable - don't perform segmentation
	    2 - enable - perform segmentation
	  "
	::= { snaSessTuneEntry 5 }

	sessFirstSide  OBJECT-TYPE
	   SYNTAX INTEGER { sideA(1) , sideB(2) }
	   MAX-ACCESS read-only
	   STATUS current
	   DESCRIPTION
	  "Specifies which side of the two SNA sides (side_a or side_b) 
	   should be started first (SNAR only, N/A to devices)
	  "
	::= { snaSessTuneEntry 6 }



	sessWindow  OBJECT-TYPE
	   SYNTAX Integer32
	   MAX-ACCESS read-write
	   STATUS current
	   DESCRIPTION
	  " The max window size (1 .. 127) for this session's side.
	  "
	::= { snaSessTuneEntry 7 }

	sessDuplex  OBJECT-TYPE
	   SYNTAX INTEGER{
	    half (1),
	    full (2) 
	   }
	   MAX-ACCESS read-write
	   STATUS current
	   DESCRIPTION
	  " Specifies the type of SDLC device on the other end
	    of the SDLC line. FULL- means a device capable of
	    transmit and receive data simultaneously.
	  "
	::= { snaSessTuneEntry 8 }

	sessRXidBlockId  OBJECT-TYPE
	   SYNTAX OCTET STRING   (SIZE (2))
	   MAX-ACCESS read-write
	   STATUS current
	   DESCRIPTION
	  "The BLOCKID part of the XID information expected to be received
	   on this  side of the SNA session
	  "
	::= { snaSessTuneEntry 9 }

	sessRXidBlockNum  OBJECT-TYPE
	   SYNTAX OCTET STRING   (SIZE (3))
	   MAX-ACCESS read-write
	   STATUS current
	   DESCRIPTION
	  "The BLOCKNUM part of the XID information expected to be received
	   on this  side of the SNA session
	  "
	::= { snaSessTuneEntry 10 }

	sessCheckXid  OBJECT-TYPE
	   SYNTAX  INTEGER { disable(1) , enable(2) }
	   MAX-ACCESS read-write
	   STATUS current
	   DESCRIPTION
	  "Specified whether the received XID information should
	   be checked and compared to the value of sessRXid:
	    1 - disable: don't check
	    2 - enable  : check
	  "
	::= { snaSessTuneEntry 11 }

	sessT1  OBJECT-TYPE
	   SYNTAX Integer32
	   MAX-ACCESS read-write
	   STATUS current
	   DESCRIPTION
	  " The T1 timer (in 100 msec) for this  session's side.
	  "
	::= { snaSessTuneEntry 12 }

	sessTi  OBJECT-TYPE
	   SYNTAX Integer32
	   MAX-ACCESS read-write
	   STATUS current
	   DESCRIPTION
	  " The Ti timer (in sec) for this  session
	  "
	::= { snaSessTuneEntry 13 }

	sessT2  OBJECT-TYPE
	   SYNTAX Integer32
	   MAX-ACCESS read-write
	   STATUS current
	   DESCRIPTION
	  " The T2 timer (in 100 msec) for this   session
	  "
	::= { snaSessTuneEntry 14 }

	sessN2  OBJECT-TYPE
	   SYNTAX Integer32
	   MAX-ACCESS read-write
	   STATUS current
	   DESCRIPTION
	  " The N2 value for this  session's side  
	  "
	::= { snaSessTuneEntry 15 }

	sessUdpPort  OBJECT-TYPE
	   SYNTAX Integer32
	   MAX-ACCESS read-write
	   STATUS current
	   DESCRIPTION
	  " The UDP port used by SNAR (IP encapsulated 
		     sessions only)
	  "
	::= { snaSessTuneEntry 16 }  


      --*********
      snaSessStatTable  OBJECT-TYPE
	   SYNTAX SEQUENCE OF SnaSessStatEntry
	   MAX-ACCESS not-accessible
	   STATUS current
	   DESCRIPTION
	  "
	  Holding SNA session parameters for each side of a
		   specific session, indexed by session_id
	  "
	::= { snarSna 5 }

       snaSessStatEntry  OBJECT-TYPE
	   SYNTAX SnaSessStatEntry
	   MAX-ACCESS not-accessible
	   STATUS current
       DESCRIPTION
	   "An entry in table snaSessStatTable."
	   INDEX  { sessStatIfIndex, sessStatId, sessStatSide }
	::= { snaSessStatTable 1 }

	SnaSessStatEntry ::=
	   SEQUENCE {
	   sessStatIfIndex
	      Integer32,
	   sessStatId
	      Integer32,
	   sessStatSide
	      INTEGER,

	   --** STATISTICS **
	   sessStatTime
	      TimeTicks,
	   sessSPius
	      Counter32,
	   sessSBytes
	      Counter32,
	   sessRPius
	      Counter32,
	   sessRBytes
	      Counter32,
	   sessSessFailure
	      Counter32,
	   sessXidDenieds
	      Counter32
       }

       sessStatIfIndex  OBJECT-TYPE
	   SYNTAX Integer32
	   MAX-ACCESS read-only
	   STATUS current
	   DESCRIPTION
	  " "
	::= { snaSessStatEntry 1 }

	sessStatId  OBJECT-TYPE
	   SYNTAX Integer32
	   MAX-ACCESS read-only
	   STATUS current
	   DESCRIPTION
	  " The unique identifier of the converted SNA session.
	  "
	 ::= { snaSessStatEntry 2 }

       sessStatSide  OBJECT-TYPE
	   SYNTAX INTEGER { sideA(1) , sideB(2) }
	   MAX-ACCESS read-only
	   STATUS current
	   DESCRIPTION
	  " The SNA session's side.
	  "
	::= { snaSessStatEntry 3 }


	sessStatTime  OBJECT-TYPE
	   SYNTAX TimeTicks
	   MAX-ACCESS read-write
	   STATUS current
	   DESCRIPTION
	  " Time since last reset of this session statistics.
	    Setting to a   value of 0 will clear all session
	       statistics.
	  "
	   ::= { snaSessStatEntry 4 }

	sessSPius  OBJECT-TYPE
	   SYNTAX Counter32
	   MAX-ACCESS read-only
	   STATUS current
	   DESCRIPTION
	  " The number of PIUs sent by this  session's side 
	  "
	   ::= { snaSessStatEntry 5 }

	sessSBytes  OBJECT-TYPE
	   SYNTAX Counter32
	   MAX-ACCESS read-only
	   STATUS current
	   DESCRIPTION
	  " The number of bytes sent by this session's side.
	  "
	::= { snaSessStatEntry 6 }

	sessRPius  OBJECT-TYPE
	   SYNTAX Counter32
	   MAX-ACCESS read-only
	   STATUS current
	   DESCRIPTION
	  " The number of PIUs received by this session 
	  "
	::= { snaSessStatEntry 7 }

	sessRBytes  OBJECT-TYPE
	   SYNTAX Counter32
	   MAX-ACCESS read-only
	   STATUS current
	   DESCRIPTION
	  " The number of bytes received by this session's side.
	  "
	::= { snaSessStatEntry 8 }

	sessSessFailure  OBJECT-TYPE
	   SYNTAX Counter32
	   MAX-ACCESS read-only
	   STATUS current
	   DESCRIPTION
	  " The number of session failures occurs to this
	    session's side.
	  "
	::= { snaSessStatEntry 9 }

	sessXidDenieds  OBJECT-TYPE
	   SYNTAX Counter32 
	   MAX-ACCESS read-only
	   STATUS current
	   DESCRIPTION
	  " The number of XID denied by this session's side
	  "
	::= { snaSessStatEntry 10 }

      snaSessQllcTable  OBJECT-TYPE
	   SYNTAX SEQUENCE OF SnaSessQllcEntry
	   MAX-ACCESS not-accessible
	   STATUS current
	   DESCRIPTION
	  "
	  Holding SNA session parameters for each side of a
		   specific session, indexed by session_id
	  "
	::= { snarSna 7 }

       snaSessQllcEntry  OBJECT-TYPE
	   SYNTAX SnaSessQllcEntry
	   MAX-ACCESS not-accessible
	   STATUS current
       DESCRIPTION
	   "An entry in table snaSessQllcTable."
	   INDEX  { sessQllcIfIndex, sessQllcId, sessQllcSide }
	::= { snaSessQllcTable 1 }

	SnaSessQllcEntry ::=
	   SEQUENCE {
	   sessQllcIfIndex
	      Integer32,
	   sessQllcId
	      Integer32,
	   sessQllcSide
	      INTEGER,

		 --***QLLC PARAM
	   sessInCalls
	      INTEGER,
	   sessOutCalls     
	      INTEGER,
	   sessPVC
	      INTEGER,
	   sessCallReqData
	      OCTET STRING,
	   sessConnReqFacility
	      OCTET STRING,
	   sessGroupId
	      OCTET STRING,
	   sessDtePswd
	      OCTET STRING,
	   sessDteId
	      OCTET STRING,
	   sessMaxInPktSize
	      Integer32,           
	   sessMaxOutPktSize
	      Integer32,           
	   sessCallIndReverse
	      OCTET STRING
	}
	sessQllcIfIndex  OBJECT-TYPE
	   SYNTAX Integer32
	   MAX-ACCESS read-only
	   STATUS current
	   DESCRIPTION
	  " 
	  "
	::= { snaSessQllcEntry 1 }

	sessQllcId  OBJECT-TYPE
	   SYNTAX Integer32
	   MAX-ACCESS read-only
	   STATUS current
	   DESCRIPTION
	  " The unique identifier of the converted SNA session.
	  "
	 ::= { snaSessQllcEntry 2 }

       sessQllcSide  OBJECT-TYPE
	   SYNTAX  INTEGER { sideA(1) , sideB(2) }
	   MAX-ACCESS read-only
	   STATUS current
	   DESCRIPTION
	  " The SNA session's side.
	  "
	::= { snaSessQllcEntry 3 }


	sessInCalls  OBJECT-TYPE
	   SYNTAX  INTEGER { disable(1) , enable(2) }
	   MAX-ACCESS read-write
	   STATUS current
	   DESCRIPTION
	  "N/Allowed to accept call indicators (QLLC only)
	    1- disable: don't allow to accept call indications
	    2- enable:  Allow to accept call indications
	  "
	::= { snaSessQllcEntry 4 }


	sessOutCalls  OBJECT-TYPE
	   SYNTAX  INTEGER { disable(1) , enable(2) }
	   MAX-ACCESS read-write
	   STATUS current
	   DESCRIPTION
	  " N/Allowed to initiate call requests (QLLC only)
	    1- disable: don't allow to initiate call requests
	    2- enable:  Allow to initiate call requests
	  "
	::= { snaSessQllcEntry 5 }

	sessPVC  OBJECT-TYPE
	   SYNTAX  INTEGER { disable(1) , enable(2) }
	   MAX-ACCESS read-write
	   STATUS current
	   DESCRIPTION
	  " PVC being used or not  (QLLC only)
	       1 - disable :not use
	       2 - enable  :use
	  "
	::= { snaSessQllcEntry 6 }

	sessCallReqData  OBJECT-TYPE
	   SYNTAX OCTET STRING
	   MAX-ACCESS read-write
	   STATUS current
	   DESCRIPTION
	  " The user's data  for call requests (QLLC only).
	  "
	::= { snaSessQllcEntry 7 }


	sessConnReqFacility  OBJECT-TYPE
	   SYNTAX OCTET STRING
	   MAX-ACCESS read-write
	   STATUS current
	   DESCRIPTION
	  " The facilities for connection requests (QLLC only).
	  "
	::= { snaSessQllcEntry 8 }

	sessGroupId  OBJECT-TYPE
	   SYNTAX OCTET STRING
	   MAX-ACCESS read-write
	   STATUS current
	   DESCRIPTION
	  " The facility group id (QLLC only)
	  "
	::= { snaSessQllcEntry 9 }

	sessDtePswd  OBJECT-TYPE
	   SYNTAX OCTET STRING
	   MAX-ACCESS read-write
	   STATUS current
	   DESCRIPTION
	  " The password for local DTE (QLLC only)
	  "
	::= { snaSessQllcEntry 10}

	sessDteId  OBJECT-TYPE
	   SYNTAX OCTET STRING
	   MAX-ACCESS read-write
	   STATUS current
	   DESCRIPTION
	  " The identification for local DTE (QLLC only).
	  "
	::= { snaSessQllcEntry 11 }

	sessMaxInPktSize  OBJECT-TYPE
	   SYNTAX Integer32
	   MAX-ACCESS read-write
	   STATUS current
	   DESCRIPTION
	  " The max inbound packet size (QLLC only).
	  "
	::= { snaSessQllcEntry 12 }

	sessMaxOutPktSize  OBJECT-TYPE
	   SYNTAX Integer32
	   MAX-ACCESS read-write
	   STATUS current
	   DESCRIPTION
	  " The max outbound packet size (QLLC only).
	  "
	::= { snaSessQllcEntry 13 }

	sessCallIndReverse  OBJECT-TYPE
	   SYNTAX OCTET STRING
	   MAX-ACCESS read-write
	   STATUS current
	   DESCRIPTION
	  " 	  "
	   ::= { snaSessQllcEntry 14 }
--
--
 
cvtIfn    OBJECT IDENTIFIER ::= {radConverters 2  }
cvtSdlc   OBJECT IDENTIFIER ::= {cvtIfn 1 }

--****************************
--**** SDLC GROUP   **********
--****************************

	sdlcLinesNumber  OBJECT-TYPE
	      SYNTAX  Integer32
	      MAX-ACCESS  read-only
	      STATUS  current
	      DESCRIPTION
		      "
		      "
	      ::= { cvtSdlc 1 }

	sdlcTable  OBJECT-TYPE
	   SYNTAX SEQUENCE OF SdlcEntry
	   MAX-ACCESS not-accessible
	   STATUS current
	   DESCRIPTION
	  "
	  "
	::= { cvtSdlc 3 }

	sdlcEntry  OBJECT-TYPE
	   SYNTAX SdlcEntry
	   MAX-ACCESS not-accessible
	   STATUS current
       DESCRIPTION
	   "An entry in table sdlcTable."
	   INDEX  { sdlcIfIndex }
	::= { sdlcTable 1 }

		SdlcEntry ::=
		   SEQUENCE {
			sdlcIfIndex 
			      Integer32,
			sdlcNrz 
			      INTEGER,
			sdlcDuplex 
			      INTEGER,
			sdlcClockType
			      INTEGER,
			sdlcSpeed
			      Integer32,
			sdlcConnectorType
			      DisplayString,
			sdlcRts 
			      INTEGER
		}

	sdlcIfIndex  OBJECT-TYPE
	      SYNTAX  Integer32
	      MAX-ACCESS  read-only
	      STATUS  current
	      DESCRIPTION
			     "The value of this object identifies the
			      interface for which this entry
			      contains management information.  The
			      value of this object for a particular
			      interface has the same value as the
			      ifIndex object, defined in [4,6],
			      for the same interface."
	      ::= { sdlcEntry 1 }

	sdlcNrz  OBJECT-TYPE
	      SYNTAX  INTEGER { nrz(1), nrzi(2) }
	      MAX-ACCESS  read-write
	      STATUS  current
	      DESCRIPTION
		      "
		      "
	      ::= { sdlcEntry 2 }

	sdlcDuplex  OBJECT-TYPE
	      SYNTAX  INTEGER { half(1), full(2) }
	      MAX-ACCESS  read-write
	      STATUS  current
	      DESCRIPTION
		      "
		      "
	      ::= { sdlcEntry 3 }

	sdlcClockType  OBJECT-TYPE
	      SYNTAX  INTEGER { external(1), internal(2)}
	      MAX-ACCESS  read-write
	      STATUS  current
	      DESCRIPTION
		      "
		      "
	      ::= { sdlcEntry 4 }

	sdlcSpeed  OBJECT-TYPE
	      SYNTAX  Integer32
	      MAX-ACCESS  read-write
	      STATUS  current
	      DESCRIPTION
		      "
		      "
	      ::= { sdlcEntry 5 }

	sdlcConnectorType  OBJECT-TYPE
	      SYNTAX  DisplayString
	      MAX-ACCESS  read-only
	      STATUS  current
	      DESCRIPTION
		      "
		      "
	      ::= { sdlcEntry 6 }

	sdlcRts  OBJECT-TYPE
	      SYNTAX  INTEGER { constatnt(1), controled(2) }
	      MAX-ACCESS  read-only
	      STATUS  current
	      DESCRIPTION
		      "
		      "
	      ::= { sdlcEntry 7 }



	--**************

	sdlcStatTable  OBJECT-TYPE
	   SYNTAX SEQUENCE OF SdlcStatEntry
	   MAX-ACCESS not-accessible
	   STATUS current
	   DESCRIPTION
	  "
	  "
	::= { cvtSdlc 4 }

	sdlcStatEntry  OBJECT-TYPE
	   SYNTAX SdlcStatEntry
	   MAX-ACCESS not-accessible
	   STATUS current
       DESCRIPTION
	   "An entry in table sdlcStatTable."
	   INDEX  { sdlcStatIfIndex }
	::= { sdlcStatTable 1 }

		SdlcStatEntry ::=
		   SEQUENCE {
			sdlcStatIfIndex 
			      Integer32,
			sdlcTimeSinceReset
			      TimeTicks,
			sdlcStatFramesTrans 
			      Counter32,
			sdlcStatBytesTrans 
			      Counter32,
			sdlcStatFramesRcv 
			      Counter32,
			sdlcStatBytesRcv
			      Counter32,
			sdlcStatFramesAbort
			      Counter32,
			sdlcStatFramesBad
			      Counter32,
			sdlcStatFramesCrc 
			      Counter32

			}

	sdlcStatIfIndex  OBJECT-TYPE
	      SYNTAX  Integer32
	      MAX-ACCESS  read-only
	      STATUS  current
	      DESCRIPTION
			     "The value of this object identifies the
			      interface for which this entry
			      contains management information.  The
			      value of this object for a particular
			      interface has the same value as the
			      ifIndex object, defined in [4,6],
			      for the same interface."
	      ::= { sdlcStatEntry 1 }

	sdlcTimeSinceReset  OBJECT-TYPE
	      SYNTAX  TimeTicks
	      MAX-ACCESS  read-write
	      STATUS  current
	      DESCRIPTION
		      " The time laps since the last reset statistics.
		Setting the object  to   0 will   reset all  line statistics.
		      "
	      ::= { sdlcStatEntry 2 }

	sdlcStatFramesTrans  OBJECT-TYPE
	      SYNTAX  Counter32
	      MAX-ACCESS  read-only
	      STATUS  current
	      DESCRIPTION
		      "
		      "
	      ::= { sdlcStatEntry 3 }

	sdlcStatBytesTrans  OBJECT-TYPE
	      SYNTAX  Counter32
	      MAX-ACCESS  read-only
	      STATUS  current
	      DESCRIPTION
		      "
		      "
	      ::= { sdlcStatEntry 4 }

	sdlcStatFramesRcv  OBJECT-TYPE
	      SYNTAX  Counter32
	      MAX-ACCESS  read-only
	      STATUS  current
	      DESCRIPTION
		      "
		      "
	      ::= { sdlcStatEntry 5 }

	sdlcStatBytesRcv  OBJECT-TYPE
	      SYNTAX  Counter32
	      MAX-ACCESS  read-only
	      STATUS  current
	      DESCRIPTION
		      "
		      "
	      ::= { sdlcStatEntry 6 }

	sdlcStatFramesAbort  OBJECT-TYPE
	      SYNTAX  Counter32
	      MAX-ACCESS  read-only
	      STATUS  current
	      DESCRIPTION
		      "
		      "
	      ::= { sdlcStatEntry 7 }

	sdlcStatFramesBad  OBJECT-TYPE
	      SYNTAX  Counter32
	      MAX-ACCESS  read-only
	      STATUS  current
	      DESCRIPTION
		      " This counter holds the number of all   bad frames.
		      "
	      ::= { sdlcStatEntry 8 }

	sdlcStatFramesCrc  OBJECT-TYPE
	      SYNTAX  Counter32
	      MAX-ACCESS  read-only
	      STATUS  current
	      DESCRIPTION
		      "
		      "
	      ::= { sdlcStatEntry 9 }

-- LAN Token Ring interface
-- Private MIB - dot5 / TR interface unit

cvtDot5     OBJECT IDENTIFIER ::= { cvtIfn 2 }

	  cvtDot5Table  OBJECT-TYPE
		     SYNTAX  SEQUENCE OF CvtDot5Entry
		     MAX-ACCESS  not-accessible
		     STATUS  current
		     DESCRIPTION
			     "This table contains Token Ring interface
			     parameters and state variables. One entry
			     per 802.3 interface."
		     ::= { cvtDot5 1 }

	  cvtDot5Entry  OBJECT-TYPE
		     SYNTAX  CvtDot5Entry
		     MAX-ACCESS  not-accessible
		     STATUS  current
	         DESCRIPTION
	  	     "An entry in table cvtDot5Table."
		     INDEX   { cvtDot5IfIndex }
		     ::= { cvtDot5Table 1 }

	  CvtDot5Entry
	      ::= SEQUENCE {
		      cvtDot5IfIndex
			  Integer32,
		      cvtDot5MacAddr
			  MacAddress,
		      cvtDot5Commands
			  INTEGER,
		      cvtDot5RingSpeed
			  INTEGER,
		      cvtDot5ActMonParticipate
			  INTEGER,
		      cvtDot5Functional
			  MacAddress

		  }

	  cvtDot5IfIndex  OBJECT-TYPE
		     SYNTAX  Integer32
		     MAX-ACCESS  read-only
		     STATUS  current
		     DESCRIPTION
			     "The value of this object identifies the
			      802.5 interface for which this entry
			      contains management information.  The
			      value of this object for a particular
			      interface has the same value as the
			      ifIndex object, defined in [4,6],
			      for the same interface."
		     ::= { cvtDot5Entry 1 }


	  cvtDot5MacAddr OBJECT-TYPE
		     SYNTAX  MacAddress
		     MAX-ACCESS  read-write
		     STATUS  current
		     DESCRIPTION
			     "
			     "
		     ::= { cvtDot5Entry 2 }

	  cvtDot5Commands  OBJECT-TYPE
		     SYNTAX  INTEGER {
				   no-op(1),
				   open(2),
				   reset(3),
				   close(4)
			     }
		     MAX-ACCESS  read-write
		     STATUS  current
		     DESCRIPTION
			     "When this object is set to the value of
			      open(2), the station should go into the
			      open state. 
			       When this object is set to the value of
			      of reset(3), the station should perform reset.
			      When this object is set to the value
			      of close(4), the station should go into
			      the stopped state by removing itself
			      from the ring.
				  Setting this object to a value of
			      no-op(1) has no effect.
				  When read, this object always has a
			      value of no-op(1)."
		     ::= { cvtDot5Entry 3 }

	  cvtDot5RingSpeed  OBJECT-TYPE
		     SYNTAX  INTEGER {
				   unknown(1),
				   oneMegabit(2),
				   fourMegabit(3),
				   sixteenMegabit(4)
			     }
		     MAX-ACCESS  read-write
		     STATUS  current
		     DESCRIPTION
			     "The ring's bandwidth."
		     ::= { cvtDot5Entry 4 }

	  cvtDot5ActMonParticipate OBJECT-TYPE
		     SYNTAX  INTEGER {
				   true(1),
				   false(2)
			     }
		     MAX-ACCESS  read-write
		     STATUS  current
		     DESCRIPTION
			     "If this object has a value of true(1) then
			     this interface will participate in the
			     active monitor selection process.  If the
			     value is false(2) then it will not.
			     Setting this object might not have an
			     effect until the next time the interface
			     is opened."
		     ::= { cvtDot5Entry 5 }

	  cvtDot5Functional OBJECT-TYPE
		     SYNTAX  MacAddress
		     MAX-ACCESS  read-write
		     STATUS  current
		     DESCRIPTION
			     "The bit mask of all TR functional
			     addresses for which this interface will
			     accept frames."
		     ::= { cvtDot5Entry 6 }

-- LAN ETHERNET interface
-- Private MIB - dot3 interface unit

	  cvtDot3       OBJECT IDENTIFIER ::= { cvtIfn 3 }

	  cvtDot3Table  OBJECT-TYPE
		     SYNTAX  SEQUENCE OF CvtDot3Entry
		     MAX-ACCESS  not-accessible
		     STATUS  current
		     DESCRIPTION
			     "This table contains ETHERNET interface
			     parameters and state variables, one entry
			     per 802.3 interface."
		     ::= { cvtDot3 1 }

	  cvtDot3Entry  OBJECT-TYPE
		     SYNTAX  CvtDot3Entry
		     MAX-ACCESS  not-accessible
		     STATUS  current
	         DESCRIPTION
		     "An entry in table cvtDot3Table."
		     INDEX   { cvtDot3IfIndex }
		     ::= { cvtDot3Table 1 }

	  CvtDot3Entry
	      ::= SEQUENCE {
		      cvtDot3IfIndex
			  Integer32,
		      cvtDot3MacAddr
			  MacAddress,
		      cvtDot3Commands
			  INTEGER,
		     cvtDot3ActMonParticipate
			  INTEGER,
		      cvtDot3Functional
			  MacAddress

		  }

	  cvtDot3IfIndex  OBJECT-TYPE
		     SYNTAX  Integer32
		     MAX-ACCESS  read-only
		     STATUS  current
		     DESCRIPTION
			     "The value of this object identifies the
			      802.3 interface for which this entry
			      contains management information.  The
			      value of this object for a particular
			      interface has the same value as the
			      ifIndex object, defined in [4,6],
			      for the same interface."
		     ::= { cvtDot3Entry 1 }


	  cvtDot3MacAddr OBJECT-TYPE
		     SYNTAX  MacAddress
		     MAX-ACCESS  read-write
		     STATUS  current
		     DESCRIPTION
			     "
			     "
		     ::= { cvtDot3Entry 2 }

	  cvtDot3Commands  OBJECT-TYPE
		     SYNTAX  INTEGER {
				   no-op(1),
				   open(2),
				   reset(3),
				   close(4)
			     }
		     MAX-ACCESS  read-write
		     STATUS  current
		     DESCRIPTION
			     "When this object is set to the value of
			      open(2), the station should go into the
			      open state. 
			      of reset(3), then the station should do
			      a reset.  On a reset, all MIB counters
			      should retain their values, if possible.
			      Other side affects are dependent on the
			      hardware chip set.
				  When this object is set to the value
			      of close(4), the station should go into
			      the stopped state by removing itself
			      from the ring.
				  Setting this object to a value of
			      no-op(1) has no effect.
				  When read, this object always has a
			      value of no-op(1)."
		     ::= { cvtDot3Entry 3 }

	  cvtDot3ActMonParticipate OBJECT-TYPE
		     SYNTAX  INTEGER {
				   true(1),
				   false(2)
			     }
		     MAX-ACCESS  read-write
		     STATUS  current
		     DESCRIPTION
			     "If this object has a value of true(1) then
			     this interface will participate in the
			     active monitor selection process.  If the
			     value is false(2) then it will not.
			     Setting this object might not have an
			     effect until the next time the interface
			     is opened."
		     ::= { cvtDot3Entry 4 }

	  cvtDot3Functional OBJECT-TYPE
		     SYNTAX  MacAddress
		     MAX-ACCESS  read-write
		     STATUS  current
		     DESCRIPTION
			     "The bit mask of all Ethernet functional
			     addresses for which this interface will
			     accept frames."
		     ::= { cvtDot3Entry 5 }



-- 
-- file :D:\Synergy\WorkArea\545\mib_rad\txt\stkhubgn.txt
-- 
--Version:   1.0		 
--Date:    17.10.94
--By:        Orly Nicklass      
--File:          stkhubgn.txt
--Last update: Smadar Tauber 12.02.96

radStkHubEvents OBJECT-IDENTITY
     STATUS  current
     DESCRIPTION
     "The events for Rad Stackable General products."
     ::= { radStkHub 0 }

 stkHubGen              OBJECT IDENTIFIER ::= { radStkHub 1 }  -- Rad Stackable General

 stkHubGenAgn OBJECT IDENTIFIER ::= { stkHubGen 1 }  -- Rad Stackable Agent



-- Stackable Hub's agent general parameters 

stkHubAgentResetConfig OBJECT-TYPE
      SYNTAX  INTEGER {
	  off(2),
	  on(3)
      }
      MAX-ACCESS  read-write
      STATUS  current
      DESCRIPTION
      "Setting the value to ON(3)is interpreted as a reset command
      for the agent NV Ram. When reset process is ended, a trap
      will be issued. "
      ::= { stkHubGenAgn 1 }

stkHubAgentSpecific OBJECT-TYPE
      SYNTAX  OBJECT IDENTIFIER
      MAX-ACCESS  read-only
      STATUS  current
      DESCRIPTION
      " Object identifier of entity containing additional information
      regarding this instance."
      ::= { stkHubGenAgn 2 }


-- Hub's Security parameters 


stkHubSecurityTable OBJECT-TYPE
	       SYNTAX SEQUENCE OF StkHubSecurityEntry
	       MAX-ACCESS not-accessible
	       STATUS current
		   DESCRIPTION
		   "Hub's Security parameters."
	       ::= { stkHubGen 2 }

stkHubSecurityEntry OBJECT-TYPE
      SYNTAX StkHubSecurityEntry
      MAX-ACCESS not-accessible
      STATUS current
	  DESCRIPTION
	  "An entry in table stkHubSecurityTable."
      INDEX {   stkHubSecID }
      ::= { stkHubSecurityTable 1 }

StkHubSecurityEntry ::=
      SEQUENCE {
      stkHubSecID
	  Integer32,
      stkHubSecEnable
	  INTEGER,
      stkHubSecurityPattern
	  OCTET STRING,
      stkHubSecurityMask
	  OCTET STRING
      }


stkHubSecID OBJECT-TYPE
      SYNTAX  Integer32  (1..3)
      MAX-ACCESS  read-only
      STATUS  current
      DESCRIPTION
	  "Segment's security unique identification number"
      ::= { stkHubSecurityEntry 1 }

stkHubSecEnable  OBJECT-TYPE
      SYNTAX  INTEGER {
	  off(2),
	  on(3)
      }
      MAX-ACCESS  read-write
      STATUS  current
      DESCRIPTION
	  "This entry indicates whether the specific segment's security is active or not"
      ::= { stkHubSecurityEntry 2 }

stkHubSecurityPattern OBJECT-TYPE
      SYNTAX OCTET STRING
      MAX-ACCESS  read-write
      STATUS  current
      DESCRIPTION
	"A six-octet(48 bit) pattern: where the masked bits of stkHubSecurityMask
	 need to match the MAC address of each port within the segment.Value of all
	 zeros  indicates no security."
      ::= { stkHubSecurityEntry 3 }

stkHubSecurityMask  OBJECT-TYPE
      SYNTAX  OCTET STRING
      MAX-ACCESS  read-write
      STATUS  current
      DESCRIPTION
	"Mask of the allowed MAC address that can be connected through
	the ports within  the segment"
      ::= { stkHubSecurityEntry 4 }

-- Port Security parameters 

stkHubPrtSecurityTable OBJECT-TYPE
	       SYNTAX SEQUENCE OF StkHubPrtSecurityEntry
	       MAX-ACCESS not-accessible
	       STATUS current
		   DESCRIPTION
		   "Port Security parameters."
	       ::= { stkHubGen 3 }

stkHubPrtSecurityEntry OBJECT-TYPE
      SYNTAX StkHubPrtSecurityEntry
      MAX-ACCESS not-accessible
      STATUS current
	  DESCRIPTION
	  "An entry in table stkHubPrtSecurityTable."
      INDEX { stkHubModuleID, stkHubPrtID, stkHubPrtSecID }
      ::= { stkHubPrtSecurityTable 1 }

StkHubPrtSecurityEntry ::=
      SEQUENCE {
    stkHubModuleID
	 Integer32,
    stkHubPrtID
	 Integer32,
    stkHubPrtSecID
	 Integer32,
    stkHubPrtSecurityEnable
	 INTEGER,
    stkHubPrtSecurityPattern
	 OCTET STRING,
    stkHubPrtSecurityMask
	 OCTET STRING
}

stkHubModuleID OBJECT-TYPE
      SYNTAX  Integer32
      MAX-ACCESS  read-only
      STATUS  current
      DESCRIPTION
      "A unique identifier of the module(slot no.)this port is attached to."
      ::= { stkHubPrtSecurityEntry 1 }

stkHubPrtID OBJECT-TYPE
      SYNTAX  Integer32
      MAX-ACCESS  read-only
      STATUS  current
      DESCRIPTION
      "A unique identifier of the port within its module."
      ::= { stkHubPrtSecurityEntry 2 }

stkHubPrtSecID OBJECT-TYPE
      SYNTAX  Integer32
      MAX-ACCESS  read-only
      STATUS  current
      DESCRIPTION
      "A unique identifier of the security of a given port within its module."
      ::= { stkHubPrtSecurityEntry 3 }

stkHubPrtSecurityEnable OBJECT-TYPE
      SYNTAX  INTEGER {
	   unknown(1),
	   off(2),
	   on(3)
      }
      MAX-ACCESS  read-write
      STATUS  current
      DESCRIPTION
      "The value of this attribute determines application of the
       port security."
      ::= { stkHubPrtSecurityEntry 4 }

stkHubPrtSecurityPattern OBJECT-TYPE
      SYNTAX  OCTET STRING
      MAX-ACCESS  read-write
      STATUS  current
      DESCRIPTION
      "A six-octet(48 bit) pattern: where the masked bits of stkHubPortSecurityMask 
       need to match the MAC address."
      ::= { stkHubPrtSecurityEntry 5 }

stkHubPrtSecurityMask OBJECT-TYPE
      SYNTAX  OCTET STRING
      MAX-ACCESS  read-write
      STATUS  current
      DESCRIPTION
      "Mask of the allowed MAC address that can be connected through
      this port. The security of the individual port over writes  the
       security of the segment where the port belongs to"
      ::= { stkHubPrtSecurityEntry 6 }


-- Traps are defined using the conventions in RFC 1215 [6].

		
softErrors NOTIFICATION-TYPE
      STATUS  current
      DESCRIPTION
      " This trap is sent when the software errors threshold is 
        exceeded."
      ::= { radStkHubEvents 33 }

resetRequired NOTIFICATION-TYPE
      OBJECTS  { trimErrorDesc, trimErrorSeverity, agnLed} 
      STATUS  current
      DESCRIPTION
      "This trap indicates that in order to perform the last SET 
       request, a reset operation  of the router/bridge is required. 
       This occurs when the layer 2 routing algorithm is changed 
       between SPF and Spanning Tree. The reset can be performed 
       manually or using the variable radBridgeAction."
      ::= { radRBHEEvents 10 }

compNotActive NOTIFICATION-TYPE
      OBJECTS  { trimErrorDesc, trimErrorSeverity, agnLed}
      STATUS  current
      DESCRIPTION
      "Compression was enabled but cannot be activated, since 
       connected device does not support correct compression. "
      ::= { radRBHEEvents 20 }

noCompression NOTIFICATION-TYPE
     OBJECTS  { trimErrorDesc, trimErrorSeverity, agnLed}
     STATUS  current
     DESCRIPTION
     "Compression card not present."
     ::= { radRBHEEvents 21 }

errorBackUp NOTIFICATION-TYPE
      OBJECTS  { trimErrorDesc, trimErrorSeverity, agnLed}
      STATUS  current
      DESCRIPTION
      "Automatic switchover to backup link because of excessive 
       link errors."
      ::= { radRBHEEvents 22 }

faultBackUp NOTIFICATION-TYPE
      OBJECTS  { trimErrorDesc, trimErrorSeverity, agnLed}
      STATUS  current
      DESCRIPTION
      "Automatic switchover to backup link because of main link 
       fault."
      ::= { radRBHEEvents 23 }

mainLinkUp NOTIFICATION-TYPE
      OBJECTS  { trimErrorDesc, trimErrorSeverity, agnLed}
      STATUS  current
      DESCRIPTION
      "Communication returned to main link."
      ::= { radRBHEEvents 24 }

failedDialUp NOTIFICATION-TYPE
      OBJECTS  { trimErrorDesc, trimErrorSeverity, agnLed}
      STATUS  current
      DESCRIPTION
      "Cannot establish backup dial-up connection."
     ::= { radRBHEEvents 25 }

extLoopBack   NOTIFICATION-TYPE
      OBJECTS  { trimErrorDesc, trimErrorSeverity, agnLed}
      STATUS  current
      DESCRIPTION
      " This trap is sent when Loopback starts on the link. "
      ::= { radRBHEEvents 29 }

dialUpConnFailed NOTIFICATION-TYPE
      OBJECTS  { trimErrorDesc, trimErrorSeverity, agnLed }
      STATUS  current
      DESCRIPTION
      " This trap is sent when the dialUp connection is terminated 
        due to a failure."
      ::= { radRBHEEvents 41 }

dialUpConnEstablished NOTIFICATION-TYPE
      OBJECTS  { trimErrorDesc, trimErrorSeverity, agnLed }
      STATUS  current
      DESCRIPTION
      " This trap is sent when the dialUp connection is established."
      ::= { radRBHEEvents 42 }

dialUpConnTerminated NOTIFICATION-TYPE
      OBJECTS  { trimErrorDesc, trimErrorSeverity, agnLed }
      STATUS  current
      DESCRIPTION
      " This trap is sent when the dialUp connection is normally 
        terminated."
      ::= { radRBHTEvents 43 }
-- 
-- file :D:\Synergy\WorkArea\545\mib_rad\txt\stkhubtr.txt
-- 
--Title:       STK-T-MIB
--Version: 2.0
--Date:      9-aug-94
--By:         Orly Nicklass & Rina Nathaniel & Benny Dolnik
--File:        STKHUBTR.TXT
--Update:    26-December-95

-- Ring information for the ring the agent is connected to.

stkHubTR OBJECT IDENTIFIER ::= { radStkHub 2 }  --  Stackable Token Ring

stkHubTRRing       OBJECT IDENTIFIER ::= { stkHubTR 1}

stkHubTRRingCorrelationEnable OBJECT-TYPE
    SYNTAX  INTEGER {
        off(2),
        on(3)
    }
    MAX-ACCESS  read-write
    STATUS  current
    DESCRIPTION
       "When set to ON(3), the in-band agent should perform
       correlation each time a station enters/leaves the segment."
    ::= { stkHubTRRing 1 }

stkHubTRRingAutorecEnable OBJECT-TYPE
    SYNTAX  INTEGER {
        off(2),
        on(3)
    }
    MAX-ACCESS  read-write
    STATUS  current
    DESCRIPTION
       "When set to ON(3), the in-band agent should perform
       autorecovery each time a beacon status is detected."
    ::= { stkHubTRRing 2 }

stkHubTRRingAutorecResult OBJECT-TYPE
    SYNTAX  INTEGER {
        not-started(1),
        started(2),
        segment-ok(3),
        segment-fixed(4),
        segment-closed(5),
        failed(6)
    }
    MAX-ACCESS  read-only
    STATUS  current
    DESCRIPTION
       "When autorecovery is completed the result will be recorded.
       While in process, STARTED will be recorded.Before process, NOT STARTED
       will be recorded"
    ::= { stkHubTRRing 3 }


stkHubTRRingResetStatistics OBJECT-TYPE
    SYNTAX  INTEGER {
       unknown(1),
       off(2),
       on(3)
    }
    MAX-ACCESS  read-write
    STATUS  current
    DESCRIPTION
      "Setting the value of this attribute to ON(3) resets all the inband
      statistics and error counters."
    ::= { stkHubTRRing 4 }

stkHubTRRingLineErrCnt OBJECT-TYPE
    SYNTAX  Counter32
    MAX-ACCESS  read-only
    STATUS  current
    DESCRIPTION
       "This counter is incremented when a frame or token is copied or
       repeated by any of the stations on the ring, the E bit is zero in the frame
       or token and one of the following conditions exists: 1) there is a
       non-data bit (J or K bit) between the SD and the ED of the frame or token, or
       2) there is an FCS error in the frame."
    ::= { stkHubTRRing 5 }

stkHubTRRingBurstErrCnt OBJECT-TYPE
    SYNTAX  Counter32
    MAX-ACCESS  read-only
    STATUS  current
    DESCRIPTION
          "This counter is incremented when any of the stations on the ring detects the
          absence of transitions for five half-bit timers (burst-five error)."
    ::= { stkHubTRRing 6 }

stkHubTRRingACFCErrCnt  OBJECT-TYPE
    SYNTAX  Counter32
    MAX-ACCESS  read-only
    STATUS  current
    DESCRIPTION
        "This counter is incremented when any of the stations on the ring receives an 
        AMP or SMP frame in which A is equal to C is equal to 0, and then receives
        another SMP frame with A is equal to C is equal to 0 without first receiving an AMP
        frame. It denotes a station that cannot set the AC bits properly."
    ::= { stkHubTRRing 7 }

stkHubTRRingTotErrCnt OBJECT-TYPE
    SYNTAX  Counter32
    MAX-ACCESS  read-only
    STATUS  current
    DESCRIPTION
        "The total of the above described errors"
    ::= { stkHubTRRing 8 }

stkHubTRRingTotErrThreshold OBJECT-TYPE
    SYNTAX  Integer32
    MAX-ACCESS  read-write
    STATUS  current
    DESCRIPTION
       "The Total Errors Threshold value. A trap indicating Soft Error
	    will be sent, if the total number of errors during the last 10 seconds,
		reached the threshold value. Threshold value = 0 , disables this trap."
    ::= { stkHubTRRing 9}

stkHubTRRingTotalFrames OBJECT-TYPE
    SYNTAX  Counter32
    MAX-ACCESS  read-only
    STATUS  current
    DESCRIPTION
        "The total frames of the Ring."
    ::= { stkHubTRRing 10 }

stkHubTRRingTotalFramesRate OBJECT-TYPE
    SYNTAX  Integer32
    MAX-ACCESS  read-only
    STATUS  current
    DESCRIPTION
        "The rate of total frames on the Ring."
    ::= { stkHubTRRing 11 }

stkHubTRRingTotalOctets OBJECT-TYPE
    SYNTAX  Counter32
    MAX-ACCESS  read-only
    STATUS  current
    DESCRIPTION
	"The total octets of the Ring."
    ::= { stkHubTRRing 12 }

stkHubTRRingOctetsRatio OBJECT-TYPE
    SYNTAX  Integer32
    MAX-ACCESS  read-only
    STATUS  current
    DESCRIPTION
    "Current traffic for the last time interval. The traffic is 
     expressed in percents of the maximum TokenRing traffic ."
    ::= { stkHubTRRing 13 }



--  Bridge Hub Module table for TR media type
--  Contains general information about the Module


stkHubTRMdl       OBJECT IDENTIFIER ::= { stkHubTR 2}

 stkHubTRMdlTable OBJECT-TYPE
    SYNTAX SEQUENCE OF  StkHubTRMdlEntry
    MAX-ACCESS not-accessible
    STATUS current
	DESCRIPTION
	"Bridge Hub Module table for TR media type
	 Contains general information about the Module"
    ::= { stkHubTRMdl 1 }

stkHubTRMdlEntry OBJECT-TYPE
    SYNTAX StkHubTRMdlEntry
    MAX-ACCESS    not-accessible
    STATUS current
	DESCRIPTION
	"An entry in table stkHubTRMdlTable."
    INDEX     {stkHubTRMdlID}
    ::= { stkHubTRMdlTable 1}

StkHubTRMdlEntry ::=
    SEQUENCE {
   stkHubTRMdlID
           Integer32,
   stkHubTRMdlType
          INTEGER,
   stkHubTRMdlReset
          INTEGER,
   stkHubTRMdlLed
          OCTET STRING,
   stkHubTRMdlSpeed
          INTEGER,
   stkHubTRMdlMngState
          INTEGER,
   stkHubTRMdlAutodisable
          INTEGER,
   stkHubTRMdlConfigMsg
          OCTET STRING
        }

stkHubTRMdlID OBJECT-TYPE
      SYNTAX  Integer32 (1..10)
      MAX-ACCESS  read-only
      STATUS  current
      DESCRIPTION
      "A unique identifier of the module in stack. Internal module identifier
      is always 1 "
      ::= {stkHubTRMdlEntry 1}

stkHubTRMdlType OBJECT-TYPE
      SYNTAX  INTEGER {
	       unknown(1),
		   sah16int(2),
		   sah16ext(3),
		   empty(255)
		      }
      MAX-ACCESS  read-only
      STATUS  current
      DESCRIPTION
       "Indicates the type of the module connected with specific identifier "
      ::= {stkHubTRMdlEntry 2 }

 stkHubTRMdlReset  OBJECT-TYPE
      SYNTAX  INTEGER {
           unknown(1),
           off(2),
           on(3)
             }
      MAX-ACCESS  read-write
      STATUS  current
      DESCRIPTION
      "When this object is set to the value of ON(3),
       the module performs software reset. Upon completion, a trap  will
       be issued to the management station and  the value
       will be set to OFF."
      ::= {stkHubTRMdlEntry 3}

stkHubTRMdlLed  OBJECT-TYPE
      SYNTAX  OCTET STRING
      MAX-ACCESS  read-only
      STATUS  current
      DESCRIPTION
        "This entry specifies  the LEDs status in the module . Each led will 
         be represented by 4 bits where the first 2 bits will specify  the 
         status (NA, OFF, ON, BLINK), and the next two bits
         will specify the color (RED, GREEN, YELLOW)"
      ::= {stkHubTRMdlEntry 4}

stkHubTRMdlSpeed OBJECT-TYPE
      SYNTAX  INTEGER {
          unknown(1),
          fourMegabit(2),
          sixteenMegabit(3)
      }
      MAX-ACCESS  read-write
      STATUS  current
      DESCRIPTION
      "Attribute describing the bandwidth of the media as set by the module
       switch.       
       For certain products, if the value of stkHubTRMdlMngState 
       is 'enabled', then stkHubTRMdlSpeed can be set to the desired 
       value. Else, it will be read-only, and will show the status 
       of the jumper set of the main module.
       Refer product's manual."
      ::= { stkHubTRMdlEntry 5}

stkHubTRMdlMngState   OBJECT-TYPE
      SYNTAX  INTEGER {
	   unknown (1),
	   disabled(2),
       enabled (3)
      }    
      MAX-ACCESS  read-only
      STATUS  current
      DESCRIPTION
       "This object indicates the status of the Manage switch 
        as set on the back panel of the main module.
        'enabled' - means that management can override setting of 
                    some HW switch/es."
      ::= {stkHubTRMdlEntry 6 }


stkHubTRMdlAutodisable  OBJECT-TYPE
      SYNTAX   INTEGER {
                unknown(1),
                off(2),
                on(3)
        }
      MAX-ACCESS  read-write
      STATUS  current
      DESCRIPTION
      "Attribute describing the status of port Autodisable 
       mechanism, that protects against inserting in Token Ring 
       adapters at the wrong speed.
       For certain products, if the value of stkHubTRMdlMngState 
       is 'enabled', then stkHubTRMdlAutodisable can be set to 
       the desired value. Else, it will be read-only, and will 
       show the status of the jumper set of the main module.
       Refer product's manual."
   ::= {stkHubTRMdlEntry 7 }


stkHubTRMdlConfigMsg OBJECT-TYPE
      SYNTAX  OCTET STRING
      MAX-ACCESS  read-only
      STATUS  current
      DESCRIPTION
      "Full configuration message  coded in internal RND application format.
      This entry describes  module' configuration. "
      ::= {stkHubTRMdlEntry 8}


--  Bridge Hub  port table for TR media type
--  Contains general information about the ports.


stkHubTRPrt       OBJECT IDENTIFIER ::= { stkHubTR 3}

stkHubTRPrtTable OBJECT-TYPE
      SYNTAX SEQUENCE OF StkHubTRPrtEntry
      MAX-ACCESS not-accessible
      STATUS current
	  DESCRIPTION
	  "Bridge Hub  port table for TR media type
	   Contains general information about the ports."
      ::= { stkHubTRPrt 1 }

stkHubTRPrtEntry OBJECT-TYPE
      SYNTAX    StkHubTRPrtEntry
      MAX-ACCESS    not-accessible
      STATUS    current
	  DESCRIPTION
	  "An entry in table stkHubTRPrtTable."
      INDEX     {  stkHubTRPrtMdlID,
                   stkHubTRPrtID }
      ::= { stkHubTRPrtTable 1 }

StkHubTRPrtEntry ::=
      SEQUENCE {
      stkHubTRPrtMdlID
             Integer32,
      stkHubTRPrtID
             Integer32,
      stkHubTRPrtFunctionality
             INTEGER,
      stkHubTRPrtConnectorType
             INTEGER,
      stkHubTRPrtAdminCmd
             INTEGER,
      stkHubTRPrtActiveState
             INTEGER,
      stkHubTRPrtTrapMaskEnable
             INTEGER,
      stkHubTRPrtStatus
             INTEGER,
      stkHubTRPrtCableProtectEnable
             INTEGER,
	  stkHubTRPrtFlipProtectEnable
	         INTEGER,
      stkHubTRPrtMACAddress
             MacAddress,
      stkHubTRPrtType
             INTEGER
      }

stkHubTRPrtMdlID OBJECT-TYPE
      SYNTAX  Integer32
      MAX-ACCESS  read-only
      STATUS  current
      DESCRIPTION
      "A unique identifier of the module this port is attached to."
      ::= { stkHubTRPrtEntry 1 }

stkHubTRPrtID OBJECT-TYPE
      SYNTAX  Integer32
      MAX-ACCESS  read-only
      STATUS  current
      DESCRIPTION
      "A unique identifier of the port within its module."
      ::= { stkHubTRPrtEntry 2 }

stkHubTRPrtFunctionality OBJECT-TYPE
      SYNTAX  INTEGER {
           unknown(1),
           ringin(2) ,
           ringout(3) ,
           satellite(4),
           lobe(5)
      }
      MAX-ACCESS  read-only
      STATUS  current
      DESCRIPTION
      "Describes the functionality of the port in a Token ring topology"
      ::= { stkHubTRPrtEntry 3 }

stkHubTRPrtConnectorType OBJECT-TYPE
      SYNTAX  INTEGER {
           notApplicable(1),
           idc(2),
           rj45(3),
           srJ45(4),
           db9(5),
           bnc(6),
           fo-st(7),
           db25(8)
--         fo-sma(8),
--         fo-fc(9)
      }
      MAX-ACCESS  read-only
      STATUS  current
      DESCRIPTION
      "Type of hardware connector in the port."
      ::= { stkHubTRPrtEntry 4 }

stkHubTRPrtAdminCmd OBJECT-TYPE
      SYNTAX  INTEGER {
          unknown(1),
          disable(2),
          enable(3),
          short(4),
          normal(5)
      }
      MAX-ACCESS  read-write
      STATUS  current
      DESCRIPTION
         "By setting this attribute to DISABLE(2) or SHORT(4) the
         management station can force this  lobe/port-connection  to be
         removed and block any access to the  network via this lobe/port.
         It is not mandatory that a certain lobe/port will support all the
         enumerated states. The state of the lobe/port is type specific and
         indicated within the specific group"
      ::= { stkHubTRPrtEntry 5 }

stkHubTRPrtActiveState OBJECT-TYPE
      SYNTAX  INTEGER {
          unknown(1),
          off(2),
          on(3),
          standby(4)
      }
      MAX-ACCESS  read-only
      STATUS  current
      DESCRIPTION
        "This attribute describes the electrical or optical activity
         state of  a lobe or the state of a port.  Certain values may
         not be applicable in some cases"
      ::= { stkHubTRPrtEntry 6 }

stkHubTRPrtTrapMaskEnable OBJECT-TYPE
      SYNTAX  INTEGER {
          off(2),
          on(3)
      }
      MAX-ACCESS  read-write
      STATUS  current
      DESCRIPTION
      "When this attribute is set to OFF by the management console the
       agent starts sending the unmasked traps related to this port.
       Otherwise no traps from this port are sent."
      ::= { stkHubTRPrtEntry 7 }

stkHubTRPrtStatus OBJECT-TYPE
      SYNTAX  INTEGER {
          unknown(1),
          disabledManual(2),
          disabledAutorec(3),
          disabledSecurity(4),
          disabledAuto(5),
          disabledFlip(6),
          inserted(7),
          bypass(8),
          forcedloop(9),
          trunkfail(10),
          normal(11)
      }
      MAX-ACCESS  read-only
      STATUS  current
      DESCRIPTION
      "This attribute indicates the status of this lobe/port connection:
      DISABLED-(2) to  (6) indicates the reason for the disabled state.
      INSERTED(7)indicates that the lobe hardware inserts this lobe into
      the ring , thus it becomes part of the ring
      BYPASSED(8)indicates that the ring bypasses this lobe and the lobe
      hardware provides loopback connection towards the station for media 
      test purposes.
      FORCEDLOOP(9) indicates the port is in a loopback state and the
      main ring is connected to the backup path.
      TRUNKFAIL (10) indicates that the ring connection is broken for a
      repeater, converter or a cable protector.
      NORMAL(11) indicates the port is in normal condition
      It is not mandatory that a certain lobe/port will support all the 
       enumerated states."
      ::= { stkHubTRPrtEntry 8 }

stkHubTRPrtCableProtectEnable OBJECT-TYPE
      SYNTAX  INTEGER {
          unknown(1),
          off(2),
          on(3),
          inhibit(4)
      }
      MAX-ACCESS  read-only
      STATUS  current
      DESCRIPTION
      "The value of this attribute determines activation of the cable-fault
      protection mechanism of  TCR and the optical link mechanism of
      TFR and TFC ."
      ::= { stkHubTRPrtEntry  9 }

stkHubTRPrtFlipProtectEnable OBJECT-TYPE
      SYNTAX  INTEGER {
          unknown(1),
          off(2),
          on(3)
      }
      MAX-ACCESS  read-write
      STATUS  current
      DESCRIPTION
      "The value of this attribute determines activation of the flipping-lobe
      protection mechanism of the port."
      ::= { stkHubTRPrtEntry  10 }

stkHubTRPrtMACAddress OBJECT-TYPE
      SYNTAX  MacAddress
      MAX-ACCESS  read-only
      STATUS  current
      DESCRIPTION
      " The value of this object is the specific MAC address
      of this interface which uniquely identifies this Interface
      on a ring."
      ::= { stkHubTRPrtEntry 11 }

stkHubTRPrtType OBJECT-TYPE
      SYNTAX  INTEGER
      {
      notApplicable(1),
      tfr(2),
      tfc(3),
      tcr(4),
      tcp(5)
      }
      MAX-ACCESS  read-only
      STATUS  current
      DESCRIPTION
      "Type of the port specific hardware"
      ::= { stkHubTRPrtEntry 12}

		
-- TRAPS

--NOTIFICATIONS

stkHubTREvents OBJECT-IDENTITY
	   STATUS  current
	   DESCRIPTION
	  "The events for Stackable Token Ring."
	  ::= { stkHubTR 0 }

macAddressUpdated  NOTIFICATION-TYPE
   OBJECTS { stkHubTRPrtMACAddress }
   STATUS  current
   DESCRIPTION
   "This trap will be sent upon every change of 
    MACAddress on a port."
   ::= { stkHubTREvents 91 }

mdlStatusChanged  NOTIFICATION-TYPE
   OBJECTS { stkHubTRMdlLed, stkHubTRMdlType }
   STATUS  current
   DESCRIPTION
   "This trap is sent each time module status was changed.When a module is 
    disconnected, the stkHubTRMdlLed status will be 00 (no led) and the
    stkHubTRMdlType will be empty(255)."
    ::= { stkHubTREvents 27 }

ringBeaconing  NOTIFICATION-TYPE
   OBJECTS  { trimErrorDesc, trimErrorSeverity, agnLed }
   STATUS  current
   DESCRIPTION
   "This trap is sent when Token Ring LAN is beaconing."
   ::= { radRBHTEvents 30 }

lanAdapterRemoved  NOTIFICATION-TYPE
   OBJECTS  { trimErrorDesc, trimErrorSeverity, agnLed }
   STATUS  current
   DESCRIPTION
   "This trap is sent when Token Ring LAN adapter was removed by LAN 
   manager."
   ::= { radRBHTEvents 31 }

-- 
-- file :D:\Synergy\WorkArea\545\mib_rad\txt\stkhubet.txt
-- 

--Title:        STK-E-MIB
-- Version: 1.0
--Date:       9.10.94
--By:          Orly Nicklass & Rina Nathaniel & Benny Dolnik
--File:         STKHUBET.TXT  

--Update:   09.03.95



stkHubET OBJECT IDENTIFIER ::= { radStkHub 3 }  --  Stackable Ethernet


--  Bridge Hub Module table for ET media type
--  Contains general information about the Module


stkHubETMdl       OBJECT IDENTIFIER ::= { stkHubET 2}

 stkHubETMdlTable OBJECT-TYPE
    SYNTAX SEQUENCE OF  StkHubETMdlEntry
    MAX-ACCESS not-accessible
    STATUS current
	DESCRIPTION
	"Bridge Hub Module table for ET media type
	 Contains general information about the Module"
    ::= { stkHubETMdl 1 }

stkHubETMdlEntry OBJECT-TYPE
    SYNTAX StkHubETMdlEntry
    MAX-ACCESS    not-accessible
    STATUS current
	DESCRIPTION
	"An entry in table stkHubETMdlTable."
    INDEX     {stkHubETMdlID}
    ::= { stkHubETMdlTable 1}

StkHubETMdlEntry ::=
    SEQUENCE {
   stkHubETMdlID
           Integer32,
   stkHubETMdlLed
           OCTET STRING,
   stkHubETMdlReset
          INTEGER
   }


stkHubETMdlID OBJECT-TYPE
      SYNTAX  Integer32 (1..10)
      MAX-ACCESS  read-only
      STATUS  current
      DESCRIPTION
      "A unique identifier of the module in stack. Internal module identifier
      is always 1 "
      ::= {stkHubETMdlEntry 1}


stkHubETMdlLed  OBJECT-TYPE
      SYNTAX  OCTET STRING
      MAX-ACCESS  read-only
      STATUS  current
      DESCRIPTION
        "This entry specifies  the LEDs status in the module . Each led will 
         be represented by 4 bits where the first 2 bits will specify  the 
         status (NA, OFF, ON, BLINK), and the next two bits
         will specify the color (RED, GREEN, YELLOW)"
      ::= {stkHubETMdlEntry 2}


stkHubETMdlReset  OBJECT-TYPE
      SYNTAX  INTEGER {
           unknown(1),
           off(2),
           hwReset(3),
		   configReset(4)
             }
      MAX-ACCESS  read-write
      STATUS  current
      DESCRIPTION
      "When this object is set to the value of hwReset(3),
       the module performs HW reset. 
	   When this object is set to the value of configReset(4),
       the module performs Configuration reset.
       Upon completion, a trap  will
       be issued to the management station and  the value
       will be set to OFF."
      ::= {stkHubETMdlEntry 3}


-- Traps are defined using the conventions in RFC 1215 [6].

portStatusChanged  NOTIFICATION-TYPE
      OBJECTS  { stkHubETMdlLed, rpMauMediaAvailable, 
                                 rptrPortOperStatus }
      STATUS  current
      DESCRIPTION
      "This trap is sent each time port status was changed."
      ::= { radStkHubEvents 26 }
-- 
-- file :D:\Synergy\WorkArea\545\mib_rad\txt\etrptr.txt
-- 
--Title:       ET-RPTR-MIB
--Version: 1.0
--Date:      26-JAN-94
--By:         Orly Nicklass 
--File:        ETRPTR.TXT

--Update:  12-MAR-95

  -- Basic Repeater Information
  --
  -- Configuration, status, and control objects for the overall
  -- repeater
  --

radEthRptr  OBJECT IDENTIFIER ::= { rad 9 } -- Ethernet Repeaters products 


etRptrTable  OBJECT-TYPE
	SYNTAX  SEQUENCE OF EtRptrEntry
	MAX-ACCESS  not-accessible
	STATUS current
	DESCRIPTION
	"This table contains repeater data specific to the etRptrIndex."
	::= { radEthRptr 1 }

etRptrEntry OBJECT-TYPE
	SYNTAX  EtRptrEntry
	MAX-ACCESS  not-accessible
	STATUS current
    DESCRIPTION
    "An entry in table etRptrTable."
	INDEX { etRptrIndex  }
	::= { etRptrTable 1 }


EtRptrEntry  ::=
	    SEQUENCE {
	etRptrIndex
	  Integer32,
	etRptrGroupCapacity
	  Integer32,
	etRptrOperStatus
	  INTEGER,
	etRptrHealthText
	  DisplayString,
	etRptrReset
	  INTEGER,
	etRptrNonDisruptTest
	  INTEGER,
	etRptrTotalPartitionedPorts
	  Gauge32,
	etRptrMdlVector
	  Integer32,
	etRptrMonitorTransmitCollisions
	  Counter32
	}

   etRptrIndex  OBJECT-TYPE		   
	   SYNTAX    Integer32 
       MAX-ACCESS    read-only
       STATUS    current
       DESCRIPTION
			   " The Repeater Id, this table data refer to." 
       ::= { etRptrEntry 1 }

   etRptrGroupCapacity OBJECT-TYPE
       SYNTAX    Integer32 (1..1024)
       MAX-ACCESS    read-only
       STATUS    current
       DESCRIPTION
               "The etRptrGroupCapacity is the number of groups
               that can be contained within the repeater.  Within
               each managed repeater, the groups are uniquely
               numbered in the range from 1 to etRptrGroupCapacity.

               Some groups may not be present in the repeater, in
               which case the actual number of groups present
               will be less than etRptrGroupCapacity.  The number
               of groups present will never be greater than
               etRptrGroupCapacity.

               Note:  In practice, this will generally be the
               number of field-replaceable units (i.e., modules,
               cards, or boards) that can fit in the physical
               repeater enclosure, and the group numbers will
               correspond to numbers marked on the physical
               enclosure."
       REFERENCE
               "Reference IEEE 802.3 Rptr Mgt, 19.2.3.2,
                RepeaterGroupCapacity."
       ::= { etRptrEntry 2 }

   etRptrOperStatus OBJECT-TYPE
       SYNTAX  INTEGER {
                   other(1),            -- undefined or unknown status
                   ok(2),               -- no known failures
                   rptrFailure(3),      -- repeater-related failure
                   groupFailure(4),     -- group-related failure
                   portFailure(5),      -- port-related failure
                   generalFailure(6)    -- failure, unspecified type
               }
       MAX-ACCESS    read-only
       STATUS    current
       DESCRIPTION
               "The etRptrOperStatus object indicates the
               operational state of the repeater.  The
               etRptrHealthText object may be consulted for more
               specific information about the state of the
               repeater's health.
               In the case of multiple kinds of failures (e.g.,
               repeater failure and port failure), the value of
               this attribute shall reflect the highest priority
               failure in the following order, listed highest
               priority first:

                   rptrFailure(3)
                   groupFailure(4)
                   portFailure(5)
                   generalFailure(6)."
       REFERENCE
               "Reference IEEE 802.3 Rptr Mgt, 19.2.3.2,
               aRepeaterHealthState."
       ::= { etRptrEntry 3 }

   etRptrHealthText OBJECT-TYPE
       SYNTAX    DisplayString (SIZE (0..255))
       MAX-ACCESS    read-only
       STATUS    current
       DESCRIPTION
               "The health text object is a text string that
               provides information relevant to the operational
               state of the repeater.  Agents may use this string
               to provide detailed information on current
               failures, including how they were detected, and/or
               instructions for problem resolution.  The contents
               are agent-specific."
       REFERENCE
               "Reference IEEE 802.3 Rptr Mgt, 19.2.3.2,
               aRepeaterHealthText."
       ::= { etRptrEntry 4 }


   etRptrReset OBJECT-TYPE
       SYNTAX    INTEGER {
                     noReset(1),
                     resetHW(2),
					 resetConfig(3)
                 }
       MAX-ACCESS    read-write
       STATUS    current
       DESCRIPTION
               "Setting this object to reset(2) causes a
               transition to the START state of Fig 9-2 in
               section 9 [IEEE 802.3 Std].

               Setting this object to noReset(1) has no effect.
               The agent will always return the value noReset(1)
               when this object is read.

               After receiving a request to set this variable to
               resetHW(2), the agent is allowed to delay the reset
               for a short period.  For example, the implementor
               may choose to delay the reset long enough to allow
               the SNMP response to be transmitted.  In any
               event, the SNMP response must be transmitted.

               This action does not reset the management counters
               defined in this document nor does it affect the
               portAdminStatus parameters.  Included in this
               action is the execution of a disruptive Self-Test
               with the following characteristics:  a) The nature
               of the tests is not specified.  b) The test resets
               the repeater but without affecting management
               information about the repeater.  c) The test does
               not inject packets onto any segment.  d) Packets
               received during the test may or may not be
               transferred.  e) The test does not interfere with
               management functions.

               After performing this self-test, the agent will
               update the repeater health information (including
               etRptrOperStatus and etRptrHealthText), and send a
               etRptrHealth trap.
               
               Setting this object to resetConfig(3) will cause
               resetting the repeater to its default values."
       REFERENCE
               "Reference IEEE 802.3 Rptr Mgt, 19.2.3.3,
               acResetRepeater."
       ::= { etRptrEntry 5 }

   etRptrNonDisruptTest OBJECT-TYPE
       SYNTAX    INTEGER {
                     noSelfTest(1),
                     selfTest(2)
                 }
       MAX-ACCESS    read-write
       STATUS    current
       DESCRIPTION
               "Setting this object to selfTest(2) causes the
               repeater to perform a agent-specific, non-
               disruptive self-test that has the following
               characteristics:  a) The nature of the tests is
               not specified.  b) The test does not change the
               state of the repeater or management information
               about the repeater.  c) The test does not inject
               packets onto any segment.  d) The test does not
               prevent the relay of any packets.  e) The test
               does not interfere with management functions.

               After performing this test, the agent will update
               the repeater health information (including
               etRptrOperStatus and etRptrHealthText) and send a
               etRptrHealth trap.

               Note that this definition allows returning an
               'okay' result after doing a trivial test.

               Setting this object to noSelfTest(1) has no
               effect.  The agent will always return the value
               noSelfTest(1) when this object is read."
       REFERENCE
               "Reference IEEE 802.3 Rptr Mgt, 19.2.3.3,
               acExecuteNonDisruptiveSelfTest."
       ::= { etRptrEntry 6 }

   etRptrTotalPartitionedPorts OBJECT-TYPE
       SYNTAX    Gauge32
       MAX-ACCESS    read-only
       STATUS    current
       DESCRIPTION
               "This object returns the total number of ports in
               the repeater whose current state meets all three
               of the following criteria:  etRptrPortOperStatus
               does not have the value notPresent(3),
               etRptrPortAdminStatus is enabled(1), and
               etRptrPortAutoPartitionState is autoPartitioned(2)."
       ::= { etRptrEntry 7 }

   etRptrMdlVector OBJECT-TYPE
       SYNTAX    Integer32
       MAX-ACCESS    read-write
       STATUS    current
       DESCRIPTION
               "This object returns a vector mapping the location of  the repeater modules
                    to their corresponding bit position. A bit that is set indicates an existing module "
       ::= { etRptrEntry 8 }


   --
   -- Repeater Monitor Information
   --
   -- Performance monitoring statistics for the repeater
   --

   etRptrMonitorTransmitCollisions OBJECT-TYPE
       SYNTAX    Counter32
       MAX-ACCESS    read-only
       STATUS    current
       DESCRIPTION
               "This counter is incremented every time the
               repeater state machine enters the TRANSMIT
               COLLISION state from any state other than ONE PORT
               LEFT (Ref: Fig 9-2, IEEE 802.3 Std).

               The approximate minimum time for rollover of this
               counter is 16 hours."
       REFERENCE
               "Reference IEEE 802.3 Rptr Mgt, 19.2.3.2,
               aTransmitCollisions."
       ::= { etRptrEntry 9 }


-- Repeater Security Table

	etRptrSecTable   OBJECT-TYPE
		   SYNTAX SEQUENCE OF EtRptrSecEntry
	       MAX-ACCESS not-accessible
	       STATUS current
		   DESCRIPTION
		   "Repeater Security Table"
	       ::= { radEthRptr 2 }

etRptrSecEntry OBJECT-TYPE
      SYNTAX EtRptrSecEntry
      MAX-ACCESS not-accessible
      STATUS current
      DESCRIPTION
	  "An entry in table etRptrSecTable."
      INDEX {etRptrId, etRptrSecID }
      ::= { etRptrSecTable 1 }

EtRptrSecEntry ::=
      SEQUENCE {
	  etRptrId
	  Integer32,
      etRptrSecID
	  Integer32,
      etRptrSecEnable
	  INTEGER,
      etRptrSecPattern
	  OCTET STRING,
      etRptrSecMask
	  OCTET STRING
      }


etRptrId  OBJECT-TYPE		   
	   SYNTAX    Integer32 
       MAX-ACCESS    read-only
       STATUS    current
       DESCRIPTION
       " The Repeater Id, this table data refer to." 
       ::= { etRptrSecEntry 1 }


etRptrSecID OBJECT-TYPE
      SYNTAX  Integer32  (1..3)
      MAX-ACCESS  read-only
      STATUS  current
      DESCRIPTION
	  "Segment's security unique identification number"
      ::= { etRptrSecEntry 2 }

etRptrSecEnable  OBJECT-TYPE
      SYNTAX  INTEGER {
	  off(2),
	  on(3)
      }
      MAX-ACCESS  read-write
      STATUS  current
      DESCRIPTION
	  "This entry indicates whether the specific segment's security is active or not"
      ::= { etRptrSecEntry 3 }

etRptrSecPattern OBJECT-TYPE
      SYNTAX OCTET STRING
      MAX-ACCESS  read-write
      STATUS  current
      DESCRIPTION
	"A six-octet(48 bit) pattern: where the masked bits of etRptrSecMask
	 need to match the MAC address of each port within the segment.Value of all
	 zeros  indicates no security."
      ::= { etRptrSecEntry 4 }


etRptrSecMask  OBJECT-TYPE
      SYNTAX  OCTET STRING
      MAX-ACCESS  read-write
      STATUS  current
      DESCRIPTION
	"Mask of the allowed MAC address that can be connected through
	the ports within  the segment"
      ::= { etRptrSecEntry 5 }



--NOTIFICATIONS

   radEthRptrEvents OBJECT-IDENTITY
	   STATUS  current
	   DESCRIPTION
	  "The events for Ethernet Repeater."
	  ::= { radEthRptr 0 }

   etRptrHealth NOTIFICATION-TYPE
       OBJECTS  { etRptrOperStatus, rptrGroupOperStatus, agnLed }
	   STATUS  current
       DESCRIPTION
               "The etRptrHealth trap conveys information related
               to the operational status of the repeater.  This
               trap is sent either when the value of
               etRptrOperStatus changes, or upon completion of a
               non-disruptive test.

               See the etRptrOperStatus object for descriptions 
               of the information that is sent.
               The agent must throttle the generation of
               consecutive etRptrHealth traps so that there is at
               least a five-second gap between traps of this
               type.  When traps are throttled, they are dropped,
               not queued for sending at a future time.  (Note
               that 'generating' a trap means sending to all
               configured recipients.)"
       REFERENCE
               "Reference IEEE 802.3 Rptr Mgt, 19.2.3.4,
               hubHealth notification."
       ::= { radEthRptrEvents 1 }


   etRptrResetEvent NOTIFICATION-TYPE
       OBJECTS   { etRptrOperStatus, etRptrIndex, agnLed }
	   STATUS  current
       DESCRIPTION
               "The etRptrResetEvent trap conveys information
               related to the operational status of the repeater.
               This trap is sent on completion of a repeater
               reset action.  A repeater reset action is defined
               as an a transition to the START state of Fig 9-2
               in section 9 [IEEE 802.3 Std], when triggered by a
               management command (e.g., an SNMP Set on the
               etRptrReset object).
               The agent must throttle the generation of
               consecutive etRptrResetEvent traps so that there is
               at least a five-second gap between traps of this
               type.  When traps are throttled, they are dropped,
               not queued for sending at a future time.  (Note
               that 'generating' a trap means sending to all
               configured recipients.)

               The etRptrResetEvent trap is not sent when the agent
               restarts and sends an SNMP coldStart or warmStart
               trap.  However, it is recommended that a repeater
               agent send the etRptrOperStatus object as an
               optional object with its coldStart and warmStart
               trap PDUs.

               The etRptrOperStatus object must be included in the
               varbind list sent with this trap.  The agent may
               optionally include the etRptrHealthText object as
               well."
       REFERENCE
               "Reference IEEE 802.3 Rptr Mgt, 19.2.3.4, hubReset
               notification."
       ::= { radEthRptrEvents 2 }


   etRptrConfig NOTIFICATION-TYPE
       OBJECTS  { etRptrMdlVector, agnLed }
	   STATUS  current
       DESCRIPTION
			   " This trap is sent upon every change of the
			     etRptrMdlVector object."
       ::= { radEthRptrEvents 3 }




-- 
-- file :D:\Synergy\WorkArea\545\mib_rad\txt\mpmx.txt
-- 
--Title:     RAD's WAN PRODUCTS MIB
--Version:   5.45
--Date:      25.01.2006
--By:        Shay Harari

--Last Update: 	 11-Sep-2008 by Liora Gafni
--Some MIB compilers need those two lines:
-- enterprises OBJECT IDENTIFIER ::=
--                       { iso org(3) dod(6) internet(1) private(4) 1 }

--systems OBJECT IDENTIFIER ::= { radGen 1}
--agnt OBJECT IDENTIFIER ::= { radGen 2}
--radSysWan OBJECT IDENTIFIER ::= { systems 3 }

--  -----------------------------------------------------------------------------

 wanGen   OBJECT IDENTIFIER ::= {radWan 1}

 muxHub OBJECT IDENTIFIER ::= {radWan 2}

--  ----------------------------------------------------------------------------------------------
chasWanGen  OBJECT IDENTIFIER ::= {wanGen 1}
agnWanGen   OBJECT IDENTIFIER ::= {wanGen 2}
mdlWanGen   OBJECT IDENTIFIER ::= {wanGen 3}
prtWanGen   OBJECT IDENTIFIER ::= {wanGen 4}
mapWanGen   OBJECT IDENTIFIER ::= {wanGen 5}
diverseIfWanGen OBJECT IDENTIFIER ::= {wanGen 6}
--diverseIfWanGen OBJECT IDENTIFIER ::= {wanGen 6}	defined  RAD-Diverse-IF-MIB

--ethIf          OBJECT IDENTIFIER ::= {diverseIfWanGen 1} (see ethif.txt)
--sonetInterface OBJECT IDENTIFIER ::= {diverseIfWanGen 2} (see radsonet.txt)
--ds3Interface	 OBJECT IDENTIFIER ::= {diverseIfWanGen 3} (see radds3.txt)
--ds1Interface	 OBJECT IDENTIFIER ::= {diverseIfWanGen 4} (see radds1.txt)
--hdlcMibObjects OBJECT IDENTIFIER ::= {diverseIfWanGen 5} (see radhdlc.txt)
--v51If          OBJECT IDENTIFIER ::= {diverseIfWanGen 6} (see v51.txt)
--ip2If          OBJECT IDENTIFIER ::= {diverseIfWanGen 7} (see ipmux.txt)
--broadbandIf    OBJECT IDENTIFIER ::= {diverseIfWanGen 8} (see bdband.txt)
--r2If           OBJECT IDENTIFIER ::= {diverseIfWanGen 9} (see r2.txt)
--adslIf		 OBJECT IDENTIFIER ::= {diverseIfWanGen 10} (see radadsl.txt)
--sdslIf		 OBJECT IDENTIFIER ::= {diverseIfWanGen 11} (see radsdsl.txt)
--shdslIf		 OBJECT IDENTIFIER ::= {diverseIfWanGen 12} (see radshdsl.txt)
--voiceIf		 OBJECT IDENTIFIER ::= {diverseIfWanGen 13} (see voiceIf.txt)
--gsmInterface	 OBJECT IDENTIFIER ::= {diverseIfWanGen 14} (see radGsm.txt)
--ds0BundleIf	 OBJECT IDENTIFIER ::= {diverseIfWanGen 15} (see radds0.txt)
--pdhInterface	 OBJECT IDENTIFIER ::= {diverseIfWanGen 16} (see radpdh.txt)

--voipWanGen OBJECT IDENTIFIER ::= {wanGen 7} (see voip.txt)


statAgnGen       OBJECT IDENTIFIER ::= {agnWanGen 1}
cnfgAgnGen       OBJECT IDENTIFIER ::= {agnWanGen 2}
cmprAgnGen       OBJECT IDENTIFIER ::= {agnWanGen 3}
alrBuffGen       OBJECT IDENTIFIER ::= {agnWanGen 4}
agnFlipDb        OBJECT IDENTIFIER ::= {agnWanGen 5}
agnSa            OBJECT IDENTIFIER ::= {agnWanGen 6}
agnListDecoding  OBJECT IDENTIFIER ::= {agnWanGen 7}
agnSystemDlci    OBJECT IDENTIFIER ::= {agnWanGen 8}
agnVoiceSwitching    OBJECT IDENTIFIER ::= {agnWanGen 9}
agnSigProfile    OBJECT IDENTIFIER ::= {agnWanGen 10}
agnSystemTs      OBJECT IDENTIFIER ::= {agnWanGen 11}
systemVoice      OBJECT IDENTIFIER ::= {agnWanGen 12}

statMdlGen   OBJECT IDENTIFIER ::= {mdlWanGen 1}
cnfgMdlGen   OBJECT IDENTIFIER ::= {mdlWanGen 2}
cmprMdlGen   OBJECT IDENTIFIER ::= {mdlWanGen 3}


statPrtGen   OBJECT IDENTIFIER ::= {prtWanGen 1}
cnfgPrtGen   OBJECT IDENTIFIER ::= {prtWanGen 2}
cmprPrtGen   OBJECT IDENTIFIER ::= {prtWanGen 3}

--statisPrtGen   OBJECT IDENTIFIER ::= {statPrtGen 3} - Statistics of Ports
--prtFrStatis    OBJECT IDENTIFIER ::= {statisPrtGen 1}
--prtCrStatis    OBJECT IDENTIFIER ::= {statisPrtGen 2}
--prtDlciStatis  OBJECT IDENTIFIER ::= {statisPrtGen 3}
--prtT1Statis    OBJECT IDENTIFIER ::= {statisPrtGen 4}

agnMux        OBJECT IDENTIFIER ::= {muxHub 1}
mdlMux        OBJECT IDENTIFIER ::= {muxHub 2}
prtMux        OBJECT IDENTIFIER ::= {muxHub 3}

--cnfgMdlMux         OBJECT IDENTIFIER ::= {mdlMux 1}
--statMdlMux         OBJECT IDENTIFIER ::= {mdlMux 2}

statPrtMux         OBJECT IDENTIFIER ::= {prtMux 1}
cnfgPrtMux         OBJECT IDENTIFIER ::= {prtMux 2}

statisPrtGen   OBJECT IDENTIFIER ::= {statPrtGen 3}

prtFrStatis    OBJECT IDENTIFIER ::= {statisPrtGen 1}
prtCrStatis    OBJECT IDENTIFIER ::= {statisPrtGen 2}
prtDlciStatis  OBJECT IDENTIFIER ::= {statisPrtGen 3}
prtT1Statis    OBJECT IDENTIFIER ::= {statisPrtGen 4}

--

--prtSExHsfStatTable   OBJECT IDENTIFIER ::= {statPrtMux 6}
--prtIsdnStatusTable   OBJECT IDENTIFIER ::= {statPrtMux 16}

--

prtClCnfg       OBJECT IDENTIFIER ::= {cnfgPrtMux 1}
prtPh1MlCnfg    OBJECT IDENTIFIER ::= {cnfgPrtMux 2} --MPH1/e1/t1
prtPhPlCnfg     OBJECT IDENTIFIER ::= {cnfgPrtMux 3} --MPH1,MPH3,MPL6
prtLs2Cnfg      OBJECT IDENTIFIER ::= {cnfgPrtMux 4} --LS2 family
--prtVc2CnfgTable      OBJECT IDENTIFIER ::= {cnfgPrtMux 5}
--prtHsfCnfgTable      OBJECT IDENTIFIER ::= {cnfgPrtMux 6}
prtHs4Cnfg      OBJECT IDENTIFIER ::= {cnfgPrtMux 7}
prtHsiCnfg      OBJECT IDENTIFIER ::= {cnfgPrtMux 8}
prtPVc4Cnfg     OBJECT IDENTIFIER ::= {cnfgPrtMux 9}
prtHsrCnfg      OBJECT IDENTIFIER ::= {cnfgPrtMux 10}
prtMbeCnfg      OBJECT IDENTIFIER ::= {cnfgPrtMux 11}
prtTreCnfg      OBJECT IDENTIFIER ::= {cnfgPrtMux 12}
prtLs6Cnfg      OBJECT IDENTIFIER ::= {cnfgPrtMux 13}
prtVc3Cnfg      OBJECT IDENTIFIER ::= {cnfgPrtMux 14}
prtVcPbxCnfg    OBJECT IDENTIFIER ::= {cnfgPrtMux 15}
prtIsdnCnfg     OBJECT IDENTIFIER ::= {cnfgPrtMux 16}
prtLogicalCnfg  OBJECT IDENTIFIER ::= {cnfgPrtMux 17}
prtFrPlusCnfg   OBJECT IDENTIFIER ::= {cnfgPrtMux 18}
prtMl4Cnfg      OBJECT IDENTIFIER ::= {cnfgPrtMux 19}
prtAcmCnfg      OBJECT IDENTIFIER ::= {cnfgPrtMux 20}
prtE2Cnfg       OBJECT IDENTIFIER ::= {cnfgPrtMux 21}
prtLanWanCnfg   OBJECT IDENTIFIER ::= {cnfgPrtMux 22}

--
-- Wan chassis general information
--

chasVersion OBJECT-TYPE
      SYNTAX  DisplayString (SIZE (0..255))
      MAX-ACCESS  read-only
      STATUS  current
      DESCRIPTION
      "An ASCII string for description and display of the agent chassis version."
      ::= { chasWanGen 1 }

chasTotalNoOfSlt  OBJECT-TYPE
      SYNTAX  Integer32
      MAX-ACCESS  read-only
      STATUS  current
      DESCRIPTION
      "This entry indicates the number of physical slots in the
       chassis."
      ::= { chasWanGen 2 }

chasTotalNoOfIoSlt  OBJECT-TYPE
      SYNTAX  Integer32
      MAX-ACCESS  read-only
      STATUS  current
      DESCRIPTION
      "This entry indicates the total number of physical IO slots
       in the chassis, (not all slots hardware should be occupied
       and active) ."
      ::= { chasWanGen 3 }

chasTotalNoOfPsSlt  OBJECT-TYPE
      SYNTAX  Integer32
      MAX-ACCESS  read-only
      STATUS  current
      DESCRIPTION
      "This entry indicates the number of physical Power Supply
       slots in the chassis."
      ::= { chasWanGen 4 }

chasTotalNoOfClSlt  OBJECT-TYPE
      SYNTAX  Integer32
      MAX-ACCESS  read-only
      STATUS  current
      DESCRIPTION
      "This entry indicates the number of physical Common Logic slots in the
       chassis."
      ::= { chasWanGen 5 }

--
-- Wan agent status general information
--
agnSDateFormat  OBJECT-TYPE
      SYNTAX  INTEGER
       {
          ddMMYYYY (1),
          mmDDYYYY (2),
          yyyyDDMM (3),
		  yyyyMMDD (4)
       }
      MAX-ACCESS  read-write
      STATUS  current
      DESCRIPTION
      "This entry indicates the date and time format used for the
       agnSDateAndTimeCmd and for the alarm history report."
      ::= { statAgnGen 1 }

agnSDateCmd  OBJECT-TYPE
      SYNTAX  DisplayString (SIZE (0..255))
      MAX-ACCESS  read-write
      STATUS  current
      DESCRIPTION
      "This entry indicates the current date as it is known by the
       agent using its own real-time clock. The format would be as
       specified by the agnSDateFormat.
       This  parameter can be set for time synchronization between
       the NMS and the Agent."
      ::= { statAgnGen 2 }

agnSTimeCmd  OBJECT-TYPE
      SYNTAX  DisplayString (SIZE (0..255))
      MAX-ACCESS  read-write
      STATUS  current
      DESCRIPTION
      "This entry indicates the current time as it is known by the
       agent using its own real-time clock.
       This  parameter can be set for time synchronization between
       the NMS and the Agent."
      ::= { statAgnGen 3 }

agnSActiveCnfg  OBJECT-TYPE
      SYNTAX  Integer32
      MAX-ACCESS  read-only
      STATUS  current
      DESCRIPTION
      "This entry specifies the unique identifier of the  configuration,
       that is currently  active and running."
      ::= { statAgnGen 4 }
-- return 1 (db1) in phase I

agnSEditCnfg OBJECT-TYPE
      SYNTAX  Integer32
      MAX-ACCESS  read-only
      STATUS  current
      DESCRIPTION
      "This entry indicates the  unique identifier of the
       configuration that is currently loaded into the tmp working
       space  for manipulation and update operations. Value of 255
       means no config. is under editing process."
      ::= { statAgnGen 5 }
-- return 1 (db1) in phase I

agnSLastCnfgFlipTime OBJECT-TYPE
      SYNTAX  DisplayString (SIZE (0..255))
      MAX-ACCESS  read-only
      STATUS  current
      DESCRIPTION
      "This entry indicates the Date & Time of the last flip to the
       current configuration at the agent."
      ::= { statAgnGen 6 }
-- return sysUpTime in phase I

agnSLastCnfgFlipCause OBJECT-TYPE
      SYNTAX  DisplayString (SIZE (0..255))
      MAX-ACCESS  read-only
      STATUS  current
      DESCRIPTION
      "This entry describes the flip's cause."
      ::= { statAgnGen 7 }
-- In phase I return two causes:
--          Power up
--          Update Db

agnSEditBy OBJECT-TYPE
      SYNTAX  INTEGER
       {
           none            (1),
           snmp            (2),
           terCon1         (3),
           terCon2         (4),
           terInbandCon1   (5),
           terInbandCon2   (6),
           lcd             (7)
       }
      MAX-ACCESS  read-only
      STATUS  current
      DESCRIPTION
      "This entry indicates which MMI application is working on  the
       edited config.
       The editing phase starts at the first modify operation and
       ends after an update(load) operation."
      ::= { statAgnGen 8 }

agnSClkSrc  OBJECT-TYPE
      SYNTAX  INTEGER
    {
        master  (1),
        fallback(2),
        internal(3)
 }
      MAX-ACCESS  read-only
      STATUS  current
      DESCRIPTION
     "This entry indicates the source of the system clock."
      ::= { statAgnGen 9 }

agnSAlrStatus OBJECT-TYPE
      SYNTAX  INTEGER
       {
  off      (2),
  event    (3),
  minor    (4),
  major    (5),
  warning  (6),
  critical (7)
       }
      MAX-ACCESS  read-only
      STATUS  current
      DESCRIPTION
      "Indicates the alarm state in the agent level, i.e. lower
       level (card/port) alarms not included.
    critical(7) - when there is at least one active (state ON)
                  critical alarm,
                  otherwise it will be set to
       major(5) - when there is at least one active (state ON)
                  major alarm,
                  otherwise it will be set to
       minor(4) - if there is at least one active (state ON) minor
                  alarm,
                  otherwise it will be set to
       warning(6) - if there is at least one active (state ON)
                  warning alarm,
                  otherwise it will be set to
       event(3) - if there was at least one alarm event (including
                  state on,off events) since the last clear operation."
      ::= { statAgnGen 10 }

agnSAlrStatusAll OBJECT-TYPE
      SYNTAX  INTEGER
       {
  off      (2),
  event    (3),
  minor    (4),
  major    (5),
     warning  (6),
  critical (7)
       }
      MAX-ACCESS  read-only
      STATUS  current
      DESCRIPTION
      "Indicates the alarm state of the entire agent, i.e.
       including card and port alarms status.
    critical(7) - when there is at least one active (state ON)
                  critical alarm,
                  otherwise it will be set to
       major(5) - when there is at least one active (state ON)
                  major alarm,
                  otherwise it will be set to
       minor(4) - if there is at least one active (state ON) minor
                  alarm,
                  otherwise it will be set to
       warning(6) - if there is at least one active (state ON)
                  warning alarm,
                  otherwise it will be set to
       event(3) - if there was at least one alarm event (including
                  state on,off events) since the last clear operation."
      ::= { statAgnGen 11 }

agnSMaskedAlrStat OBJECT-TYPE
      SYNTAX  INTEGER
       {
  off      (2),
  event    (3),
  minor    (4),
  major    (5),
     warning  (6),
  critical (7)
       }
      MAX-ACCESS  read-only
      STATUS  current
      DESCRIPTION
      "Indicates the alarm state in the agent level,[ i.e. lower
       level (card/port) alarms not included] including Masked
       alarms.
    critical(7) - when there is at least one active (state ON)
                  critical alarm,
                  otherwise it will be set to
       major(5) - when there is at least one active (state ON)
                  major alarm,
                  otherwise it will be set to
       minor(4) - if there is at least one active (state ON) minor
                  alarm,
                  otherwise it will be set to
       warning(6) - if there is at least one active (state ON)
                  warning alarm,
                  otherwise it will be set to
       event(3) - if there was at least one alarm event (including
                  state on,off events) since the last clear operation."
      ::= { statAgnGen 12 }

agnSMaskedAlrStatAll OBJECT-TYPE
      SYNTAX  INTEGER
       {
  off      (2),
  event    (3),
  minor    (4),
  major    (5),
     warning  (6),
  critical (7)
       }
      MAX-ACCESS  read-only
      STATUS  current
      DESCRIPTION
      "Indicates the alarm state of the entire agent, i.e.
       including card and port alarms status,including
       Masked alarms.
    critical(7) - when there is at least one active (state ON)
                  critical alarm,
                  otherwise it will be set to
       major(5) - when there is at least one active (state ON)
                  major alarm,
                  otherwise it will be set to
       minor(4) - if there is at least one active (state ON) minor
                  alarm,
                  otherwise it will be set to
       warning(6) - if there is at least one active (state ON)
                  warning alarm,
                  otherwise it will be set to
       event(3) - if there was at least one alarm event (including
                  state on,off events) since the last clear operation."
      ::= { statAgnGen 13 }

agnSTstStatAll OBJECT-TYPE
      SYNTAX  INTEGER
       {
  off(2),
  on (3)
       }
      MAX-ACCESS  read-only
      STATUS  current
      DESCRIPTION
      "on(3) - when there is at least one test in progress in one
               of the agent cards,
       otherwise the value will be off(2)."
      ::= { statAgnGen 14 }

agnSAlrTable OBJECT-TYPE
      SYNTAX SEQUENCE OF AgnSAlrEntry
      MAX-ACCESS not-accessible
      STATUS current
      DESCRIPTION
      "List of agent related alarms and indications for alarms at
       system level."
      ::= { statAgnGen 15 }

agnSAlrEntry OBJECT-TYPE
      SYNTAX AgnSAlrEntry
      MAX-ACCESS not-accessible
      STATUS current
	DESCRIPTION  "An entry in table."
	INDEX { agnSAlrIdx}
      ::= { agnSAlrTable 1}

AgnSAlrEntry ::=
      SEQUENCE {
  agnSAlrIdx              Integer32,
  agnSAlrCodeDescription  DisplayString,
  agnSAlrCode             Integer32,
  agnSAlrSeverity         INTEGER,
  agnSAlrState            INTEGER,
  agnSAlrCounter          Integer32,
  agnSAlrMask             INTEGER,
  agnSAlrInvert           INTEGER
      }

agnSAlrIdx OBJECT-TYPE
      SYNTAX  Integer32
      MAX-ACCESS  read-only
      STATUS  current
      DESCRIPTION
      "A unique number to identify an entry in the alarm status table
       of the agent."
      ::= { agnSAlrEntry 1 }

agnSAlrCodeDescription OBJECT-TYPE
      SYNTAX  DisplayString (SIZE (0..255))
      MAX-ACCESS  read-only
      STATUS  current
      DESCRIPTION
      "This attribute is a full text description of the alarm .
       The alarm description includes the following information:
       alarm code, alarm text, alarm severity, Masked or Inverted
       flag and counter."
     ::= { agnSAlrEntry 2 }

agnSAlrCode OBJECT-TYPE
      SYNTAX  Integer32
      MAX-ACCESS  read-only
      STATUS  current
      DESCRIPTION
      "A code identifying the alarm of an entry in the alarm status
       table at system level."
      ::= { agnSAlrEntry 3 }

agnSAlrSeverity OBJECT-TYPE
      SYNTAX  INTEGER
       {
  event    (3),
  minor    (4),
  major    (5),
  warning  (6),
  critical (7)
       }
      MAX-ACCESS  read-only
      STATUS  current
      DESCRIPTION
      "The severity of the alarm."
      ::= { agnSAlrEntry 4 }

agnSAlrState  OBJECT-TYPE
      SYNTAX  INTEGER
       {
  off(2),
  on (3)
       }
      MAX-ACCESS  read-only
      STATUS  current
      DESCRIPTION
      "State of the alarm."
      ::= { agnSAlrEntry 5 }

agnSAlrCounter OBJECT-TYPE
      SYNTAX  Integer32
      MAX-ACCESS  read-only
      STATUS  current
      DESCRIPTION
      "A counter - how many times the alarm occured since last
       clear operation.
       ON and OFF Alarm will be counted separately."
      ::= { agnSAlrEntry 6 }

agnSAlrMask  OBJECT-TYPE
      SYNTAX  INTEGER
       {
  off(2),
  on (3)
       }
      MAX-ACCESS  read-only
      STATUS  current
      DESCRIPTION
      "Alarm mask : on/off."
      ::= { agnSAlrEntry 7 }

agnSAlrInvert  OBJECT-TYPE
      SYNTAX  INTEGER
       {
  off(2),
  on (3)
       }
      MAX-ACCESS  read-only
      STATUS  current
      DESCRIPTION
      "Alarm invert : on/off."
      ::= { agnSAlrEntry 8 }


agnSClearAlrCmd  OBJECT-TYPE
      SYNTAX  INTEGER
       {
  off(2),
  on (3)
       }
      MAX-ACCESS  read-write
      STATUS  current
      DESCRIPTION
      "Setting this attribute to ON, enforce a  clear operation on
       all the agent(general) events. General alarms are alarms
       which are not specific to a card or port. The clear
       operation will not be applied for masked/inverted alarms."
      ::= { statAgnGen 16 }

agnSClearAllAlrCmd OBJECT-TYPE
      SYNTAX  INTEGER
       {
  off(2),
  on (3)
       }
      MAX-ACCESS  read-write
      STATUS  current
      DESCRIPTION
      "Setting this attribute to ON, enforce a clear operation on
       all MUX alarm events at the levels of agent, slots and ports.
       The clear operation will not be applied for masked/inverted
       alarms."
      ::= { statAgnGen 17 }

agnSSanityCheckStatus OBJECT-TYPE
      SYNTAX  INTEGER
       {
  unknown (1),
  fail    (2),
  warning (3),
  ok      (4)
       }
      MAX-ACCESS  read-only
      STATUS  current
      DESCRIPTION
      "Upon completion of the Sanity check process on the TmpCnfg
       this attribute will be set to:
       FAIL(2) - when there is at least one error encountered and
                 possibly some warnings.
       WARNING(3) - when there are only warnings.
       otherwise, the value will be OK(4).
       The value will be UNKNOWN(1) if changes were made in the
       TmpCnfg following the last Sanity check."
      ::= { statAgnGen 18 }

agnSNoOfSanityCheckErr OBJECT-TYPE
      SYNTAX  Integer32
      MAX-ACCESS  read-only
      STATUS  current
      DESCRIPTION
      "This entry indicates the number of errors/warnings discovered
       by the last SanityCheck process."
      ::= { statAgnGen 19 }

agnSErrListTable OBJECT-TYPE
      SYNTAX SEQUENCE OF AgnSErrListEntry
      MAX-ACCESS not-accessible
      STATUS current
      DESCRIPTION
      "List of errors and warnings found during Sanity Check
       process."
      ::= { statAgnGen 20 }

agnSErrListEntry OBJECT-TYPE
      SYNTAX AgnSErrListEntry
      MAX-ACCESS not-accessible
      STATUS current
	DESCRIPTION  "An entry in table."
	INDEX { agnSErrIdx}
      ::= { agnSErrListTable 1}

AgnSErrListEntry ::=
      SEQUENCE {
     agnSErrIdx          Integer32,
     agnSErrDescription  DisplayString 
               }

agnSErrIdx OBJECT-TYPE
      SYNTAX  Integer32
      MAX-ACCESS  read-only
      STATUS  current
      DESCRIPTION
      "Unique number to identify an entry in the  error list table.
       The maximum entry  value cannot exceed the value of
       'agnSNoOfSanityCheckErr'. "
    ::= { agnSErrListEntry 1}

agnSErrDescription OBJECT-TYPE
      SYNTAX  DisplayString (SIZE (0..255))
      MAX-ACCESS  read-only
      STATUS  current
      DESCRIPTION
      "This attribute is a full text description of the sanity check
       error including error code, slot and port numbers related to
       the code ."
  ::= { agnSErrListEntry 2}

agnSMaxNoOfCnfg OBJECT-TYPE
      SYNTAX  Integer32
      MAX-ACCESS  read-only
      STATUS  current
      DESCRIPTION
      "Maximum number of configurations that can be defined and
       stored in the MUX.
       If the mux has a large capacity, the maximum will be limited
       to  254."
      ::= { statAgnGen 21}
-- return 1 (db1) in phase I

agnSCnfgTable OBJECT-TYPE
      SYNTAX SEQUENCE OF AgnSCnfgEntry
      MAX-ACCESS not-accessible
      STATUS  current
      DESCRIPTION
      "This table contains an entry per configuration. It indicates
       if the configuration is valid."
      ::= { statAgnGen 22 }
--  - in phase I only one entry

agnSCnfgEntry OBJECT-TYPE
      SYNTAX AgnSCnfgEntry
      MAX-ACCESS not-accessible
      STATUS current
	DESCRIPTION  "An entry in table."
	INDEX { agnSEntryIdx}
      ::= {agnSCnfgTable  1}

AgnSCnfgEntry ::=
      SEQUENCE  {
 agnSEntryIdx         Integer32,
 agnSEntryIsValid     INTEGER
      }

agnSEntryIdx OBJECT-TYPE
      SYNTAX  Integer32
      MAX-ACCESS  read-only
      STATUS  current
      DESCRIPTION
      "Unique number to identify an entry in the configuration table."
    ::= { agnSCnfgEntry 1}

agnSEntryIsValid OBJECT-TYPE
      SYNTAX  INTEGER
       {
  no  (2),
  yes (3)
       }
      MAX-ACCESS  read-only
      STATUS  current
      DESCRIPTION
      "This attribute indicates whether the specific configuration
       is valid in the MUX . Value of NO indicates: no such
       configuration  in the MUX. "
    ::= { agnSCnfgEntry 2}

--
-- Wan agent configuration information
--
agnCSanityCheckCmd OBJECT-TYPE
      SYNTAX  INTEGER
       {
       off(2),
       on (3)
       }
      MAX-ACCESS  read-write
      STATUS  current
      DESCRIPTION
      "Setting this attribute to on(3) will initiate the process
       of Sanity check on the TmpCnfg. Upon completion the value
       will automatically be changed to off(2)."
      ::= { cnfgAgnGen 1 }

agnCSaveCnfgIdxCmd OBJECT-TYPE
      SYNTAX  Integer32   (1..100)
      MAX-ACCESS  read-write
      STATUS  current
      DESCRIPTION
      "This attribute specifies the Id of the target RealCnfg to
       which the TmpCnfg should be transferred. Upon set command the
       MUX will initiate the Sanity-Check  process first. If
       successful, the actual transfer will be performed. If warnings
       are detected, the user will have to perform the command again
       to confirm the operation. Setting this object a second time
       to the same value without performing any change in the database,
       will cause the result: agnSSanityCheckStatus = unknown"
      ::= { cnfgAgnGen 2 }
-- In phase I only the value 1 (Cnfg1) is valid.

agnCLoadCnfgIdxCmd OBJECT-TYPE
      SYNTAX  Integer32  (1..100)
      MAX-ACCESS  read-write
      STATUS  current
      DESCRIPTION
      "This attribute specifies the Id of the source Cnfg to be
       loaded into the TmpCnfg. Upon set operation the actual
       transfer will be initiated.
       The operation is valid only on Valid configurations
       (agnSEntryIsValid)"
      ::= { cnfgAgnGen 3 }
-- In phase I only the value 1 (Cnfg1) is valid.


agnCClkSrcTable  OBJECT-TYPE
      SYNTAX SEQUENCE OF AgnCClkSrcEntry
      MAX-ACCESS not-accessible
      STATUS  current
      DESCRIPTION
      "All the entries of this table are identical (have the same
       value) for all the configurations (1..100) except the
       TmpCnfg.
       The write operation into the Table Objects is valid only
       for the TmpCnfg entry."
       ::= { cnfgAgnGen 4}

agnCClkSrcEntry OBJECT-TYPE
      SYNTAX AgnCClkSrcEntry
      MAX-ACCESS not-accessible
      STATUS current
	DESCRIPTION  "An entry in table."
	INDEX {agnCClkCnfgIdx, agnCClkSrcIdx}
      ::= { agnCClkSrcTable 1}

AgnCClkSrcEntry ::=
      SEQUENCE {
   agnCClkCnfgIdx      Integer32,
   agnCClkSrcIdx       Integer32,
   agnCClkSrcMode      INTEGER,
   agnCClkSrcSlt       INTEGER,
   agnCClkSrcPrt       Integer32
      }

agnCClkCnfgIdx OBJECT-TYPE
      SYNTAX Integer32 (1..255)
      MAX-ACCESS read-only
      STATUS current
      DESCRIPTION
      "This attribute indicates the Idx of the Cnfg(1..100) being
       accessed and Idx 255 relates to the TmpCnfg."
      ::= { agnCClkSrcEntry 1}
-- In phase I only the values 1 (Cnfg1) and 255 (temp) are valid.

agnCClkSrcIdx OBJECT-TYPE
      SYNTAX  Integer32 (1..2)
      MAX-ACCESS  read-only
      STATUS  current
      DESCRIPTION
      "An index to the table. There are only two entries to this
       table.
       Index 1 points to the Master clock parameters and Index 2
       points to the Fallback clock parameters"
      ::= { agnCClkSrcEntry 2}

agnCClkSrcMode OBJECT-TYPE
      SYNTAX  INTEGER
       {
           internal   (1),
           rxClk      (2),
		   adaptive   (3)
       }
      MAX-ACCESS  read-write
      STATUS  current
      DESCRIPTION
      "The source of the nodal timing."
      ::= { agnCClkSrcEntry 3}

agnCClkSrcSlt OBJECT-TYPE
      SYNTAX  INTEGER
        {
       notApplicable   (1),
       io1   (5),
       io2   (6),
       io3   (7),
       io4   (8),
       io5   (9),
       io6  (10),
       io7  (11),
       io8  (12),
       io9  (13),
       io10 (14),
       io11 (15),
       io12 (16)
     }
      MAX-ACCESS  read-write
      STATUS  current
      DESCRIPTION
      "This entry is valid only when we are working in rxClk mode.
       For an invalid entry, the return value will be '7fff'h."
      ::= { agnCClkSrcEntry 4}

agnCClkSrcPrt OBJECT-TYPE
      SYNTAX  Integer32
      MAX-ACCESS  read-write
      STATUS  current
      DESCRIPTION
      "This entry is valid only when we are working in rxClk or 
       adaptive mode.
       For an invalid entry, the return value will be '7fff'h.
       - For rxClk mode, the values can be:
              exPrt1    (1) ,
              exPrt2    (2) ,
              exPrt3    (3) ,
              exPrt4    (4) ,
              exPrt5    (5) ,
              exPrt6    (6) ,
              exPrt7    (7) ,
              exPrt8    (8) ,
              exPrt9    (9) ,
              exPrt10  (10) ,
              exPrt11  (11) ,
              exPrt12  (12) ,
              notApplicable   (100),
	 	 	  inPrt1  (101) ,
	 	 	  inPrt2  (102) ,
	 	 	  inPrt3  (103) ,
	 	 	  inPrt4  (104)
       - For adaptive mode, the value will be the ifIndex of the 
         selected IP Bundle."
      ::= { agnCClkSrcEntry 5}

agnCDeleteCnfgIdxCmd OBJECT-TYPE
  SYNTAX  Integer32 (1..100)
  MAX-ACCESS  read-write
  STATUS  current
  DESCRIPTION
  "Setting this attribute will delete the requested DB
   from the NVRAM ."
  ::= { cnfgAgnGen 5 }

agnCDefaultCnfgIdxCmd OBJECT-TYPE
  SYNTAX  Integer32 (1..100)
  MAX-ACCESS  read-write
  STATUS  current
  DESCRIPTION
  "Setting this attribute will define the desired working
   configuration when no conditions of the Flip DB Table are
   fulfilled and no Net GO command was issued. This command
   will be accepted only if the Configuration number exists
   (agnSEntryIsValid=yes)."
  ::= { cnfgAgnGen 6 }

agnCnfgDataTable OBJECT-TYPE
      SYNTAX SEQUENCE OF AgnCnfgDataEntry
      MAX-ACCESS not-accessible
      STATUS  current
      DESCRIPTION
      "This table contains data about the agent configurations.
       The table will support only data about valid configurations
       of the agent."
       ::= { cnfgAgnGen 7}

agnCnfgDataEntry OBJECT-TYPE
      SYNTAX AgnCnfgDataEntry
      MAX-ACCESS not-accessible
      STATUS current
	DESCRIPTION  "An entry in table."
	INDEX {agnCnfgIdx}
      ::= { agnCnfgDataTable 1}

AgnCnfgDataEntry ::=
      SEQUENCE {
   agnCnfgIdx      Integer32,
   agnCnfgDesc     DisplayString,
   agnCnfgUpdDate  DisplayString,
   agnCnfgUpdTime  DisplayString,
   agnCnfgUpdMnger IpAddress
      }

agnCnfgIdx OBJECT-TYPE
      SYNTAX Integer32 (1..255)
      MAX-ACCESS read-only
      STATUS current
      DESCRIPTION
      "This object indicates the Idx of the agent' Cnfg the following 
       objects refer.
       255=Temporary Cnfg (Set is done only to this configuration)."
      ::= { agnCnfgDataEntry 1}
-- Only the values 1..10, 255 are valid.

agnCnfgDesc OBJECT-TYPE
      SYNTAX DisplayString (SIZE (0..30))
      MAX-ACCESS read-write
      STATUS current
      DESCRIPTION
      "This object is a description of the Configuration, entered
       by user, to enhance Cnfg recognition."
      ::= { agnCnfgDataEntry 2}

agnCnfgUpdDate  OBJECT-TYPE
      SYNTAX  DisplayString (SIZE (0..255))
      MAX-ACCESS  read-only
      STATUS  current
      DESCRIPTION
      "This object indicates the date when last update of this
       configuration was performed, as it is known by the
       agent using its own real-time clock. The format would be as
       specified by the agnSDateFormat.
       When update is performed, the agent should save the date."
      ::= { agnCnfgDataEntry 3 }

agnCnfgUpdTime  OBJECT-TYPE
      SYNTAX  DisplayString (SIZE (0..255))
      MAX-ACCESS  read-only
      STATUS  current
      DESCRIPTION
      "This object indicates the time when last update of this
       configuration was performed, as it is known by the
       agent using its own real-time clock.
       When update is performed, the agent should save the time."
      ::= { agnCnfgDataEntry 4 }

agnCnfgUpdMnger  OBJECT-TYPE
      SYNTAX  IpAddress
      MAX-ACCESS  read-only
      STATUS  current
      DESCRIPTION
      "This object indicates the IP Address of the Manager who
       performed the last update of this configuration.
       When update is performed, the agent should save the
       IP Address of the Manager who commanded the update.
       That will enable a manager to know if he performed the last
       update, or another manager did."
      ::= { agnCnfgDataEntry 5 }


agnCnfgAlarm   OBJECT IDENTIFIER ::= { cnfgAgnGen 8}

agnCnfgAlrFilterWindow OBJECT-TYPE
      SYNTAX Integer32 (0..255)
      MAX-ACCESS read-write
      STATUS current
      DESCRIPTION
      "Window of time, in seconds.
       During this Window, the alarms filter is performed.
       Same Window for all agent alarms that need filtering.
       Upon end of the Window, the state of the alarm is updated
       and a new Window starts.
       If no alarm needs filtering, this object's value will not be
       used."
      ::= { agnCnfgAlarm 1}

agnCnfgAlrTable OBJECT-TYPE
      SYNTAX SEQUENCE OF AgnCnfgAlrEntry
      MAX-ACCESS not-accessible
      STATUS  current
      DESCRIPTION
      "This table enables the user to set attributes to each alarm.
       Setting  for a non-existing entry agnCnfgAlrMask,
       agnCnfgAlrInvert or agnCnfgAlrFilter to 'yes'(or yesAndSave
       for Mask) will add this new entry to the table.
       Setting  for an existing entry agnCnfgAlrMask/
       agnCnfgAlrInvert/agnCnfgAlrFilter (one or more) to 'no'
       (noAndSave for Mask)  so that ALL  these objects' values are
       'no' , will delete this entry from the table.
       For agnCnfgAlrMask, only if [(last saved value=noAndSave)
       AND (new value is 'no' or 'noAndSave')] the object's value
       is considered 'no' for deleting the entry.
       
       For some products (like MP, MPH, Vmux2100) the Active Alarms are always
       part of the table and cannot be removed even if their Mask/Invert/Filter
       are No."
       ::= { agnCnfgAlarm 2}

agnCnfgAlrEntry OBJECT-TYPE
      SYNTAX AgnCnfgAlrEntry
      MAX-ACCESS not-accessible
      STATUS current
	DESCRIPTION  "An entry in table."
	INDEX {agnCnfgAlrCode, agnCnfgAlrSlot, agnCnfgAlrPort}
      ::= { agnCnfgAlrTable 1}

AgnCnfgAlrEntry ::=
      SEQUENCE {
   agnCnfgAlrCode        Integer32,
   agnCnfgAlrSlot        INTEGER,
   agnCnfgAlrPort        Integer32,
   agnCnfgAlrMask        INTEGER,
   agnCnfgAlrInvert      INTEGER,
   agnCnfgAlrFilter      INTEGER,
   agnCnfgAlrFilterSet   Integer32,
   agnCnfgAlrFilterReset Integer32,
   agnCnfgAlrSeverity    INTEGER 
    
	}

agnCnfgAlrCode OBJECT-TYPE
      SYNTAX Integer32
      MAX-ACCESS read-only
      STATUS current
      DESCRIPTION
      "The alarm code. The following attributes refer this code."
      ::= { agnCnfgAlrEntry 1 }

agnCnfgAlrSlot OBJECT-TYPE
      SYNTAX INTEGER
      {
       psA   (1),
       psB   (2),
       clA   (3),
       clB   (4),
       io1   (5),
       io2   (6),
       io3   (7),
       io4   (8),
       io5   (9),
       io6  (10),
       io7  (11),
       io8  (12),
       io9  (13),
       io10 (14),
       io11 (15),
       io12 (16),
       io13 (17),
       io14 (18),
       io15 (19),
       all           (200),
       notApplicable (255)
   }
      MAX-ACCESS read-only
      STATUS current
      DESCRIPTION
      "The alarm slot. The following attributes apply for the alarm
       code and slot selected.
       all = the attributes apply to all slots.
       notApplicable = the selected alarm is for system level.
       For the Vmux2100 Main Board clA  (3) is used."
      ::= { agnCnfgAlrEntry 2 }

agnCnfgAlrPort OBJECT-TYPE
      SYNTAX Integer32
      MAX-ACCESS read-only
      STATUS current
      DESCRIPTION
      "The alarm port. The following attributes apply for the alarm
       code,slot and port selected.
       200 = all = the attributes apply to all ports of the selected slot.
             When selected Slot is 'all', only 'all' or	'notApplicable' are valid  
             Port selections.
       notApplicable = the selected alarm is for system or card
                       level.
					   =255 for MP
					   =100 for DXC
	   - For MP:
	     - valid cards' ports are: exPrt1(1)..exPrt16(16)
								   inPrt1(101)..inPrt48 (148)
		 - IP Bundles 
	   - For DXC, the port index will include the Slot, as for all DXC 
	     tables: [(IO Slot+10)&n]  ; n=odd  for external ports
		                             n=even for internal ports."
      ::= { agnCnfgAlrEntry 3 }

agnCnfgAlrMask OBJECT-TYPE
      SYNTAX INTEGER
      {
       no         (1),
       noAndSave  (2),
       yes        (3),
       yesAndSave (4)
   }
      MAX-ACCESS read-write
      STATUS current
      DESCRIPTION
      "An attribute defining the desired Mask state of an alarm .
       no - unmask (this command is not saved in agent's common
            database)
       noAndSave -  unmask ; this command is saved in agent's
             common database
       yes - mask  (this command is not saved in agent's
             common database)
       yesAndSave - mask  ; this command is saved in
             agent's common database.
       Commands that are not saved, will be lost upon power-up or
       selected card removal.      "
      ::= { agnCnfgAlrEntry 4 }

agnCnfgAlrInvert OBJECT-TYPE
      SYNTAX INTEGER
      {
       no            (2),
       yes           (3)
   }
      MAX-ACCESS read-write
      STATUS current
      DESCRIPTION
      "An attribute defining the desired Invert state of an alarm .
       no  - not inverted.
       yes - inverted. For MP, it is not applicable for alarms
             that are currently OFF."
      ::= { agnCnfgAlrEntry 5 }

agnCnfgAlrFilter OBJECT-TYPE
      SYNTAX INTEGER
      {
       no            (2),
       yes           (3)
   }
      MAX-ACCESS read-write
      STATUS current
      DESCRIPTION
      "An attribute defining if Filter is desired for the alarm .
       no  - no  filter.
       yes - filter activate.

       This filter is activated within a window of time defined by
       agnCnfgAlrFilterWindow.
       Its purpose is to avoid frequent changes of an alarm between
       ON/OFF states."
      ::= { agnCnfgAlrEntry 6 }

agnCnfgAlrFilterSet OBJECT-TYPE
      SYNTAX Integer32
      MAX-ACCESS read-write
      STATUS current
      DESCRIPTION
      "This is a top threshold causing the alarm that passes it,
       to be declared Set (ON) at the end of the respective
       window of time.
       - For alarms defined by default as state alarms (minor,major)
         this value will be in [%].
       - For alarms defined by default as events, this value will be
         an integer meaning how many times this event should appear
         at least, during the window in order to be considered ON.
       The maximum value will be 255.
       This value should be greater than the one of
       agnCnfgAlrFilterReset.
       Agents that do not support Alarms Filter, will return 0."
      ::= { agnCnfgAlrEntry 7 }

agnCnfgAlrFilterReset OBJECT-TYPE
      SYNTAX Integer32
      MAX-ACCESS read-write
      STATUS current
      DESCRIPTION
      "This is a bottom threshold causing the alarm that does not
       pass it, to be declared Reset (ON) at the end of the
       respective window of time.
       - For alarms defined by default as state alarms (minor,major)
         this value will be in [%].
       - For alarms defined by default as events, this value will be
         an integer meaning how many times this event should appear
         at most, during the window, in order to be considered OFF.
       This value should be less than the one of
       agnCnfgAlrFilterSet.
       Agents that do not support Alarms Filter, will return 0."
      ::= { agnCnfgAlrEntry 8 }


agnCnfgAlrSeverity     OBJECT-TYPE
      SYNTAX INTEGER
      {
       event    (3),
       minor    (4),
       major    (5),
       warning  (6),
       critical (7)
       }
      MAX-ACCESS read-write
      STATUS current
      DESCRIPTION
      "An attribute defining desired severity of an alarm code 
      per slot/port "
      ::= { agnCnfgAlrEntry 9 }


agnCnfgAlrReportTable OBJECT-TYPE
      SYNTAX SEQUENCE OF AgnCnfgAlrReportEntry
      MAX-ACCESS not-accessible
      STATUS  current
      DESCRIPTION
      "This table enables the user to configure the desired Alarm
       Reports according to alarms severity."
       ::= { agnCnfgAlarm 3}

agnCnfgAlrReportEntry OBJECT-TYPE
      SYNTAX AgnCnfgAlrReportEntry
      MAX-ACCESS not-accessible
      STATUS current
	DESCRIPTION  "An entry in table."
	INDEX {agnCnfgAlrReportType}
      ::= { agnCnfgAlrReportTable 1}

AgnCnfgAlrReportEntry ::=
      SEQUENCE {
   agnCnfgAlrReportType        INTEGER,
   agnCnfgAlrStartReportOn     INTEGER,
   agnCnfgAlrStartReportOff    INTEGER
      }

agnCnfgAlrReportType OBJECT-TYPE
      SYNTAX INTEGER
         {
          trap        (1),
          buffer      (2),
          relay       (3),	 --Relay 1 = R1
          alrLedOn    (4),	 --Minor LED
          alrLedBlink (5),	 --Major LED
		  relay2      (6)    --Relay 2 = R2
         }
      MAX-ACCESS read-only
      STATUS current
      DESCRIPTION
      "The alarm report type.
       trap - traps will be sent only for alarms having the
              selected On/Off severity or higher.
       buffer - only alarms having the selected On/Off severity and
                higher, will be reported to the buffer.
       relay -  relay contact will be activated only for alarms
                having the selected On severity or higher.
				For products having 2 relays, this is the R1 Relay.

       alrLedOn/alrLedBlink - user should select a higher severity
                (ReportOn) for alrLedBlink than for alrLedOn
                (Blinking Led means a more severe alarm than steady
                 ON Led).
       alrLedOn - MTCL-1 Alarm Led will be ON only when
                agnSAlrStatusAll equals the selected severity or
                higher, but lower severity than that selected for
                'alrLedBlink'.
				For products having 2 LEDs, this is the Minor LED.
       alrLedBlink - MTCL-1 Alarm Led will Blink only when
                agnSAlrStatusAll equals the selected severity or
                higher.
				For products having 2 LEDs, this is the Major LED.
       relay2 -  relay 2 contact will be activated only for alarms
                having the selected On severity or higher.
				This is the R2 Relay."
      ::= { agnCnfgAlrReportEntry 1 }

agnCnfgAlrStartReportOn OBJECT-TYPE
      SYNTAX INTEGER
         {
          noReport (2),
          event    (3),
          minor    (4),
          major    (5),
          warning  (6),
          critical (7)
         }  
      MAX-ACCESS read-write
      STATUS current
      DESCRIPTION
      "This object specifies the severity from which alarms will 
       be reported. Alarms having this severity or higher, will be
       reported.
       This object specifies the report severity only for alarms
       that turn to ON state.
       noReport - no Report at all (for any severity)."
      ::= { agnCnfgAlrReportEntry 2 }

agnCnfgAlrStartReportOff OBJECT-TYPE
      SYNTAX INTEGER
         {
        notApplicable (1),
        noReport (2),
        event    (3),
        minor    (4),
        major    (5),
        warning  (6),
        critical (7)
         }  
      MAX-ACCESS read-write
      STATUS current
      DESCRIPTION
      "This object specifies the severity from which alarms will 
       be reported. Alarms having this severity or higher, will be
       reported.
       This object specifies the report severity only for alarms
       that turn to OFF state. 
       notApplicable - for 'relay','alrLedOn','alrLedBlink', 'relay2' report 
                       types, in MP.
       noReport - no Report at all (for any severity)."
      ::= { agnCnfgAlrReportEntry 3 }

agnCOffsetCmd OBJECT-TYPE
      SYNTAX INTEGER
      {
       notApplicable (1),
       normal        (2),
       u1            (3)
      }
      MAX-ACCESS read-write
      STATUS current
      DESCRIPTION
      "An object defining special user request.
       notApplicable - is RO value for products that do not support this object.
       normal -  nothing special
       u1 - user 1 - for all Voice cards, the DISPLAYED Tx and Rx Levels
            will have the following Offsets:
            - 2 Wires port: Tx Level: the base value (for 0dBm) = 0
                            Rx Level: the base value (for 0dBm) = -2
            - 4 Wires port: Tx Level: the base value (for 0dBm) = -16
                            Rx Level: the base value (for 0dBm) = 7    
            The MIB and application DB will use the values without Offset."
      ::= { cnfgAgnGen 9 }


--System T1/E1 Ring Table
--
--This table contains all ML ports that participate in a T1/E1 Ring,
--and their ML port pair. 
--The table indexes are Cnfg and the Primary card & port

agnCT1E1RingTable OBJECT-TYPE
      SYNTAX SEQUENCE OF AgnCT1E1RingEntry
      MAX-ACCESS not-accessible
      STATUS current
      DESCRIPTION
      "Configuration of all T1/E1 Ring ML cards and ports.
       The write operation into the table objects is valid only
       for the TmpCnfg.
       A Slot/Port that does not participate in the T1/E1 Ring, 
       will not exist in this table.
       A ML port that exists in this table, cannot exist at the same
       time in the IO Redundancy table (sysCRdnTable)."
      ::= { cnfgAgnGen 10 }

agnCT1E1RingEntry OBJECT-TYPE
      SYNTAX AgnCT1E1RingEntry
      MAX-ACCESS not-accessible
      STATUS current
      DESCRIPTION
	  "An Entry in table agnCT1E1RingTable"
      INDEX { agnCT1E1RingCnfgIdx, agnCT1E1RingPrimeSlot, agnCT1E1RingPrimePort}
      ::= { agnCT1E1RingTable 1}

AgnCT1E1RingEntry ::=
      SEQUENCE {
     agnCT1E1RingCnfgIdx   Integer32,
     agnCT1E1RingPrimeSlot INTEGER,
     agnCT1E1RingPrimePort Integer32,
     agnCT1E1RingSecSlot   INTEGER,
     agnCT1E1RingSecPort   Integer32,
	 agnCT1E1RingRecTime   Integer32,
     agnCT1E1RingRowStatus RowStatus,
	 agnCT1E1RingWTR       Unsigned32,
	 agnCT1E1RingDualFailDetection INTEGER
      }

agnCT1E1RingCnfgIdx OBJECT-TYPE
      SYNTAX  Integer32
      MAX-ACCESS  read-only
      STATUS  current
      DESCRIPTION
      "This object indicates the Idx of the Cnfg(1..255) being 
       accessed ; Idx of 255 relates to the TmpCnfg."
      ::= { agnCT1E1RingEntry 1 }

agnCT1E1RingPrimeSlot OBJECT-TYPE
      SYNTAX  INTEGER 
       {
       io1   (5),
       io2   (6),
       io3   (7),
       io4   (8),
       io5   (9),
       io6  (10),
       io7  (11),
       io8  (12),
       io9  (13),
       io10 (14),
       io11 (15),
       io12 (16),
       notApplicable (255)
       }
      MAX-ACCESS  read-only
      STATUS  current
      DESCRIPTION
      "The slot number of the Primary card of the Ring Pair."      
	  ::= { agnCT1E1RingEntry 2 }

agnCT1E1RingPrimePort OBJECT-TYPE
      SYNTAX  Integer32 
      MAX-ACCESS  read-only
      STATUS  current
      DESCRIPTION
      "The port number in the Primary Card.
	   For external ports, the value will be as that of the port in the
	       card. Example: external-3 -> 3
                          external-4 -> 4
	   For internal ports, the value will be 100 + the port in the
	       card. Example: internal-1 -> 101
                          internal-4 -> 104  "      
      ::= { agnCT1E1RingEntry 3 }

agnCT1E1RingSecSlot OBJECT-TYPE
      SYNTAX  INTEGER 
       {
       io1   (5),
       io2   (6),
       io3   (7),
       io4   (8),
       io5   (9),
       io6  (10),
       io7  (11),
       io8  (12),
       io9  (13),
       io10 (14),
       io11 (15),
       io12 (16),
       notApplicable (255)
       }
      MAX-ACCESS  read-create
      STATUS  current
      DESCRIPTION
      "The slot number of the Secondary card of the Ring Pair."      
	  ::= { agnCT1E1RingEntry 4 }

agnCT1E1RingSecPort OBJECT-TYPE
      SYNTAX  Integer32 
      MAX-ACCESS  read-create
      STATUS  current
      DESCRIPTION
      "The port number in the Secondary Card.
	   For external ports, the value will be as that of the port in the
	       card. Example: external-3 -> 3
                          external-4 -> 4
	   For internal ports, the value will be 100 + the port in the
	       card. Example: internal-1 -> 101
                          internal-4 -> 104  "      
      ::= { agnCT1E1RingEntry 5 }

agnCT1E1RingRecTime OBJECT-TYPE
      SYNTAX  Integer32 
      MAX-ACCESS  read-create
      STATUS  current
      DESCRIPTION
      "T1/E1 Ring Recovery Time (sec).
       Valid Values: 1..99, 65535.
       65535=NA."
      ::= { agnCT1E1RingEntry 6 }

agnCT1E1RingRowStatus  OBJECT-TYPE
      SYNTAX  RowStatus
      MAX-ACCESS   read-create
      STATUS   current
      DESCRIPTION
      "This parameter allows NMS to create/delete entries of this table.
       The only possible supported RowStatus vaules are
       active (1) and destroy (6)."
      ::= { agnCT1E1RingEntry 7 }

agnCT1E1RingWTR OBJECT-TYPE
      SYNTAX  Unsigned32 
      MAX-ACCESS  read-create
      STATUS  current
      DESCRIPTION
      "T1/E1 Ring Wait to Restore (sec).
       Valid Values: 0..999, 65535.
       65535=NA.
       When the value <> 65535, the value of agnCT1E1RingRecTime must be 65535."
      ::= { agnCT1E1RingEntry 8 }

agnCT1E1RingDualFailDetection OBJECT-TYPE
      SYNTAX  INTEGER 
       {
       disable (2),
       enable  (3)
       }
      MAX-ACCESS  read-create
      STATUS  current
      DESCRIPTION
      "T1/E1 Ring - Dual Failure Detection enable/disable."      
	  ::= { agnCT1E1RingEntry 9 }


agnCMainExitPort OBJECT-TYPE
      SYNTAX INTEGER
      {
       notApplicable   (1),
       eth             (2),
       e1T1SerialLink  (3)
      }
      MAX-ACCESS read-write
      STATUS current
      DESCRIPTION
      "An object defining the Main Exit Port for the Data of the device.
       In the Vmux-120 Device the Data can Exit via one of the 2 existing ports:
       1. Ethernet port (2)
       2. A port that can be E1 or T1 or a Serial Link (3)."
      ::= { cnfgAgnGen 11 }

-- 	Backup Configuration Table for Main Link Module
 
agnCBuMlTable OBJECT-TYPE
      SYNTAX SEQUENCE OF AgnCBuMlEntry
      MAX-ACCESS not-accessible
      STATUS current
      DESCRIPTION
      "Configuration for Primary, Secondary and Third Link.
       These are used for Link Backup."
      ::= { cnfgAgnGen 12 }

agnCBuMlEntry OBJECT-TYPE
      SYNTAX AgnCBuMlEntry
      MAX-ACCESS not-accessible
      STATUS current
      DESCRIPTION
	  "An Entry in table agnCBuMlTable"
      INDEX { agnCBuMlCnfgIdx, agnCBuMlRole}
      ::= { agnCBuMlTable 1}

AgnCBuMlEntry ::=
      SEQUENCE {
     agnCBuMlCnfgIdx          Integer32,
     agnCBuMlRole             INTEGER,
     agnCBuMlType             INTEGER,
     agnCBuMlDefaultGateway   IpAddress,
     agnCBuMlSubnetMask       IpAddress,
	 agnCBuMlOamFrequency     Integer32,
	 agnCBuMlOamTimeoutCycles Integer32,
	 agnCBuMlWaitToRestore    Unsigned32,
	 agnCBuMlBfdSessionNum    Unsigned32
	 }

agnCBuMlCnfgIdx OBJECT-TYPE
      SYNTAX  Integer32
      MAX-ACCESS  not-accessible
      STATUS  current
      DESCRIPTION
     "This object indicates the Index of the Configuration database (1..255) being 
       accessed. Index of 255 relates to the Temporary Configuration."
      ::= { agnCBuMlEntry 1 }

agnCBuMlRole OBJECT-TYPE
      SYNTAX  INTEGER 
       {
       primary   (2),
       secondary (3),
       third     (4),
	   fourth    (5)
       }
      MAX-ACCESS  not-accessible
      STATUS  current
      DESCRIPTION
      "The Role of the Link. Primary Link is the Link that should usually work.
      If the Primary Link fails, the data will go through the Secondary Link.
      If both Primary and Secondary Links fail, the data will go through the Third
      Link, provided it is up."      
	  ::= { agnCBuMlEntry 2 }

agnCBuMlType OBJECT-TYPE
      SYNTAX  INTEGER 
       {
       none  (2),
       e1T1a (3),
       e1T1b (4),
	   eth   (5),
	   ethNetUser (6)
       }
      MAX-ACCESS  read-write
      STATUS  current
      DESCRIPTION
      "The Type of the Link.
       For E1/T1 the Link can be Link A - e1T1a or Link B - e1T1b.
       For ETH-NET, eth (5) can be used.
       For ETH-NET/USER ethNetUser (6) can be used."      
	  ::= { agnCBuMlEntry 3 }

agnCBuMlDefaultGateway OBJECT-TYPE
      SYNTAX  IpAddress 
      MAX-ACCESS  read-write
      STATUS  current
      DESCRIPTION
      "Default Gateway's IP Address."    
	  ::= { agnCBuMlEntry 4 }
  
agnCBuMlSubnetMask  OBJECT-TYPE
      SYNTAX  IpAddress 
      MAX-ACCESS  read-write
      STATUS  current
      DESCRIPTION
      "The Link subnet mask."  
	  ::= { agnCBuMlEntry 5 }

agnCBuMlOamFrequency  OBJECT-TYPE
      SYNTAX  Integer32 
      MAX-ACCESS  read-write
      STATUS  current
      DESCRIPTION
      "Time in sec. between 2 OAM packets." 
	  ::= { agnCBuMlEntry 6 }

agnCBuMlOamTimeoutCycles  OBJECT-TYPE
      SYNTAX  Integer32 
      MAX-ACCESS  read-write
      STATUS  current
      DESCRIPTION
      "No. of cycles the Link will send OAM packets without receiving a response
      from the remote Link before switching to the Backup Link."
	  ::= { agnCBuMlEntry 7 }

agnCBuMlWaitToRestore  OBJECT-TYPE
    SYNTAX       Unsigned32 
    MAX-ACCESS   read-write
    STATUS       current
    DESCRIPTION
    "This object defines traffic recovery time (in milliseconds) 
     of the link after its recovery.
     This object is applicable only when Recovery Mode is revertive."
    ::= { agnCBuMlEntry 8 }

agnCBuMlBfdSessionNum  OBJECT-TYPE
    SYNTAX       Unsigned32 
    MAX-ACCESS   read-write
    STATUS       current
    DESCRIPTION
    "This object defines the BFD (Bidirectional Forwarding Detection) session number of the link.
     When no session exists or when N/A, the value will be 0."
    ::= { agnCBuMlEntry 9 }


agnCQ50Table OBJECT-TYPE
      SYNTAX SEQUENCE OF AgnCQ50Entry
      MAX-ACCESS not-accessible
      STATUS current
      DESCRIPTION
      "Table for the device Q50 parameters.
       Q50 is a Signaling protocol used between PBX devices.
       It is possible to control the initiation of calls using Q.50.
       This is useful for devices when there is a congestion."
      ::= { cnfgAgnGen 13 }

agnCQ50Entry OBJECT-TYPE
      SYNTAX AgnCQ50Entry
      MAX-ACCESS not-accessible
      STATUS current
      DESCRIPTION
	  "An Entry in table agnCQ50Table"
      INDEX { agnCQ50CnfgIdx}
      ::= { agnCQ50Table 1}

AgnCQ50Entry ::=
      SEQUENCE {
     agnCQ50CnfgIdx          				Integer32,
     agnCQ50StopCallsThresh  				Integer32,
     agnCQ50DiscardPktThresh 				Integer32,
	 agnCQ50BlockNewModemVbdCallsThresh		Integer32,
	 agnCQ50BlockNewModemRelayCallsThresh	Integer32
 	 }

agnCQ50CnfgIdx OBJECT-TYPE
      SYNTAX  Integer32
      MAX-ACCESS  not-accessible
      STATUS  current
      DESCRIPTION
      "This object indicates the Index of the Configuration database (1..255) being 
       accessed. Index of 255 relates to the Temporary Configuration."
      ::= { agnCQ50Entry 1 }

 agnCQ50StopCallsThresh OBJECT-TYPE
      SYNTAX  Integer32
      MAX-ACCESS  read-write
      STATUS  current
      DESCRIPTION
      "This object indicates the Bandwidth Threshold percent (%) above which
       new Calls from the PBX will be disabled."
      ::= { agnCQ50Entry 2 }

agnCQ50DiscardPktThresh OBJECT-TYPE
      SYNTAX  Integer32
      MAX-ACCESS  read-write
      STATUS  current
      DESCRIPTION
      "This object indicates the Bandwidth Threshold percent (%) above which
       voice packets will be discarded. Usually, the value selected should be higher
       than the value of agnCQ50StopCallsThresh."
      ::= { agnCQ50Entry 3 }

agnCQ50BlockNewModemVbdCallsThresh OBJECT-TYPE
      SYNTAX  Integer32
      MAX-ACCESS  read-write
      STATUS  current
      DESCRIPTION
      "This object indicates the Modem VBD Calls Threshold percent (%) above which
       new modem calls will be rejected."
      ::= { agnCQ50Entry 4 }

agnCQ50BlockNewModemRelayCallsThresh OBJECT-TYPE
      SYNTAX  Integer32
      MAX-ACCESS  read-write
      STATUS  current
      DESCRIPTION
      "This object indicates the Modem Relay Calls Threshold percent (%) above which
       new modem calls will be rejected."
      ::= { agnCQ50Entry 5 }


--
-- Compressed information.
--
-- Specially for RadView management station
--
agnCmprTable  OBJECT-TYPE
      SYNTAX SEQUENCE OF AgnCmprEntry
      MAX-ACCESS not-accessible
      STATUS current
	DESCRIPTION  "A table."
	::=  { cmprAgnGen 1 }

agnCmprEntry OBJECT-TYPE
      SYNTAX AgnCmprEntry
      MAX-ACCESS not-accessible
      STATUS current
	DESCRIPTION  "An entry in table."
	INDEX { agnCmprTypIdx, agnCmprCnfgIdx ,agnCmprVersion}
      ::= {agnCmprTable  1}

AgnCmprEntry ::=
      SEQUENCE {
     agnCmprTypIdx      Integer32,
     agnCmprCnfgIdx     Integer32,
     agnCmprVersion     Integer32,
     agnCmprObj         OCTET STRING
      }

agnCmprTypIdx OBJECT-TYPE
      SYNTAX  Integer32
      MAX-ACCESS  read-only
      STATUS  current
      DESCRIPTION
      "This attribute indicates the Type of the Compressed being
       referred."
      ::= { agnCmprEntry 1}

agnCmprCnfgIdx OBJECT-TYPE
      SYNTAX  Integer32
      MAX-ACCESS  read-only
      STATUS  current
      DESCRIPTION
      "This attribute indicates the configuration to which the
       Compressed information is  related."
      ::= { agnCmprEntry 2}

agnCmprVersion OBJECT-TYPE
      SYNTAX  Integer32
      MAX-ACCESS  read-only
      STATUS  current
      DESCRIPTION
      "This attribute indicates the version of the internal format
       of the Compressed data"
      ::= { agnCmprEntry 3}

agnCmprObj OBJECT-TYPE
      SYNTAX  OCTET STRING
      MAX-ACCESS  read-write
      STATUS  current
      DESCRIPTION
      "This attribute is the compressed information itself."
      ::= { agnCmprEntry 4}


-- Compressed Dlci table in the Agent level
-- The only way of reading this table is by the command 'GET NEXT'

agnDlciCmprTable  OBJECT-TYPE
      SYNTAX SEQUENCE OF AgnDlciCmprEntry
      MAX-ACCESS not-accessible
      STATUS current
	DESCRIPTION  "A table."
	::=  {cmprAgnGen 2}

agnDlciCmprEntry OBJECT-TYPE
      SYNTAX AgnDlciCmprEntry
      MAX-ACCESS not-accessible
      STATUS current
	DESCRIPTION  "An entry in table."
	INDEX {agnDlciCmprCnfgIdx,agnDlciCmprVersion,agnDlciCmprDlciIdx}
      ::= {agnDlciCmprTable  1}

AgnDlciCmprEntry ::=
      SEQUENCE {
     agnDlciCmprCnfgIdx       Integer32,
     agnDlciCmprVersion       Integer32,
     agnDlciCmprDlciIdx       Integer32,
     agnDlciCmprObj          OCTET STRING
      }

agnDlciCmprCnfgIdx OBJECT-TYPE
      SYNTAX  Integer32
      MAX-ACCESS  read-only
      STATUS  current
      DESCRIPTION
      "This attribute indicates the configuration to which the
       Compressed information is  related."
      ::= { agnDlciCmprEntry 1}

agnDlciCmprVersion OBJECT-TYPE
      SYNTAX  Integer32
      MAX-ACCESS  read-only
      STATUS  current
      DESCRIPTION
      "This attribute indicates the version of the internal format
       of the Compressed data"
      ::= { agnDlciCmprEntry 2}

agnDlciCmprDlciIdx  OBJECT-TYPE
      SYNTAX  Integer32
      MAX-ACCESS  read-only
      STATUS  current
      DESCRIPTION
      "This attribute indicates a unique identifier of  the Dlci,
       the compressed information relates to.
       The values are between 16 - 991."
      ::= { agnDlciCmprEntry 3}

agnDlciCmprObj OBJECT-TYPE
      SYNTAX  OCTET STRING
      MAX-ACCESS  read-write
      STATUS  current
      DESCRIPTION
      "This attribute is the compressed information itself."
      ::= { agnDlciCmprEntry 4}

-- Compressed Status Alarm table at the Agent level
-- The only way of reading this table is by the command 'GET NEXT'

agnAlarmsCmprTable  OBJECT-TYPE
      SYNTAX SEQUENCE OF AgnAlarmsCmprEntry
      MAX-ACCESS not-accessible
      STATUS current
	DESCRIPTION  "A table."
	::=  {cmprAgnGen 3}

agnAlarmsCmprEntry OBJECT-TYPE
      SYNTAX AgnAlarmsCmprEntry
      MAX-ACCESS not-accessible
      STATUS current
	DESCRIPTION  "An entry in table."
	INDEX {agnAlarmsCmprVersion,agnAlarmsCmprAlarmIdx}
      ::= {agnAlarmsCmprTable  1}

AgnAlarmsCmprEntry ::=
      SEQUENCE {
     agnAlarmsCmprVersion      Integer32,
     agnAlarmsCmprAlarmIdx     Integer32,
     agnAlarmsCmprObj          OCTET STRING
      }

agnAlarmsCmprVersion OBJECT-TYPE
      SYNTAX  Integer32
      MAX-ACCESS  read-only
      STATUS  current
      DESCRIPTION
      "This attribute indicates the version of the internal
       format of the Compressed data"
      ::= { agnAlarmsCmprEntry 1}

agnAlarmsCmprAlarmIdx  OBJECT-TYPE
      SYNTAX  Integer32
      MAX-ACCESS  read-only
      STATUS  current
      DESCRIPTION
      "A unique number to identify an entry in the alarm status table
       of the agent."
      ::= { agnAlarmsCmprEntry 2}

agnAlarmsCmprObj OBJECT-TYPE
      SYNTAX  OCTET STRING
      MAX-ACCESS  read-only
      STATUS  current
      DESCRIPTION
      "This attribute is the compressed information itself."
      ::= { agnAlarmsCmprEntry 3}

-- Compressed History Alarms buffer
-- The only way of reading this table is by the command 'GET NEXT'

agnAlrBufCmprTable  OBJECT-TYPE
      SYNTAX SEQUENCE OF AgnAlrBufCmprEntry
      MAX-ACCESS not-accessible
      STATUS current
	DESCRIPTION  "A table."
	::=  {cmprAgnGen 4}

agnAlrBufCmprEntry OBJECT-TYPE
      SYNTAX AgnAlrBufCmprEntry
      MAX-ACCESS not-accessible
      STATUS current
	DESCRIPTION  "An entry in table."
	INDEX {agnAlrBufCmprVersion,agnAlrBufCmprAlarmIdx}
      ::= {agnAlrBufCmprTable  1}

AgnAlrBufCmprEntry ::=
      SEQUENCE {
     agnAlrBufCmprVersion      Integer32,
     agnAlrBufCmprAlarmIdx     Integer32,
     agnAlrBufCmprObj          OCTET STRING
      }

agnAlrBufCmprVersion OBJECT-TYPE
      SYNTAX  Integer32
      MAX-ACCESS  read-only
      STATUS  current
      DESCRIPTION
      "This attribute indicates the version of the internal format of
       the Compressed data"
      ::= { agnAlrBufCmprEntry 1}

agnAlrBufCmprAlarmIdx  OBJECT-TYPE
      SYNTAX  Integer32
      MAX-ACCESS  read-only
      STATUS  current
      DESCRIPTION
      "A unique number to identify an entry in the history alarms
       buffer of the agent."
      ::= { agnAlrBufCmprEntry 2}

agnAlrBufCmprObj OBJECT-TYPE
      SYNTAX  OCTET STRING
      MAX-ACCESS  read-only
      STATUS  current
      DESCRIPTION
      "This attribute is the compressed information itself."
      ::= { agnAlrBufCmprEntry 3}


-- Compressed Sanity Errors buffer
-- The only way of reading this table is by the command 'GET NEXT'


agnSCmprErrListTable OBJECT-TYPE
      SYNTAX SEQUENCE OF AgnSCmprErrListEntry
      MAX-ACCESS not-accessible
      STATUS current
	DESCRIPTION  "A table."
	::=  { cmprAgnGen 5 }

agnSCmprErrListEntry OBJECT-TYPE
      SYNTAX AgnSCmprErrListEntry
      MAX-ACCESS not-accessible
      STATUS current
	DESCRIPTION  "An entry in table."
	INDEX {agnSCmprErrVersion,agnSCmprErrIdx}
      ::= { agnSCmprErrListTable 1}

AgnSCmprErrListEntry ::=
      SEQUENCE {
     agnSCmprErrVersion      Integer32,
     agnSCmprErrIdx          Integer32,
     agnSCmprErrObj          OCTET STRING
      }

agnSCmprErrVersion OBJECT-TYPE
      SYNTAX  Integer32
      MAX-ACCESS  read-only
      STATUS  current
      DESCRIPTION
      "The version of the compressed data "
       ::= { agnSCmprErrListEntry 1}

agnSCmprErrIdx OBJECT-TYPE
      SYNTAX  Integer32
      MAX-ACCESS  read-only
      STATUS  current
      DESCRIPTION
      "Unique number to identify an entry in the errors list table.
       The maximum entry  value  cannot exceed the value of
       'agnSNoOfSanityCheckErr'. "
       ::= { agnSCmprErrListEntry 2}

agnSCmprErrObj OBJECT-TYPE
      SYNTAX  OCTET STRING
      MAX-ACCESS  read-only
      STATUS  current
      DESCRIPTION
      "This attribute is a full text description of the error,
       including: error code, slot and port numbers related to the
       code ."
     ::= { agnSCmprErrListEntry 3}


-- New TS Assignment compressed table, per port 01/09/98
-- The only way of reading this table is by the command 'GET NEXT'

agnTsCmprTable  OBJECT-TYPE
      SYNTAX SEQUENCE OF AgnTsCmprEntry
      MAX-ACCESS not-accessible
      STATUS current
	DESCRIPTION  "A table."
	::=  { cmprAgnGen 6 }

agnTsCmprEntry OBJECT-TYPE
      SYNTAX AgnTsCmprEntry
      MAX-ACCESS not-accessible
      STATUS current
	DESCRIPTION  "An entry in table."
	INDEX { agnTsCmprVerIdx,  agnTsCmprCnfgIdx , agnTsCmprSlotIdx,
              agnTsCmprPortIdx, agnTsCmprPduIdx }
      ::= {agnTsCmprTable  1}

AgnTsCmprEntry ::=
      SEQUENCE {
     agnTsCmprVerIdx      Integer32,
     agnTsCmprCnfgIdx     Integer32,
     agnTsCmprSlotIdx     Integer32,
     agnTsCmprPortIdx     Integer32,
     agnTsCmprPduIdx      Integer32,
     agnTsCmprData        OCTET STRING
      }

agnTsCmprVerIdx OBJECT-TYPE
      SYNTAX  Integer32
      MAX-ACCESS  read-only
      STATUS  current
      DESCRIPTION
      "This object indicates the version of the internal format
       of the Compressed data."
      ::= { agnTsCmprEntry 1}

agnTsCmprCnfgIdx OBJECT-TYPE
      SYNTAX  Integer32
      MAX-ACCESS  read-only
      STATUS  current
      DESCRIPTION
      "This object indicates the configuration to which the
       Compressed information is related.
       255=temporary configuration.
       Set can be performed only to the temporary configuration."
      ::= { agnTsCmprEntry 2}

agnTsCmprSlotIdx OBJECT-TYPE
      SYNTAX  Integer32
      MAX-ACCESS  read-only
      STATUS  current
      DESCRIPTION
      "This object indicates the Slot to which the
       Compressed information is  related.
       For MP-2100: IO-1..IO-12 = (5).. (16)
       For DXC-30 : IO-1..IO-15 = (5).. (19).
       NA=255."
      ::= { agnTsCmprEntry 3}

agnTsCmprPortIdx OBJECT-TYPE
      SYNTAX  Integer32
      MAX-ACCESS  read-only
      STATUS  current
      DESCRIPTION
      "This object indicates the Port within the Slot, to which the
       Compressed information is  related.
       For Port Index see each product's spec."
      ::= { agnTsCmprEntry 4}

agnTsCmprPduIdx OBJECT-TYPE
      SYNTAX  Integer32
      MAX-ACCESS  read-only
      STATUS  current
      DESCRIPTION
      "This object indicates the PDU index within the same port.
       That provides for the case when one PDU is not sufficient for all TS
       Assignment data of the same port."
      ::= { agnTsCmprEntry 5}

agnTsCmprData OBJECT-TYPE
      SYNTAX  OCTET STRING
      MAX-ACCESS  read-write
      STATUS  current
      DESCRIPTION
      "This object is the compressed information itself. It provides
       information about all TSs of a port."
      ::= { agnTsCmprEntry 6}

-- Extended Compress General Table with 7 indexes -  10/02/99
-- Used for: V5.1 and V5.2 Variant 

agnXCmprTable  OBJECT-TYPE
      SYNTAX SEQUENCE OF AgnXCmprEntry
      MAX-ACCESS not-accessible
      STATUS current
	DESCRIPTION  "A table."
	::=  { cmprAgnGen 7 }

agnXCmprEntry OBJECT-TYPE
      SYNTAX AgnXCmprEntry
      MAX-ACCESS not-accessible
      STATUS current
	DESCRIPTION  "An entry in table."
	INDEX {agnXCmprTypIdx, agnXCmprVersion, agnXCmprIdx3,agnXCmprIdx4,
             agnXCmprIdx5, agnXCmprIdx6, agnXCmprIdx7}
      ::= {agnXCmprTable  1}

AgnXCmprEntry ::=
      SEQUENCE {
     agnXCmprTypIdx       Integer32,
     agnXCmprVersion      Integer32,
     agnXCmprIdx3         Integer32,
     agnXCmprIdx4         Integer32,
     agnXCmprIdx5         Integer32,
     agnXCmprIdx6         Integer32,
     agnXCmprIdx7         Integer32,
     agnXCmprObj          OCTET STRING
      }

agnXCmprTypIdx OBJECT-TYPE
      SYNTAX  Integer32
      MAX-ACCESS  read-only
      STATUS  current
      DESCRIPTION
      "This attribute indicates the Type of the Compressed being
       referred. 
       One of the types is V5.1 Variant data."
      ::= { agnXCmprEntry 1}

agnXCmprVersion OBJECT-TYPE
      SYNTAX  Integer32
      MAX-ACCESS  read-only
      STATUS  current
      DESCRIPTION
      "This attribute indicates the version of the internal format of
       the Compressed data."
      ::= { agnXCmprEntry 2}

agnXCmprIdx3 OBJECT-TYPE
      SYNTAX  Integer32
      MAX-ACCESS  read-only
      STATUS  current
      DESCRIPTION
      "3rd index - can be used for any purpose according to the 
       agnXCmprTypIdx.
       Example: for V5.1 Variant, this attribute indicates the configuration
       to which the Compressed information is  related.
       255=temporary configuration.
       Set can be performed only to the temporary configuration."
      ::= { agnXCmprEntry 3}

agnXCmprIdx4  OBJECT-TYPE
      SYNTAX  Integer32
      MAX-ACCESS  read-only
      STATUS  current
      DESCRIPTION
      "4th index - can be used for any purpose according to the 
       agnXCmprTypIdx.
       Example: for V5.1 Variant,this attribute indicates a unique number of 
       the slot position where the card is inserted.
	   Valid values: psA(1),psB(2),clA(3),clB(4),io1(5)..io12(16); notApplicable=255."
      ::= { agnXCmprEntry 4}

agnXCmprIdx5   OBJECT-TYPE
      SYNTAX  Integer32
      MAX-ACCESS  read-only
      STATUS  current
      DESCRIPTION
      "5th index - can be used for any purpose according to the 
       agnXCmprTypIdx.
       Example: for V5.1 Variant,this attribute indicates a unique identifier 
       of  the port	the compressed information relates to.
       Valid values: exPrt1    (1) .. exPrt12  (12) ,
                     inPrt1  (101) .. inPrt48 (148)."
      ::= { agnXCmprEntry 5}

agnXCmprIdx6  OBJECT-TYPE
      SYNTAX  Integer32
      MAX-ACCESS  read-only
      STATUS  current
      DESCRIPTION
      "6th index - can be used for any purpose according to the 
       agnXCmprTypIdx.
       Example: for V5.1 Variant,this attribute indicates the Variant index. 
       Valid values are: 0..127, 255 (= temp cnfg).Set can be performed only 
       to the temporary configuration."
      ::= { agnXCmprEntry 6}

agnXCmprIdx7  OBJECT-TYPE
      SYNTAX  Integer32
      MAX-ACCESS  read-only
      STATUS  current
      DESCRIPTION
      "7th index - can be used for any purpose according to the 
       agnXCmprTypIdx.
       Example: for V5.1 Variant,this attribute is not needed. Therefore, its 
       value will be always 255=notApplicable."
      ::= { agnXCmprEntry 7}

agnXCmprObj OBJECT-TYPE
      SYNTAX  OCTET STRING
      MAX-ACCESS  read-write
      STATUS  current
      DESCRIPTION
      "This attribute is the compressed information itself."
      ::= { agnXCmprEntry 8}

--
-- Link Mapping Table for internal use
--
agnLinkMapTable OBJECT-TYPE
      SYNTAX SEQUENCE OF AgnLinkMapEntry
      MAX-ACCESS not-accessible
      STATUS current
	DESCRIPTION  "A table."
	::=  { mapWanGen 1}

agnLinkMapEntry OBJECT-TYPE
      SYNTAX AgnLinkMapEntry
      MAX-ACCESS not-accessible
      STATUS current
	DESCRIPTION  "An entry in table."
	INDEX {mapLinkId}
      ::= {agnLinkMapTable 1}

AgnLinkMapEntry ::=
      SEQUENCE {
      mapLinkId               Integer32,
      mapLinkSltIdx           INTEGER,
      mapLinkPrtIdx           INTEGER,
      mapLinkStatus           INTEGER
      }

mapLinkId     OBJECT-TYPE
      SYNTAX  Integer32
      MAX-ACCESS  read-only
      STATUS  current
      DESCRIPTION
      "A unique identifier of the link"
::=  {agnLinkMapEntry 1}

mapLinkSltIdx    OBJECT-TYPE
      SYNTAX  INTEGER
        {
          noConnect   (2),
       clA   (3),
       io1   (5),
       io2   (6),
       io3   (7),
       io4   (8),
       io5   (9),
       io6  (10),
       io7  (11),
       io8  (12),
       io9  (13),
       io10 (14),
       io11 (15),
       io12 (16),
    notApplicable (255)
     }
      MAX-ACCESS  read-write
      STATUS  current
      DESCRIPTION
      "This attribute indicates a unique  slot  position where
       the card is inserted.
       In the ?004 Unit the entries clA(3), io6(10)..io12(16) are
       not valid."
::=  {agnLinkMapEntry 2}

mapLinkPrtIdx  OBJECT-TYPE
      SYNTAX  INTEGER
      {
         exPrt1    (1) ,
         exPrt2    (2) ,
         exPrt3    (3) ,
         exPrt4    (4) ,
         exPrt5    (5) ,
         exPrt6    (6) ,
         exPrt7    (7) ,
         exPrt8    (8) ,
         exPrt9    (9) ,
         exPrt10  (10) ,
         exPrt11  (11) ,
         exPrt12  (12) ,
         noConnect  (100) ,
         inPrt1  (101) ,
         inPrt2  (102) ,
         inPrt3  (103) ,
         inPrt4  (104) ,
         inPrt5  (105) ,
         inPrt6  (106) ,
         inPrt7  (107) ,
         inPrt8  (108) ,
         inPrt9  (109) ,
         inPrt10 (110) ,
         inPrt11 (111) ,
         inPrt12 (112)
      }
      MAX-ACCESS  read-write
      STATUS  current
      DESCRIPTION
      "This attribute indicates a unique  port number. "
::=  {agnLinkMapEntry 3}

mapLinkStatus   OBJECT-TYPE
      SYNTAX  INTEGER
 {
 unknown(1),
 down(2),
 up(3)
 }
      MAX-ACCESS  read-only
      STATUS  current
      DESCRIPTION
      "This attribute indicates the status of the link between the
       two muxes"
::=  {agnLinkMapEntry 4}


--
-- diverseIfWanGen - diverse NON-DS1 interfaces of WAN products
--



--sonetInterface  OBJECT IDENTIFIER  ::=  {diverseIfWanGen 2}     (see radsonet.txt)
--ds3Interface    OBJECT IDENTIFIER  ::=  {diverseIfWanGen 3}	  (see radds3.txt)
--ds1Interface    OBJECT IDENTIFIER  ::=  {diverseIfWanGen 4}	  (see radds1.txt)
--hdlcMibObjects  OBJECT IDENTIFIER  ::=  {diverseIfWanGen 5}     (see radhdlc.txt)
--ip2If           OBJECT IDENTIFIER ::= { diverseIfWanGen 7 }	  (see ipmux.txt)


--
-- Wan alarm buffer (history) information
--
alrBufTable  OBJECT-TYPE
      SYNTAX SEQUENCE OF AlrBufEntry
      MAX-ACCESS not-accessible
      STATUS current
	DESCRIPTION  "A table."
	::=  { alrBuffGen 1 }

alrBufEntry OBJECT-TYPE
      SYNTAX AlrBufEntry
      MAX-ACCESS not-accessible
      STATUS current
	DESCRIPTION  "An entry in table."
	INDEX { alrBufIdx }
      ::= { alrBufTable 1}

AlrBufEntry ::=
      SEQUENCE {
     alrBufIdx          Integer32,
     alrBufDescription  DisplayString,
     alrBufCode         Unsigned32,
     alrBufSlot 		INTEGER,
	 alrBufPort         Unsigned32,
	 alrBufSeverity     INTEGER,
	 alrBufState        INTEGER
      }

alrBufIdx OBJECT-TYPE
      SYNTAX  Integer32
      MAX-ACCESS  read-only
      STATUS  current
      DESCRIPTION
      "This attribute indicates a  unique number to identify this
       entry"
    ::= { alrBufEntry 1}

alrBufDescription  OBJECT-TYPE
      SYNTAX  DisplayString (SIZE (0..255))
      MAX-ACCESS  read-only
      STATUS  current
      DESCRIPTION
      "This entry is a unique text description of the alarm in the
       buffer.
       The alarm description includes the following information:
       alarm code, slot id, card type, channel id ,
       alarm text, alarm status, masked flag and event counter"
       ::= { alrBufEntry 2}

alrBufCode OBJECT-TYPE
      SYNTAX  Unsigned32
      MAX-ACCESS  read-only
      STATUS  current
      DESCRIPTION
      "A code identifying the alarm of an entry in the alarm buffer
       table."
      ::= { alrBufEntry 3 }

alrBufSlot OBJECT-TYPE
      SYNTAX  INTEGER 
       {
       psA   (1),
       psB   (2),
       clA   (3),
       clB   (4),
       io1   (5),
       io2   (6),
       io3   (7),
       io4   (8),
       io5   (9),
       io6  (10),
       io7  (11),
       io8  (12),
       io9  (13),
       io10 (14),
       notApplicable (255)
       }
      MAX-ACCESS  read-only
      STATUS  current
      DESCRIPTION
      "The slot number this alarm refers to.
       When the alarm refers to a system alarm, the value will be 'notApplicable(255)'."      
      ::= { alrBufEntry 4 }

alrBufPort OBJECT-TYPE
      SYNTAX  Unsigned32 
      MAX-ACCESS  read-only
      STATUS  current
      DESCRIPTION
      "The port number this alarm refers to.
       If the port number is irrelevant to this alarm (if it is
       a system/card level alarm) the value will be 9999."     
      ::= { alrBufEntry 5 }

alrBufSeverity OBJECT-TYPE
      SYNTAX  INTEGER
       {
       event    (3),
       minor    (4),
       major    (5),
       warning  (6),
       critical (7)
       }
      MAX-ACCESS  read-only
      STATUS  current
      DESCRIPTION
      "The severity of the alarm."
      ::= { alrBufEntry 6 }

alrBufState  OBJECT-TYPE
      SYNTAX  INTEGER
       {
       off(2),
       on (3)
       }
      MAX-ACCESS  read-only
      STATUS  current
      DESCRIPTION
      "State of the alarm (On/Off)."
      ::= { alrBufEntry 7 }


alrBufferClearCmd OBJECT-TYPE
      SYNTAX  INTEGER
       {
      off(2),
      on (3)
       }
      MAX-ACCESS  read-write
      STATUS  current
      DESCRIPTION
      "Setting this attribute to ON, will enforce a  clear 
       operation on the Alarms Buffer. Upon completion, 
       the value will automatically change to off(2).
       For MP-2100/2200, this command will not really erase
       the Alarm Buffer, but is only an ACK of seeing the Buffer.
       It marks a pointer of the last entry's alrBufIdx, in order 
       to allow view of new alarms entered after this pointer
       (alrBufIdxUponLastAck)."
      ::= { alrBuffGen 2 }

alrBufIdxUponLastAck OBJECT-TYPE
      SYNTAX  Unsigned32
      MAX-ACCESS  read-only
      STATUS  current
      DESCRIPTION
      "This attribute indicates the value of alrBufIdx for the 
       last existing entry of alrBufTable, when alrBufferClearCmd
       was last Set to on(3).
       That will enable a user to see only Alarms that entered the 
       alrBufTable after last Set of alrBufferClearCmd, by GetNext 
       of alrBufDescription	with this index."
      ::= { alrBuffGen 3 }

--
-- Wan Flip Data-Base parameters
--
--         agnCAgendaTable :
--

agnCAgendaTable OBJECT-TYPE
      SYNTAX SEQUENCE OF AgnCAgendaEntry
      MAX-ACCESS not-accessible
      STATUS  current
      DESCRIPTION
      "This table devides the week days into categories needed for
       DB flip consideration."
      ::= {agnFlipDb 1}

agnCAgendaEntry OBJECT-TYPE
      SYNTAX AgnCAgendaEntry
      MAX-ACCESS not-accessible
      STATUS current
	DESCRIPTION  "An entry in table."
	INDEX {agnCAgendaCnfgIdx, agnCAgendaDayIdx}
      ::= {agnCAgendaTable 1}

AgnCAgendaEntry ::=
      SEQUENCE {
           agnCAgendaCnfgIdx    INTEGER,
           agnCAgendaDayIdx           INTEGER,
           agnCAgendaDayCategory      INTEGER
               }

agnCAgendaCnfgIdx OBJECT-TYPE
      SYNTAX  INTEGER
              {
                active    (1),
                temporary  (255)
              }
      MAX-ACCESS  read-only
      STATUS  current
      DESCRIPTION
      "Active or Temporary Agenda Table.
       Both configurations can be read but only the Temporary can
       be written to."
      ::= {agnCAgendaEntry 1}

agnCAgendaDayIdx OBJECT-TYPE
      SYNTAX  INTEGER
              {
                sunday    (1),
                monday    (2),
                tuesday   (3),
                wednesday (4),
                thursday  (5),
                friday    (6),
                saturday  (7)
              }
      MAX-ACCESS  read-only
      STATUS  current
      DESCRIPTION
      "Day of week"
      ::= {agnCAgendaEntry 2}

agnCAgendaDayCategory OBJECT-TYPE
      SYNTAX  INTEGER
              {
                fullWorkday    (1),
                partialWorkday (2),
                weekend        (3)
              }
      MAX-ACCESS  read-write
      STATUS  current
      DESCRIPTION
      "The Category of the Day "
      ::= {agnCAgendaEntry 3}


--          agnCFlipNetEventsTable :
--

agnCFlipNetEventsTable OBJECT-TYPE
      SYNTAX SEQUENCE OF AgnCFlipNetEventsEntry
      MAX-ACCESS not-accessible
      STATUS  current
      DESCRIPTION
      "This table holds the Net Events the MUX should trace"
      ::= {agnFlipDb 2}

agnCFlipNetEventsEntry OBJECT-TYPE
      SYNTAX AgnCFlipNetEventsEntry
      MAX-ACCESS not-accessible
      STATUS current
	DESCRIPTION  "An entry in table."
	INDEX {agnCFlipNetEventsCnfgIdx, agnCFlipNetEventIdx}
      ::= {agnCFlipNetEventsTable 1}

AgnCFlipNetEventsEntry ::=
      SEQUENCE {
    agnCFlipNetEventsCnfgIdx   INTEGER,
                agnCFlipNetEventIdx        Integer32,
                agnCFlipNetEventActive     INTEGER,
                agnCFlipNetEventType       INTEGER,
                agnCFlipNetEventNo         Integer32,
                agnCFlipNetEventSlot       INTEGER,
                agnCFlipNetEventPort       Integer32,
                agnCFlipNetEventISD        Integer32,
                agnCFlipNetEventOSD        Integer32,
                agnCFlipNetEventDayType    INTEGER,
                agnCFlipNetEventStartTime  DisplayString,
                agnCFlipNetEventEndTime    DisplayString
               }

agnCFlipNetEventsCnfgIdx OBJECT-TYPE
      SYNTAX  INTEGER
              {
                active    (1),
                temporary  (255)
              }
      MAX-ACCESS  read-only
      STATUS  current
      DESCRIPTION
      "Active or Temporary Net Events Table.
       Both configurations can be read but only the Temporary can
       be written to."
      ::= {agnCFlipNetEventsEntry 1}

agnCFlipNetEventIdx OBJECT-TYPE
      SYNTAX  Integer32  (1..10)
      MAX-ACCESS  read-only
      STATUS  current
      DESCRIPTION
      "Entry within the table"
      ::= {agnCFlipNetEventsEntry 2}

agnCFlipNetEventActive     OBJECT-TYPE
      SYNTAX  INTEGER
              {
                no  (2),
                yes (3)
              }
      MAX-ACCESS  read-write
      STATUS  current
      DESCRIPTION
      "Indicates if the entry is valid.
       In order to Add/Modify parameters of an entry, this object
       should be set to Yes.
       In order to delete an entry, this object should be Set to No."
      ::= {agnCFlipNetEventsEntry 3}


agnCFlipNetEventType OBJECT-TYPE
      SYNTAX  INTEGER
              {
                time       (1),
                linkDown   (2),
                congestion (3)   -- MP3000 Only
              }
      MAX-ACCESS  read-write
      STATUS  current
      DESCRIPTION
      "The Net Event type "
      ::= {agnCFlipNetEventsEntry 4}

agnCFlipNetEventNo OBJECT-TYPE
      SYNTAX  Integer32  (1..512)
      MAX-ACCESS  read-write
      STATUS  current
      DESCRIPTION
      "The Net Event No. (Bit Index)"
      ::= {agnCFlipNetEventsEntry 5}

agnCFlipNetEventSlot OBJECT-TYPE
      SYNTAX  INTEGER
              {
                notApplicable   (1),
                clA   (3),
                clB   (4),
                io1   (5),
                io2   (6),
                io3   (7),
                io4   (8),
                io5   (9),
                io6  (10),
                io7  (11),
                io8  (12),
                io9  (13),
                io10 (14),
                io11 (15),
                io12 (16)
              }
      MAX-ACCESS  read-write
      STATUS  current
      DESCRIPTION
      "The slot to which the net event relates .
       Not applicable for time event"
      ::= {agnCFlipNetEventsEntry 6}

agnCFlipNetEventPort OBJECT-TYPE
      SYNTAX  Integer32
      MAX-ACCESS  read-write
      STATUS  current
      DESCRIPTION
      "The port within the relevant slot.
	   Valid values:
	   - extPrt1(1)..exPrt16(16) 
	   - notApplicable(100)
	   - inPrt1(101)..inPrt84(184)"
      ::= {agnCFlipNetEventsEntry 7}

agnCFlipNetEventISD OBJECT-TYPE
      SYNTAX  Integer32  (1..999)
      MAX-ACCESS  read-write
      STATUS  current
      DESCRIPTION
      "The time in seconds since the Net Event was reported as ON
       until it is considered as ON.
       Not relevant for time events."
      ::= {agnCFlipNetEventsEntry 8}

agnCFlipNetEventOSD OBJECT-TYPE
      SYNTAX  Integer32  (1..999)
      MAX-ACCESS  read-write
      STATUS  current
      DESCRIPTION
      "The time in seconds since the net event was reported as OFF
       until it is considered as OFF.
       Not relevant for time events."
      ::= {agnCFlipNetEventsEntry 9}

agnCFlipNetEventDayType OBJECT-TYPE
      SYNTAX  INTEGER
              {
                notApplicable  (1),
                fullWorkday    (2),
                partialWorkday (3),
    weekend        (4)
              }
      MAX-ACCESS  read-write
      STATUS  current
      DESCRIPTION
      "The time event relates to all days defined in this category in
       the agnCAgendaTable.
       Applicable only for time event"
      ::= {agnCFlipNetEventsEntry 10}

agnCFlipNetEventStartTime    OBJECT-TYPE
      SYNTAX    DisplayString (SIZE (5))
      MAX-ACCESS  read-write
      STATUS  current
      DESCRIPTION
      "The time event will be activated at this time.
       The format is hh:mm."
      ::= {agnCFlipNetEventsEntry 11}

agnCFlipNetEventEndTime     OBJECT-TYPE
      SYNTAX    DisplayString (SIZE (5))
      MAX-ACCESS  read-write
      STATUS  current
      DESCRIPTION
      "The time event will be deactivated at this time.
       The format is hh:mm."
      ::= {agnCFlipNetEventsEntry 12}


--         agnCFlipTable :
--

agnCFlipTable OBJECT-TYPE
     SYNTAX SEQUENCE OF AgnCFlipEntry
     MAX-ACCESS not-accessible
     STATUS  current
     DESCRIPTION
     "The DB Flip Decisions Table"
     ::= {agnFlipDb 3}

agnCFlipEntry OBJECT-TYPE
     SYNTAX AgnCFlipEntry
     MAX-ACCESS not-accessible
     STATUS current
	DESCRIPTION  "An entry in table."
	INDEX {agnCFlipCnfgIdx, agnCFlipIdx}
     ::= {agnCFlipTable 1}

AgnCFlipEntry ::=
     SEQUENCE {
               agnCFlipCnfgIdx    INTEGER,
               agnCFlipIdx         Integer32,
               agnCFlipActive      INTEGER,
               agnCFlipLogicalExp  DisplayString,
               agnCFlipDbNo        Integer32,
               agnCFlipDiscardDe   INTEGER
              }

agnCFlipCnfgIdx OBJECT-TYPE
      SYNTAX  INTEGER
              {
                active     (1),
                temporary  (255)
              }
      MAX-ACCESS  read-only
      STATUS  current
      DESCRIPTION
      "Active or Temporary Flip Decisions Table.
       Both configurations can be read but only the Temporary can
       be written to."
      ::= {agnCFlipEntry 1}



agnCFlipIdx OBJECT-TYPE
     SYNTAX  Integer32  (1..10)
     MAX-ACCESS  read-only
     STATUS  current
     DESCRIPTION
     "Entry number within the table"
     ::= {agnCFlipEntry 2}

agnCFlipActive     OBJECT-TYPE
     SYNTAX  INTEGER
             {
               no  (2),
               yes (3)
             }
     MAX-ACCESS  read-write
     STATUS  current
     DESCRIPTION
     "Indicates if the entry is valid.
      In order to Add/Modify parameters of an entry this object
      should be Set to Yes.
      In order to delete an entry, this object should be Set to No."
     ::= {agnCFlipEntry 3}

agnCFlipLogicalExp    OBJECT-TYPE
     SYNTAX    DisplayString (SIZE (1..20))
     MAX-ACCESS  read-write
     STATUS  current
     DESCRIPTION
     "A logical expression composed of events numbers (which were
      configured in the 'AgnCFlipNetEvantsTable') and logical operators
      ('|', '&', '!', '(', ')') between them.
      e.g - (1 & !2) | (121 & 230)"
     ::= {agnCFlipEntry 4}

agnCFlipDbNo OBJECT-TYPE
     SYNTAX  Integer32  (1..10)
     MAX-ACCESS  read-write
     STATUS  current
     DESCRIPTION
     "The ID of the required DB "
     ::= {agnCFlipEntry 5}

agnCFlipDiscardDe     OBJECT-TYPE
     SYNTAX  INTEGER
             {
               notApplicable (1),
               no            (2),
               yes           (3)
             }
     MAX-ACCESS  read-write
     STATUS  current
     DESCRIPTION
     "Indicates whether the Mux should start discarding
      all DE. (MP3000 Only)."
     ::= {agnCFlipEntry 6}

--  Commands concerning the Flip DB

agnFlipDbControls    OBJECT IDENTIFIER ::= {agnFlipDb 4}


agnCFlipDbSanityCheckCmd OBJECT-TYPE
     SYNTAX  INTEGER
             {
               off(2),
               on (3)
             }
     MAX-ACCESS  read-write
     STATUS  current
     DESCRIPTION
     "Setting this attribute to on(3) will initiate the process
      of Sanity check on the Temp Flip Db and automatically be
      changed to off(2)."
     ::= { agnFlipDbControls 1 }

agnCSaveFlipDbCmd OBJECT-TYPE
     SYNTAX  INTEGER
             {
               off(2),
               on (3)
             }
     MAX-ACCESS  read-write
     STATUS  current
     DESCRIPTION
     "Setting this attribute to on(3) will initiate the process
      of Sanity check on the Temp Flip Db and if it is OK, it will
      save the Flip Db in the NVRAM, activating the new  Flip DB .
      If check detects errors, the save will not be performed.
      Afterwards, the object's value will change automatically to off(2)."
     ::= { agnFlipDbControls 2 }

agnCSaveNetCnfgIdxCmd OBJECT-TYPE
     SYNTAX  Integer32   (1..10)
     MAX-ACCESS  read-write
     STATUS  current
     DESCRIPTION
     "This attribute specifies the Id of the target NVRAM Cnfg to
      which the TmpCnfg should be transferred. Upon set command the
      MUX will initiate the Sanity-Check  process first. If
      successful, the actual transfer will be performed. If warnings
      are detected, the user will have to perform the command again
      to confirm the operation. Setting this object a second time
      to the same value without performing any change in the database,
      will cause the result: agnSSanityCheckStatus = unknown.
      This attribute doesn't cause actual Flip."
     ::= { agnFlipDbControls 3 }

agnCSaveNetFlipDbCmd OBJECT-TYPE
     SYNTAX  INTEGER
             {
               off(2),
               on (3)
             }
     MAX-ACCESS  read-write
     STATUS  current
     DESCRIPTION
     "Setting this attribute to on(3) will save the Temp Flip DB
      Into the NVRAM without actual flip."
     ::= { agnFlipDbControls 4 }

agnCNetGoCmd OBJECT-TYPE
     SYNTAX  INTEGER
             {
               off(2),
               on (3)
             }
     MAX-ACCESS  read-write
     STATUS  current
     DESCRIPTION
     "Setting this attribute to On will broadcast a 'GO' command
      to the network.  When a Mux receives a 'GO' command it issues
      a delay for 'agnCNetDelay' seconds and then activates
      the DB which was pre-defined by one of the commands :
      'agnCSaveNetCnfgIdxCmd' or 'agnCSaveNetFlipDbCmd'."
     ::= { agnFlipDbControls 5 }

agnCNetDelay OBJECT-TYPE
     SYNTAX  Integer32 (1..999)
     MAX-ACCESS  read-write
     STATUS  current
     DESCRIPTION
     "This attribute determines the period of time in seconds that
      takes for a message to be transferred over all the network.
      After a 'GO' command the MUX issues a delay of
      'agnCNetDelay' before activating the appropriate DB.
      The delay will be applied only after performing
      agnCSaveFlipDbCmd."
     ::= { agnFlipDbControls 6 }

agnCNetEventsBcast OBJECT-TYPE
     SYNTAX  INTEGER
             {
               disabled(2),
               enabled (3)
             }
     MAX-ACCESS  read-write
     STATUS  current
     DESCRIPTION
     "This object determines if the Net Events will be Broadcasted to
      other Muxes of the Net or not.
      disabled - Net Events will NOT be Broadcasted
      enabled  - Net Events will be Broadcasted.
   Default=disabled.
      The value will be applied only after performing
      agnCSaveFlipDbCmd."
     ::= { agnFlipDbControls 7 }

agnCNetEventsBcastInterval OBJECT-TYPE
     SYNTAX  Integer32 (10..60)
     MAX-ACCESS  read-write
     STATUS  current
     DESCRIPTION
     "When agnCNetEventsBcast is enabled, this object determines
      the interval of time in seconds, between two consecutive
      Net Events transferred over the network.
   Default=40 sec.
      The interval will be applied only after performing
      agnCSaveFlipDbCmd."
     ::= { agnFlipDbControls 8 }

--
-- agnSa = agent Stand-Alone (not HUB) specific objects
--
agnSaSwchStatus OBJECT-TYPE
     SYNTAX  Integer32
     MAX-ACCESS  read-only
     STATUS  current
     DESCRIPTION
  "This object indicates the status of the switches on the
   stand-alone unit.
   Each switch is represented by a bit. The status is a sum of
   2**n, according to the bits:
   bit 0   NMS (LSB)
   bit 1   Terminal    '1' = forces the DCE to be terminal with
         Rate=9600bps, Data bits=8,
         Stop bits=1
   bit 2   Xray
   bit 3   SW-Load      '1' = when SW is loaded
   bit 4   DBS
   Default of all bits=0
   When the status of these switches is unknown, the value of
   this object is 255."
     ::= { agnSa 1 }

--Decoding Table: Code vs. Description

agnListDecodingTable  OBJECT-TYPE
      SYNTAX SEQUENCE OF AgnListDecodingEntry
      MAX-ACCESS not-accessible
      STATUS  current
   DESCRIPTION
      "A decoding table . For each type of list, a description is
       given for each existing code."
      ::= { agnListDecoding 1 }

agnListDecodingEntry OBJECT-TYPE
      SYNTAX AgnListDecodingEntry
      MAX-ACCESS not-accessible
      STATUS current
	DESCRIPTION  "An entry in table."
	INDEX { agnListDecodingType, agnListDecodingCode }
      ::= { agnListDecodingTable 1}

AgnListDecodingEntry ::=
      SEQUENCE {
     agnListDecodingType        INTEGER,
     agnListDecodingCode        Integer32,
     agnListDecodingDescription DisplayString,
     agnListDecodingDefState    INTEGER,
     agnListDecodingSeverity    INTEGER,
     agnListDecodingAcmRelaySlt INTEGER,
     agnListDecodingAcmRelayPrt INTEGER
      }

agnListDecodingType OBJECT-TYPE
      SYNTAX  INTEGER
       {
       alr      (1),
       sanity   (2),
       counter  (3)
       }
      MAX-ACCESS  read-only
      STATUS  current
      DESCRIPTION
      "The type of list the decoding data refers to.
       alr - Alarms list
       sanity - Sanity Check Error list.
       counter - Counter type of ifPerfCounterType "
      ::= { agnListDecodingEntry 1}

agnListDecodingCode OBJECT-TYPE
      SYNTAX  Integer32
      MAX-ACCESS  read-only
      STATUS  current
      DESCRIPTION
      "The specific code for which decoding is needed. "
      ::= { agnListDecodingEntry 2}

agnListDecodingDescription OBJECT-TYPE
      SYNTAX  DisplayString (SIZE (0..255))
      MAX-ACCESS  read-only
      STATUS  current
      DESCRIPTION
      "The description fitting the specific code and type of list
       required. "
      ::= { agnListDecodingEntry 3}

agnListDecodingDefState OBJECT-TYPE
      SYNTAX  INTEGER
       {
  notApplicable (1),
  event    (3),
  minor    (4),
  major    (5),
  warning  (6),
  critical (7)
       }
      MAX-ACCESS  read-only
      STATUS  current
      DESCRIPTION
      "This object is applicable only for agnListDecodingType=alr.
       It reports the default state/severity of each alarm.
       User can change the  severity of the alarms defined by
       this default via the agnListDecodingSeverity object."
      ::= { agnListDecodingEntry 4}

agnListDecodingSeverity OBJECT-TYPE
      SYNTAX  INTEGER
       {
  notApplicable (1),
  event    (3),
  minor    (4),
  major    (5),
  warning  (6),
  critical (7)
       }
      MAX-ACCESS  read-write
      STATUS  current
      DESCRIPTION
      "This object is applicable only for agnListDecodingType=alr.
       It enables the user to select a severity for each alarm.
    The severity is set per alarm code (same for all slots/ports
    using this code).
    event - can be set only for an alarm that is defined by
            default as 'event'.
       User can change the  severity of the alarms defined by
       default as minor or major.
       The severity of an event may be set to another severity,
       but the change will actually happen only if the event
       threshold is active and passed the Set/ON condition.
       An event alarm that passed the threshold and changed its
       severity, will return automatically to event severity when
       meeting its Reset/OFF condition."
      ::= { agnListDecodingEntry 5}

agnListDecodingAcmRelaySlt OBJECT-TYPE
      SYNTAX  INTEGER
     { none  (1),
       io1   (5),
       io2   (6),
       io3   (7),
       io4   (8),
       io5   (9),
       io6  (10),
       io7  (11),
       io8  (12),
       io9  (13),
       io10 (14),
       io11 (15),
       io12 (16),
	   notApplicable(255)
	    }
      MAX-ACCESS  read-write
      STATUS  current
      DESCRIPTION
      "This object indicates the ACM slot, desired for outbound relay
       (report) for the selected alarm.
       In the ?004 Unit the entries io6(10)..io12(16) are not valid.
	   none - when agnListDecodingType=alr AND the selected
                       alarm should not be reported by an ACM card.
       notApplicable - when agnListDecodingType=sanity OR when
             [agnListDecodingType=alr and there is no ACM card installed in the Mux]."
      ::= { agnListDecodingEntry 6}

agnListDecodingAcmRelayPrt OBJECT-TYPE
      SYNTAX  INTEGER
       {
      exPrt1    (1) ,
      exPrt2    (2) ,
      exPrt3    (3) ,
      exPrt4    (4) ,
      notApplicable(255)
	    }
      MAX-ACCESS  read-write
      STATUS  current
      DESCRIPTION
      "This object indicates the ACM port within the slot, desired for outbound relay
       (report) for the selected alarm.
       notApplicable - when agnListDecodingType=sanity OR when
                       agnListDecodingAcmRelaySlt=notApplicable."
      ::= { agnListDecodingEntry 7}


-- Dlci Table from system point of view
agnDlciTable  OBJECT-TYPE
     SYNTAX SEQUENCE OF AgnDlciEntry
     MAX-ACCESS not-accessible
     STATUS  current
     DESCRIPTION
      "The write operation into the Table Objects is valid only
       to the TmpCnfg entry."
     ::= { agnSystemDlci 1}

agnDlciEntry OBJECT-TYPE
      SYNTAX AgnDlciEntry
      MAX-ACCESS not-accessible
      STATUS current
	DESCRIPTION  "An entry in table."
	INDEX {agnDlciCnfgIdx, agnDlciLSltIdx, agnDlciLPrtIdx, agnDlciHIdx,
         agnDlciHSltIdx, agnDlciHPrtIdx, agnDlciLIdx }
      ::= { agnDlciTable 1}

AgnDlciEntry ::=
      SEQUENCE {
 	agnDlciCnfgIdx 	 Integer32,
 	agnDlciLSltIdx 	 INTEGER,
    agnDlciLPrtIdx	 Integer32,
    agnDlciLIdx		 Integer32,
	agnDlciHSltIdx	 INTEGER,
    agnDlciHPrtIdx	 Integer32,
    agnDlciHIdx		 Integer32,
	agnDlciTxBc	     INTEGER,
    agnDlciTxBe      INTEGER,
    agnDlciRxBc      INTEGER,
    agnDlciRxBe      INTEGER,
	agnDlciPriority  Integer32,
	agnDlciStatus    INTEGER,
	agnDlciSpoofing  INTEGER,
	agnDlciFunnelEnable INTEGER,
	agnDlciRoutingProtocol INTEGER,
	agnDlciRowStatus RowStatus
      }

agnDlciCnfgIdx OBJECT-TYPE
      SYNTAX  Integer32 (1..255)
      MAX-ACCESS  read-only
      STATUS  current
      DESCRIPTION
      "This attribute indicates the Idx of the Cnfg (1..100) being
       accessed.
       Idx 255 relates to the TmpCnfg. "
      ::= { agnDlciEntry 1}
-- In phase I only the values 1 (Cnfg1) and 255 (temp) are valid.

agnDlciLSltIdx OBJECT-TYPE
      SYNTAX  INTEGER
     { cl(3),
       io1   (5),
       io2   (6),
       io3   (7),
       io4   (8),
       io5   (9),
       io6  (10),
       io7  (11),
       io8  (12),
       io9  (13),
       io10 (14),
       io11 (15),
       io12 (16),
	   vs  (254),
	   notApplicable(255)
	    }
      MAX-ACCESS  read-only
      STATUS  current
      DESCRIPTION
      "This attribute indicates a unique  slot  position where
       the card is inserted. This is the Source Slot of the DLCI.
	   vs=Voice Switching
       In the ?004 Unit the entries io6(10)..io16) are not valid.
       For ISDN BRI ports of MX300/30 units:
           io1(5) = isdn1(5) and io2(6) = isdn2(6)
       LSlotIdx is defined according one of the following possiblities:
 1. LSlotIdx is < HSlotIdx.
 2. LSlotIdx is = HSlotIdx and LPrtIdx is < HPrtIdx.
 3. LSlotIdx is = HSlotIdx and LPrtIdx is = HPrtIdx but LIdx is < HIdx."
      ::= { agnDlciEntry 2}

agnDlciLPrtIdx OBJECT-TYPE
      SYNTAX  Integer32
      MAX-ACCESS  read-only
      STATUS  current
      DESCRIPTION
      "This attribute indicates a unique external or internal port number,
       including linkSelector or encapsulator. This is the Source Port of the DLCI.
	   100=noConnect  (for voice switching)
        LPrtIdx is defined according one of the following possiblities:
	1. LSlotIdx is < HSlotIdx.
	2. LSlotIdx is = HSlotIdx and LPrtIdx is < HPrtIdx.
	3. LSlotIdx is = HSlotIdx and LPrtIdx is = HPrtIdx but LIdx is < HIdx."
   ::= { agnDlciEntry 3}

agnDlciLIdx OBJECT-TYPE
      SYNTAX  Integer32 (0..991)
      MAX-ACCESS  read-only
      STATUS  current
      DESCRIPTION
      "This attribute indicates a unique index for each possible
       used DLCI(16..991). This is the Source Side of the DLCI.
       0=notApplicable (for voice switching)
       LIdx is defined according one of the following possiblities:
 1. LSlotIdx is < HSlotIdx.
 2. LSlotIdx is = HSlotIdx and LPrtIdx is < HPrtIdx.
 3. LSlotIdx is = HSlotIdx and LPrtIdx is = HPrtIdx but LIdx is < HIdx."
      ::= { agnDlciEntry 4}

agnDlciHSltIdx OBJECT-TYPE
      SYNTAX  INTEGER
 {   cl    (3),
       io1   (5),
       io2   (6),
       io3   (7),
       io4   (8),
       io5   (9),
       io6  (10),
       io7  (11),
       io8  (12),
       io9  (13),
       io10 (14),
       io11 (15),
       io12 (16),
       notApplicable(255)
       }
      MAX-ACCESS  read-only
      STATUS  current
      DESCRIPTION
      "This attribute indicates a unique slot position In the Mux
       where the DLCI is routed to - Destination Slot.
       For ISDN BRI ports of MX300/30 units:
           io1(5) = isdn1(5) and io2(6) = isdn2(6)
       In the ?004 Unit the entries io6(10)..io16) are not valid"
      ::= { agnDlciEntry 5}

agnDlciHPrtIdx OBJECT-TYPE
      SYNTAX  Integer32
      MAX-ACCESS  read-only
      STATUS  current
      DESCRIPTION
      "This attribute indicates a unique port number where the DLCI is
       routed to - Destination Port."
      ::= { agnDlciEntry 6}

agnDlciHIdx OBJECT-TYPE
      SYNTAX  Integer32    (1..991)
      MAX-ACCESS  read-only
      STATUS  current
      DESCRIPTION
      "This attribute indicates a unique internal connection DLCI
       number where the Source DLCI is routed to - the Destination Side of the DLCI."
      ::= { agnDlciEntry 7}

agnDlciTxBc OBJECT-TYPE
      SYNTAX  INTEGER
        {
         full           (1),
         zero           (2),
         txBc5100bps    (3),
         txBc6400bps    (4),
         txBc8300bps    (5),
         txBc9600bps    (6),
        txBc14400bps    (7),
        txBc19200bps    (8),
        txBc28800bps    (9),
        txBc32000bps   (10),
        txBc38400bps   (11),
        txBc48000bps   (12),
        txBc56000bps   (13),
        txBc57600bps   (14),
          txBc64Kbps   (15),
         txBc128Kbps   (16),
         txBc192Kbps   (17),
         txBc256Kbps   (18),
         txBc320Kbps   (19),
         txBc384Kbps   (20),
         txBc448Kbps   (21),
         txBc512Kbps   (22),
         txBc768Kbps   (23),
         txBc896Kbps   (24),
        txBc1024Kbps   (25),
        txBc1152Kbps   (26),
        txBc1280Kbps   (27),
        txBc1344Kbps   (28),
        txBc1472Kbps   (29),
        txBc1600Kbps   (30),
        txBc1728Kbps   (31),
        txBc1856Kbps   (32),
        txBc1920Kbps   (33),
        txBc1984Kbps   (34),
        txBc2048Kbps   (35),
		txBc16000bps   (36), -- Added here: No room between (7) and (8).

		-- For Mx 30/300
		txBc112Kbps    (37),
		txBc168Kbps    (38),
        txBc224Kbps    (39),
		txBc336Kbps    (40),
        txBc672Kbps    (41),
        txBc1536Kbps   (42),
        txBc1792Kbps   (43)
        }
      MAX-ACCESS  read-create
      STATUS  current
      DESCRIPTION
      "This attribute indicates a unique Tx committed bandwidth on
       the user transmit line or at the port receive line."
      DEFVAL { full }
      ::= { agnDlciEntry 8}

agnDlciTxBe OBJECT-TYPE
      SYNTAX  INTEGER
        {
         full           (1),
         zero           (2),
         txBe5100bps    (3),
         txBe6400bps    (4),
         txBe8300bps    (5),
         txBe9600bps    (6),
        txBe14400bps    (7),
        txBe19200bps    (8),
        txBe28800bps    (9),
        txBe32000bps   (10),
        txBe38400bps   (11),
        txBe48000bps   (12),
        txBe56000bps   (13),
        txBe57600bps   (14),
          txBe64Kbps   (15),
         txBe128Kbps   (16),
         txBe192Kbps   (17),
         txBe256Kbps   (18),
         txBe320Kbps   (19),
         txBe384Kbps   (20),
         txBe448Kbps   (21),
         txBe512Kbps   (22),
         txBe768Kbps   (23),
         txBe896Kbps   (24),
        txBe1024Kbps   (25),
        txBe1152Kbps   (26),
        txBe1280Kbps   (27),
        txBe1344Kbps   (28),
        txBe1472Kbps   (29),
        txBe1600Kbps   (30),
        txBe1728Kbps   (31),
        txBe1856Kbps   (32),
        txBe1920Kbps   (33),
        txBe1984Kbps   (34),
        txBe2048Kbps   (35),
		txBe16000bps   (36), -- Added here: No room between (7) and (8).

		-- For Mx 30/300
		txBe112Kbps    (37),
		txBe168Kbps    (38),
        txBe224Kbps    (39),
		txBe336Kbps    (40),
        txBe672Kbps    (41),
        txBe1536Kbps   (42),
        txBe1792Kbps   (43)
        }
      MAX-ACCESS  read-create
      STATUS  current
      DESCRIPTION
      "This attribute indicates a unique Tx excess bandwidth on the
      user transmit line or at the port receive line."
      DEFVAL { zero }
      ::= { agnDlciEntry 9}

agnDlciRxBc OBJECT-TYPE
      SYNTAX  INTEGER
        {
         full           (1),
         zero           (2),
         rxBc5100bps    (3),
         rxBc6400bps    (4),
         rxBc8300bps    (5),
         rxBc9600bps    (6),
        rxBc14400bps    (7),
        rxBc19200bps    (8),
        rxBc28800bps    (9),
        rxBc32000bps   (10),
        rxBc38400bps   (11),
        rxBc48000bps   (12),
        rxBc56000bps   (13),
        rxBc57600bps   (14),
          rxBc64Kbps   (15),
         rxBc128Kbps   (16),
         rxBc192Kbps   (17),
         rxBc256Kbps   (18),
         rxBc320Kbps   (19),
         rxBc384Kbps   (20),
         rxBc448Kbps   (21),
         rxBc512Kbps   (22),
         rxBc768Kbps   (23),
         rxBc896Kbps   (24),
        rxBc1024Kbps   (25),
        rxBc1152Kbps   (26),
        rxBc1280Kbps   (27),
        rxBc1344Kbps   (28),
        rxBc1472Kbps   (29),
        rxBc1600Kbps   (30),
        rxBc1728Kbps   (31),
        rxBc1856Kbps   (32),
        rxBc1920Kbps   (33),
        rxBc1984Kbps   (34),
        rxBc2048Kbps   (35),
		rxBc16000bps   (36), -- Added here: No room between (7) and (8).

				-- For Mx 30/300
		rxBc112Kbps    (37),
		rxBc168Kbps    (38),
        rxBc224Kbps    (39),
		rxBc336Kbps    (40),
        rxBc672Kbps    (41),
        rxBc1536Kbps   (42),
        rxBc1792Kbps   (43)
        }
      MAX-ACCESS  read-create
      STATUS  current
      DESCRIPTION
      "This attribute indicates a unique Rx committed bandwidth on
       the user receive line or at the port transmit line."
      DEFVAL { full }
      ::= { agnDlciEntry 10}

agnDlciRxBe OBJECT-TYPE
      SYNTAX  INTEGER
        {
         full           (1),
         zero           (2),
         rxBe5100bps    (3),
         rxBe6400bps    (4),
         rxBe8300bps    (5),
         rxBe9600bps    (6),
        rxBe14400bps    (7),
        rxBe19200bps    (8),
        rxBe28800bps    (9),
        rxBe32000bps   (10),
        rxBe38400bps   (11),
        rxBe48000bps   (12),
        rxBe56000bps   (13),
        rxBe57600bps   (14),
          rxBe64Kbps   (15),
         rxBe128Kbps   (16),
         rxBe192Kbps   (17),
         rxBe256Kbps   (18),
         rxBe320Kbps   (19),
         rxBe384Kbps   (20),
         rxBe448Kbps   (21),
         rxBe512Kbps   (22),
         rxBe768Kbps   (23),
         rxBe896Kbps   (24),
        rxBe1024Kbps   (25),
        rxBe1152Kbps   (26),
        rxBe1280Kbps   (27),
        rxBe1344Kbps   (28),
        rxBe1472Kbps   (29),
        rxBe1600Kbps   (30),
        rxBe1728Kbps   (31),
        rxBe1856Kbps   (32),
        rxBe1920Kbps   (33),
        rxBe1984Kbps   (34),
        rxBe2048Kbps   (35),
		rxBe16000bps   (36), -- Added here: No room between (7) and (8).

		-- For Mx 30/300
		rxBe112Kbps    (37),
		rxBe168Kbps    (38),
        rxBe224Kbps    (39),
		rxBe336Kbps    (40),
        rxBe672Kbps    (41),
        rxBe1536Kbps   (42),
        rxBe1792Kbps   (43)
		}
      MAX-ACCESS  read-create
      STATUS  current
      DESCRIPTION
      "This attribute indicates a unique Rx excess bandwidth on the
      user receive line or at the port transmit line."
      DEFVAL { zero }
      ::= { agnDlciEntry 11}

agnDlciPriority OBJECT-TYPE
      SYNTAX  Integer32  (1..8)
      MAX-ACCESS  read-create
      STATUS  current
      DESCRIPTION
      "This attribute indicates a unique priority of the pcv.
       1 is the lowest priority and 7 is the highest priority."
      ::= { agnDlciEntry 12}

agnDlciStatus OBJECT-TYPE
      SYNTAX  INTEGER
 {
          disconnected (1),
          connected    (2)
       }
      MAX-ACCESS  read-only
      STATUS  current
      DESCRIPTION
      "This attribute indicates the status of the pvc. The status is
       disconnected(1) when one of the sides is programmed as
       not connected"
      ::= { agnDlciEntry 13}

agnDlciSpoofing OBJECT-TYPE
      SYNTAX  INTEGER
      {   no     (2),
          yes    (3)
	      }
      MAX-ACCESS  read-create
      STATUS  current
      DESCRIPTION
      "This object refers to sending of RIP messages:
       - yes : RIP messages will be sent ONLY if there is a change in the Net.
	   - no  : RIP messages will be always sent.
	   This object is relevant only when one side of the DLCI is a CL-NMS interface.
	   Default=no. "
      ::= { agnDlciEntry 14}

agnDlciFunnelEnable OBJECT-TYPE
      SYNTAX  INTEGER
      {   disabled    (2),
          enabled     (3),
		  source      (4),
		  destination (5)
	      }
      MAX-ACCESS  read-create
      STATUS  current
      DESCRIPTION
      "This object selects Funnel activation:

       - disabled:   Funnel operation will be disabled.
                     The agnDlciTxBe and agnDlciTxBc values are not used for funneling.
	   - enabled :   Funnel operation will be enabled both for Source and Destination
	                 of the DLCI. The agnDlciTxBe and agnDlciTxBc values are used
	                 for funneling calculations.
	   - source:     Funnel operation will be enabled only for the Source of the DLCI.
	   - destination:Funnel operation will be enabled only for the Destination of the DLCI.
	   
	   This object is relevant only for an encapsulating DLCI.

	   In case of a Link Selector DLCI, the agnDlciTxBe and agnDlciTxBc
	               values are used for bandwidth of Link Selector.
	   Default=disabled. "
      ::= { agnDlciEntry 15}

agnDlciRoutingProtocol OBJECT-TYPE
      SYNTAX  INTEGER
      {   notApplicable(1),
          rip (2),
          rip2(3),
          none(4)
	      }
      MAX-ACCESS  read-create
      STATUS  current
      DESCRIPTION
      "This object is relevant only when one side of the DLCI is a CL-NMS interface.
	   It defines which Routing Protocol will be used for management via CL-NMS port.
	   notApplicable will be used for all slots but CL.
	   rip is a proprietary rip protocol.

	   Default=rip. "
      ::= { agnDlciEntry 16}

agnDlciRowStatus OBJECT-TYPE
      SYNTAX  RowStatus
      MAX-ACCESS  read-create
      STATUS  current
      DESCRIPTION
      "This attribute allows to create/delete a row in this table.
       For creating a row, the NMS should set
	   agnRowStatus.255.id2.id3.id4.id5.id6.id7 = active(1).
       For destroying a row, the NMS should set:
	   agnRowStatus.255.id2.id3.id4.id5.id6.id7 = destroy(6).
       Only rows with status active(1) are relevant.
       The only possible supported RowStatus vaules are
       active (1) and destroy (6)."
      ::= { agnDlciEntry 17}


-- Voice Switching Configuration Support: agnVoiceSwitching group
agnVoiceSwConfTable  OBJECT-TYPE
      SYNTAX SEQUENCE OF AgnVoiceSwConfEntry
      MAX-ACCESS not-accessible
      STATUS  current
      DESCRIPTION
      "MXcess Configuration for Voice Switching."
     ::= { agnVoiceSwitching 1 }

agnVoiceSwConfEntry OBJECT-TYPE
      SYNTAX AgnVoiceSwConfEntry
      MAX-ACCESS not-accessible
      STATUS current
	DESCRIPTION  "An entry in table."
	INDEX { agnVoiceSwConfIdx }
      ::= { agnVoiceSwConfTable 1}

AgnVoiceSwConfEntry ::=
      SEQUENCE {
 agnVoiceSwConfIdx INTEGER,
 agnVoiceSwConfZoneId  DisplayString,
 agnVoiceSwConfNodeId  DisplayString,
 agnVoiceSwConfNoOfHops 	Integer32,
 agnVoiceSwConfSidt         Integer32,
 agnVoiceSwConfLidt         Integer32,
 agnVoiceSwConfDialPlan		INTEGER 
	}

agnVoiceSwConfIdx OBJECT-TYPE
      SYNTAX  INTEGER {    active(1),  temporary(255)  }
      MAX-ACCESS  read-only
      STATUS  current
      DESCRIPTION
      "Active or Temporary Table.
       Both configurations can be read but only the Temporary can
       be written to."
      ::= { agnVoiceSwConfEntry 1}

agnVoiceSwConfZoneId OBJECT-TYPE
      SYNTAX  DisplayString(SIZE(1..2))
      MAX-ACCESS  read-write
      STATUS  current
      DESCRIPTION
      "1 or 2 digits, (0-9)(1-9)."
      ::= { agnVoiceSwConfEntry 2}

agnVoiceSwConfNodeId OBJECT-TYPE
      SYNTAX  DisplayString(SIZE(1..3))
      MAX-ACCESS  read-write
      STATUS  current
      DESCRIPTION
      "1, 2 or 3 digits, (1-9),(0-9),(0-9)."
      ::= { agnVoiceSwConfEntry 3}

agnVoiceSwConfNoOfHops OBJECT-TYPE
      SYNTAX  Integer32 (0..20)
      MAX-ACCESS  read-write
      STATUS  current
      DESCRIPTION
      "Number of hops the frame will go through the net before deciding to discard
       the frame (like time-to-live in IP).

       0 = notApplicable
       Default=20 ."
      ::= { agnVoiceSwConfEntry 4}

agnVoiceSwConfSidt OBJECT-TYPE
      SYNTAX  Integer32 (0..30)
      MAX-ACCESS  read-write
      STATUS  current
      DESCRIPTION
      "SIDT: Short Inter Digit Timeout used as timer (in sec.) between digits
       after routing is completed.
       The timeout indicates end of dialing and the call can then be setup.

       0 = notApplicable
       Default=2 sec."
      ::= { agnVoiceSwConfEntry 5}

agnVoiceSwConfLidt OBJECT-TYPE
      SYNTAX  Integer32 (0..30)
      MAX-ACCESS  read-write
      STATUS  current
      DESCRIPTION
      "LIDT: Long Inter Digit Timeout used as timer between digits before routing
       is completed. If no digits were dialed and LIDT expired then the user will get
       an error tone and the call will be disconnected.

       0 = notApplicable
       Default=15 sec."
      ::= { agnVoiceSwConfEntry 6}

agnVoiceSwConfDialPlan OBJECT-TYPE
      SYNTAX  INTEGER {
	   staticDialPlan(2),
	   staticDialPlanPlus(3),
	   flexDialPlan(4)
 	   }
      MAX-ACCESS  read-write
      STATUS  current
      DESCRIPTION
      "This is the Dialing Plan method that will be used in the Voice Switching.
      Static Dialing Plan - Routing is defined by the current device Zone and
                            Node ID in the Network.
      Static Dialing Plan Plus - Includes the Static Dialing Plan but contains an
                            addition of defining the number of dialed digits.
      Flexible Dialing Plan - Routing is defined in a flexible form.
                              In this plan the user can configure the extension number
                              of a local voice channel, Route a call to a remote
                              destination and enter the Number of Digits for a specific
                              dial prefix."
      ::= { agnVoiceSwConfEntry 7}


agnVoiceSwConfRtTable  OBJECT-TYPE
      SYNTAX SEQUENCE OF AgnVoiceSwConfRtEntry
      MAX-ACCESS not-accessible
      STATUS  current
      DESCRIPTION
      "Routing Table for Voice Switching."
     ::= { agnVoiceSwitching 2 }

agnVoiceSwConfRtEntry OBJECT-TYPE
      SYNTAX AgnVoiceSwConfRtEntry
      MAX-ACCESS not-accessible
      STATUS current
	DESCRIPTION  "An entry in table."
	INDEX { agnVoiceSwConfRtDbId, agnVoiceSwConfRtIdx }
      ::= { agnVoiceSwConfRtTable 1}

AgnVoiceSwConfRtEntry ::=
      SEQUENCE {
 agnVoiceSwConfRtDbId   INTEGER,
 agnVoiceSwConfRtIdx        Integer32,
 agnVoiceSwConfRtDigits  DisplayString,
 agnVoiceSwConfRtAction  INTEGER,
 agnVoiceSwConfRtData  DisplayString,
 agnVoiceSwConfRtSlot  INTEGER,
 agnVoiceSwConfRtPort  Integer32,
 agnVoiceSwConfRtDlci  Integer32,
 agnVoiceSwConfRtRowStatus RowStatus,
 agnVoiceSwConfRtMaxCalls  Integer32,
 agnVoiceSwConfRtPriority  Integer32 
	}

agnVoiceSwConfRtDbId OBJECT-TYPE
      SYNTAX  INTEGER {    active(1),  temporary(255)  }
      MAX-ACCESS  read-only
      STATUS  current
      DESCRIPTION
      "Active or Temporary Table.
       Both configurations can be read but only the Temporary can
       be written to."
 ::= { agnVoiceSwConfRtEntry 1 }

agnVoiceSwConfRtIdx  OBJECT-TYPE
 SYNTAX  Integer32
 MAX-ACCESS read-only
 STATUS current
 DESCRIPTION
 " The Index of the row."
 ::= { agnVoiceSwConfRtEntry 2 }

agnVoiceSwConfRtDigits OBJECT-TYPE
 SYNTAX  DisplayString ( SIZE(1..7) )
 MAX-ACCESS read-create
 STATUS current
 DESCRIPTION
 " Dialed digits: Series of digits 0...9, '*', '#' or '%'.
   The '*' and '#' can have many uses according to the user's decision.
   For example, they can be used as part of the Dialed Number,
   they exist on the phone number panel.
   '*' can also be used instead of a series of numbers.
   The '%' means any digits (wildcard) and is used without a series of digits.
 
   When the agnVoiceSwConfRtAction is del (7), the series of digits that
   are configured via this MIB object will be deleted from the prefix of
   the dialed number."
 ::= { agnVoiceSwConfRtEntry 3 }

agnVoiceSwConfRtAction OBJECT-TYPE
 SYNTAX  INTEGER {
   notApplicable(1),
   zone(2),
   node(3),
   shortDialing(4), 
   in(5),  -- Internal switching
   hgr(6), -- Hunt Group
   del(7), -- Delete a prefix from the Dialed Number
   rep(8), -- Replace a prefix with a given string of digits
   pri(9), -- for ISDN
   bri(10),-- for ISDN
   numDigDP(11), -- Number of Digits user will dial according to Dialing Plan.
   route(12), -- Route to a Remote Destination
   ext(13) -- Extension to a local voice channel
 }
 MAX-ACCESS read-create
 STATUS current
 DESCRIPTION
 " Action that the system should perform for the digits:
   agnVoiceSwConfRtDigits.
   The action that is allowed depends on the Dialing Plan.
   Here is the list of the allowed actions:
   For Static Dialing Plan - zone, node, in, shortDialing, hgr, del, rep
   For Static Dialing Plan Plus - zone, node, in, shortDialing, hgr, del, rep, numDigDP
   For Flexible Dialing Plan - hgr, del, rep, numDigDP, route, ext"
 DEFVAL { notApplicable }
 ::= { agnVoiceSwConfRtEntry 4 }

agnVoiceSwConfRtData   OBJECT-TYPE
 SYNTAX  DisplayString(SIZE(1..7))
 MAX-ACCESS read-create
 STATUS current
 DESCRIPTION
 " This field is relevant for actions hgr(6), and rep(8), numDigDP(11)
   and contains the following information:
   For hgr - the number of the Hunt Group.
   For rep - the number of digits to be replaced with.
   For numDigDP - the number of digits collected before establishing the call.
                  0 indicates no defined length. In this case SIDT will be used."
-- DEFVAL {"0" }
 ::= { agnVoiceSwConfRtEntry 5 }

agnVoiceSwConfRtSlot OBJECT-TYPE
 SYNTAX  INTEGER{
       noConnect(2),
       cl    (3),
       io1   (5),
       io2   (6),
       io3   (7),
       io4   (8),
       io5   (9),
       io6  (10),
       io7  (11),
       io8  (12),
       io9  (13),
       io10 (14),
       io11 (15),
       io12 (16),
       notApplicable(255)
       }
 MAX-ACCESS read-create
 STATUS current
 DESCRIPTION
 " Routing Slot- Relevant for actions zone(2), node(3), shortDialing(4),
   route(12), ext(13)."
 DEFVAL { noConnect }
 ::= { agnVoiceSwConfRtEntry 6 }

agnVoiceSwConfRtPort OBJECT-TYPE
 SYNTAX  Integer32
 MAX-ACCESS read-create
 STATUS current
 DESCRIPTION
	" Routing Port- Relevant for actions zone(2), node(3), shortDialing(4),
      route(12), ext(13).
	  100=noConnect (for non-routing case)."
 DEFVAL { 0 }
 ::= { agnVoiceSwConfRtEntry 7 }

agnVoiceSwConfRtDlci OBJECT-TYPE
	SYNTAX 	Integer32
	MAX-ACCESS	read-create
	STATUS	current
	DESCRIPTION
	" Routing DLCI- Relevant for actions zone(2), node(3), shortDialing(4),
      route(12), ext(13). 
	  Valid values:
	  0=notApplicable (for non-routing case).
	  1, 16..991 "
    DEFVAL { 15 }
	::= { agnVoiceSwConfRtEntry 8 }

agnVoiceSwConfRtRowStatus OBJECT-TYPE
 SYNTAX  RowStatus
 MAX-ACCESS read-create
 STATUS current
 DESCRIPTION
 " Status of the row for creating/deleting entries in the table.
   The only possible supported RowStatus vaules are
   active (1), notInService (2), notReady(3), createAndGo(4),
   createAndWait(5) and destroy(6)."
 ::= { agnVoiceSwConfRtEntry 9 }

agnVoiceSwConfRtMaxCalls OBJECT-TYPE
      SYNTAX  Integer32 
      MAX-ACCESS  read-create
      STATUS  current
      DESCRIPTION
      "Maximum no. of simultaneous voice calls that are allowed in the direction
       defined by the current entry.

       Default=0 (No Limit)."
      ::= { agnVoiceSwConfRtEntry 10}

agnVoiceSwConfRtPriority OBJECT-TYPE
      SYNTAX  Integer32 
      MAX-ACCESS  read-create
      STATUS  current
      DESCRIPTION
      "This attribute indicates a unique priority of the Voice Switching Route.
       1 is the lowest priority and 7 is the highest priority.
	   0 means N/A "       
      ::= { agnVoiceSwConfRtEntry 11}


agnVoiceSwConfHGTable  OBJECT-TYPE
      SYNTAX SEQUENCE OF AgnVoiceSwConfHGEntry
      MAX-ACCESS not-accessible
      STATUS  current
      DESCRIPTION
      "Table of Hunt Groups."
     ::= { agnVoiceSwitching 5 }

agnVoiceSwConfHGEntry OBJECT-TYPE
      SYNTAX AgnVoiceSwConfHGEntry
      MAX-ACCESS not-accessible
      STATUS current
	DESCRIPTION  "An entry in table."
	INDEX { agnVoiceSwConfHGdbIdx, agnVoiceSwConfHGIdx }
      ::= { agnVoiceSwConfHGTable 1}

AgnVoiceSwConfHGEntry ::=
      SEQUENCE {
 		agnVoiceSwConfHGdbIdx			INTEGER,
 		agnVoiceSwConfHGIdx				Integer32,
 		agnVoiceSwConfHGConnect			INTEGER,
 		agnVoiceSwConfHGExt				Integer32,
		agnVoiceSwConfHGExtString		SnmpAdminString,
		agnVoiceSwConfHGUserParams		SnmpAdminString,
		agnVoiceSwConfHGStatus			INTEGER
		}

agnVoiceSwConfHGdbIdx OBJECT-TYPE
      SYNTAX  INTEGER {    active(1),  temporary(255)  }
      MAX-ACCESS  read-only
      STATUS  current
      DESCRIPTION
      "Active or Temporary Table.
       Both configurations can be read but only the Temporary can
       be written to."
      ::= { agnVoiceSwConfHGEntry 1}

agnVoiceSwConfHGIdx OBJECT-TYPE
      SYNTAX  Integer32
      MAX-ACCESS  read-only
      STATUS  current
      DESCRIPTION
      "For Vmux-300 devices -
	   This object represents a combination of
	   - Hunt Group number and Extension number OR
	   - Port number and Extension number.

       For other devices (e.g. MXcess, MP-2100H) -
       There may be up to 10 Hunt Groups per MXcess. That's the
       index of the hunt group relevant to this row."
      ::= { agnVoiceSwConfHGEntry 2}

agnVoiceSwConfHGConnect OBJECT-TYPE
      SYNTAX  INTEGER {  no(2),  yes(3)   }
      MAX-ACCESS  read-write
      STATUS  current
      DESCRIPTION
      "This attribute indicates whether the  hunt group  should be
       considered in any of the mux algorithms."
      ::= { agnVoiceSwConfHGEntry 3}

 agnVoiceSwConfHGExt OBJECT-TYPE
      SYNTAX  Integer32(0..99)
      MAX-ACCESS  read-write
      STATUS  current
      DESCRIPTION
      "This is the extension number of the hunt group.
       0 is for not valid. The allowed range is 10 - 99."
      DEFVAL { 0 }
      ::= { agnVoiceSwConfHGEntry 4}

 agnVoiceSwConfHGExtString OBJECT-TYPE
      SYNTAX		SnmpAdminString
      MAX-ACCESS	read-write
      STATUS		current
      DESCRIPTION
      "This is the extension string of the hunt group.
	   This string is a combination of digits, * and #."
      ::= { agnVoiceSwConfHGEntry 5}

 agnVoiceSwConfHGUserParams OBJECT-TYPE
      SYNTAX		SnmpAdminString
      MAX-ACCESS	read-write
      STATUS		current
      DESCRIPTION
      "This object indicates the User's parameters."
      ::= { agnVoiceSwConfHGEntry 6}

 agnVoiceSwConfHGStatus OBJECT-TYPE
      SYNTAX		INTEGER
	  {
		active			(1),
		notInService	(2),
		notReady	 	(3),
		createAndGo		(4),
		createAndWait	(5),
		destroy			(6),
		notApplicable	(255)
	  }
      MAX-ACCESS	read-write
      STATUS		current
      DESCRIPTION
	  "This object enables the user to create/delete entries in this table.
	   Its usage for values (1)..(6) should be identical to RowStatus SYNTAX.
	   notApplicable(255) - should be used when the table is static
	                        (i.e. whenever create/delete entries is not allowed)."
      ::= { agnVoiceSwConfHGEntry 7}

--
-- Signaling Profiles for MP-2200 and MP-2100
--
-- Legacy Profile Table

agnSigProfileTable  OBJECT-TYPE
     SYNTAX SEQUENCE OF AgnSigProfileEntry
     MAX-ACCESS not-accessible
     STATUS  current
     DESCRIPTION
      "- For products supporting more than one configuration, the write operation 
          into the Table is valid only to the TmpCnfg entry.
        - For products that do not support configurations, the write operation 
          into the Table will be to agnSigProfileCnfgIdx=1.
       The table includes signaling profile parameters for Legacy Profiles."
     ::= { agnSigProfile 1}

agnSigProfileEntry OBJECT-TYPE
      SYNTAX AgnSigProfileEntry
      MAX-ACCESS not-accessible
      STATUS current
	DESCRIPTION  "An entry in table."
	INDEX {agnSigProfileCnfgIdx, agnSigProfileIdx, agnSigProfileRxTx}
      ::= { agnSigProfileTable 1}

AgnSigProfileEntry ::=
      SEQUENCE {
      agnSigProfileCnfgIdx       Integer32,
      agnSigProfileIdx           Integer32,
      agnSigProfileRxTx          INTEGER,
      agnSigProfileABCD          OCTET STRING,
	  agnSigProfileEcanActSignal INTEGER,
	  agnSigProfileEcanRespDelay Unsigned32
      }

agnSigProfileCnfgIdx OBJECT-TYPE
      SYNTAX  Integer32 
      MAX-ACCESS  read-only
      STATUS  current
      DESCRIPTION
      "This attribute indicates the Idx of the Cnfg (1..100) being
       accessed.
       Idx 255 relates to the TmpCnfg.
       For products supporting more than one configuration,the write 
       operation is valid only to the TmpCnfg.
       For Gmux2000 the range limitation (1..255) was discarded
       since the Idx is computed as: <IO Card No.> x 1000 + 255."
      ::= { agnSigProfileEntry 1}

agnSigProfileIdx OBJECT-TYPE
      SYNTAX  Integer32 (1..5)
      MAX-ACCESS  read-only
      STATUS  current
      DESCRIPTION
      "This attribute indicates the Signaling Profile (1..5).
       For MP-104/204, only Profile=1 will exist."
      ::= { agnSigProfileEntry 2}

agnSigProfileRxTx OBJECT-TYPE
      SYNTAX  INTEGER
       {
       rx   (1),
       tx   (2)
       }
      MAX-ACCESS  read-only
      STATUS  current
      DESCRIPTION
      "This attribute indicates if the following objects refer to:
       Rx or Tx translation.
       Rx : ML->IO
       Tx : IO->ML  .
       For MP-104/204, that means:
       Rx : Signaling to FXS CH
       Tx : Signaling to E1 Link. "
      ::= { agnSigProfileEntry 3}

agnSigProfileABCD OBJECT-TYPE
      SYNTAX  OCTET STRING
      MAX-ACCESS  read-write
      STATUS  current
      DESCRIPTION
      "For MP-2100/MP-2200 and for MP-104/204 from R2:
       This object represents 6 parameters, by 3 Octets :
       Busy  Code-MSB nibble, - applicable only for Rx translation
       Idle  Code-    nibble, - applicable only for Rx translation
       D Bit Code-    nibble,
       C Bit Code-    nibble,
       B Bit Code-    nibble,
       A Bit Code-LSB nibble.

       Each of Busy and Idle Code nibble will have the valid values:
       0000 .. FFFF.

       Each of A,B,C,D Bit Code nibble represents:
       0 hex = 0000 = 0
       1 hex = 0001 = 1
       2 hex = 0010 = A bit
       3 hex = 0011 = B bit
       4 hex = 0100 = C bit
       5 hex = 0101 = D bit
       6 hex = 0110 = A bit inverse
       7 hex = 0111 = B bit inverse
       8 hex = 1000 = C bit inverse
       9 hex = 1001 = D bit inverse
       A-F hex - not used (invalid values)

       For MP-104/204 R1:
	   This object represents 3 parameters, by 2 Octets :
       Bit  1 = Bit A - OFF Hook for Tx	; Ring for Rx (LSB)
	   Bit  2 = Bit B - OFF Hook for Tx	; Ring for Rx 
	   Bit  3 = Bit C - OFF Hook for Tx	; Ring for Rx 
	   Bit  4 = Bit D - OFF Hook for Tx	; Ring for Rx 
	   Bit  5 = Bit A - ON  Hook for Tx ; Idle for Rx
	   Bit  6 = Bit B - ON  Hook for Tx ; Idle for Rx
	   Bit  7 = Bit C - ON  Hook for Tx ; Idle for Rx
	   Bit  8 = Bit D - ON  Hook for Tx ; Idle for Rx

	   Bit  9 = Bit A - OOS State for both Tx and Rx
	   Bit 10 = Bit B - OOS State for both Tx and Rx 
	   Bit 11 = Bit C - OOS State for both Tx and Rx 
	   Bit 12 = Bit D - OOS State for both Tx and Rx 
	   Bit 13 = Spare (always 0)
	   Bit 14 = Spare (always 0)
	   Bit 15 = Spare (always 0)
	   Bit 16 = Spare (always 0)  (MSB)

       When the object is not applicable, the Octet String will have 0 bytes."
      ::= { agnSigProfileEntry 4}

agnSigProfileEcanActSignal OBJECT-TYPE
      SYNTAX  INTEGER 
       {
          notApplicable (1),
          aBit1         (2),
          aBit0         (3),
		  bBit1         (4),
		  bBit0         (5),
		  cBit1         (6),
		  cBit0         (7),
		  dBit1         (8),
		  dBit0         (9)
       }
      MAX-ACCESS  read-write
      STATUS  current
      DESCRIPTION
      "Echo Canceller Activation Signal.
       This object specifies which BIT (A, B, C, or D) and which value (0 or 1)
       will be used for the echo canceller activation. The inverse value will cause the
       deactivation of the echo canceller."
      ::= { agnSigProfileEntry 5}
 
agnSigProfileEcanRespDelay OBJECT-TYPE
      SYNTAX  Unsigned32 
      MAX-ACCESS  read-write
      STATUS  current
      DESCRIPTION
      "Echo Canceller Response Delay.
       This object specifies the response delay in msec for the activation/deactivation
       of the echo canceller.
       The value should be in multiples of 100 msec: 100, 200, 300, ...2000."
      ::= { agnSigProfileEntry 6}


-- General Profile Table

agnSigProfTable  OBJECT-TYPE
     SYNTAX SEQUENCE OF AgnSigProfEntry
     MAX-ACCESS not-accessible
     STATUS  current
     DESCRIPTION
      "The write operation into the Table Objects is valid only
       to the TmpCnfg entry. This is the general table of signaling profiles."
     ::= { agnSigProfile 2}

agnSigProfEntry OBJECT-TYPE
      SYNTAX AgnSigProfEntry
      MAX-ACCESS not-accessible
      STATUS current
	DESCRIPTION  "An entry in table."
	INDEX {agnSigProfCnfgIdx, agnSigProfIdx}
      ::= { agnSigProfTable 1}

AgnSigProfEntry ::=
      SEQUENCE {
      agnSigProfCnfgIdx       Integer32,
      agnSigProfIdx           Integer32,
      agnSigProfName          DisplayString,
	  agnSigProfType          INTEGER
      }

agnSigProfCnfgIdx OBJECT-TYPE
      SYNTAX  Integer32 (1..255)
      MAX-ACCESS  read-only
      STATUS  current
      DESCRIPTION
      "This attribute indicates the Idx of the Cnfg (1..100) being
       accessed.
       Idx 255 relates to the TmpCnfg.
       The write operation is valid only to the TmpCnfg."
      ::= { agnSigProfEntry 1}

agnSigProfIdx OBJECT-TYPE
      SYNTAX  Integer32 (1..5)
      MAX-ACCESS  read-only
      STATUS  current
      DESCRIPTION
      "This attribute indicates the Signaling Profile (1..5)."
      ::= { agnSigProfEntry 2}

agnSigProfName   OBJECT-TYPE
      SYNTAX  DisplayString(SIZE(0..12))
      MAX-ACCESS read-write
      STATUS current
      DESCRIPTION
      "Profile Name given by user."
      ::= { agnSigProfEntry 3 }

agnSigProfType OBJECT-TYPE
      SYNTAX  INTEGER 
       {
          notApplicable (1),
          legacy        (2),
          r2Cas         (3)
       }
      MAX-ACCESS  read-write
      STATUS  current
      DESCRIPTION
      "Profile Type.
       legacy - usual signaling. The parameters for the Legacy Profiles 
                are detailed in the agnSigProfileTable, above.
       r2Cas  - R2 signaling. The parameters for the R2 Profiles are detailed
                in the r2 ProfileCnfg tables (belong to r2If).   "
      ::= { agnSigProfEntry 4 }


--
-- TS Assignment Table from system point of view
--
-- agnTsTable  OBJECT-TYPE ::= { agnSystemTs 1}
--
-- For this table see tsa.txt file.


-- General System Voice parameters
--
systemVoiceTable  OBJECT-TYPE
      SYNTAX SEQUENCE OF SystemVoiceEntry
      MAX-ACCESS not-accessible
      STATUS  current
      DESCRIPTION
      "General Parameters for voice - system level."
     ::= { systemVoice 1 }

systemVoiceEntry OBJECT-TYPE
      SYNTAX SystemVoiceEntry
      MAX-ACCESS not-accessible
      STATUS current
	DESCRIPTION  "An entry in table."
	INDEX { systemVoiceConfIdx }
      ::= { systemVoiceTable 1}

SystemVoiceEntry ::=
      SEQUENCE {
 			systemVoiceConfIdx					Integer32,
 			systemVoiceNationalTone 			INTEGER,
 			systemVoicePacketRate				Unsigned32,
			systemVoiceFaxSupport				INTEGER,
			systemVoiceFaxRate					INTEGER,
			systemVoiceModemSupport				INTEGER,
			systemVoiceCoderAndRate				INTEGER,
			systemVoiceEchoCanceler				INTEGER,
			systemVoiceTxGain					Integer32,
			systemVoiceDtmfRelayMethod			INTEGER,
			systemVoiceDtmfRelayRxPayloadType	Unsigned32,
			systemVoiceDtmfRelayPayloadTypeNeg	INTEGER,
			systemVoiceDtmfRelayTxPayloadType	Unsigned32
 	  }

systemVoiceConfIdx OBJECT-TYPE
      SYNTAX  Integer32 
      MAX-ACCESS  read-only
      STATUS  current
      DESCRIPTION
      "This attribute indicates the Idx of the Cnfg (1..100) being
       accessed - Active or Temporary Configurations.
       Idx  255 relates to the temporary TmpCnfg.
       All configurations can be read but only the Temporary can
       be written to."
      ::= { systemVoiceEntry 1}

systemVoiceNationalTone OBJECT-TYPE
      SYNTAX  INTEGER 
       {
          notApplicable (1),
          usa           (2),
          australia     (3),
		  brazil        (4),
		  canada        (5),
		  france        (6),
		  germany       (7),
		  israel        (8),
		  mexico        (9),
		  portugal      (10),
		  russia        (11),
		  spain         (12),
		  unitedKingdom (13),
		  czech         (14),
  		  china         (15)  
       }
      MAX-ACCESS  read-write
      STATUS  current
      DESCRIPTION
      "Tone Characteristics (Amplitude, Frequency, delays etc.).
       These characteristics are defined according to the country."
      ::= { systemVoiceEntry 2}

systemVoicePacketRate OBJECT-TYPE
      SYNTAX		Unsigned32
      MAX-ACCESS	read-write
      STATUS		current
      DESCRIPTION
      "This object indicates the G.729 and G.711 Coders
       transmitted Packet Rate in milliseconds."
      ::= { systemVoiceEntry 3}

systemVoiceFaxSupport OBJECT-TYPE
      SYNTAX		INTEGER 
      {
			notApplicable   (1),
			disable			(2),
			faxRelayT38		(3),
			vbdPassThrou	(4)
      }
      MAX-ACCESS	read-write
      STATUS		current
      DESCRIPTION
      "This object allows the user to Disable/Enable Fax support."
      ::= { systemVoiceEntry 4}

systemVoiceFaxRate OBJECT-TYPE
      SYNTAX		INTEGER 
      {
			notConnected	(1),
			r4800bps		(2),
			-- reserved for r7200bps		(3)
			r9600bps		(4),
			-- reserved for r12000bps		(5)
			r14400bps		(6)
      }
      MAX-ACCESS	read-write
      STATUS		current
      DESCRIPTION
      "This object indicates the Fax Rate limit.
       It is irrelevant when Fax support is NA or disabled."
      ::= { systemVoiceEntry 5}

systemVoiceModemSupport OBJECT-TYPE
      SYNTAX		INTEGER 
      {
			notApplicable   (1),
			disable			(2),
			vbdV152			(3),
			vbdPassThrou	(4)
      }
      MAX-ACCESS	read-write
      STATUS		current
      DESCRIPTION
      "This object allows the user to Disable/Enable Modem support."
      ::= { systemVoiceEntry 6}

systemVoiceCoderAndRate OBJECT-TYPE
      SYNTAX		INTEGER 
      {
			notApplicable   (1),
			-- reserved for g7231r6300BPS	(2)
			-- reserved for g7231r5300BPS	(3)
			-- reserved for g729A8KBPS		(4)
			g711aLAW        (5),
			g711uLAW        (6)
      }
      MAX-ACCESS	read-write
      STATUS		current
      DESCRIPTION
      "This object indicates the Coder and Rate for the Voice Compression."
      ::= { systemVoiceEntry 7}

systemVoiceEchoCanceler OBJECT-TYPE
      SYNTAX		INTEGER 
      {
			notApplicable	(1),
			disable			(2),
			enable			(3)
      }
      MAX-ACCESS	read-write
      STATUS		current
      DESCRIPTION
      "This object indicates the Echo Canceler activation."
      ::= { systemVoiceEntry 8}

systemVoiceTxGain OBJECT-TYPE
      SYNTAX		Integer32
      MAX-ACCESS	read-write
      STATUS		current
      DESCRIPTION
      "This object indicates the Transmit Gain (volume) in dB."
      ::= { systemVoiceEntry 9}

systemVoiceDtmfRelayMethod OBJECT-TYPE
      SYNTAX		INTEGER 
      {
			rfc2833			(1),
			sipInfo			(2)
      }
      MAX-ACCESS	read-write
      STATUS		current
      DESCRIPTION
      "This object indicates the DTMF Relay Method
       that is used to transmit DTMF tones.
       
       rfc2833(1) - inband DTMF relay according to RFC-2833.
       sipInfo(2) - out of band DTMF relay using SIP INFO method."
      ::= { systemVoiceEntry 10}

systemVoiceDtmfRelayRxPayloadType OBJECT-TYPE
      SYNTAX		Unsigned32
      MAX-ACCESS	read-write
      STATUS		current
      DESCRIPTION
      "This object indicates the Rx Payload Type
       for DTMF relay RTP packets.
       It is relevant only when DTMF Relay Method is RFC-2833."
      ::= { systemVoiceEntry 11}

systemVoiceDtmfRelayPayloadTypeNeg OBJECT-TYPE
      SYNTAX		INTEGER 
      {
			notApplicable	(1),
			disable			(2),
			enable			(3)
      }
      MAX-ACCESS	read-write
      STATUS		current
      DESCRIPTION
      "This object indicates whether Payload Type Negotiation is used
       (according to RFC-2833) or not.
       It is relevant only when DTMF Relay Method is RFC-2833."
      ::= { systemVoiceEntry 12}

systemVoiceDtmfRelayTxPayloadType OBJECT-TYPE
      SYNTAX		Unsigned32
      MAX-ACCESS	read-write
      STATUS		current
      DESCRIPTION
      "This object indicates the Tx Payload Type
       for DTMF relay RTP packets.
       It is relevant only when the Payload Type Negotiation is disabled."
      ::= { systemVoiceEntry 13}


systemVoiceCoderTable  OBJECT-TYPE
      SYNTAX		SEQUENCE OF SystemVoiceCoderEntry
      MAX-ACCESS	not-accessible
      STATUS		current
      DESCRIPTION
      "Voice Coders table."
     ::= { systemVoice 2 }

systemVoiceCoderEntry OBJECT-TYPE
      SYNTAX		SystemVoiceCoderEntry
      MAX-ACCESS	not-accessible
      STATUS		current
	  DESCRIPTION  "An entry in Voice Coders table."
	  INDEX { systemVoiceCoderConfIdx, systemVoiceCoderPriority }
      ::= { systemVoiceCoderTable 1}

SystemVoiceCoderEntry ::=
      SEQUENCE {
 			systemVoiceCoderConfIdx      	Unsigned32,
 			systemVoiceCoderPriority		Unsigned32,
			systemVoiceCoderCoderAndRate	INTEGER
 	  }

systemVoiceCoderConfIdx OBJECT-TYPE
      SYNTAX		Unsigned32 
      MAX-ACCESS	not-accessible
      STATUS		current
      DESCRIPTION
	"The first index of the table.
	 
	 This object might represent the Configuration Index (1..100) being accessed;
	 Index=255 relates to the TmpCnfg.
	 For devices with multiple configurations, Set is permitted to TmpCnfg(255) only.
	 
	 Not-Applicable = 1."
      ::= { systemVoiceCoderEntry 1}

systemVoiceCoderPriority OBJECT-TYPE
      SYNTAX		Unsigned32 
      MAX-ACCESS	not-accessible
      STATUS		current
      DESCRIPTION
      "This object indicates the Coder's Priority."
      ::= { systemVoiceCoderEntry 2}

systemVoiceCoderCoderAndRate OBJECT-TYPE
      SYNTAX		INTEGER
      {
			notApplicable		(1),
			g7231r6300BPS		(2),
			g7231r5300BPS		(3),
			g729A8KBPS			(4),
			g711aLAW			(5),
			g711uLAW			(6),
			none				(255)
      }
      MAX-ACCESS	read-write
      STATUS		current
      DESCRIPTION
      "This object indicates the Coder and Rate for the Voice Compression."
      ::= { systemVoiceCoderEntry 3}


--
-- Wan installed module status general information
--
mdlSInstTable  OBJECT-TYPE
    SYNTAX SEQUENCE OF MdlSInstEntry
    MAX-ACCESS not-accessible
    STATUS current
	DESCRIPTION  "A table."
	::=  { statMdlGen 1 }

mdlSInstEntry OBJECT-TYPE
    SYNTAX MdlSInstEntry
    MAX-ACCESS not-accessible
    STATUS current
	DESCRIPTION  "An entry in table."
	INDEX { mdlSInstSltIdx }
      ::= { mdlSInstTable 1}

MdlSInstEntry ::=
      SEQUENCE {
     mdlSInstSltIdx        INTEGER,
     mdlSInstCardType      INTEGER,
     mdlSHwVersion         DisplayString,
     mdlSSwVersion         DisplayString,
     mdlSAlrStatus         INTEGER,
     mdlSAlrStatusAll      INTEGER,
     mdlSMaskedAlrStat     INTEGER,
     mdlSMaskedAlrStatAll  INTEGER,
     mdlSTstStatusAll      INTEGER,
     mdlSClearAlrCmd       INTEGER,
     mdlSClearAllAlrCmd    INTEGER,
	 mdlSTemperature       Integer32
      }

mdlSInstSltIdx OBJECT-TYPE
   SYNTAX  INTEGER
   {
       psA   (1),
       psB   (2),
       clA   (3),
       clB   (4),
       io1   (5),
       io2   (6),
       io3   (7),
       io4   (8),
       io5   (9),
       io6  (10),
       io7  (11),
       io8  (12),
       io9  (13),
       io10 (14),
       io11 (15),
       io12 (16)
   }
   MAX-ACCESS  read-only
   STATUS  current
   DESCRIPTION
   "A unique number to identify a slot position in the mux.
    In the ?004 Unit the entries PsB(2),ClB(4),io6(10)..io(16)
    are not valid.
    For the Vmux2100 Main Board clA  (3) is used."
   ::= { mdlSInstEntry 1}

mdlSInstCardType OBJECT-TYPE
   SYNTAX  INTEGER
   {
  --
  -- General types
  --		 
         unknown        (1),
         empty          (2),

  -- (3)..(7) are reserved ; they appear in the compress structure

		 acm            (9), --alarm module
  --
  -- Power Supply Modules
  --
        ps60W          (10),
        ps100W         (11),
   -- (12)..(16) are reserved for the Programmed PS cards
		ps             (17), 

  --
  -- Cl Modules
  --
        cl1            (20),
        clEth          (21),
        cl2            (22),
		cl2Eth         (23),
        cl3            (24),
		cl3Eth         (25),
		cl1Clk         (26), --CL1 with Station Clock (for LRS102)
  --
  -- Packet Cards of Megaplex
  --
        mPh1            (31),
        mPh3            (32),
        mPh1T1DSU       (33),
        mPh1T1CSU       (34),
        mPh1E1DSU       (35),
        mPh1E1LTU       (36),

  -- TDM Cards

        mtmlFT1         (37),
        mtmlFE1         (38),
		mtmlH4E1        (39),
		mtmlH4E12W      (40),
		mtmlH4T1        (41),
		mtmlH4T12W      (42),
		mtHsh4E1        (43),
		mtHsh4E12W      (44),
		mtHsh4T1        (45),
		mtHsh4T12W      (46),
		mtmlH2E1        (47),
		mtmlH2E12W      (48),
		mtmlH2T1        (49),
		mtmlH2T12W      (50),
		hsh2E1          (51),
		hsh2E12W        (52),
		hsh2T1          (53),
		hsh2T12W        (54),
		mlIp            (55),
		mtml4Ip         (56),
		ml20N1          (57),
		ml20N2          (58),

  -- Packet Cards of Megaplex

        mPl6            (60),
        mPl3            (61),

  -- VF cards of Megaplex
        vf24T1          (62),
		vf30E1          (63),
		vf48T1          (64),
		vf60E1          (65),

  -- Vmux-2100 Main Link cards 
	    ml2E1           (68),
	    ml4E1           (69),
        ml2T1           (70),
	    ml4T1           (71),

        mPv4            (72), 
  --
  -- TDM Cards
  --
      vc16A             (73),
      vc8EandM          (74),
      vc8Fxo            (75),
      vc8Fxs            (76),
      vc16EandM         (77),
      vc16Fxo           (78),
      vc16Fxs           (79),

      vf3EandM          (80),
      vf3Fxs            (81),
      vf3Fxo            (82),

      vfPbx             (83),
      vfPbxT1           (84),
      vfPbxE1           (85),

	  mtMlE2S           (86), --Single Link
	  mtMlE2D           (87), --Dual Link 
      mtMlF2T1          (88),
      mtMlF2E1          (89),
      mtMlT1Fiber       (90),
      mtMlE1Fiber       (91),
      mtMlT1FiberFb     (92),
      mtMlE1FiberFb     (93),
      mtmlHE1           (94),
      mtmlH1E1          (95),
      mtmlHSE1          (96),
      ml20              (97),
      mtMl4T1           (98),
      mtMl4E1           (99),

      mtMl1T1DSU       (100),
      mtMl1T1CSU       (101),
      mtMl1E1DSU       (102),
      mtMl1E1LTU       (103),
      mtMl1T1DSUfb     (104),
      mtMl1T1CSUfb     (105),
      mtMl1E1DSUfb     (106),
      mtMl1E1LTUfb     (107),
      mtMl2T1          (108),
      mtMl2E1          (109),

       ls2CcittX50     (110),
       ls2CcittX58     (111),
       ls2ATandTSdm    (112),
       ls2ACcittX50    (113),
       ls2ACcittX58    (114),
       ls2AATandTSdm   (115),
       ls2A2Ts         (116),
       ls2M            (117),

      mtMlT1           (118),
      mtMlE1           (119),

       hs2             (120),
       hs3             (121),
       hsq             (122),
       hs703           (123),
       hsQM            (124),
       hsqN            (125),
       hs6             (126),
       hs12            (127),
	   hsDp            (128),
	   hsp             (129), 

       hs4T1           (130),
       hs4E1           (131),
       hs4             (132),
       hsEth           (133),

	   ml8T1           (134),
	   ml8E1           (135),     

  --  Vmux-2100  Voice cards 
       vc2E1           (136),
       vc4E1           (137),
       vc2T1           (138),
       vc4T1           (139), 

       vc2EandM        (140),
       vc2Fxs1Plar     (141),
       vc2Fxo1         (142),
       vc2Fxs2         (143),
       vc2Fxo2         (144),
       vc2Fxs3         (145),
       vc2Fxo3         (146),
       vc26EandM       (147),
       mtvc2           (148),
       vc2R2Fxs        (149),

       hsu             (150),

       mbeA            (151),
       mbeB            (152),
       mbeU            (153),
       tre             (154),

       hsuI            (155),
       hsr             (156),
       hss             (157),
       hsu1            (158),

       ls12            (159),
       ls6             (160),
       ls6V1EandM      (161),
       ls6V1Fxo        (162),
       ls6V1Fxs        (163),
       ls6V2EandM      (164),
       ls6V2Fxo        (165),
       ls6V2Fxs        (166),
       ls6VfEandM      (167),
       ls6VfFxo        (168),
       ls6VfFxs        (169),

       vc3EandM        (170),
       vc3Fxo          (171),
       vc3Fxs          (172),

       vcPbx           (173),
       vcPbxT1         (174),
       vcPbxE1         (175),

       vc6EandM        (176),
       vc6Fxo          (177),
       vc6Fxs          (178),

       vcq             (179),

       ls6n            (180),

  --
  -- Packet Cards of MAXcess and Hybrid
  --

        -- High speed cards

        mhs1V36          (181),
        mhs1V35          (182),
        mhs1G703         (183),
        mhs1DDS          (184),
        mhs3             (185),
        mhs1X21          (186),
        mhs1V24          (187),
		mhs4             (188),
        mhsE1Hs          (189),
		mhsT1Hs          (190),
		mhsHyE1Hs        (191), -- 2 HS ports + 1 Hybrid E1 port
		mhsHyT1Hs        (192), -- 2 HS ports + 1 Hybrid T1 port
        mlfHybE1Hs       (193), -- Fiber Optic Hybrid: 2 HS + 1 Hybrid E1 port
        mlfHybT1Hs       (194), -- Fiber Optic Hybrid: 2 HS + 1 Hybrid T1 port 

        -- T1/E1 cards

        mhs2e1			 (195),
		mhs2t1           (196),
		mhsHy2e1         (197), -- 2 Hybrid E1 ports
		mhsHy2t1         (198), -- 2 Hybrid T1 ports
        mlfHybE12        (199), -- Fiber Optic Hybrid: 2 E1 ports
   

        -- Low speed cards

        mls6             (200),
        mls3             (201),


        -- More  T1/E1 cards

        mlHybAtmE1       (202), -- Hybrid ATM E1
        mlHybAtmT1       (203), -- Hybrid ATM T1
        mlfHybT12        (204), -- Fiber Optic Hybrid: 2 T1 ports


		--  Voice cards

        mvc8             (205), -- MVC-8 name in marketing: MVC-4N
        mvc8PbxE1        (206),
        mvc8PbxT1Dsu     (207),
        mvc8PbxT1Csu     (208),
        mvc8PbxE1Slave   (209),

        mvc4             (210),
        mvc4PbxE1        (211),
        mvc4PbxT1Dsu     (212),
        mvc4PbxT1Csu     (213),
        mvc4PbxE1Slave   (214),
        mvc4PbxT1Slave   (215),
 
        mvc8PbxT1Slave   (216),	-- MVC-8 T1 Slave is here
        mvc8ExtAnalog    (217), -- MVC-8 with 8 External ports
		mvcE1            (218), -- 8 External ports & 30 Internals
		mvcT1            (219), -- 8 External ports & 24 Internals

		-- ISDN for Maxcess
        mhsS             (220),
        mhsU             (221),
        mhsPriE1         (222),
        mhsPriT1         (223),

        --Card of MP-2100/4
        hsEthSwitch      (224),

        -- CCS for Maxcess & MPH
        mPriE1FramerCcs  (225),
        mPriT1FramerCcs  (226),
        mPriE1SlaveCcs   (227),
        mPriT1SlaveCcs   (228),
		mDualBri         (229),

        --Voice cards for MP
        vc12EandM        (230),
        vc12Fxo          (231),
        vc12Fxs          (232),
		vc6aEandM        (233),
        vc6aFxo          (234),
        vc6aFxs          (235),
        vc6AgFxo         (236),
        vc6AgFxs         (237),
        vc6a4LB          (238),

        --Video card for MP
		vid              (239),

        --ISDN cards for MP
		hsu12            (240),
		hsu6             (241),
		hss12            (242),
		hss6             (243),

        -- MPH and MP-2100/4 cards
        hsDp3			 (244),	  
        hsDp6			 (245),	  

        -- MP-2100/4 card
        hsf1             (246),

        -- More Hybrid cards + IP cards for MPH
    	mhsHyE1          (247),   -- 1 Hybrid E1 port
		mhsHyT1          (248),   -- 1 Hybrid T1 port         
        mhsIp            (249),   -- 1 Eth  port + 1 HS port
        mlIpHs           (250),   -- 1 Eth  port + 3 HS ports
        mlHybIpE1        (251),   -- 1 Eth  port + 1 HS port + 1 E1
        mlHybIpT1        (252),   -- 1 Eth  port + 1 HS port + 1 T1

        -- VOIP cards for MPH & MX
        mvg1Lan          (253),
        mvg2Lan          (254),

        -- MP-2100/4 card
        vc4Fxs           (255),
		vc4EandM         (256),
		vc4Fxo           (257),
        hsf2             (258),

        -- More VOIP cards for MPH
        mvgSwitch4Lan    (260),

        --SHDSL cards of Megaplex
        msl4E1W2         (261),
		msl4E1W4         (262),
		msl8E1W2         (263),
        msl4E1W2Eth      (264),
		msl8E1W2Eth      (265),
		asmi54cE1AndEth  (266), -- & LRS-102 (E1 & ETH)
		asmi54cT1AndEth  (267), -- & LRS-102 (T1 & ETH)
		asmi54c          (268), -- & LRS-102 (ETH only)

        --HS cards of Megaplex
		hs6N             (271),
		hs12N            (272),
		hsNRZ            (273),

       -- Vmux 2100 Enhanced Voice Cards
	   evc2E1            (281),
	   evc4E1            (282),
	   evc2T1            (283),
	   evc4T1            (284),

   --  Vmux-2200  Voice cards 
       vc2E1Pri          (285),
       vc4E1Pri          (286),

   --  MP Voice cards
       vc4OmniEandM      (291),
       vc4OmniWestern    (292),
       
   --  MP-4100 and/or LRS-102 cards
       clx1              (301),
       clx1GbE           (302),
       clx1S155          (303),
       clx1S155GbE       (304),
       ml8T1Eth          (305),
       ml8E1Eth          (306),
	   op106cEth         (307),	--no external T1
	   op108cEth         (308),	--no external E1
	   op106cEthT1       (309), --with external T1 (used also by LRS-102)
	   op108cEthE1       (310), --with external E1 (used also by LRS-102)
	   op108cEthE1Unbal  (311),	--used only by LRS-102
	   mpw1              (312),
       
  -- VFS cards of Megaplex
        vfs24T1          (321),
		vfs30E1          (322),
		vfs48T1          (323),	 --2T1
		vfs60E1          (324),  --2E1

-- MiniCVS cards
        mm4E1            (325),
        mm4T1            (326),
        mm8E1            (327),
        mm8T1            (328),
        mm12E1           (329),
        mm12T1           (330),
        mm16E1           (331),
        mm16T1           (332)
     }
   MAX-ACCESS  read-only
   STATUS  current
   DESCRIPTION
   "This attribute indicates the type of card installed
    in the specific slot position.
    Only PS cards are possible in the PS slots.
    Only CL cards are possible in the CL slots.
    Only IO cards are possible in the IO slots."
   ::= { mdlSInstEntry 2}

mdlSHwVersion OBJECT-TYPE
   SYNTAX  DisplayString (SIZE (0..255))
   MAX-ACCESS  read-only
   STATUS  current
   DESCRIPTION
   "This attribute indicates the Hardware version of the
    installed card in the specific slot position."
   ::= { mdlSInstEntry 3 }

mdlSSwVersion OBJECT-TYPE
   SYNTAX  DisplayString (SIZE (0..255))
   MAX-ACCESS  read-only
   STATUS  current
   DESCRIPTION
   "This attribute indicates the Software version of the
    installed card in the specific slot position."
   ::= {mdlSInstEntry 4}

mdlSAlrStatus OBJECT-TYPE
  SYNTAX  INTEGER
  {
  off      (2),
  event    (3),
  minor    (4),
  major    (5),
  warning  (6),
  critical (7)
  }
  MAX-ACCESS  read-only
  STATUS  current
  DESCRIPTION
  "Indicates the alarm state at module level, i.e. lower level
  (port alarms) status is not included.
  This attribute will be set to:
    critical(7) - when there is at least one active (state ON)
                  critical alarm,
                  otherwise it will be set to
       major(5) - when there is at least one active (state ON)
                  major alarm,
                  otherwise it will be set to
       minor(4) - if there is at least one active (state ON) minor
                  alarm,
                  otherwise it will be set to
       warning(6) - if there is at least one active (state ON)
                  warning alarm,
                  otherwise it will be set to
       event(3) - if there was at least one alarm event (including
                  state on,off events) since the last clear operation."
   ::= { mdlSInstEntry 5 }

mdlSAlrStatusAll OBJECT-TYPE
  SYNTAX  INTEGER
  {
  off      (2),
  event    (3),
  minor    (4),
  major    (5),
  warning  (6),
  critical (7)
  }
  MAX-ACCESS  read-only
  STATUS  current
  DESCRIPTION
  "Indicates the alarm state in the module-all level, i.e. lower level
  (port alarms) included.
  This attribute will be set to:
    critical(7) - when there is at least one active (state ON)
                  critical alarm,
                  otherwise it will be set to
       major(5) - when there is at least one active (state ON)
                  major alarm,
                  otherwise it will be set to
       minor(4) - if there is at least one active (state ON) minor
                  alarm,
                  otherwise it will be set to
       warning(6) - if there is at least one active (state ON)
                  warning alarm,
                  otherwise it will be set to
       event(3) - if there was at least one alarm event (including
                  state on,off events) since the last clear operation."
   ::= { mdlSInstEntry 6 }

mdlSMaskedAlrStat OBJECT-TYPE
  SYNTAX  INTEGER
  {
  off      (2),
  event    (3),
  minor    (4),
  major    (5),
  warning  (6),
  critical (7)
  }
  MAX-ACCESS  read-only
  STATUS  current
  DESCRIPTION
  "Indicates the alarm state at module level, [i.e. lower level
  (port alarms) status is not included],including Masked alarms.
  This attribute will be set to:
    critical(7) - when there is at least one active (state ON)
                  critical alarm,
                  otherwise it will be set to
       major(5) - when there is at least one active (state ON)
                  major alarm,
                  otherwise it will be set to
       minor(4) - if there is at least one active (state ON) minor
                  alarm,
                  otherwise it will be set to
       warning(6) - if there is at least one active (state ON)
                  warning alarm,
                  otherwise it will be set to
       event(3) - if there was at least one alarm event (including
                  state on,off events) since the last clear operation."
  ::= { mdlSInstEntry 7 }

mdlSMaskedAlrStatAll OBJECT-TYPE
  SYNTAX  INTEGER
  {
  off      (2),
  event    (3),
  minor    (4),
  major    (5),
  warning  (6),
  critical (7)
  }
  MAX-ACCESS  read-only
  STATUS  current
  DESCRIPTION
  "Indicates the alarm state in the module-all level, i.e. lower level
  (port alarms) included, including Masked alarms.
  This attribute will be set to:
    critical(7) - when there is at least one active (state ON)
                  critical alarm,
                  otherwise it will be set to
       major(5) - when there is at least one active (state ON)
                  major alarm,
                  otherwise it will be set to
       minor(4) - if there is at least one active (state ON) minor
                  alarm,
                  otherwise it will be set to
       warning(6) - if there is at least one active (state ON)
                  warning alarm,
                  otherwise it will be set to
       event(3) - if there was at least one alarm event (including
                  state on,off events) since the last clear operation."
  ::= { mdlSInstEntry 8 }

mdlSTstStatusAll OBJECT-TYPE
  SYNTAX  INTEGER
  {
  off(2),
  on (3)
  }
  MAX-ACCESS  read-only
  STATUS  current
  DESCRIPTION
  "This attribute will be set to on(3) when there is at least
   one test in progress on a channel of the card, otherwise
   the value will be off(2)."
  ::= { mdlSInstEntry 9 }

mdlSClearAlrCmd  OBJECT-TYPE
  SYNTAX  INTEGER
  {
  off(2),
  on (3)
  }
  MAX-ACCESS  read-write
  STATUS  current
  DESCRIPTION
  "Setting this command to ON, enforces a clear of all the
   alarms in the given slot, excluding alarms of port level.
   The clear operation will not be applied for masked/inverted
   alarms."
  ::= { mdlSInstEntry 10 }

mdlSClearAllAlrCmd  OBJECT-TYPE
  SYNTAX  INTEGER
  {
  off(2),
  on (3)
  }
  MAX-ACCESS  read-write
  STATUS  current
  DESCRIPTION
  "Setting this command to ON, enforces a  clear of all the
   alarms in the given slot, including all its ports alarms.
   The clear operation will not be applied for masked/inverted
   alarms."
  ::= { mdlSInstEntry 11 }

mdlSTemperature OBJECT-TYPE
  SYNTAX  Integer32
  MAX-ACCESS  read-only
  STATUS  current
  DESCRIPTION
  "Temperature of the card, in Celsius degrees."
  ::= { mdlSInstEntry 12 }


mdlSAlrTable OBJECT-TYPE
      SYNTAX SEQUENCE OF MdlSAlrEntry
      MAX-ACCESS not-accessible
      STATUS current
      DESCRIPTION
      "The list of card agent alarms ; includes also an alarm
       indicating existence of alarms on its ports if there are any."
      ::= { statMdlGen 2 }

mdlSAlrEntry OBJECT-TYPE
      SYNTAX MdlSAlrEntry
      MAX-ACCESS not-accessible
      STATUS current
	DESCRIPTION  "An entry in table."
	INDEX {mdlSAlrSltIdx , mdlSAlrIdx}
      ::= { mdlSAlrTable 1}

MdlSAlrEntry ::=
      SEQUENCE {
  mdlSAlrSltIdx           INTEGER,
  mdlSAlrIdx              Integer32,
  mdlSAlrCodeDescription  DisplayString,
  mdlSAlrCode             Integer32,
  mdlSAlrSeverity         INTEGER,
  mdlSAlrState            INTEGER,
  mdlSAlrCounter          Integer32,
  mdlSAlrMask             INTEGER,
  mdlSAlrInvert           INTEGER
      }

mdlSAlrIdx OBJECT-TYPE
      SYNTAX  Integer32
      MAX-ACCESS  read-only
      STATUS  current
      DESCRIPTION
      "A unique number to identify an entry in the alarm status table.
       Users should use the get next function to read this table because
       the indexes are not consecutive."
      ::= { mdlSAlrEntry 1}

mdlSAlrSltIdx OBJECT-TYPE
      SYNTAX  INTEGER
       {
       psA   (1),
       psB   (2),
       clA   (3),
       clB   (4),
       io1   (5),
       io2   (6),
       io3   (7),
       io4   (8),
       io5   (9),
       io6  (10),
       io7  (11),
       io8  (12),
       io9  (13),
       io10 (14),
       io11 (15),
       io12 (16)
       }
      MAX-ACCESS  read-only
      STATUS  current
      DESCRIPTION
      "This attribute indicates the  desired slot position.
       In the ?004 Unit the entries PsB(2),ClB(4),io6(10)..io12(16)
       are not valid.
       For the Vmux2100 Main Board clA  (3) is used."
      ::= { mdlSAlrEntry 2}

mdlSAlrCodeDescription OBJECT-TYPE
      SYNTAX  DisplayString (SIZE (0..255))
      MAX-ACCESS  read-only
      STATUS  current
      DESCRIPTION
      "This attribute is a full text description of the alarm .
       The alarm description includes the following information:
       alarm code, alarm text, alarm severity, Masked or Inverted
       flag and counter."
      ::= { mdlSAlrEntry 3}

mdlSAlrCode OBJECT-TYPE
      SYNTAX  Integer32
      MAX-ACCESS  read-only
      STATUS  current
      DESCRIPTION
      "A code identifying the alarm of an entry in the alarm status
       table at card level."
      ::= { mdlSAlrEntry 4 }

mdlSAlrSeverity OBJECT-TYPE
      SYNTAX  INTEGER
       {
  event    (3),
  minor    (4),
  major    (5),
  warning  (6),
  critical (7)
       }
      MAX-ACCESS  read-only
      STATUS  current
      DESCRIPTION
      "The severity of the alarm."
      ::= { mdlSAlrEntry 5 }

mdlSAlrState  OBJECT-TYPE
      SYNTAX  INTEGER
       {
  off(2),
  on (3)
       }
      MAX-ACCESS  read-only
      STATUS  current
      DESCRIPTION
      "State of the alarm."
      ::= { mdlSAlrEntry 6 }

mdlSAlrCounter OBJECT-TYPE
      SYNTAX  Integer32
      MAX-ACCESS  read-only
      STATUS  current
      DESCRIPTION
      "A counter - how many times the alarm occured since last
       clear operation.
       ON and OFF Alarm will be counted separately."
      ::= { mdlSAlrEntry 7 }

mdlSAlrMask  OBJECT-TYPE
      SYNTAX  INTEGER
       {
  off(2),
  on (3)
       }
      MAX-ACCESS  read-only
      STATUS  current
      DESCRIPTION
      "Alarm mask : on/off."
      ::= { mdlSAlrEntry 8 }

mdlSAlrInvert  OBJECT-TYPE
      SYNTAX  INTEGER
       {
  off(2),
  on (3)
       }
      MAX-ACCESS  read-only
      STATUS  current
      DESCRIPTION
      "Alarm invert : on/off."
      ::= { mdlSAlrEntry 9 }


--
-- Wan module configuration information
--
mdlCPrgTable  OBJECT-TYPE
      SYNTAX SEQUENCE OF MdlCPrgEntry
      MAX-ACCESS not-accessible
      STATUS current
	DESCRIPTION  "A table."
	::=  { cnfgMdlGen 1 }

mdlCPrgEntry OBJECT-TYPE
      SYNTAX MdlCPrgEntry
      MAX-ACCESS not-accessible
      STATUS current
	DESCRIPTION  "An entry in table."
	INDEX { mdlCCnfgIdx, mdlCSltIdx  }
      ::= { mdlCPrgTable 1}

MdlCPrgEntry ::=
      SEQUENCE {
   		mdlCCnfgIdx           Integer32,
      	mdlCSltIdx            INTEGER,
   		mdlCPrgCardType       INTEGER,
   		mdlCNoOfExternPrt     Integer32,   -- RO
   		mdlCNoOfInternPrt     Integer32,   -- RO
		mdlCWorkMode          INTEGER,
		mdlCDhcpClientEnable  INTEGER,
		mdlCRdnExists         INTEGER,	   -- RO
		mdlCInterfaces        OCTET STRING
      }

mdlCCnfgIdx OBJECT-TYPE
      SYNTAX  Integer32 (1..255)
      MAX-ACCESS  read-only
      STATUS  current
      DESCRIPTION
      "This attribute indicates the Idx of the Cnfg(1..100) being
       referred.
       Value  255 specifies the TmpCnfg "
      ::= { mdlCPrgEntry 1}
-- In phase I only the values 1 (Cnfg1) and 255 (temp) are valid.

mdlCSltIdx OBJECT-TYPE
      SYNTAX  INTEGER
       {
       psA   (1),
       psB   (2),
       clA   (3),
       clB   (4),
       io1   (5),
       io2   (6),
       io3   (7),
       io4   (8),
       io5   (9),
       io6  (10),
       io7  (11),
       io8  (12),
       io9  (13),
       io10 (14),
       io11 (15),
       io12 (16)
       }
      MAX-ACCESS  read-only
      STATUS  current
      DESCRIPTION
      "This attribute indicates a unique number of  the slot
       position where the card is inserted.
       In the ?004 Unit the entries psB(2),clB(4),io6(10)..io(16)
       are not valid."
      ::= { mdlCPrgEntry 2}

mdlCPrgCardType OBJECT-TYPE
      SYNTAX  INTEGER
       {
  --
  -- General types
  --
        unknown         (1),
        empty           (2),

  -- (3)..(7) are reserved ; they appear in the compress structure

		 acm            (9), --alarm module

  --
  -- Power Supply Modules
  --
        ps48x60W       (10),
        ps48x100W      (11),
        ps110x60W      (12),
        ps110x100W     (13),
        ps220x60W      (14),
        ps220x100W     (15),
        ps180W         (16),
		ps             (17), 

  --
  -- Cl Modules
  --
        cl1            (20),
        clEth          (21),
        cl2            (22),
		cl2Eth         (23),
        cl3            (24),
		cl3Eth         (25),
		cl1Clk         (26), --CL1 with Station Clock (for LRS102)
--
  -- Packet Cards of Megaplex
  --
        mPh1            (31),
        mPh3            (32),
        mPh1T1DSU       (33),
        mPh1T1CSU       (34),
        mPh1E1DSU       (35),
        mPh1E1LTU       (36),

  -- TDM Cards

        mtmlFT1         (37),
        mtmlFE1         (38),
		mtmlH4E1        (39),
		mtmlH4E12W      (40),
		mtmlH4T1        (41),
		mtmlH4T12W      (42),
		mtHsh4E1        (43),
		mtHsh4E12W      (44),
		mtHsh4T1        (45),
		mtHsh4T12W      (46),
		mtmlH2E1        (47),
		mtmlH2E12W      (48),
		mtmlH2T1        (49),
		mtmlH2T12W      (50),
		hsh2E1          (51),
		hsh2E12W        (52),
		hsh2T1          (53),
		hsh2T12W        (54),
		mlIp            (55),
		mtml4Ip         (56),
		ml20N1          (57),
		ml20N2          (58),

  -- Packet Cards of Megaplex

        mPl6            (60),
--      mPl3            (61),

  -- VF cards of Megaplex
        vf24T1          (62),
		vf30E1          (63),
		vf48T1          (64),
		vf60E1          (65),

 -- Vmux-2100 Main Link cards 
	    ml2E1           (68),
	    ml4E1           (69),
        ml2T1           (70),
	    ml4T1           (71),

--      mPv4            (72),

  --
  -- TDM Cards
  --
      vc16A             (73),
      vc8EandM          (74),
      vc8Fxo            (75),
      vc8Fxs            (76),
      vc16EandM         (77),
      vc16Fxo           (78),
      vc16Fxs           (79),

      vf3EandM          (80),
      vf3Fxs            (81),
      vf3Fxo            (82),

      vfPbx             (83),
      vfPbxT1           (84),
      vfPbxE1           (85),

	  mtMlE2S           (86), --Single Link
	  mtMlE2D           (87), --Dual Link 
      mtMlF2T1          (88),
      mtMlF2E1          (89),
      mtMlT1Fiber       (90),
      mtMlE1Fiber       (91),
      mtMlT1FiberFb     (92),
      mtMlE1FiberFb     (93),
      mtmlHE1           (94),
      mtmlH1E1          (95),
      mtmlHSE1          (96),
      ml20              (97),
      mtMl4T1           (98),
      mtMl4E1           (99),

      mtMl1T1DSU       (100),
      mtMl1T1CSU       (101),
      mtMl1E1DSU       (102),
      mtMl1E1LTU       (103),
      mtMl1T1DSUfb     (104),
      mtMl1T1CSUfb     (105),
      mtMl1E1DSUfb     (106),
      mtMl1E1LTUfb     (107),
      mtMl2T1          (108),
      mtMl2E1          (109),

      ls2CcittX50      (110),
      ls2CcittX58      (111),
      ls2ATandTSdm     (112),
      ls2ACcittX50     (113),
      ls2ACcittX58     (114),
      ls2AATandTSdm    (115),
      ls2A2Ts          (116),
      ls2M             (117),

      mtMlT1           (118),
      mtMlE1           (119),

      hs2              (120),
      hs3              (121),
      hsq              (122),
      hs703            (123),
      hsQM             (124),
      hsqN             (125),
      hs6              (126),
      hs12             (127),
	  hsDp             (128), 
	  hsp              (129), 

      hs4T1            (130),
      hs4E1            (131),
--    hs4              (132),
      hsEth            (133),

	  ml8T1            (134),
	  ml8E1            (135),     

  --  Vmux-2100  Voice cards 
      vc2E1            (136),
      vc4E1            (137),
      vc2T1            (138),
      vc4T1            (139),

      vc2EandM         (140),
      vc2Fxs1Plar      (141),
      vc2Fxo1          (142),
      vc2Fxs2          (143),
      vc2Fxo2          (144),
      vc2Fxs3          (145),
      vc2Fxo3          (146),
      vc26EandM        (147),
      mtvc2            (148),
      vc2R2Fxs         (149),

      hsu              (150),

      mbeA             (151),
      mbeB             (152),
      mbeU             (153),
      tre              (154),

      hsuI             (155),
      hsr              (156),
      hss              (157),
      hsu1             (158),

      ls12            (159),
      ls6             (160),
      ls6V1EandM      (161),
      ls6V1Fxo        (162),
      ls6V1Fxs        (163),
      ls6V2EandM      (164),
      ls6V2Fxo        (165),
      ls6V2Fxs        (166),
      ls6VfEandM      (167),
      ls6VfFxo        (168),
      ls6VfFxs        (169),

      vc3EandM        (170),
      vc3Fxo          (171),
      vc3Fxs          (172),

      vcPbx           (173),
      vcPbxT1         (174),
      vcPbxE1         (175),

      vc6EandM        (176),
      vc6Fxo          (177),
      vc6Fxs          (178),

      vcq             (179),

      ls6n            (180),

  --
  -- Packet Cards of Maxcess and Hybrid
  --

        -- High speed cards

        mhs1V36          (181),
        mhs1V35          (182),
        mhs1G703         (183),
        mhs1DDS          (184),
        mhs3             (185),
        mhs1X21          (186),
        mhs1V24          (187),
		mhs4             (188),
        mhsE1Hs          (189),
		mhsT1Hs          (190),
		mhsHyE1Hs        (191), -- 2 HS ports + 1 Hybrid E1 port
		mhsHyT1Hs        (192), -- 2 HS ports + 1 Hybrid T1 port
        mlfHybE1Hs       (193), -- Fiber Optic Hybrid: 2 HS + 1 Hybrid E1 port
        mlfHybT1Hs       (194), -- Fiber Optic Hybrid: 2 HS + 1 Hybrid T1 port 

        -- T1/E1 cards

        mhs2e1			 (195),
		mhs2t1           (196),
		mhsHy2e1         (197), -- 2 Hybrid E1 ports
		mhsHy2t1         (198), -- 2 Hybrid T1 ports
        mlfHybE12        (199), -- Fiber Optic Hybrid: 2 E1 ports

        -- Low speed cards

        mls6             (200),
        mls3             (201),


        -- More  T1/E1 cards
        mlHybAtmE1       (202), -- Hybrid ATM E1
        mlHybAtmT1       (203), -- Hybrid ATM T1
        mlfHybT12        (204), -- Fiber Optic Hybrid: 2 T1 ports

		--  Voice cards

        mvc8             (205), -- MVC-8 name in marketing: MVC-4N
        mvc8PbxE1        (206),
        mvc8PbxT1Dsu     (207),
        mvc8PbxT1Csu     (208),
        mvc8PbxE1Slave   (209),

  
        mvc4             (210),
        mvc4PbxE1        (211),
        mvc4PbxT1Dsu     (212),
        mvc4PbxT1Csu     (213),
        mvc4PbxE1Slave   (214),
        mvc4PbxT1Slave   (215),

        mvc8PbxT1Slave   (216),	-- MVC-8 T1 Slave is here 
        mvc8ExtAnalog    (217), -- MVC-8 with 8 External ports
		mvcE1            (218), -- 8 External ports & 30 Internals
		mvcT1            (219), -- 8 External ports & 24 Internals

		-- ISDN for Maxcess
        mhsS             (220),
        mhsU             (221),
        mhsPriE1         (222),
        mhsPriT1         (223),

        --Card of MP-2100/4
        hsEthSwitch      (224),

        -- CCS for Maxcess & MPH
        mPriE1FramerCcs  (225),
        mPriT1FramerCcs  (226),
        mpriE1SlaveCcs   (227),
        mpriT1SlaveCcs   (228),
		mDualBri         (229),

        --Voice cards for MP
        vc12EandM        (230),
        vc12Fxo          (231),
        vc12Fxs          (232),
		vc6aEandM        (233),
        vc6aFxo          (234),
        vc6aFxs          (235),
        vc6AgFxo         (236),
        vc6AgFxs         (237),
        vc6a4LB          (238),

        --Video card for MP
		vid              (239),

        --ISDN cards for MP
		hsu12            (240),
		hsu6             (241),
		hss12            (242),
		hss6             (243),

        -- MPH and MP-2100/4 cards
        hsDp3			 (244),	  
        hsDp6			 (245),	  

        -- MP-2100/4 card
        hsf1             (246),

        -- More Hybrid cards + IP cards for MPH
    	mhsHyE1          (247),   -- 1 Hybrid E1 port
		mhsHyT1          (248),   -- 1 Hybrid T1 port         
        mhsIp            (249),   -- 1 Eth  port + 1 HS port
        mlIpHs           (250),   -- 1 Eth  port + 3 HS ports
        mlHybIpE1        (251),   -- 1 Eth  port + 1 HS port + 1 E1
        mlHybIpT1        (252),   -- 1 Eth  port + 1 HS port + 1 T1

        -- VOIP cards for MPH & MX
        mvg1Lan          (253),
        mvg2Lan          (254),

        -- MP-2100/4 card
        vc4Fxs           (255),
		vc4EandM         (256),
		vc4Fxo           (257),
        hsf2             (258),

        -- More VOIP cards for MPH
        mvgSwitch4Lan    (260),

        --SHDSL cards of Megaplex
        msl4E1W2         (261),
		msl4E1W4         (262),
		msl8E1W2         (263),
        msl4E1W2Eth      (264),
		msl8E1W2Eth      (265),
		asmi54cE1AndEth  (266), -- & LRS-102 (E1 & ETH)
		asmi54cT1AndEth  (267), -- & LRS-102 (T1 & ETH)
		asmi54c          (268), -- & LRS-102 (ETH only)

        --HS cards of Megaplex
		hs6N             (271),
		hs12N            (272),
		hsNRZ            (273),

        -- Vmux 2100 Enhanced Voice Cards
	   evc2E1            (281),
	   evc4E1            (282),
	   evc2T1            (283),
	   evc4T1            (284),

       --  Vmux-2200  Voice cards 
       vc2E1Pri          (285),
       vc4E1Pri          (286),

   --  MP Voice cards
       vc4OmniEandM      (291),
       vc4OmniWestern    (292),
       
   --  MP-4100 and/or LRS-102 cards
       clx1              (301),
       clx1GbE           (302),
       clx1S155          (303),
       clx1S155GbE       (304),
       ml8T1Eth          (305),
       ml8E1Eth          (306),
	   op106cEth         (307),	--no external T1
	   op108cEth         (308),	--no external E1
	   op106cEthT1       (309), --with external T1 (used also by LRS-102)
	   op108cEthE1       (310), --with external E1 (used also by LRS-102)
	   op108cEthE1Unbal  (311),	--used only by LRS-102
	   mpw1              (312),
       
  -- VFS cards of Megaplex
        vfs24T1          (321),
		vfs30E1          (322),
		vfs48T1          (323),	 --2T1
		vfs60E1          (324)   --2E1                

-- MiniCVS cards: This is a placeholder. The following cards exist only in the mdlSInstCardType.
--        mm4E1            (325),
--        mm4T1            (326),
--        mm8E1            (327),
--        mm8T1            (328),
--        mm12E1           (329),
--        mm12T1           (330),
--        mm16E1           (331),
--        mm16T1           (332)

        }
      MAX-ACCESS  read-write
      STATUS  current
      DESCRIPTION
      "This attribute indicates the type of card assigned to the
       specific slot in the common configuration.
       This object is identical in all the configurations (1..100).
       Only the TmpCnf(255) may have different value.
       The write operation is valid only to the TmpCnfg entry."
      ::= { mdlCPrgEntry 3}

mdlCNoOfExternPrt OBJECT-TYPE
      SYNTAX  Integer32
      MAX-ACCESS  read-only
      STATUS  current
      DESCRIPTION
      "Number of external ports in the programmed card of the
       specific slot position"
      ::= { mdlCPrgEntry 4}

mdlCNoOfInternPrt OBJECT-TYPE
      SYNTAX  Integer32
      MAX-ACCESS  read-only
      STATUS  current
      DESCRIPTION
      "Number of internal ports in the programmed card of the
       specific slot position."
      ::= { mdlCPrgEntry 5}

mdlCWorkMode OBJECT-TYPE
      SYNTAX  INTEGER
       {
       notApplicable (1),
	   standAlone    (2),
	   integrated    (3)
       }
      MAX-ACCESS  read-write
      STATUS  current
      DESCRIPTION
      "Working mode of the card.
       The user may configure the card to work in a stand alone mode or integrated
       with the device.
       
	   Example for use in MHS-IP cards:

       - standAlone - in this mode, the router works so that data is received
         via the LAN (Eth) port and is transmitted via the WAN (HS) external port
         without going through the MPH device.

       - integrated - in this mode, the router works so that it is integrated in the MPH
         and routes DLCIs into the device."
      ::= { mdlCPrgEntry 6}

mdlCDhcpClientEnable OBJECT-TYPE
      SYNTAX  INTEGER
       {
       notApplicable (1),
	   disable       (2),
	   enable        (3)
       }
      MAX-ACCESS  read-write
      STATUS  current
      DESCRIPTION
      "Enable/Disable the feature of DHCP Client for the selected card."
      ::= { mdlCPrgEntry 7} 

mdlCRdnExists OBJECT-TYPE
      SYNTAX  INTEGER
       {
	   no            (2),
	   yes           (3)
       }
      MAX-ACCESS  read-only
      STATUS  current
      DESCRIPTION
      "This object indicates whether any port of the programmed card is
       configured to be part of a Redundancy/APS pair.
       If at least one port of the programmed card is configured to be
       part of a Redundancy/APS pair, the value will be 'yes'. 
       Otherwise, it will be 'no'."
      ::= { mdlCPrgEntry 8}
      
mdlCInterfaces OBJECT-TYPE
  SYNTAX      OCTET STRING
  MAX-ACCESS  read-only
  STATUS  current
  DESCRIPTION
  "Octet string which indicates 'present' interfaces in card. 
  Each '0' bit  stands for non-present interface.
  Each '1' bit stands for present interface.

  For ASMi54C card of LRS-102 and MP-4100 notPresent interfaces may be:
     - SHDSL Line ID with no wire pairs assigned to it	(does not exist in ifTable)  
     - PCS without SHDSL Line binded to it, (exist in ifTable, with 
       ifOperStatus= notPresent)
     - External DS1 when its LIU is used by an Internal DS1 of the same card
     - Internal DS1 when single bearer is not TDM.

     In each octet, MS bit represents port 1 
     and LS bit represents port 8

         MSB           LSB
          1 0 0 0 1 0 0 0 -- Example: Port # 1 and 5 are present.
     Port 1 2 3 4 5 6 7 8 
  
     1st Octet (MSB octet) represents SDHSL Lines
     2nd Octet represents PCS 
     3rd Octet represents External DS1 
     4th Octet represents Internal DS1
     5th and 6th Octets are reserved for future Internal DS1.
  
  For OP-108/106 cards of LRS-102 and MP-4100 notPresent interfaces may be:
     - External DS1 when its 'associated' Int-DS1 port is connected to another card
     - Internal DS1 when its 'associated' Ext-DS1 port is connected to another card
    (Both may be 'present' when inter-connected).
     1st Octet represents External DS1 
     2nd Octet represents Internal DS1
	 Bit representation, same as for ASMi-54C card.
  "
  ::= { mdlCPrgEntry 9 }
      
       

--
-- Compressed information.
--
-- Specially for RadView management station
--
mdlCmprTable  OBJECT-TYPE
      SYNTAX SEQUENCE OF MdlCmprEntry
      MAX-ACCESS not-accessible
      STATUS current
	DESCRIPTION  "A table."
	::=  { cmprMdlGen 1 }

mdlCmprEntry OBJECT-TYPE
      SYNTAX MdlCmprEntry
      MAX-ACCESS not-accessible
      STATUS current
	DESCRIPTION  "An entry in table."
	INDEX { mdlCmprTypIdx, mdlCmprCnfgIdx ,mdlCmprVersion,mdlCmprSltIdx }
      ::= {mdlCmprTable  1}

MdlCmprEntry ::=
      SEQUENCE {
  mdlCmprTypIdx     Integer32,
  mdlCmprCnfgIdx    Integer32,
  mdlCmprVersion    Integer32,
  mdlCmprSltIdx     INTEGER,
  mdlCmprObj        OCTET STRING
      }

mdlCmprTypIdx OBJECT-TYPE
      SYNTAX  Integer32
      MAX-ACCESS  read-only
      STATUS  current
      DESCRIPTION
      "This attribute indicates the Type of the Compressed being
       referred."
      ::= { mdlCmprEntry 1}

mdlCmprCnfgIdx OBJECT-TYPE
      SYNTAX  Integer32
      MAX-ACCESS  read-only
      STATUS  current
      DESCRIPTION
      "This attribute indicates the configuration to which the
       Compressed information is  related."
      ::= { mdlCmprEntry 2}

mdlCmprVersion OBJECT-TYPE
      SYNTAX  Integer32
      MAX-ACCESS  read-only
      STATUS  current
      DESCRIPTION
      "This attribute indicates the version of the internal format
       of the Compressed data"
      ::= { mdlCmprEntry 3}

mdlCmprSltIdx  OBJECT-TYPE
      SYNTAX  INTEGER
       {
       psA   (1),
       psB   (2),
       clA   (3),
       clB   (4),
       io1   (5),
       io2   (6),
       io3   (7),
       io4   (8),
       io5   (9),
       io6  (10),
       io7  (11),
       io8  (12),
       io9  (13),
       io10 (14),
       io11 (15),
       io12 (16)
       }
      MAX-ACCESS  read-only
      STATUS  current
      DESCRIPTION
      "This attribute indicates a unique number of  the slot
       position where the card is inserted.
       In the ?004 Unit the entries psB(2),clB(4),io6(10)..io(16)
       are not valid."
      ::= { mdlCmprEntry 4}

mdlCmprObj OBJECT-TYPE
      SYNTAX  OCTET STRING
      MAX-ACCESS  read-write
      STATUS  current
      DESCRIPTION
      "This attribute is the compressed information itself."
      ::= { mdlCmprEntry 5}

-- Compressed Alarm table at Card level
-- The only way of reading this table is by the command 'GET NEXT'

mdlAlarmsCmprTable  OBJECT-TYPE
      SYNTAX SEQUENCE OF MdlAlarmsCmprEntry
      MAX-ACCESS not-accessible
      STATUS current
	DESCRIPTION  "A table."
	::=  {cmprMdlGen 2}

mdlAlarmsCmprEntry OBJECT-TYPE
      SYNTAX MdlAlarmsCmprEntry
      MAX-ACCESS not-accessible
      STATUS current
	DESCRIPTION  "An entry in table."
	INDEX {mdlAlarmsCmprVersion,
             mdlAlarmsCmprAlarmSlot,mdlAlarmsCmprAlarmIdx}
      ::= {mdlAlarmsCmprTable  1}

MdlAlarmsCmprEntry ::=
      SEQUENCE {
     mdlAlarmsCmprVersion      Integer32,
     mdlAlarmsCmprAlarmSlot    Integer32,
     mdlAlarmsCmprAlarmIdx     Integer32,
     mdlAlarmsCmprObj          OCTET STRING
      }

mdlAlarmsCmprVersion OBJECT-TYPE
      SYNTAX  Integer32
      MAX-ACCESS  read-only
      STATUS  current
      DESCRIPTION
      "This attribute indicates the version of the internal format
       of the Compressed data"
      ::= { mdlAlarmsCmprEntry 1}

mdlAlarmsCmprAlarmSlot  OBJECT-TYPE
      SYNTAX  Integer32
      MAX-ACCESS  read-only
      STATUS  current
      DESCRIPTION
      "This attribute indicates the  desired slot position.
       In the ?004 Unit the entries PsB(2),ClB(4),io6(10)..io(16)
       are not valid."
      ::= { mdlAlarmsCmprEntry 2}

mdlAlarmsCmprAlarmIdx  OBJECT-TYPE
      SYNTAX  Integer32
      MAX-ACCESS  read-only
      STATUS  current
      DESCRIPTION
      "A unique number to identify an entry in the alarm status table
       of the agent."
      ::= { mdlAlarmsCmprEntry 3}

mdlAlarmsCmprObj OBJECT-TYPE
      SYNTAX  OCTET STRING
      MAX-ACCESS  read-write
      STATUS  current
      DESCRIPTION
      "This attribute is the compressed information itself."
      ::= { mdlAlarmsCmprEntry 4}


--
-- Wan port status general information
--
prtSInstTable  OBJECT-TYPE
      SYNTAX SEQUENCE OF PrtSInstEntry
      MAX-ACCESS not-accessible
      STATUS current
	DESCRIPTION  "A table."
	::=  { statPrtGen 1 }

prtSInstEntry OBJECT-TYPE
      SYNTAX PrtSInstEntry
      MAX-ACCESS not-accessible
      STATUS current
	DESCRIPTION  "An entry in table."
	INDEX { prtSInstSltIdx, prtSInstPrtIdx }
      ::= { prtSInstTable 1}

PrtSInstEntry ::=
      SEQUENCE {
        prtSInstSltIdx       INTEGER,
        prtSInstPrtIdx       Integer32,
        prtSInstPrtType      INTEGER,
        prtSInstIfIndex      Integer32,
        prtSActiveStatus     INTEGER,
        prtSAlrStatus        INTEGER,
        prtSMaskedAlrStat    INTEGER,
        prtSClearAlrCmd      INTEGER,
        prtSTestMask         Integer32,
--        prtSTstStatus        INTEGER,
        prtSTstCmd           INTEGER,
        prtSTstDuration      Integer32,
        prtSBertClrCmd       INTEGER,
        prtSBertTstRslt      Integer32,
        prtSInterfaceType    DisplayString,
        prtSParamStatus      OCTET STRING,	   
		prtSTestMaskXp		 OCTET STRING,
		prtSRdnStatus        INTEGER
      }

prtSInstSltIdx OBJECT-TYPE
      SYNTAX  INTEGER
       {
       clA   (3),
       clB   (4),
       io1   (5),
       io2   (6),
       io3   (7),
       io4   (8),
       io5   (9),
       io6  (10),
       io7  (11),
       io8  (12),
       io9  (13),
       io10 (14),
       io11 (15),
       io12 (16),
       notApplicable (255)
       }
      MAX-ACCESS  read-only
      STATUS  current
      DESCRIPTION
      "This attribute indicates a unique number to identify the
       slot where the card is inserted.
       In the ?004 Unit the entries io6(10)..io(16) are not valid.
       For the Vmux2100 Main Board clA  (3) is used."
      ::= { prtSInstEntry 1}

prtSInstPrtIdx OBJECT-TYPE
      SYNTAX  Integer32
      MAX-ACCESS  read-only
      STATUS  current
      DESCRIPTION
      "This attribute indicates a unique number to identify a port
       in a specific card.
       The valid ports depend on the installed card:
       the valid external ports (interfaces) are (1..mdlCNoOfExternPrt) if any,
       and the valid internal ports are (101..100+mdlCNoOfInternPrt) if any.
       Generally, for MP-2100/2200:  exPrt1 (1) .. exPrt16  (16),inPrt1(101) 
       .. inPrt48 (148)

	   For the Vmux-2100 device:
	   This index will have values of 1...4 for the physical ports & values
	   of ifIndex for the bundles.

	   For other products, see product's spec."
      ::= { prtSInstEntry 2}

prtSInstPrtType  OBJECT-TYPE
      SYNTAX  INTEGER
       {
  external      (2),
  internal      (3),
  highSpeedV35  (4),
  highSpeedV24  (5),
  highSpeedV36  (6),
  highSpeedX21  (7),
  highSpeedG703 (8),
  highSpeedDDS  (9),
  lowSpeed      (10),
  voice         (11),
  cl            (12),
  isdns         (13),
  isdnu         (14),
  ethernet      (15),
  voiceS0       (16),
  voiceU        (17),
  voiceQsigS    (18),
  voiceQsigU    (19)
       }
      MAX-ACCESS  read-only
      STATUS  current
      DESCRIPTION
       "This attribute describes the type of the designated port.
	   In MX 3000 only external & internal options are used.
	   All the other options are only for MX 30/300 which need special handling.
	   In order to support interface types in MX 3000, return an ascii string for
	   prtSInterfaceType in this table or support the general RAD value of
       physicalConnector.

       External port - is a port with  a physical connector.
       Internal port - might be of two types:
         a) A composite port which collects a few external ports
            data into a common bandwidth (usually routed through
            DS1 link)
         b) A port which gets only part of the external ports
            (usually a few DS0's)
    The following types are used when all ports are external/
    internal and the connector/interface type is necessary
    (for example, stand-alone units):
       High Speed port types
       Low  Speed port types
       Voice port types, CL port types.
       
       ISDN Voice in MX 30/300 Phase 4: voiceS0   (16), voiceU     (17) should be used.
       ISDN Voice in MX 30/300 Phase 5: voiceQsigS(18), voiceQsigU (19) should be used."
      ::= { prtSInstEntry 3}

prtSInstIfIndex  OBJECT-TYPE
      SYNTAX  Integer32
      MAX-ACCESS  read-only
      STATUS  current
      DESCRIPTION
      "This attribute indicates the  unique  interface number
       assigned to the port. The specific interface of this
       attribute is the same as the interface identified by the
       value of ifindex  in MIB-II.If there is no interface for
       the specific prtIdx the value will be '7fffffff'h."
      ::= { prtSInstEntry 4}

prtSActiveStatus   OBJECT-TYPE
      SYNTAX  INTEGER
       {
         unknown           (1),
         notUsed           (2),
         offLine           (3),
         onLine            (4),
         offLineRedundancy (5),
         onLineRedundancy  (6)
       }
      MAX-ACCESS  read-only
      STATUS  current
      DESCRIPTION
      "This attribute describes the activity status of the port.
       unknown(1) indicates that the information is not supported.
       notUsed(2) indicates that the ch is not connected according
                  to the active config.
       offLine(3) indicates that the ch is down (not working)
                  because of any problem.
       onLine(4)  indicates that the ch is up (working)
       offLineRedundancy(5) indicates that the ch is down, because
                            it is redundant port.
       onLineRedundancy(6)  indicates that the ch is up, and it is
                            the active link"
      ::= { prtSInstEntry 5}

prtSAlrStatus OBJECT-TYPE
      SYNTAX  INTEGER
       {
  off      (2),
  event    (3),
  minor    (4),
  major    (5),
  warning  (6),
  critical (7)
       }
      MAX-ACCESS  read-only
      STATUS  current
      DESCRIPTION
      "Indicates the alarm state in the port(ch) agent level.
      This attribute will be set to:
    critical(7) - when there is at least one active (state ON)
                  critical alarm,
                  otherwise it will be set to
       major(5) - when there is at least one active (state ON)
                  major alarm,
                  otherwise it will be set to
       minor(4) - if there is at least one active (state ON) minor
                  alarm,
                  otherwise it will be set to
       warning(6) - if there is at least one active (state ON)
                  warning alarm,
                  otherwise it will be set to
       event(3) - if there was at least one alarm event (including
                  state on,off events) since the last clear operation."
      ::= { prtSInstEntry 6}

prtSMaskedAlrStat OBJECT-TYPE
      SYNTAX  INTEGER
       {
  off      (2),
  event    (3),
  minor    (4),
  major    (5),
  warning  (6),
  critical (7)
       }
      MAX-ACCESS  read-only
      STATUS  current
      DESCRIPTION
      "Indicates the alarm state in the port(ch) agent level,
       including Masked alarms.
       This attribute will be set to:
    critical(7) - when there is at least one active (state ON)
                  critical alarm,
                  otherwise it will be set to
       major(5) - when there is at least one active (state ON)
                  major alarm,
                  otherwise it will be set to
       minor(4) - if there is at least one active (state ON) minor
                  alarm,
                  otherwise it will be set to
       warning(6) - if there is at least one active (state ON)
                  warning alarm,
                  otherwise it will be set to
       event(3) - if there was at least one alarm event (including
                  state on,off events) since the last clear operation."
 ::= {prtSInstEntry 7}

prtSClearAlrCmd  OBJECT-TYPE
      SYNTAX  INTEGER
       {
  off(2),
  on (3)
       }
      MAX-ACCESS  read-write
      STATUS  current
      DESCRIPTION
      "Setting this attribute to on(3) enforces a clear operation
       of the alarm status events in the given port. The clear
       operation will not be applied for masked/inverted alarms."
      ::= { prtSInstEntry 8}

prtSTestMask OBJECT-TYPE
      SYNTAX  Integer32
      MAX-ACCESS  read-only
      STATUS  current
      DESCRIPTION
      "This is a mask which indicates which tests from the
       'prtSTstCmd' list are allowed for the requested port.
       If a specific test is allowed, its respective bit
       will be SET in the mask :

         TEST                  BIT
        -----------            ---
        local-loop              1
        remote-loop             2
        loc-and-rem-main-loops  3
        remote-analog-loop      4
        remote-digital-loop     5
        rem-loop-on-ext-unit    6
        bert                    7
        tone-injection          8
        dlci local-loop         9
        all dlci local-loop    10
        dlci remote-loop       11
        all dlci remote-loop   12
        bert-and-rem-loop-on-rem-unit 13
        rem-loop-on-rem-unit   14
        block                  15
        backward-tone-inject   16
        llb                    17
        rlb                    18

        ft1Enable              21
		lbbd                   22  --for 2B+D
		lb1                    23  --for B1
		lb2                    24  --for B2
		llb-on-rem-unit        25
		bert-on-rem-unit       26
		bert-on-rem-and-llb-on-rem-unit 27
		local-and-bert-on-rem-unit 28
		local-loop-on-rem-unit 29
		localBert              30  --towards IO ports
		test-per-TS            31

        e.g : If the return value is 3 -> 0000000000000011  ->
              Bits 1 & 2 are set -> the allowed tests are :
                                           local-loop
                                           remote-loop
        "
      ::= { prtSInstEntry 9}

-- prtSTstStatus OBJECT-TYPE
--      SYNTAX  INTEGER
--          {
--        off(2),
--        on (3)
--          }
--      MAX-ACCESS  read-only
--      STATUS  current
--      DESCRIPTION
--      "This attribute will be set to on(3) when there is at least
--       one test in progress in the port, otherwise the value
--       will be off(2)."
--      ::= { prtSInstEntry 10}
--


prtSTstCmd OBJECT-TYPE
      SYNTAX  INTEGER
       {
        none                 (1),
        localLoop            (2),
        remoteLoop           (3),
        locAndRemMainLoops   (4),
        remoteAnalogLoop     (5),
        remoteDigitalLoop    (6),
        remLoopOnExtUnit     (7),
        bert                 (8),
        toneInjection        (9),
        dlciLocalLoop        (10),
        allDlciLocalLoop     (11),
        dlciRemoteLoop       (12),
        allDlciRemoteLoop    (13),
        extInitLocalLoop     (14),
        bertAndRemLoopOnRemUnit (15),
        remLoopOnRemUnit     (16),
        block                (17),
        backwardToneInject   (18),
        llb                  (19),
        rlb                  (20),
        ft1Enable            (21),
		lbbd                 (22),	--for 2B+D
		lb1                  (23),	--for B1
		lb2                  (24),	--for B2
		llbOnRemUnit         (25),
		bertOnRemUnit        (26),
		bertOnRemAndLlbOnRemUnit (27),
		localAndBertOnRemUnit(28),
		localLoopOnRemUnit   (29),
		localBert            (30),
		testPerTS            (31),
		csuLoopAndBert		 (32),
		dsuLoopAndBert		 (33),
		remoteOcuLoopAndBert (34),
		remoteCsuLoopAndBert (35),
		remoteDsuLoopAndBert (36)

       }
      MAX-ACCESS  read-write
      STATUS  current
      DESCRIPTION
      "Setting this attribute to any of the above values will
       initiate a test on the specific port if the operation is
       legal. If the operation is not legal, the mux will ignore
       the operation.
	   testPerTS(31) - when this test is selected, the selection of tests
	                   for each TS is done via the prtExPh1MlTsTest object. 
       If a test time out is needed, the test will be set with a
       default timeout of 2 minutes until the user will set the
       parameter 'prtSTstDuration' to the required time out.
       If no time out is needed , the test will be set with infinite
       timeout until the user will set the parameter
       'prtSTstDuration' to the required time out."
      ::= { prtSInstEntry 10}

prtSTstDuration OBJECT-TYPE
      SYNTAX  Integer32
      MAX-ACCESS  read-write
      STATUS  current
      DESCRIPTION
      "This attribute indicates the maximum duration of executing
      a test on the specific port. This entry applies to all the
      test operations. The resolution will be a minute, and the
      maximum duration is limited to 30 minutes.

      For Vmux devices, the values are in seconds.

      A zero  value specifies no time limitation.
      When the test isn't active, the agent initiates this object to
      2 when the duration is needed and to 0 if its not required.
      The user should set this parameter after setting the
      'prtSTstCmd' parameter."
      ::= { prtSInstEntry 11}

prtSBertClrCmd  OBJECT-TYPE
      SYNTAX  INTEGER {
      off(2),
      on (3)
      }
      MAX-ACCESS  read-write
      STATUS  current
      DESCRIPTION
      "Setting this attribute initiates bert count clear operation.
       It is valid only when bert test is active on the specific
       port."
      ::= { prtSInstEntry 12}

prtSBertTstRslt   OBJECT-TYPE
      SYNTAX  Integer32
      MAX-ACCESS  read-only
      STATUS  current
      DESCRIPTION
      "This attribute indicates the number of Bit Error Rate
       indicated during the BERT operation.
       It is valid only when bert test is active on the specific
       port."
      ::= { prtSInstEntry 13}

prtSInterfaceType OBJECT-TYPE
      SYNTAX  DisplayString (SIZE (0..255))
      MAX-ACCESS  read-only
      STATUS  current
      DESCRIPTION
      "This attribute indicates a unique HW interface type of the
       selected port."
      ::= { prtSInstEntry 14}

prtSParamStatus OBJECT-TYPE
      SYNTAX  OCTET STRING
      MAX-ACCESS  read-only
      STATUS  current
      DESCRIPTION
      "This object indicates Status of parameters specific to the
       selected port.
       - For a port that has no special status or is supported
         by prtSExHsfStatTable - 1 Octet: 00hex

       - For VC-6, VC-6A, VC-6AG, VC-6A/4LB, VC-12, VC-12/6,  external ports - 1 Octet :
         Bit 7 (MSB)..Bit 2 = 0 (NA)
         Bit 1:       Tx Signaling '1'=On ; '0'=Off
         Bit 0 (LSB): Rx Signaling '1'=On ; '0'=Off

       - For VC-2/R2(FXS) external ports - 1 Octet :
         Bit  -   7 6 5 4 3 2 1 0
                  |_| |_________|
                  Call  Call State
             Direction

         Bit 7 (MSB) and Bit 6  : Call Direction
         00 - Incoming
         01 - Outgoing
         Bit 5..Bit 0: Call State
         000000 - Idle
         000001 - Seized
         000010 - Both-Way Conflict
         000011 - Seizure Ack
         000100 - Answered
         000101 - Clear Backward
         000110 - Clear Forward
         000111 - Blocked
         001000 - Fault
         001001 - Fault 3
         001010 - Fault 4
         001011 - Fault 5
         001100 - Fault 6
         001101 - Fault 7

       - For ML-20 external port - 3 Octets :
         - 1 MS Octet will represent the Real Rate used:
               Bit    - 7 6 5 4 3 2 1 0
                        |___| |_______|
                        spare    Rate

           Valid values: 0..31, meaning 0..31x64Kbps
           Invalid values: 32..255.
         - 2 LS Octets will represent the Status of 7 Control
           Signals:
           Signal - ---  CTS  DSR  DCD   RJ   TM   DTR  RTS
           Bit   - 7 6  5 4  3 2  1 0    7 6  5 4  3 2  1 0
           Octet  -          2                     3 (LS)
           '---' will always have the value 00
           Rest of the Signals (2 bits each) can have the following
           values:
           00=NA   ;  01=unused ; 10=Off  ; 11=On

       - For ML-H/E1, ML-H/1/E1, ML-H/S/E1 internal port - 1 Octet
         Bit    - 7 6 5 4 3 2 1 0
                  |___________|
                    spare       Mode of Operation

         Mode of Operation: '1'=Central  ; '0'=Remote

       - For ACM external port - 1 Octet
         Bit    - 7 6 5 4 3 2 1 0
                  |_________|
                    spare       Alarm State

         Alarm State: according to bits 1,0:
         00=NA   ;  01=unused ; 10=Off  ; 11=On

       - For HS-U/1 external port - 1 Octet
	     Bit 7  6  5  4  3  2  1  0 LSB
             |________|  |__|  |__|
               spare     modem  sync  
               
         modem: 00 = other         sync:  00 = not sync
                01 = unknown              01 = sync
                10 = ASMi-31/2            10 = reserved
                11 = reserved             11 = reserved
		 
	   - For MTML-2/4  external ports, ML-8 externalports, ML-IP (MTML-IP) 
	     internal ports and MTML-E2 internal ports - 1 Octet :
	     Bit 7  6  5  4  3  2  1  0 LSB
                                  |
                     			 BERT State
		 BERT State (Bit 0):
		 0 = OFF (BERT is not running on this port or any of its TSs/Bits)
		 1 = ON  (BERT is running on this port OR on one of its TSs/Bits)
		 
	   - For ML-20N external ports - 4 Octets 
	     - 1 MS Octet will represent the Actual Link Rate:
               Bit    - 7 6 5 4 3 2 1 0
                        |_| |_________|
                       spare    Rate

           Valid values: 0..34, meaning: 
           0..32 = (0..32)x64Kbps
           33 = Invalid Rate
           34 = not applicable (when Rate is not Auto)
		   35 = 0 Kbps

           Invalid values: 36..255.

	     - 2 middle Octets will represent the Status of 4 Control
           Signals: 
	       - LS Octet - Bits 3-0: RTS/C (Command, for X.21 interface)
	                    Bits 7-4: DCD/I (Indication for X.21 interface) 
	       - MS Octet - Bits 3-0: DTR
	                    Bits 7-4: DSR
	       Each 4 Bits are divided as follows:
	       - 2 MS bits: DCE
	       - 2 LS bits: DTE
	       For each 2 bits (DCE/DTE): 
	       00=NA   ;  01=unused ; 10=Off  ; 11=On.

        
	     - LS Octet: (as for MTML-2):
	       Bit 7  6  5  4  3  2  1  0 LSB
                                    |
                      			 BERT State
		   BERT State (Bit 0):
		   0 = OFF (BERT is not running on this port or any of its TSs/Bits)
		   1 = ON  (BERT is running on this port OR on one of its TSs/Bits) 

	       
       - For MP-2100/2200 MSL-4/E1, MSL-8/E1 External ports - 3 Octets
         - MS octet: far-end modem channel interface
		 - Middle octet: Material (plastic/metal), far-end modem type,   
		                 synchronization with far-end modem
		 - LS octet: BERT state (at port/TS/Bit level)

         - MS octet: 0000 0000 = no interface
					 0000 0001 = db15 (X21)
					 0000 0010 = IR-IP
					 0000 0011 = IR-ETH-Q
					 0000 0100 = V35
					 0000 0101 = ETH-RJ45
					 0000 0110 = G703
					 0000 0111 = db25 (RS530)
					 0000 1000 = ETH-BNC
					 0000 1001 = E1(Balanced)
					 0000 1010 = E1(Unbalanced)
					 0000 1011 = IR-ETH-QN 
					 Rest of the combinations: reserved
   
          - Middle octet:
		             
	     Bit 7  6  5  4  3  2  1  0 LSB
             |  |___________|  |__|
    Box material     modem     sync
          
               
    Box material      modem: 00000 = other      sync:  00 = not sync
    (for ASMi-52 SA)         00001 = unknown           01 = sync
    0=metal                  00010 = reserved          10 = reserved
    1=plastic                00011 = reserved          11 = reserved
                             00100 = reserved           
                             00101 = reserved
                             00110 = ASMi-52 SA/2W/Slave
	     	   	 	    	 00111 = ASMi-52 SA/2W/Master     
							 01000 = ASMi-52/CQ card of LRS-24
							 01001 = ASMi-52/CD card of LRS-24
							 01010 = D16GSDSL card of DXC-3000
							 01011 = LRS-52
							 01100 = FCD-IP
							 01101 = FCD-IPM  
                             01110 = D8SL card of DXC-30
                             01111 = ASMi-52A
                             10000 = MP card (SHDSL)
                             10001 = ASMi-52L 
							 Rest  = reserved 

	      - LS Octet: (as for MTML-2):
	        Bit 7  6  5  4  3  2  1  0 LSB
                                     |
                      			 BERT State
		    BERT State (Bit 0):
		    0 = OFF (BERT is not running on this port or any of its TSs)
		    1 = ON  (BERT is running on this port OR on one of its TSs)

       - For MP-4100 MSL card Links - 4 Octets
         - MS octet: far-end modem DTE2 interface (same as for MP-2100 MSL cards)
		 - after MS octet: far-end modem DTE1 interface	(same as for MP-2100 MSL cards)
		 - before LS octet: Material (plastic/metal), far-end modem type,   
		                 synchronization with far-end modem	(same as for MP-2100 MSL cards)
		 - LS octet: BERT state (at port/TS/Bit level)- same as for MP-2100 MSL cards

       - For MP-4100, LRS-102 OP-108/106 Links - 3 Octets
         - MS octet: far-end PS type and state
		 - Middle octet: synchronization with far-end device
		 - LS octet: BERT state (at port/TS level) - same as for MP-2100 MSL cards

         - MS octet:
		   Bit 7  6  5  4    3  2  1  0 LSB
			   |__|  |__|    |__|  |__|
			   PS-A	 PS-A    PS-B  PS-B  
		    PS Type PS State PS Type PS State
			00=None					 00=None
			01=AC-DC				 01=OK
			10=DC					 10=Fail
			
          - Middle octet:
		             
	       Bit 7  6  5  4  3  2  1  0 LSB
                                 |__|
                                 sync:          
               					     00 = not sync
                                     01 = sync
                                     10 = reserved
                                     11 = reserved
            Rest  = reserved 			 
		    "
      ::= { prtSInstEntry 15}

prtSTestMaskXp OBJECT-TYPE
      SYNTAX  OCTET STRING
      MAX-ACCESS  read-write
      STATUS  current
      DESCRIPTION
      "This is an Expanded test mask of the prtSTestMask object.
       The prtSTestMask object reached its maximum, being an Integer with 32 bits.
       This object indicates which tests from the  'prtSTstCmdXP' list are 
       allowed for the selected port.
       If a specific test is allowed, its respective bit will be SET 
       in the mask :

         TEST                  BIT
        -----------            ---
        local-loop              1
        remote-loop             2
        loc-and-rem-main-loops  3
        remote-analog-loop      4
        remote-digital-loop     5
        rem-loop-on-ext-unit    6
        bert                    7
        tone-injection          8
        dlci local-loop         9
        all dlci local-loop    10
        dlci remote-loop       11
        all dlci remote-loop   12
        bert-and-rem-loop-on-rem-unit 13
        rem-loop-on-rem-unit   14
        block                  15
        backward-tone-inject   16
        llb                    17
        rlb                    18

        ft1Enable              21
		lbbd                   22  --for 2B+D
		lb1                    23  --for B1
		lb2                    24  --for B2
		llb-on-rem-unit        25
		bert-on-rem-unit       26
		bert-on-rem-and-llb-on-rem-unit 27
		local-and-bert-on-rem-unit 28
		local-loop-on-rem-unit 29
		localBert              30  --towards IO ports
		test-per-TS            31
		csuLoopAndBert		   32
		dsuLoopAndBert		   33
		remoteOcuLoopAndBert   34
		remoteCsuLoopAndBert   35
		remoteDsuLoopAndBert   36

        e.g : If the return value is  00000003 hex  ->
              Bits 1 & 2 are set -> the allowed tests are :
                                           local-loop
                                           remote-loop  "
      ::= { prtSInstEntry 16}

prtSRdnStatus  OBJECT-TYPE
      SYNTAX  INTEGER {
	  noRdn  (1),
      offline(2),
      online (3)
      }
      MAX-ACCESS  read-only
      STATUS  current
      DESCRIPTION
      "Redundancy Status of this port.
       noRdn - this port is not part of a Redundancy pair/group.
       offline - this port is offline from Redundancy point of view.
       online  - this port is online from Redundancy point of view."
      ::= { prtSInstEntry 17}




prtSAlrTable OBJECT-TYPE
      SYNTAX SEQUENCE OF PrtSAlrEntry
      MAX-ACCESS not-accessible
      STATUS current
      DESCRIPTION
      "The list of port agent alarms."
      ::= { statPrtGen 2 }

prtSAlrEntry OBJECT-TYPE
      SYNTAX PrtSAlrEntry
      MAX-ACCESS not-accessible
      STATUS current
	DESCRIPTION  "An entry in table."
	INDEX { prtSAlrSltIdx, prtSAlrPrtIdx, prtSAlrIdx}
      ::= { prtSAlrTable 1}

PrtSAlrEntry ::=
      SEQUENCE {
  prtSAlrSltIdx            INTEGER,
  prtSAlrPrtIdx            Integer32,
  prtSAlrIdx               Integer32,
  prtSAlrCodeDescription   DisplayString,
  prtSAlrCode              Integer32,
  prtSAlrSeverity          INTEGER,
  prtSAlrState             INTEGER,
  prtSAlrCounter           Integer32,
  prtSAlrMask              INTEGER,
  prtSAlrInvert            INTEGER,
  prtSAlrCardType          INTEGER
      }

prtSAlrIdx OBJECT-TYPE
      SYNTAX  Integer32
      MAX-ACCESS  read-only
      STATUS  current
      DESCRIPTION
      "A unique number to identify an entry in the alarm status table.
       Users should use the get next function to read this table because
       the indexes are not consecutive"
      ::= { prtSAlrEntry 1}

prtSAlrSltIdx OBJECT-TYPE
      SYNTAX  INTEGER
       {
       psA   (1),
       psB   (2),
       clA   (3),
       clB   (4),
       io1   (5),
       io2   (6),
       io3   (7),
       io4   (8),
       io5   (9),
       io6  (10),
       io7  (11),
       io8  (12),
       io9  (13),
       io10 (14),
       io11 (15),
       io12 (16),
    notApplicable (255)
       }
      MAX-ACCESS  read-only
      STATUS  current
      DESCRIPTION
      "This attribute indicates a unique identifier of  the slot
       where the card is inserted.
       In the ?004 Unit the entries PsB(2),ClB(4),io6(10)..io12(16)
       are not valid.
       For the Vmux2100 Main Board clA  (3) is used."
    ::= { prtSAlrEntry 2}

prtSAlrPrtIdx OBJECT-TYPE
      SYNTAX  Integer32
      MAX-ACCESS  read-only
      STATUS  current
      DESCRIPTION
      "This attribute indicates a unique identifier of  the port
       the alarm applies to.
       All the values are valid. No alarms exist for a port
       which does not exist.
       Valid valuesfor MP-2100/2200: exPrt1    (1) .. exPrt16  (16) ,
                     inPrt1  (101) .. inPrt48 (148),
                     IP Bundles.
       For other products, see product's spec."
    ::= { prtSAlrEntry 3}

prtSAlrCodeDescription OBJECT-TYPE
      SYNTAX  DisplayString (SIZE (0..255))
      MAX-ACCESS  read-only
      STATUS  current
      DESCRIPTION
      "This attribute is a full text description of the alarm.
       The alarm description includes the following information:
       alarm code, alarm text, alarm severity, Masked  or Inverted
       flag and counter."
       ::= { prtSAlrEntry 4}

prtSAlrCode OBJECT-TYPE
      SYNTAX  Integer32
      MAX-ACCESS  read-only
      STATUS  current
      DESCRIPTION
      "A code identifying the alarm of an entry in the alarm status
       table at port level."
      ::= { prtSAlrEntry 5 }

prtSAlrSeverity OBJECT-TYPE
      SYNTAX  INTEGER
       {
  event    (3),
  minor    (4),
  major    (5),
     warning  (6),
  critical (7)
       }
      MAX-ACCESS  read-only
      STATUS  current
      DESCRIPTION
      "The severity of the alarm."
      ::= { prtSAlrEntry 6 }

prtSAlrState  OBJECT-TYPE
      SYNTAX  INTEGER
       {
  off(2),
  on (3)
       }
      MAX-ACCESS  read-only
      STATUS  current
      DESCRIPTION
      "State of the alarm."
      ::= { prtSAlrEntry 7 }

prtSAlrCounter OBJECT-TYPE
      SYNTAX  Integer32
      MAX-ACCESS  read-only
      STATUS  current
      DESCRIPTION
      "A counter - how many times the alarm occured since last
       clear operation.
       ON and OFF Alarm will be counted separately."
      ::= { prtSAlrEntry 8 }

prtSAlrMask  OBJECT-TYPE
      SYNTAX  INTEGER
       {
       off(2),
       on (3)
       }
      MAX-ACCESS  read-only
      STATUS  current
      DESCRIPTION
      "Alarm mask : on/off."
      ::= { prtSAlrEntry 9 }

prtSAlrInvert  OBJECT-TYPE
      SYNTAX  INTEGER
       {
       off(2),
       on (3)
       }
      MAX-ACCESS  read-only
      STATUS  current
      DESCRIPTION
      "Alarm invert : on/off."
      ::= { prtSAlrEntry 10 }

prtSAlrCardType OBJECT-TYPE
   SYNTAX  INTEGER
   {
  --
  -- General types
  --		 
         unknown        (1),
         empty          (2),
  --
  -- Power Supply Modules
  --
		ps             (17), 


  --
  -- Cl Modules
  --
		cl1				(20),
		cl1Clk          (26), --CL1 with Station Clock (for LRS102)


 
  -- VF cards of Megaplex
        vf24T1          (62),
		vf30E1          (63),
		vf48T1          (64),
		vf60E1          (65),
  --
  -- TDM Cards
  --
      vc8EandM          (74),
      vc8Fxo            (75),
      vc8Fxs            (76),
      vc16EandM         (77),
      vc16Fxo           (78),
      vc16Fxs           (79),

	   ml8T1           (134),
	   ml8E1           (135),     

       hsr             (156),

       ls12            (159),

       ls6n            (180),

       hsEthSwitch     (224),

       hsu12           (240),
	   hsu6            (241),

       vc4Fxs          (255),
       vc4EandM        (256),
	   vc4Fxo          (257),

       msl4E1W2        (261),

	   msl8E1W2        (263),
       msl4E1W2Eth     (264),
	   msl8E1W2Eth     (265),
       asmi54cE1AndEth (266), -- & LRS-102 (E1 & ETH)
       asmi54cT1AndEth (267), -- & LRS-102 (T1 & ETH)
	   asmi54c         (268), -- & LRS-102 (ETH only)

 	   hs6N            (271),
	   hs12N           (272),
       
   --  MP-4100 (and LRS-102) cards
       clx1            (301),
       clx1GbE         (302),
       clx1S155        (303),
       clx1S155GbE     (304),
       ml8T1Eth        (305),
       ml8E1Eth        (306),
	   op106cEth       (307), --no external T1
	   op108cEth       (308), --no external E1
	   op106cEthT1     (309), --with external T1 (used also by LRS-102)
	   op108cEthE1     (310), --with external E1 (used also by LRS-102)
	   op108cEthE1Unbal(311), --used only by LRS-102
	   mpw1            (312),
       
  -- VFS cards of Megaplex
        vfs24T1        (321),
		vfs30E1        (322),
		vfs48T1        (323),  --2T1
		vfs60E1        (324)   --2E1                
     }
   MAX-ACCESS  read-only
   STATUS  current
   DESCRIPTION
   "This attribute indicates the type of card installed
    in the specific slot position. The enumeration is according
    to mdlSInstCardType."
    ::= { prtSAlrEntry 11 }

--
-- Statistics of Ports
--

--statisPrtGen   OBJECT IDENTIFIER ::= {statPrtGen 3}

--prtFrStatis    OBJECT IDENTIFIER ::= {statisPrtGen 1}
--prtCrStatis    OBJECT IDENTIFIER ::= {statisPrtGen 2}
--prtDlciStatis  OBJECT IDENTIFIER ::= {statisPrtGen 3}
--prtT1Statis    OBJECT IDENTIFIER ::= {statisPrtGen 4}


--prtFrStatis - Port Statistics for (FR) Frame Relay protocol

prtFrStatisTable  OBJECT-TYPE
     SYNTAX SEQUENCE OF PrtFrStatisEntry
     MAX-ACCESS not-accessible
     STATUS  current
     DESCRIPTION
      "This table is applicable only for an active port running an
       FR protocol ."
  ::= { prtFrStatis 1}

prtFrStatisEntry OBJECT-TYPE
      SYNTAX PrtFrStatisEntry
      MAX-ACCESS not-accessible
      STATUS current
	DESCRIPTION  "An entry in table."
	INDEX {prtFrStatisSltIdx, prtFrStatisPrtIdx, prtFrStatisInvIdx}
      ::= { prtFrStatisTable 1}

PrtFrStatisEntry ::=
      SEQUENCE {
      prtFrStatisSltIdx    INTEGER,
      prtFrStatisPrtIdx    INTEGER,
   prtFrStatisInvIdx    INTEGER,
      prtFrTimeElapsed     Integer32,
      prtFrRxTotalFrames   Counter32,
      prtFrTxTotalFrames   Counter32,
      prtFrRxTotalBytes    Counter32,
      prtFrTxTotalBytes    Counter32,
      prtFrRxMngFrames     Counter32,
      prtFrTxMngFrames     Counter32,
      prtFrRxDeFrames      Counter32,
      prtFrTxDeFrames      Counter32,
      prtFrRxDcrdCongDeFr  Counter32,
      prtFrTxDcrdCongDeFr  Counter32,
      prtFrRxDcrdCongAllFr Counter32,
      prtFrTxDcrdCongAllFr Counter32,
      prtFrRxFecn     Counter32,
      prtFrTxFecn     Counter32,
      prtFrRxBecn     Counter32,
      prtFrTxBecn     Counter32,
      prtFrRxBeViol     Counter32,
      prtFrTxBeViol        Counter32,
      prtFrRxBcViol     Counter32,
      prtFrTxBcViol     Counter32
      }

prtFrStatisSltIdx    OBJECT-TYPE
      SYNTAX  INTEGER
       {
       io1   (5),
       io2   (6),
       io3   (7),
       io4   (8),
       io5   (9),
       io6  (10),
       io7  (11),
       io8  (12),
       io9  (13),
       io10 (14),
       io11 (15),
       io12 (16),
       notApplicable (255)
       }
      MAX-ACCESS  read-only
      STATUS  current
      DESCRIPTION
      "This attribute indicates a unique  slot  position where
       the module is inserted.
       In the ?004 Unit the entries io6(10)..io12(16) are not valid.
       For stand-alone units this index will be notApplicable (255)."
      ::= { prtFrStatisEntry 1}

prtFrStatisPrtIdx OBJECT-TYPE
      SYNTAX  INTEGER
      {
          exPrt1  (1) ,
          exPrt2  (2) ,
          exPrt3  (3) ,
          exPrt4  (4) ,
          exPrt5  (5) ,
          exPrt6  (6)
       }
      MAX-ACCESS  read-only
      STATUS  current
      DESCRIPTION
      "This attribute indicates a unique  port number."
      ::= { prtFrStatisEntry 2}

prtFrStatisInvIdx OBJECT-TYPE
      SYNTAX  INTEGER
       {
          currentInv (1),
    last       (2)
    }
      MAX-ACCESS  read-only
      STATUS  current
      DESCRIPTION
   "The Interval of 15 min. for which the following statistics
    counters are applicable."
      ::= { prtFrStatisEntry 3}

prtFrTimeElapsed OBJECT-TYPE
      SYNTAX  Integer32 (0..899)
      MAX-ACCESS  read-only
      STATUS  current
      DESCRIPTION
      "The number of seconds that have elapsed  since the
       beginning of the current error-measurement interval.
       This object is applicable mainly for the current interval.
       For other interval:
       - if data is available: value will be 899.
       - if data is not available: value will be 0."
      ::= { prtFrStatisEntry 4 }

prtFrRxTotalFrames OBJECT-TYPE
      SYNTAX   Counter32
      MAX-ACCESS   read-only
      STATUS   current
      DESCRIPTION
      "The total number of frames received by this port during the
       selected interval."
      ::= { prtFrStatisEntry 5 }

prtFrTxTotalFrames OBJECT-TYPE
      SYNTAX   Counter32
      MAX-ACCESS   read-only
      STATUS   current
      DESCRIPTION
      "The total number of frames sent by this port during the
       selected interval."
      ::= { prtFrStatisEntry 6 }

prtFrRxTotalBytes OBJECT-TYPE
      SYNTAX   Counter32
      MAX-ACCESS   read-only
      STATUS   current
      DESCRIPTION
      "The total number of bytes received by this port during the
       selected interval."
      ::= { prtFrStatisEntry 7 }

prtFrTxTotalBytes OBJECT-TYPE
      SYNTAX   Counter32
      MAX-ACCESS   read-only
      STATUS   current
      DESCRIPTION
      "The total number of bytes sent by this port during the
       selected interval."
      ::= { prtFrStatisEntry 8 }

prtFrRxMngFrames OBJECT-TYPE
      SYNTAX   Counter32
      MAX-ACCESS   read-only
      STATUS   current
      DESCRIPTION
      "The management number of frames received by this port
       during the selected interval."
      ::= { prtFrStatisEntry 9 }

prtFrTxMngFrames OBJECT-TYPE
      SYNTAX   Counter32
      MAX-ACCESS   read-only
      STATUS   current
      DESCRIPTION
      "The management number of frames sent by this port during the
       selected interval."
      ::= { prtFrStatisEntry 10 }

prtFrRxDeFrames OBJECT-TYPE
      SYNTAX   Counter32
      MAX-ACCESS   read-only
      STATUS   current
      DESCRIPTION
      "The number of De frames received by this port during the
       selected interval."
      ::= { prtFrStatisEntry 11 }

prtFrTxDeFrames OBJECT-TYPE
      SYNTAX   Counter32
      MAX-ACCESS   read-only
      STATUS   current
      DESCRIPTION
      "The number of De frames sent by this port during the
       selected interval."
      ::= { prtFrStatisEntry 12 }

prtFrRxDcrdCongDeFr OBJECT-TYPE
      SYNTAX   Counter32
      MAX-ACCESS   read-only
      STATUS   current
      DESCRIPTION
      "The number of De frames discarded due to congestion,
       received by this port during the selected interval."
      ::= { prtFrStatisEntry 13 }

prtFrTxDcrdCongDeFr OBJECT-TYPE
      SYNTAX   Counter32
      MAX-ACCESS   read-only
      STATUS   current
      DESCRIPTION
      "The number of De frames discarded due to congestion,
       sent by this port during the selected interval."
      ::= { prtFrStatisEntry 14 }

prtFrRxDcrdCongAllFr OBJECT-TYPE
      SYNTAX   Counter32
      MAX-ACCESS   read-only
      STATUS   current
      DESCRIPTION
      "All the frames discarded due to congestion,
       received by this port during the selected interval."
      ::= { prtFrStatisEntry 15 }

prtFrTxDcrdCongAllFr OBJECT-TYPE
      SYNTAX   Counter32
      MAX-ACCESS   read-only
      STATUS   current
      DESCRIPTION
      "All the frames discarded due to congestion,
       sent by this port during the selected interval."
      ::= { prtFrStatisEntry 16 }

prtFrRxFecn OBJECT-TYPE
      SYNTAX   Counter32
      MAX-ACCESS   read-only
      STATUS   current
      DESCRIPTION
      "Number of frames received by this port during the
       selected interval, indicating forward congestion."
      ::= { prtFrStatisEntry 17 }

prtFrTxFecn OBJECT-TYPE
      SYNTAX   Counter32
      MAX-ACCESS   read-only
      STATUS   current
      DESCRIPTION
      "Number of frames sent by this port during the
       selected interval, indicating forward congestion."
      ::= { prtFrStatisEntry 18 }

prtFrRxBecn OBJECT-TYPE
      SYNTAX   Counter32
      MAX-ACCESS   read-only
      STATUS   current
      DESCRIPTION
      "Number of frames received by this port during the
       selected interval, indicating backward congestion."
      ::= { prtFrStatisEntry 19 }

prtFrTxBecn OBJECT-TYPE
      SYNTAX   Counter32
      MAX-ACCESS   read-only
      STATUS   current
      DESCRIPTION
      "Number of frames sent by this port during the
       selected interval, indicating backward congestion."
      ::= { prtFrStatisEntry 20 }

prtFrRxBeViol OBJECT-TYPE
      SYNTAX   Counter32
      MAX-ACCESS   read-only
      STATUS   current
      DESCRIPTION
      "Number of data frames received by this port during the
       selected interval, exceeding the Burst Excess value."
      ::= { prtFrStatisEntry 21 }

prtFrTxBeViol OBJECT-TYPE
      SYNTAX   Counter32
      MAX-ACCESS   read-only
      STATUS   current
      DESCRIPTION
      "Number of data frames sent by this port during the
       selected interval, exceeding the Burst Excess value."
      ::= { prtFrStatisEntry 22 }

prtFrRxBcViol OBJECT-TYPE
      SYNTAX   Counter32
      MAX-ACCESS   read-only
      STATUS   current
      DESCRIPTION
      "Number of data frames received by this port during the
       selected interval, exceeding the Burst Committed value."
      ::= { prtFrStatisEntry 23 }

prtFrTxBcViol OBJECT-TYPE
      SYNTAX   Counter32
      MAX-ACCESS   read-only
      STATUS   current
      DESCRIPTION
      "Number of data frames sent by this port during the
       selected interval, exceeding the Burst Committed value."
      ::= { prtFrStatisEntry 24 }


--prtCrStatis - Port Statistics for (CR) Cell Relay protocol

prtCrStatisTable  OBJECT-TYPE
     SYNTAX SEQUENCE OF PrtCrStatisEntry
     MAX-ACCESS not-accessible
     STATUS  current
     DESCRIPTION
      "This table is applicable only for an active port running a
       CR protocol ."
  ::= { prtCrStatis 1}

prtCrStatisEntry OBJECT-TYPE
      SYNTAX PrtCrStatisEntry
      MAX-ACCESS not-accessible
      STATUS current
	DESCRIPTION  "An entry in table."
	INDEX {prtCrStatisSltIdx, prtCrStatisPrtIdx, prtCrStatisInvIdx}
      ::= { prtCrStatisTable 1}

PrtCrStatisEntry ::=
      SEQUENCE {
      prtCrStatisSltIdx    INTEGER,
      prtCrStatisPrtIdx    INTEGER,
      prtCrStatisInvIdx    INTEGER,
      prtCrTimeElapsed     Integer32,
      prtCrRxTotalCells    Counter32,
      prtCrTxTotalCells    Counter32,
      prtCrRxDataCells     Counter32,
      prtCrTxDataCells     Counter32
      }

prtCrStatisSltIdx    OBJECT-TYPE
      SYNTAX  INTEGER
       {
       io1   (5),
       io2   (6),
       io3   (7),
       io4   (8),
       io5   (9),
       io6  (10),
       io7  (11),
       io8  (12),
       io9  (13),
       io10 (14),
       io11 (15),
       io12 (16),
       notApplicable (255)
       }
      MAX-ACCESS  read-only
      STATUS  current
      DESCRIPTION
      "This attribute indicates a unique  slot  position where
       the module is inserted.
       In the ?004 Unit the entries io6(10)..io12(16) are not valid.
       For stand-alone units this index will be notApplicable (255)."
      ::= { prtCrStatisEntry 1}

prtCrStatisPrtIdx OBJECT-TYPE
      SYNTAX  INTEGER
      {
          exPrt1  (1) ,
          exPrt2  (2) ,
          exPrt3  (3) ,
          exPrt4  (4) ,
          exPrt5  (5) ,
          exPrt6  (6)
       }
      MAX-ACCESS  read-only
      STATUS  current
      DESCRIPTION
      "This attribute indicates a unique  port number."
      ::= { prtCrStatisEntry 2}

prtCrStatisInvIdx OBJECT-TYPE
      SYNTAX  INTEGER
       {
          currentInv (1),
    last       (2)
    }
      MAX-ACCESS  read-only
      STATUS  current
      DESCRIPTION
   "The Interval of 15 min. for which the following statistics
    counters are applicable."
      ::= { prtCrStatisEntry 3}

prtCrTimeElapsed OBJECT-TYPE
      SYNTAX  Integer32 (0..899)
      MAX-ACCESS  read-only
      STATUS  current
      DESCRIPTION
      "The number of seconds that have elapsed  since the
       beginning of the current error-measurement interval.
       This object is applicable mainly for the current interval.
       For other interval:
       - if data is available: value will be 899.
       - if data is not available: value will be 0."
      ::= { prtCrStatisEntry 4 }

prtCrRxTotalCells OBJECT-TYPE
      SYNTAX   Counter32
      MAX-ACCESS   read-only
      STATUS   current
      DESCRIPTION
      "The total number of cells received by this port during the
       selected interval."
      ::= { prtCrStatisEntry 5 }

prtCrTxTotalCells OBJECT-TYPE
      SYNTAX   Counter32
      MAX-ACCESS   read-only
      STATUS   current
      DESCRIPTION
      "The total number of cells sent by this port during the
       selected interval."
      ::= { prtCrStatisEntry 6 }

prtCrRxDataCells OBJECT-TYPE
      SYNTAX   Counter32
      MAX-ACCESS   read-only
      STATUS   current
      DESCRIPTION
      "The number of Data Cells received by this port during the
       selected interval."
      ::= { prtCrStatisEntry 7 }

prtCrTxDataCells OBJECT-TYPE
      SYNTAX   Counter32
      MAX-ACCESS   read-only
      STATUS   current
      DESCRIPTION
      "The number of Data Cells sent by this port during the
       selected interval."
      ::= { prtCrStatisEntry 8 }


--prtDlciStatis - Port DLCI Statistics for FR, FR+ and CR protocol

prtDlciStatisTable  OBJECT-TYPE
     SYNTAX SEQUENCE OF PrtDlciStatisEntry
     MAX-ACCESS not-accessible
     STATUS  current
     DESCRIPTION
      "This table is applicable only for an active port running an
       FR, FR+ or CR protocol, with valid DLCIs ."
  ::= { prtDlciStatis 1}

prtDlciStatisEntry OBJECT-TYPE
      SYNTAX PrtDlciStatisEntry
      MAX-ACCESS not-accessible
      STATUS current
	DESCRIPTION  "An entry in table."
	INDEX {prtDlciSltIdx, prtDlciPrtIdx, prtDlciIdx}
      ::= { prtDlciStatisTable 1}

PrtDlciStatisEntry ::=
      SEQUENCE {
      prtDlciSltIdx          INTEGER,
      prtDlciPrtIdx          INTEGER,
      prtDlciIdx             Integer32,
      prtDlciRxDeFrames      Counter32,
      prtDlciTxDeFrames      Counter32,
      prtDlciRxDcrdCongDeFr  Counter32,
      prtDlciTxDcrdCongDeFr  Counter32,
      prtDlciRxDcrdCongAllFr Counter32,
      prtDlciTxDcrdCongAllFr Counter32,
      prtDlciTxFecn       Counter32,
      prtDlciTxBecn       Counter32,
      prtDlciRxBeViol      Counter32,
      prtDlciTxBeViol        Counter32,
      prtDlciRxBcViol      Counter32,
      prtDlciTxBcViol       Counter32
      }

prtDlciSltIdx    OBJECT-TYPE
      SYNTAX  INTEGER
       {
       io1   (5),
       io2   (6),
       io3   (7),
       io4   (8),
       io5   (9),
       io6  (10),
       io7  (11),
       io8  (12),
       io9  (13),
       io10 (14),
       io11 (15),
       io12 (16),
       notApplicable (255)
       }
      MAX-ACCESS  read-only
      STATUS  current
      DESCRIPTION
      "This attribute indicates a unique  slot  position where
       the module is inserted.
       In the ?004 Unit the entries io6(10)..io12(16) are not valid.
       For stand-alone units this index will be notApplicable (255)."
      ::= { prtDlciStatisEntry 1}

prtDlciPrtIdx OBJECT-TYPE
      SYNTAX  INTEGER
      {
          exPrt1  (1) ,
          exPrt2  (2) ,
          exPrt3  (3) ,
          exPrt4  (4) ,
          exPrt5  (5) ,
          exPrt6  (6)
       }
      MAX-ACCESS  read-only
      STATUS  current
      DESCRIPTION
      "This attribute indicates a unique  port number."
      ::= { prtDlciStatisEntry 2}

prtDlciIdx OBJECT-TYPE
      SYNTAX  Integer32 (1..991)
      MAX-ACCESS  read-only
      STATUS  current
      DESCRIPTION
      "This attribute indicates a unique DLCI index for each valid
       DLCI (16..991). "
      ::= { prtDlciStatisEntry 3}

prtDlciRxDeFrames OBJECT-TYPE
      SYNTAX   Counter32
      MAX-ACCESS   read-only
      STATUS   current
      DESCRIPTION
      "The number of De frames received by this DLCI."
      ::= { prtDlciStatisEntry 4 }

prtDlciTxDeFrames OBJECT-TYPE
      SYNTAX   Counter32
      MAX-ACCESS   read-only
      STATUS   current
      DESCRIPTION
      "The number of De frames sent by this DLCI."
      ::= { prtDlciStatisEntry 5 }

prtDlciRxDcrdCongDeFr OBJECT-TYPE
      SYNTAX   Counter32
      MAX-ACCESS   read-only
      STATUS   current
      DESCRIPTION
      "The number of De frames discarded due to congestion,
       received by this DLCI."
      ::= { prtDlciStatisEntry 6 }

prtDlciTxDcrdCongDeFr OBJECT-TYPE
      SYNTAX   Counter32
      MAX-ACCESS   read-only
      STATUS   current
      DESCRIPTION
      "The number of De frames discarded due to congestion,
       sent by this DLCI."
      ::= { prtDlciStatisEntry 7 }

prtDlciRxDcrdCongAllFr OBJECT-TYPE
      SYNTAX   Counter32
      MAX-ACCESS   read-only
      STATUS   current
      DESCRIPTION
      "All the frames discarded due to congestion,
       received by this DLCI."
      ::= { prtDlciStatisEntry 8 }

prtDlciTxDcrdCongAllFr OBJECT-TYPE
      SYNTAX   Counter32
      MAX-ACCESS   read-only
      STATUS   current
      DESCRIPTION
      "All the frames discarded due to congestion,
       sent by this DLCI."
      ::= { prtDlciStatisEntry 9 }

prtDlciTxFecn OBJECT-TYPE
      SYNTAX   Counter32
      MAX-ACCESS   read-only
      STATUS   current
      DESCRIPTION
      "Number of frames sent by this DLCI, indicating forward
       congestion."
      ::= { prtDlciStatisEntry 10 }

prtDlciTxBecn OBJECT-TYPE
      SYNTAX   Counter32
      MAX-ACCESS   read-only
      STATUS   current
      DESCRIPTION
      "Number of frames sent by this DLCI, indicating backward
       congestion."
      ::= { prtDlciStatisEntry 11 }

prtDlciRxBeViol OBJECT-TYPE
      SYNTAX   Counter32
      MAX-ACCESS   read-only
      STATUS   current
      DESCRIPTION
      "Number of data frames received by this DLCI, exceeding the
       Burst Excess value."
      ::= { prtDlciStatisEntry 12 }

prtDlciTxBeViol OBJECT-TYPE
      SYNTAX   Counter32
      MAX-ACCESS   read-only
      STATUS   current
      DESCRIPTION
      "Number of data frames sent by this DLCI, exceeding the Burst
       Excess value."
      ::= { prtDlciStatisEntry 13 }

prtDlciRxBcViol OBJECT-TYPE
      SYNTAX   Counter32
      MAX-ACCESS   read-only
      STATUS   current
      DESCRIPTION
      "Number of data frames received by this DLCI, exceeding the
       Burst Committed value."
      ::= { prtDlciStatisEntry 14 }

prtDlciTxBcViol OBJECT-TYPE
      SYNTAX   Counter32
      MAX-ACCESS   read-only
      STATUS   current
      DESCRIPTION
      "Number of data frames sent by this DLCI, exceeding the Burst
       Committed value."
      ::= { prtDlciStatisEntry 15 }


--prtT1 Last FDL Message Table - Statistics

prtT1FdlMsgTable  OBJECT-TYPE
     SYNTAX SEQUENCE OF PrtT1FdlMsgEntry
     MAX-ACCESS not-accessible
     STATUS  current
     DESCRIPTION
      "This table is applicable for a T1 interface with 'esf'
       LineType ."
  ::= { prtT1Statis 1}

prtT1FdlMsgEntry OBJECT-TYPE
      SYNTAX PrtT1FdlMsgEntry
      MAX-ACCESS not-accessible
      STATUS current
	DESCRIPTION  "An entry in table."
	INDEX {prtT1FdlMsgSltIdx, prtT1FdlMsgPrtIdx, prtT1FdlMsgFdlTxRx}
      ::= { prtT1FdlMsgTable 1}

PrtT1FdlMsgEntry ::=
      SEQUENCE {
      prtT1FdlMsgSltIdx    INTEGER,
      prtT1FdlMsgPrtIdx    INTEGER,
      prtT1FdlMsgFdlTxRx   INTEGER,
      prtT1FdlMsg          OCTET STRING
      }

prtT1FdlMsgSltIdx    OBJECT-TYPE
      SYNTAX  INTEGER
       {
       io1   (5),
       io2   (6),
       io3   (7),
       io4   (8),
       io5   (9),
       io6  (10),
       io7  (11),
       io8  (12),
       io9  (13),
       io10 (14),
       io11 (15),
       io12 (16)
       }
      MAX-ACCESS  read-only
      STATUS  current
      DESCRIPTION
      "This attribute indicates a unique  slot  position where
       the module is inserted.
       In the ?004 Unit the entries io6(10)..io12(16) are not valid."
      ::= { prtT1FdlMsgEntry 1}

prtT1FdlMsgPrtIdx OBJECT-TYPE
      SYNTAX  INTEGER
       {
       exPrt1    (1)
       }
      MAX-ACCESS  read-only
      STATUS  current
      DESCRIPTION
      "This attribute indicates a unique  port number.
       MTML-1/T1 modules have just one external interface."
      ::= { prtT1FdlMsgEntry 2}

prtT1FdlMsgFdlTxRx OBJECT-TYPE
      SYNTAX  INTEGER
       {
          tx    (1),
          rx    (2)
    }
      MAX-ACCESS  read-only
      STATUS  current
      DESCRIPTION
   "The Fdl tx/rx reference of the Fdl message."
      ::= { prtT1FdlMsgEntry 3}


prtT1FdlMsg  OBJECT-TYPE
   SYNTAX  OCTET STRING
      MAX-ACCESS  read-only
      STATUS  current
      DESCRIPTION
      "FDL message."
      ::= { prtT1FdlMsgEntry 4}

--
-- Extension of the Time Slot Config Table of ML ports
--
-- Time Slot is split to 8 Bits


prtExTsSplitTable OBJECT-TYPE
     SYNTAX SEQUENCE OF PrtExTsSplitEntry
     MAX-ACCESS not-accessible
     STATUS  current
     DESCRIPTION
      "The write operation into the Table Objects is valid only
       to the TmpCnfg entry, except prtExTsBitTest that will be
       written directly to the Active Configuration."
     ::= {cnfgPrtGen 1}

prtExTsSplitEntry OBJECT-TYPE
      SYNTAX PrtExTsSplitEntry
      MAX-ACCESS not-accessible
      STATUS current
	DESCRIPTION  "An entry in table."
	INDEX {prtExTsCnfgIdx, prtExTsSltIdx, prtExTsPrtIdx,
             prtExTsIdx, prtExTsBit}
      ::= { prtExTsSplitTable 1}

PrtExTsSplitEntry ::=
      SEQUENCE {
      prtExTsCnfgIdx        Integer32,
      prtExTsSltIdx         INTEGER,
      prtExTsPrtIdx         Integer32,
      prtExTsIdx            Integer32,
      prtExTsBit            Integer32,
      prtExTsIConSlot       INTEGER,
      prtExTsIConPrt        Integer32,
	  prtExTsBitTest        INTEGER,
	  prtExTsTxSignaling    OCTET STRING,
	  prtExTsRxSignaling    OCTET STRING,
	  prtExTsTxIoSignaling  OCTET STRING,
	  prtExTsRxIoSignaling  OCTET STRING
      }

prtExTsCnfgIdx OBJECT-TYPE
      SYNTAX  Integer32  (1..255)
      MAX-ACCESS  read-only
      STATUS  current
      DESCRIPTION
      "This attribute indicates the Idx of the Cnfg (1..100) being
       accessed.
       Idx 255 relates to the TmpCnfg. "
      ::= { prtExTsSplitEntry 1}

prtExTsSltIdx OBJECT-TYPE
      SYNTAX  INTEGER
     {
       io1   (5),
       io2   (6),
       io3   (7),
       io4   (8),
       io5   (9),
       io6  (10),
       io7  (11),
       io8  (12),
       io9  (13),
       io10 (14),
       io11 (15),
       io12 (16),
       notApplicable (255)
        }
      MAX-ACCESS  read-only
      STATUS  current
      DESCRIPTION
      "This attribute indicates a unique  slot  position where
       the card is inserted.
       In the ?004 Unit the entries io6(10)..io12(16) are not valid.
       notApplicable - for stand-alone units."
      ::= { prtExTsSplitEntry 2}

prtExTsPrtIdx OBJECT-TYPE
      SYNTAX  Integer32
--  For MP:
--    {
--      exPrt1    (1),
--     inPrt1  (101)
--     }
      MAX-ACCESS  read-only
      STATUS  current
      DESCRIPTION
      "This attribute indicates a unique  port number.
       Most ML cards have only one external interface.
       inPrt1 - for MTML-H/E1 cards.
       For other products' index see their specification."
      ::= { prtExTsSplitEntry 3}

prtExTsIdx OBJECT-TYPE
      SYNTAX  Integer32
      MAX-ACCESS  read-only
      STATUS  current
      DESCRIPTION
      "This attribute indicates a unique time slot  position.
       The valid time slots are:
       1..24 for T1 Card and
       1..31 for E1 interface.
       In G732S-E1 lines, time slot 16 is not valid for data,
       it is dedicated to multiframe synchronization bits
       and voice signaling."
      ::= { prtExTsSplitEntry 4}

prtExTsBit OBJECT-TYPE
      SYNTAX  Integer32 
      MAX-ACCESS  read-only
      STATUS  current
      DESCRIPTION
      "This attribute indicates a unique Bit within the time slot.
       The valid Bits are: 1..8.
       255=NA."
      ::= { prtExTsSplitEntry 5}

prtExTsIConSlot OBJECT-TYPE
      SYNTAX  INTEGER
       {
       noConnect (2),
          io1       (5),
          io2       (6),
          io3       (7),
          io4       (8),
          io5       (9),
          io6      (10),
          io7      (11),
          io8      (12),
          io9      (13),
          io10     (14),
          io11     (15),
          io12     (16),
    notApplicable (255)
       }
      MAX-ACCESS  read-write
      STATUS  current
      DESCRIPTION
      "This attribute indicates whether the specified time slot is
       connected/routed internally in the Agent and to which card
       it is connected.
       In the ?004 Unit the entries io6(10)..io12(16) are not valid.
       notApplicable - for stand-alone units."
      ::= {prtExTsSplitEntry 6}

prtExTsIConPrt OBJECT-TYPE
      SYNTAX  Integer32
--    For MP:
--       {
--       exPrt1    (1) ,
--       exPrt2    (2) ,
--       exPrt3    (3) ,
--       exPrt4    (4) ,
--       exPrt5    (5) ,
--       exPrt6    (6) ,
--       exPrt7    (7) ,
--       exPrt8    (8) ,
--       exPrt9    (9) ,
--       exPrt10  (10) ,
--       exPrt11  (11) ,
--       exPrt12  (12) ,
--
--        noConnect (100),
--
--       inPrt1  (101) ,
--       inPrt2  (102) ,
--       inPrt3  (103) ,
--       inPrt4  (104) ,
--       inPrt5  (105) ,
--       inPrt6  (106) ,
--       inPrt7  (107) ,
--       inPrt8  (108) ,
--       inPrt9  (109) ,
--       inPrt10 (110) ,
--    inPrt11 (111) ,
--    inPrt12 (112)
--       }
      MAX-ACCESS  read-write
      STATUS  current
      DESCRIPTION
      "This attribute indicates the internally (In Mux)
       connected/routed port.
       For other products' index see their specification."
      ::= {prtExTsSplitEntry 7}

prtExTsBitTest OBJECT-TYPE
      SYNTAX  INTEGER
     {
       none                    (1),
       remoteBert              (8),
       localBert               (30),
       notApplicable           (255)
        }
      MAX-ACCESS  read-write
      STATUS  current
      DESCRIPTION
      "This attribute indicates a test to be activated on the selected Bit.
	   It is applicable only when prtExPh1MlTsTest=split(254).
	   none - no test is applied for the selected Bit.
       notApplicable - when prtExPh1MlTsTest is NOT split(254)."
      ::= { prtExTsSplitEntry 8}

prtExTsTxSignaling OBJECT-TYPE
        SYNTAX OCTET STRING
        MAX-ACCESS read-only
        STATUS current
        DESCRIPTION
        "Link - Tx Signaling per TS, for TSs having TS Type=Voice
         (agnTsType=voice(2)). 
         It monitors what is sent to Link for the selected TS, 
         for A,B,C,D Signaling Bits.
         Bit 1= LSB
         Bit 8= MSB 
        Bit  1-2 = A Signaling Bit:  00='0'  ; 01='1' ; 10=not used ; 11=NA
        Bit  3-4 = B Signaling Bit:  00='0'  ; 01='1' ; 10=not used ; 11=NA
        Bit  5-6 = C Signaling Bit:  00='0'  ; 01='1' ; 10=not used ; 11=NA        
        Bit  7-8 = D Signaling Bit:  00='0'  ; 01='1' ; 10=not used ; 11=NA"
        ::= { prtExTsSplitEntry 9}

prtExTsRxSignaling OBJECT-TYPE
        SYNTAX OCTET STRING
        MAX-ACCESS read-only
        STATUS current
        DESCRIPTION
        "Link - Rx Signaling per TS, for TSs having TS Type=Voice
         (agnTsType=voice(2)). 
         It monitors what is received from Link for the selected TS, 
         for A,B,C,D Signaling Bits.
         Bit 1= LSB
         Bit 8= MSB 
        Bit  1-2 = A Signaling Bit:  00='0'  ; 01='1' ; 10=not used ; 11=NA
        Bit  3-4 = B Signaling Bit:  00='0'  ; 01='1' ; 10=not used ; 11=NA
        Bit  5-6 = C Signaling Bit:  00='0'  ; 01='1' ; 10=not used ; 11=NA        
        Bit  7-8 = D Signaling Bit:  00='0'  ; 01='1' ; 10=not used ; 11=NA"
        ::= { prtExTsSplitEntry 10}

prtExTsTxIoSignaling OBJECT-TYPE
        SYNTAX OCTET STRING
        MAX-ACCESS read-only
        STATUS current
        DESCRIPTION
        "IO - Tx Signaling per TS, for TSs having TS Type=Voice
         (agnTsType=voice(2)). 
         It monitors what is sent to IO port for the selected TS, 
         for A,B,C,D Signaling Bits.
         Bit 1= LSB
         Bit 8= MSB 
        Bit  1-2 = A Signaling Bit:  00='0'  ; 01='1' ; 10=not used ; 11=NA
        Bit  3-4 = B Signaling Bit:  00='0'  ; 01='1' ; 10=not used ; 11=NA
        Bit  5-6 = C Signaling Bit:  00='0'  ; 01='1' ; 10=not used ; 11=NA        
        Bit  7-8 = D Signaling Bit:  00='0'  ; 01='1' ; 10=not used ; 11=NA"
        ::= { prtExTsSplitEntry 11}

prtExTsRxIoSignaling OBJECT-TYPE
        SYNTAX OCTET STRING
        MAX-ACCESS read-only
        STATUS current
        DESCRIPTION
        "IO - Rx Signaling per TS, for TSs having TS Type=Voice
         (agnTsType=voice(2)). 
         It monitors what is received from IO port for the selected TS, 
         for A,B,C,D Signaling Bits.
         Bit 1= LSB
         Bit 8= MSB 
        Bit  1-2 = A Signaling Bit:  00='0'  ; 01='1' ; 10=not used ; 11=NA
        Bit  3-4 = B Signaling Bit:  00='0'  ; 01='1' ; 10=not used ; 11=NA
        Bit  5-6 = C Signaling Bit:  00='0'  ; 01='1' ; 10=not used ; 11=NA        
        Bit  7-8 = D Signaling Bit:  00='0'  ; 01='1' ; 10=not used ; 11=NA"
        ::= { prtExTsSplitEntry 12}


prtCnfgAgenda OBJECT IDENTIFIER ::= {cnfgPrtGen 2}

prtAgendaBehaviourTable OBJECT-TYPE
     SYNTAX SEQUENCE OF PrtAgendaBehaviourEntry
     MAX-ACCESS not-accessible
     STATUS  current
     DESCRIPTION
      "The write operation into the Table Objects is valid only
       to the TmpCnfg entry."
     ::= { prtCnfgAgenda 1}

prtAgendaBehaviourEntry OBJECT-TYPE
      SYNTAX PrtAgendaBehaviourEntry
      MAX-ACCESS not-accessible
      STATUS current
	DESCRIPTION  "An entry in table."
	INDEX {prtAgendaBehaviourCnfgIdx, prtAgendaBehaviourSltIdx,
             prtAgendaBehaviourPrtIdx }
      ::= { prtAgendaBehaviourTable 1}

PrtAgendaBehaviourEntry ::=
      SEQUENCE {
      prtAgendaBehaviourCnfgIdx Integer32,
      prtAgendaBehaviourSltIdx  Integer32,
      prtAgendaBehaviourPrtIdx  Integer32,
      prtAgendaBehaviourOnOff   INTEGER
}

prtAgendaBehaviourCnfgIdx OBJECT-TYPE
      SYNTAX  Integer32  (1..255)
      MAX-ACCESS  read-only
      STATUS  current
      DESCRIPTION
      "This attribute indicates the Idx of the Cnfg (1..100) being
       accessed.
       Idx 255 relates to the TmpCnfg. "
      ::= { prtAgendaBehaviourEntry 1}

prtAgendaBehaviourSltIdx  OBJECT-TYPE
      SYNTAX  Integer32
      MAX-ACCESS  read-only
      STATUS  current
      DESCRIPTION
      "This parameter should be:
 - slot number for MX3000
 - 255 = N/A  for MX300/30. "
      ::= { prtAgendaBehaviourEntry 2 }

prtAgendaBehaviourPrtIdx  OBJECT-TYPE
      SYNTAX  Integer32
      MAX-ACCESS  read-only
      STATUS  current
      DESCRIPTION
      "This parameter should be:
 - port number for MX300/30
 - 100 = N/A  for MX3000. "
      ::= { prtAgendaBehaviourEntry 3 }

prtAgendaBehaviourOnOff   OBJECT-TYPE
      SYNTAX  INTEGER
              {
                notApplicable(1),
                off(2),
                on (3)
              }
      MAX-ACCESS  read-write
      STATUS  current
      DESCRIPTION
      "Setting this command to on(3) enables the agenda function
       at module (3000) or port (300/30) level."
      DEFVAL { off }
      ::= { prtAgendaBehaviourEntry 4 }

prtCnfgAgendaTable OBJECT-TYPE
     SYNTAX SEQUENCE OF PrtCnfgAgendaEntry
     MAX-ACCESS not-accessible
     STATUS  current
     DESCRIPTION
      "This table allows the user to schedule the time a session
        is active per week basis."
     ::= { prtCnfgAgenda 2}

prtCnfgAgendaEntry OBJECT-TYPE
      SYNTAX PrtCnfgAgendaEntry
      MAX-ACCESS not-accessible
      STATUS current
	DESCRIPTION  "An entry in table."
	INDEX { prtCnfgAgendaCnfgIdx, prtCnfgAgendaSltIdx,
 prtCnfgAgendaPrtIdx, prtCnfgAgendaDayIdx, prtCnfgAgendaSesId }
      ::= { prtCnfgAgendaTable 1}

PrtCnfgAgendaEntry ::=
      SEQUENCE {
      prtCnfgAgendaCnfgIdx        Integer32,
      prtCnfgAgendaSltIdx         Integer32,
      prtCnfgAgendaPrtIdx         Integer32,
      prtCnfgAgendaDayIdx         INTEGER,
      prtCnfgAgendaSesId          Integer32,
      prtCnfgAgendaFrom           Integer32,
      prtCnfgAgendaTo             Integer32 
	}

prtCnfgAgendaCnfgIdx OBJECT-TYPE
      SYNTAX  Integer32  (1..255)
      MAX-ACCESS  read-only
      STATUS  current
      DESCRIPTION
      "This attribute indicates the Idx of the Cnfg (1..100) being
       accessed.
       Idx 255 relates to the TmpCnfg. "
      ::= { prtCnfgAgendaEntry 1}

prtCnfgAgendaSltIdx OBJECT-TYPE
      SYNTAX  Integer32
      MAX-ACCESS  read-only
      STATUS  current
      DESCRIPTION
      "This attribute is equal to:
 -slot number for MX3000
 -255 = N/A for MX300/30"
      ::= { prtCnfgAgendaEntry 2}

prtCnfgAgendaPrtIdx OBJECT-TYPE
      SYNTAX  Integer32
      MAX-ACCESS  read-only
      STATUS  current
      DESCRIPTION
      "This attribute is equal to:
       - port number for MX300/30
	   - port number for MX3000. For example 1-4 in MHS-4 cards.
       - 100 = N/A for MX3000 when not used."
      ::= { prtCnfgAgendaEntry 3}


prtCnfgAgendaDayIdx OBJECT-TYPE
      SYNTAX  INTEGER {
                monday   (1),
                tuesday  (2),
                wednesday(3),
                thursday (4),
                friday   (5),
                saturday (6),
                sunday   (7)
        }
      MAX-ACCESS  read-only
      STATUS  current
      DESCRIPTION
      "This attribute for which day of the week this row applies."
      ::= { prtCnfgAgendaEntry 4 }


prtCnfgAgendaSesId OBJECT-TYPE
      SYNTAX  Integer32 (1..4)
      MAX-ACCESS  read-only
      STATUS  current
      DESCRIPTION
      "The user may define 4 different active intervals per day."
      ::= { prtCnfgAgendaEntry  5 }

prtCnfgAgendaFrom OBJECT-TYPE
      SYNTAX  Integer32 (0..86400)
      MAX-ACCESS  read-write
      STATUS  current
      DESCRIPTION
      "Start from time interval in seconds."
      DEFVAL {86400}
      ::= { prtCnfgAgendaEntry 6 }

prtCnfgAgendaTo OBJECT-TYPE
      SYNTAX  Integer32 (0..86400)
      MAX-ACCESS  read-write
      STATUS  current
      DESCRIPTION
      "To time interval in seconds."
      DEFVAL {86400}
      ::= { prtCnfgAgendaEntry 7 }

-- General Port Configuration parameters

prtGenCnfgTable OBJECT-TYPE
     SYNTAX SEQUENCE OF PrtGenCnfgEntry
     MAX-ACCESS not-accessible
     STATUS  current
     DESCRIPTION
      "This table allows the user to configure general
       port parameters."
     ::= {cnfgPrtGen 3}

prtGenCnfgEntry OBJECT-TYPE
      SYNTAX PrtGenCnfgEntry
      MAX-ACCESS not-accessible
      STATUS current
	DESCRIPTION  "An entry in table."
	INDEX { prtGenCnfgIdx, prtGenCnfgSltIdx, prtGenCnfgPrtIdx }
      ::= { prtGenCnfgTable 1}

PrtGenCnfgEntry ::=
      SEQUENCE {
      prtGenCnfgIdx            Integer32,
      prtGenCnfgSltIdx         INTEGER,
      prtGenCnfgPrtIdx         Integer32,
      prtGenCnfgLinkToSlot     INTEGER,
      prtGenCnfgLinkToPort     Integer32,
	  prtGenCnfgPortId         Integer32,
	  prtGenCnfgBusConnection  INTEGER,
	  prtGenCnfgInbandMng      INTEGER,
	  prtGenCnfgInbandMngRoutProt INTEGER,
	  prtGenCnfgProtectionMode INTEGER,	 --not used
	  prtGenCnfgConnect        INTEGER,  
	  prtGenCnfgSignalingType  INTEGER  
	}

prtGenCnfgIdx OBJECT-TYPE
      SYNTAX  Integer32  (1..255)
      MAX-ACCESS  read-only
      STATUS  current
      DESCRIPTION
      "This attribute indicates the Idx of the Cnfg (1..100) being
       accessed.
       Idx 255 relates to the TmpCnfg.
       The write operation is valid only to the TmpCnfg."
      ::= { prtGenCnfgEntry 1}

prtGenCnfgSltIdx OBJECT-TYPE
      SYNTAX  INTEGER
   {   clA   (3),
	   clB   (4),
       io1   (5),
       io2   (6),
       io3   (7),
       io4   (8),
       io5   (9),
       io6  (10),
       io7  (11),
       io8  (12),
       io9  (13),
       io10 (14),
       io11 (15),
       io12 (16),
    notApplicable (255)
   }
      MAX-ACCESS  read-only
      STATUS  current
      DESCRIPTION
      "This attribute indicates a unique  slot  position where
       the card is inserted."
      ::= { prtGenCnfgEntry 2}

prtGenCnfgPrtIdx OBJECT-TYPE
      SYNTAX  Integer32
      MAX-ACCESS  read-only
      STATUS  current
      DESCRIPTION
      "This attribute indicates a unique external or internal port number.
     For MP:
     exPrt1    (1) .. exPrt16  (16) ,
     notApplicable(100),
     inPrt1  (101) .. inPrt84 (184) "
      ::= { prtGenCnfgEntry 3}

prtGenCnfgLinkToSlot OBJECT-TYPE
      SYNTAX  INTEGER
       {
       clA   (3),
       clB   (4),
       io1   (5),
       io2   (6),
       io3   (7),
       io4   (8),
       io5   (9),
       io6  (10),
       io7  (11),
       io8  (12),
       io9  (13),
       io10 (14),
       io11 (15),
       io12 (16),
    notApplicable (255)
       }
      MAX-ACCESS  read-write
      STATUS  current
      DESCRIPTION
      "This attribute indicates the slot of the ML card to which
       the IO port is mapped."
      ::= { prtGenCnfgEntry 4}

prtGenCnfgLinkToPort OBJECT-TYPE
      SYNTAX  Integer32
      MAX-ACCESS  read-write
      STATUS  current
      DESCRIPTION
      "This attribute indicates the port in the prtGenCnfgLinkToSlot of
       the ML card to which the IO port is mapped.
    For MP:
     exPrt1    (1) ,
     exPrt2    (2) ,
     exPrt3    (3) ,
     exPrt4    (4) ,
     exPrt5    (5) ,
     exPrt6    (6) ,
     exPrt7    (7) ,
     exPrt8    (8) ,
     inPrt1  (101) ,
     inPrt2  (102) ,
     inPrt3  (103) ,
     inPrt4  (104) ,
	 inPrt5  (105) ,
     inPrt6  (106) ,
     inPrt7  (107) ,
     inPrt8  (108) ,
     inPrt9  (109),
     inPrt10 (110),
     inPrt11 (111),
     inPrt12 (112),
     inPrt13 (113),
     inPrt14 (114),
     inPrt15 (115),
     inPrt16 (116),
     inPrt17 (117),
     inPrt18 (118),
     inPrt19 (119),
     inPrt20 (120),
     inPrt21 (121),
     inPrt22 (122),
     inPrt23 (123),
     inPrt24 (124),
     inPrt25 (125),
     inPrt26 (126),
     inPrt27 (127),
     inPrt28 (128),
     inPrt29 (129),
     inPrt30 (130),
     inPrt31 (131),
     inPrt32 (132),
     inPrt33 (133),
     inPrt34 (134),
     inPrt35 (135),
     inPrt36 (136),
     inPrt37 (137),
     inPrt38 (138),
     inPrt39 (139),
     inPrt40 (140),
     inPrt41 (141),
     inPrt42 (142),
     inPrt43 (143),
     inPrt44 (144),
     inPrt45 (145),
     inPrt46 (146),
     inPrt47 (147),
     inPrt48 (148),
     inPrt49 (149),
     inPrt50 (150),
     inPrt51 (151),
     inPrt52 (152),
     inPrt53 (153),
     inPrt54 (154),
     inPrt55 (155),
     inPrt56 (156),
     inPrt57 (157),
     inPrt58 (158),
     inPrt59 (159),
     inPrt60 (160),
     inPrt61 (161),
     inPrt62 (162),
     inPrt63 (163),
     inPrt64 (164),
     inPrt65 (165),
     inPrt66 (166),
     inPrt67 (167),
     inPrt68 (168),
     inPrt69 (169),
     inPrt70 (170),
     inPrt71 (171),
     inPrt72 (172),
     inPrt73 (173),
     inPrt74 (174),
     inPrt75 (175),
     inPrt76 (176),
     inPrt77 (177),
     inPrt78 (178),
     inPrt79 (179),
     inPrt80 (180),
     inPrt81 (181),
     inPrt82 (182),
     inPrt83 (183),
     inPrt84 (184),
     notApplicable (255) "
      ::= { prtGenCnfgEntry 5}

prtGenCnfgPortId OBJECT-TYPE
      SYNTAX  Integer32 (0..16777215)
      MAX-ACCESS  read-write
      STATUS  current
      DESCRIPTION
      "IO Port Id for V5.1 use.
       This object is applicable only for part of the PSTN and ISDN IO ports.       
       Generally, 0 is a valid value.
       Nevertheless, for ports that do not support this object, the value
       will be: notApplicable= 0"
      ::= { prtGenCnfgEntry 6}

prtGenCnfgBusConnection OBJECT-TYPE
      SYNTAX  INTEGER
       {
       notApplicable (1),
       partial       (2),
       full          (3),
	   partialCD     (4)
       }
      MAX-ACCESS  read-write
      STATUS  current
      DESCRIPTION
      "This object indicates the support of the card regarding Bus Connection.
	   Same value for all ports of the card.
       partial = 2 Buses (AB)
       full    = 4 Buses (ABCD)
	   partial CD = 2 Buses CD
       Actually the support depends on the card's HW. But, since CL has to assign
       data on Buses even when the card is not installed, this object has to be 
       configured.
       If the actual card installed will not match the value configured, an Alarm
       will be issued."
      ::= { prtGenCnfgEntry 7}

prtGenCnfgInbandMng  OBJECT-TYPE
      SYNTAX  INTEGER
       {
       notApplicable(1),
       off (2),
       on  (3)
       }
      MAX-ACCESS  read-write
      STATUS  current
      DESCRIPTION
      "This object indicates whether Inband Management is used over the
       link."
      ::= {prtGenCnfgEntry 8}

prtGenCnfgInbandMngRoutProt  OBJECT-TYPE
      SYNTAX  INTEGER
       {
      none           (1),
      rip2           (2),
      proprietaryRip (3),
	  notApplicable  (255)
       }
      MAX-ACCESS  read-write
      STATUS  current
      DESCRIPTION
      "This object indicates the Inband Mng Routing Protocol of
       the port."
      ::= {prtGenCnfgEntry 9}

prtGenCnfgProtectionMode  OBJECT-TYPE
      SYNTAX  INTEGER
       {
      notApplicable (1),
      secondary     (2),
      primary       (3)
       }
      MAX-ACCESS  read-write
      STATUS  current
      DESCRIPTION
      "This object indicates the Protection Mode of the port.
       notApplicable- when Bus Protection Point=No.
       For VC-4/Omni card this object is supported RO."
      ::= {prtGenCnfgEntry 10}

prtGenCnfgConnect  OBJECT-TYPE
      SYNTAX  INTEGER
       {
      no        (2),
      yes       (3)
       }
      MAX-ACCESS  read-write
      STATUS  current
      DESCRIPTION
      "This object indicates whether the port should be considered in
       any of the mux  algorithms."
      ::= {prtGenCnfgEntry 11}
      
prtGenCnfgSignalingType  OBJECT-TYPE
      SYNTAX  INTEGER
       {
      legacy       (3),
 	  abcd         (4),
	  none         (5) 
       }
      MAX-ACCESS  read-write
      STATUS  current
      DESCRIPTION
      "This object selects the Type of Signaling used by the port."
      ::= {prtGenCnfgEntry 12} 
       

--
-- Compressed information.
--
-- Specially for RadView management station
--
prtCmprTable  OBJECT-TYPE
      SYNTAX SEQUENCE OF PrtCmprEntry
      MAX-ACCESS not-accessible
      STATUS current
	DESCRIPTION  "A table."
	::=  { cmprPrtGen 1 }

prtCmprEntry OBJECT-TYPE
      SYNTAX PrtCmprEntry
      MAX-ACCESS not-accessible
      STATUS current
	DESCRIPTION  "An entry in table."
	INDEX {prtCmprTypIdx, prtCmprCnfgIdx,prtCmprVersion,prtCmprSltIdx,prtCmprPrtIdx}
      ::= {prtCmprTable  1}

PrtCmprEntry ::=
      SEQUENCE {
     prtCmprTypIdx       Integer32,
     prtCmprCnfgIdx      Integer32,
     prtCmprVersion      Integer32,
     prtCmprSltIdx       INTEGER,
     prtCmprPrtIdx       Integer32,
     prtCmprObj          OCTET STRING,
	 prtCmprStatisticObj OCTET STRING
      }

prtCmprTypIdx OBJECT-TYPE
      SYNTAX  Integer32
      MAX-ACCESS  read-only
      STATUS  current
      DESCRIPTION
      "This attribute indicates the Type of the Compressed being
       referred."
      ::= { prtCmprEntry 1}

prtCmprCnfgIdx OBJECT-TYPE
      SYNTAX  Integer32
      MAX-ACCESS  read-only
      STATUS  current
      DESCRIPTION
      "This attribute indicates the configuration to which the
       Compressed information is  related."
      ::= { prtCmprEntry 2}

prtCmprVersion OBJECT-TYPE
      SYNTAX  Integer32
      MAX-ACCESS  read-only
      STATUS  current
      DESCRIPTION
      "This attribute indicates the version of the internal format of
       the Compressed data"
      ::= { prtCmprEntry 3}

prtCmprSltIdx  OBJECT-TYPE
      SYNTAX  INTEGER
       {
       psA   (1),
       psB   (2),
       clA   (3),
       clB   (4),
       io1   (5),
       io2   (6),
       io3   (7),
       io4   (8),
       io5   (9),
       io6  (10),
       io7  (11),
       io8  (12),
       io9  (13),
       io10 (14),
       io11 (15),
       io12 (16),
    notApplicable (255)
       }
      MAX-ACCESS  read-only
      STATUS  current
      DESCRIPTION
      "This attribute indicates a unique number of the slot position
       where the card is inserted.
       In the ?004 Unit the entries psB(2),clB(4),io6(10)..io(16)
       are not valid."
      ::= { prtCmprEntry 4}

prtCmprPrtIdx  OBJECT-TYPE
      SYNTAX  Integer32
      MAX-ACCESS  read-only
      STATUS  current
      DESCRIPTION
      "This attribute indicates a unique identifier of  the port
       the compressed information relates to.
       Valid values: exPrt1    (1) .. exPrt16  (16) ,
                     inPrt1  (101) .. inPrt48 (148)."
      ::= { prtCmprEntry 5}

prtCmprObj OBJECT-TYPE
      SYNTAX  OCTET STRING
      MAX-ACCESS  read-write
      STATUS  current
      DESCRIPTION
      "This attribute is the compressed information itself."
      ::= { prtCmprEntry 6}

prtCmprStatisticObj OBJECT-TYPE
      SYNTAX  OCTET STRING
      MAX-ACCESS  read-only
      STATUS  current
      DESCRIPTION
      "This attribute is the compressed statistics information itself."
      ::= { prtCmprEntry 7}


-- Compressed Dlci table in the Port level
-- The only way of reading this table is by the command 'GET NEXT'

prtDlciCmprTable  OBJECT-TYPE
      SYNTAX SEQUENCE OF PrtDlciCmprEntry
      MAX-ACCESS not-accessible
      STATUS current
	DESCRIPTION  "A table."
	::=  { cmprPrtGen 2 }

prtDlciCmprEntry OBJECT-TYPE
      SYNTAX PrtDlciCmprEntry
      MAX-ACCESS not-accessible
      STATUS current
	DESCRIPTION  "An entry in table."
	INDEX {prtDlciCmprCnfgIdx,prtDlciCmprVersion,
             prtDlciCmprSltIdx,prtDlciCmprPrtIdx,prtDlciCmprDlciIdx}
      ::= {prtDlciCmprTable  1}

PrtDlciCmprEntry ::=
      SEQUENCE {
     prtDlciCmprCnfgIdx       Integer32,
     prtDlciCmprVersion    Integer32,
     prtDlciCmprSltIdx    INTEGER,
     prtDlciCmprPrtIdx    INTEGER,
     prtDlciCmprDlciIdx       Integer32,
     prtDlciCmprObj          OCTET STRING
      }

prtDlciCmprCnfgIdx OBJECT-TYPE
      SYNTAX  Integer32
      MAX-ACCESS  read-only
      STATUS  current
      DESCRIPTION
      "This attribute indicates the configuration to which the
       Compressed information is  related."
      ::= { prtDlciCmprEntry 1}

prtDlciCmprVersion OBJECT-TYPE
      SYNTAX  Integer32
      MAX-ACCESS  read-only
      STATUS  current
      DESCRIPTION
      "This attribute indicates the version of the internal format of
       the Compressed data"
      ::= { prtDlciCmprEntry 2}

prtDlciCmprSltIdx  OBJECT-TYPE
     SYNTAX  INTEGER
         {
         io1   (5),
         io2   (6),
         io3   (7),
         io4   (8),
         io5   (9),
         io6  (10),
         io7  (11),
         io8  (12),
         io9  (13),
         io10 (14),
         io11 (15),
         io12 (16),
      notApplicable (255)
         }
     MAX-ACCESS  read-only
     STATUS  current
     DESCRIPTION
     "This attribute indicates a unique number of the slot position
      where the module is inserted.
      In the ?004 Unit the entries psB(2),clB(4),io6(10)..io(16)
      are not valid."
     ::= { prtDlciCmprEntry 3}

prtDlciCmprPrtIdx  OBJECT-TYPE
     SYNTAX  INTEGER
     {
    exPrt1    (1) ,
    exPrt2    (2) ,
    exPrt3    (3) ,
    exPrt4    (4) ,
    exPrt5    (5) ,
    exPrt6    (6) ,
    exPrt7    (7) ,
    exPrt8    (8) ,
    exPrt9    (9) ,
    exPrt10  (10) ,
    inPrt1  (101) ,
    inPrt2  (102) ,
    inPrt3  (103) ,
    inPrt4  (104) ,
    inPrt5  (105) ,
    inPrt6  (106) ,
    inPrt7  (107) ,
    inPrt8  (108) ,
    inPrt9  (109) ,
    inPrt10 (110) ,
 inPrt11 (111) ,
 inPrt12 (112)
     }
     MAX-ACCESS  read-only
     STATUS  current
     DESCRIPTION
     "This attribute indicates a unique identifier of  the port
      the compressed information relates to.
      All the values are valid."
     ::= { prtDlciCmprEntry 4}

prtDlciCmprDlciIdx  OBJECT-TYPE
      SYNTAX  Integer32
      MAX-ACCESS  read-only
      STATUS  current
      DESCRIPTION
      "This attribute indicates a unique identifier of  the Dlci
       the compressed information relates to.
       The values are between 16 - 991."
      ::= { prtDlciCmprEntry 5}

prtDlciCmprObj OBJECT-TYPE
      SYNTAX  OCTET STRING
      MAX-ACCESS  read-write
      STATUS  current
      DESCRIPTION
      "This attribute is the compressed information itself."
      ::= { prtDlciCmprEntry 6}


-- Compressed Alarm table in the Port level
-- The only way of reading this table is by the command 'GET NEXT'

prtAlarmsCmprTable  OBJECT-TYPE
      SYNTAX SEQUENCE OF PrtAlarmsCmprEntry
      MAX-ACCESS not-accessible
      STATUS current
	DESCRIPTION  "A table."
	::=  {cmprPrtGen 3}

prtAlarmsCmprEntry OBJECT-TYPE
      SYNTAX PrtAlarmsCmprEntry
      MAX-ACCESS not-accessible
      STATUS current
	DESCRIPTION  "An entry in table."
	INDEX {prtAlarmsCmprVersion,prtAlarmsCmprAlarmSlot,
             prtAlarmsCmprAlarmPort,prtAlarmsCmprAlarmIdx}
      ::= {prtAlarmsCmprTable  1}

PrtAlarmsCmprEntry ::=
      SEQUENCE {
     prtAlarmsCmprVersion      Integer32,
     prtAlarmsCmprAlarmSlot    Integer32,
     prtAlarmsCmprAlarmPort    Integer32,
     prtAlarmsCmprAlarmIdx     Integer32,
     prtAlarmsCmprObj          OCTET STRING
      }

prtAlarmsCmprVersion OBJECT-TYPE
      SYNTAX  Integer32
      MAX-ACCESS  read-only
      STATUS  current
      DESCRIPTION
      "This attribute indicates the version of the internal format of
       the Compressed data"
      ::= { prtAlarmsCmprEntry 1}

prtAlarmsCmprAlarmSlot  OBJECT-TYPE
      SYNTAX  Integer32
      MAX-ACCESS  read-only
      STATUS  current
      DESCRIPTION
      "This attribute indicates the  desired slot position.
       In the ?004 Unit the entries PsB(2),ClB(4),io6(10)..io(16)
       are not valid.
       For Stand-alone units, notApplicable(255) will appear."
      ::= { prtAlarmsCmprEntry 2}

prtAlarmsCmprAlarmPort  OBJECT-TYPE
      SYNTAX  Integer32
      MAX-ACCESS  read-only
      STATUS  current
      DESCRIPTION
      "This attribute indicates a unique identifier of  the port
       the alarm applies to.
       All the values are valid. No alarms exist for a non-existing
       port. IP Bundles are considered a port too, for this matter."
      ::= { prtAlarmsCmprEntry 3}

prtAlarmsCmprAlarmIdx  OBJECT-TYPE
      SYNTAX  Integer32
      MAX-ACCESS  read-only
      STATUS  current
      DESCRIPTION
      "A unique number to identify an entry in the alarm status table
       of the agent."
      ::= { prtAlarmsCmprEntry 4}

prtAlarmsCmprObj OBJECT-TYPE
      SYNTAX  OCTET STRING
      MAX-ACCESS  read-only
      STATUS  current
      DESCRIPTION
      "This attribute is the compressed information itself."
      ::= { prtAlarmsCmprEntry 5}


--
-- Specific port status for each module Type
-- *****************************************
--

-- Megaplex?000/?004 port specific status for HS(TDM) modules
-- HS-2,HS-3,HS-Q, HS-6, HS-12
prtSExHsfStatTable OBJECT-TYPE
      SYNTAX SEQUENCE OF PrtSExHsfStatEntry
      MAX-ACCESS not-accessible
      STATUS current
	DESCRIPTION  "A table."
	::=  {statPrtMux 6}

prtSExHsfStatEntry OBJECT-TYPE
      SYNTAX PrtSExHsfStatEntry
      MAX-ACCESS not-accessible
      STATUS current
	DESCRIPTION  "An entry in table."
	INDEX {prtSExHsfSltIdx, prtSExHsfPrtIdx }
      ::= {prtSExHsfStatTable 1}

PrtSExHsfStatEntry ::=
      SEQUENCE {
      prtSExHsfSltIdx           INTEGER,
      prtSExHsfPrtIdx           INTEGER,
      prtSExHsfInterfaceTyp     INTEGER,
      prtSExHsfRts              INTEGER
      }


prtSExHsfSltIdx OBJECT-TYPE
      SYNTAX  INTEGER
        {
       io1   (5),
       io2   (6),
       io3   (7),
       io4   (8),
       io5   (9),
       io6  (10),
       io7  (11),
       io8  (12),
       io9  (13),
       io10 (14),
       io11 (15),
       io12 (16)
     }
      MAX-ACCESS  read-only
      STATUS  current
      DESCRIPTION
      "This attribute indicates a unique  slot  position where
       the card is inserted.
       In the ?004 Unit the entries io6(10)..io16) are not valid."
      ::= { prtSExHsfStatEntry 1}

prtSExHsfPrtIdx OBJECT-TYPE
      SYNTAX  INTEGER
      {
      exPrt1    (1) ,
      exPrt2    (2) ,
      exPrt3    (3) ,
      exPrt4    (4) ,
      exPrt5    (5) ,
      exPrt6    (6) ,
      exPrt7    (7) ,
      exPrt8    (8) ,
      exPrt9    (9) ,
      exPrt10  (10) ,
      exPrt11  (11) ,
      exPrt12  (12)
      }
      MAX-ACCESS  read-only
      STATUS  current
      DESCRIPTION
      "This attribute indicates a unique  port number. "
      ::= { prtSExHsfStatEntry 2}

prtSExHsfInterfaceTyp OBJECT-TYPE
      SYNTAX  INTEGER
        {
         unknown     (1),
         v35         (2),
         rs422       (3)
     }
      MAX-ACCESS  read-only
      STATUS  current
      DESCRIPTION
      "This attribute indicates a unique interface type of a
       selected port."
      ::= { prtSExHsfStatEntry 3}

prtSExHsfRts OBJECT-TYPE
      SYNTAX  INTEGER
        {
         unknown     (1),
         notActive   (2),
         active      (3)
     }
      MAX-ACCESS  read-only
      STATUS  current
      DESCRIPTION
      "This attribute indicates a unique  RTS control signal state."
      ::= { prtSExHsfStatEntry 4}



-- ISDN Port Status

prtIsdnStatusTable OBJECT-TYPE
       SYNTAX SEQUENCE OF PrtIsdnStatusEntry
       MAX-ACCESS not-accessible
       STATUS current
       DESCRIPTION
          "This table contains ISDN Statistics parameters that do not appear
           in the standard MIBs or for agents that don't support the standard Index
           of Call Set Up Time."
       ::= { statPrtMux 16 }
			  
prtIsdnStatusEntry OBJECT-TYPE
       SYNTAX  PrtIsdnStatusEntry
       MAX-ACCESS  not-accessible
       STATUS  current
       DESCRIPTION
           "Entries for ISDN Statistics parameters that do not appear in the standard MIBs
            or for agents that don't support the standard Index of Call Set Up Time."
       INDEX { ifIndex }
       ::= { prtIsdnStatusTable 1 }


PrtIsdnStatusEntry ::=
       SEQUENCE {
              prtIsdnStatusDspMode            INTEGER,
              prtIsdnStatusCallState          INTEGER,
			  prtIsdnStatusCallingNumber      DisplayString,
			  prtIsdnStatusCalledNumber       DisplayString,
			  prtIsdnStatusCalledIP           IpAddress,
			  prtIsdnStatusCallDirection      INTEGER
       }

prtIsdnStatusDspMode OBJECT-TYPE
       SYNTAX INTEGER
       {
          voice (2),
          idle  (3),
          fax   (4),
		  vbd   (5)
       }
       MAX-ACCESS read-only
       STATUS current
       DESCRIPTION
           "The DSP can be in one of the following Modes:
            Voice, Idle, Fax, Voice Band Data (VBD)- Modem."
       ::= { prtIsdnStatusEntry 1 }	

prtIsdnStatusCallState OBJECT-TYPE
       SYNTAX INTEGER
       {
          present            (2),
          overlapReceive     (3),
          incoming           (4),
		  receive            (5),
		  initiated          (6),
		  overlapSend        (7),
		  outGoingProceed    (8),
		  callDeliver        (9),
		  active             (10),
		  disconnectIndicate (11),
		  releaseRequest     (12),
		  disconnectReq      (13),
		  notActive          (14)
       }
       MAX-ACCESS read-only
       STATUS current
       DESCRIPTION
           "The state that the current call is in."
       ::= { prtIsdnStatusEntry 2 }

prtIsdnStatusCallingNumber OBJECT-TYPE
       SYNTAX DisplayString
       MAX-ACCESS read-only
       STATUS current
       DESCRIPTION
           "This is the local Number (ISDN Address) associated with this entry."
       ::= { prtIsdnStatusEntry 3 }

prtIsdnStatusCalledNumber OBJECT-TYPE
       SYNTAX DisplayString
       MAX-ACCESS read-only
       STATUS current
       DESCRIPTION
           "This is the remote Number (ISDN Address) associated with this entry."
       ::= { prtIsdnStatusEntry 4 }

prtIsdnStatusCalledIP OBJECT-TYPE
       SYNTAX IpAddress
       MAX-ACCESS read-only
       STATUS current
       DESCRIPTION
           "This is the remote IP Address associated with this entry."
       ::= { prtIsdnStatusEntry 5 }

prtIsdnStatusCallDirection OBJECT-TYPE
       SYNTAX INTEGER
       {
          notApplicable      (1),
          incoming           (2),
          outgoing           (3)
        }
       MAX-ACCESS read-only
       STATUS current
       DESCRIPTION
       "Attribute indicating the Direction of the Call.
        The value of notApplicable will be used for example when
        prtIsdnStatusCallState = notActive(14)."
       ::= { prtIsdnStatusEntry 6 }


cnfgMdlMux         OBJECT IDENTIFIER ::= {mdlMux 1}
mdlPbxFramerCnfg   OBJECT IDENTIFIER ::= {cnfgMdlMux 1}

mdlPbxFramerCnfgTable   OBJECT-TYPE
        SYNTAX SEQUENCE OF MdlPbxFramerCnfgEntry
        MAX-ACCESS not-accessible
        STATUS current
        DESCRIPTION
        "This table contains parameters relevant to a module belonging to
         a digital voice system, except mdlPbxFraEnhEcho which is relevant
         also for analog cards."
::= {mdlPbxFramerCnfg 1}

mdlPbxFramerCnfgEntry  OBJECT-TYPE
        SYNTAX MdlPbxFramerCnfgEntry
        MAX-ACCESS not-accessible
        STATUS current
	DESCRIPTION  "An entry in table."
	INDEX { mdlPbxFraCnfgIdx, mdlPbxFraSltIdx }
        ::=  {mdlPbxFramerCnfgTable 1}

MdlPbxFramerCnfgEntry ::=
        SEQUENCE {
                mdlPbxFraCnfgIdx Integer32,
                mdlPbxFraSltIdx  INTEGER,
                mdlPbxFraEnhEcho INTEGER,
                mdlPbxFraTSGroupAss INTEGER,
                mdlPbxFraSignalMode INTEGER,
                mdlPbxFraSignalVector OCTET STRING,
                mdlPbxFraSignalMask   OCTET STRING,
	            mdlPbxFraFramerSlot INTEGER,
				mdlPbxFraSignaling  INTEGER,
				mdlPbxFraTransSigTs Integer32 
	}

mdlPbxFraCnfgIdx OBJECT-TYPE
SYNTAX Integer32
        MAX-ACCESS read-only
        STATUS current
        DESCRIPTION
      "This attribute indicates the Idx of the Cnfg (1..100) being
       accessed.
       Idx 255 relates to the TmpCnfg. "
--        DEFVAL {1}
        ::= { mdlPbxFramerCnfgEntry 1}

mdlPbxFraSltIdx OBJECT-TYPE
        SYNTAX INTEGER{ io1(5), io2(6), io3(7), io4(8), io5(9),
                        io6(10), io7(11), io8(12), io9(13), io10(14),
                        io11(15), io12(16) }
        MAX-ACCESS read-only
        STATUS current
        DESCRIPTION
        "The slot relevant to this module."
        ::= { mdlPbxFramerCnfgEntry 2}

mdlPbxFraEnhEcho OBJECT-TYPE
 SYNTAX INTEGER     { notApplicable(1) ,
   disabled(2),
   ms16(3),
   ms32(4)
    }
        MAX-ACCESS read-write
        STATUS current
        DESCRIPTION
        "Refers to external ports of an analogue module
        and to the internal ports of the other mvc4 types
        of modules.
        ms16(3) means that the four voice ports have enhanced
                echo of 16ms.
        ms32(4) means that the two first ports have enhanced
                echo of 32 ms while the last two ports have no
                enhanced echo."
        ::= { mdlPbxFramerCnfgEntry 3}

mdlPbxFraTSGroupAss OBJECT-TYPE
        SYNTAX INTEGER{ group1(1), group2(2), group3(3), group4(4),
                        group5(5), group6(6), group7(7), group8(8),
                        notApplicable(255) }
        MAX-ACCESS read-write
        STATUS current
        DESCRIPTION
        "In case of T1 modules:
        group1=(1,2,3,4), ...., group6=(21,22,23,24)
        while in case of E1 modules:
		   - If prtExPh1MlLineType=g732sE1 or g732sE1CRC:
             group1=(1,2,3,4),..,group4=(13,14,15,17),
             group5=(18,19,20,21),...,group7=(26,27,28,29)
             group8=(30,31).
		   - If prtExPh1MlLineType=g732nE1 or g732nE1CRC:
             group1=(1,2,3,4),..,group4=(13,14,15,16),
             group5=(17,18,19,20),...,group7=(25,26,27,28)
             group8=(29,30,31)."
        ::= { mdlPbxFramerCnfgEntry 4}

mdlPbxFraSignalMode OBJECT-TYPE
        SYNTAX INTEGER { notApplicable(1),
			tieTrunk(2),
			tieInvert(3),
			casTrans(4),
            userDefined(5),
			ccsTrans(6),
			noSignaling(7)
			}
        MAX-ACCESS read-write
        STATUS current
        DESCRIPTION
        "Refers to the signaling mode of the Framer module.
         tieTrunk(2), tieInvert(3), casTrans(4) are standard
        coding of the signaling protocol.

        casTrans(4) is Channel Associated Signaling (the signaling is within the
        channels time slot).
		ccsTrans(6) is Transparent Common Channel Signaling (the signaling is not within
		the channels time slot - a TS for signaling is used).

        userDefined(5) allows the user to define the signaling
        protocol he wants. In this case, the next two MIB fields
        are relevant."
        DEFVAL { casTrans }
        ::= { mdlPbxFramerCnfgEntry 5}

mdlPbxFraSignalVector OBJECT-TYPE
        SYNTAX OCTET STRING
        MAX-ACCESS read-write
        STATUS current
        DESCRIPTION
        "In the case of mdlPbxFraSignalMode = userDefined(5), this
        field defines the A,B,C Bits. D bit is supplied for future
        versions.
        Bit  1 = Bit A ON Hook  - Local
        Bit  2 = Bit B ON Hook  - Local
        Bit  3 = Bit C ON Hook  - Local
        Bit  4 = Bit D ON Hook  - Local
        Bit  5 = Bit A OFF Hook - Local
        Bit  6 = Bit B OFF Hook - Local
        Bit  7 = Bit C OFF Hook - Local
        Bit  8 = Bit D OFF Hook - Local

        Bit  9 = Bit A ON Hook  - Remote
        Bit 10 = Bit B ON Hook  - Remote
        Bit 11 = Bit C ON Hook  - Remote
        Bit 12 = Bit D ON Hook  - Remote
        Bit 13 = Bit A OFF Hook - Remote
        Bit 14 = Bit B OFF Hook - Remote
        Bit 15 = Bit C OFF Hook - Remote
        Bit 16 = Bit D OFF Hook - Remote

        In conjunction with the Mask, mdlPbxFraSignalMask, it is
        possible to compute the signal mode."
        DEFVAL { '0000'H}
        ::= { mdlPbxFramerCnfgEntry 6}

mdlPbxFraSignalMask OBJECT-TYPE
        SYNTAX OCTET STRING
        MAX-ACCESS read-write
        STATUS current
        DESCRIPTION
        "In the case of mdlPbxFraSignalMode = userDefined(5), this
        field defines the 'don't care' A,B,C Bits. D bit is supplied
        for future versions.
        Bit  1 = Bit A ON Hook  - Local
        Bit  2 = Bit B ON Hook  - Local
        Bit  3 = Bit C ON Hook  - Local
        Bit  4 = Bit D ON Hook  - Local
        Bit  5 = Bit A OFF Hook - Local
        Bit  6 = Bit B OFF Hook - Local
        Bit  7 = Bit C OFF Hook - Local
        Bit  8 = Bit D OFF Hook - Local

        Bit  9 = Bit A ON Hook  - Remote
        Bit 10 = Bit B ON Hook  - Remote
        Bit 11 = Bit C ON Hook  - Remote
        Bit 12 = Bit D ON Hook  - Remote
        Bit 13 = Bit A OFF Hook - Remote
        Bit 14 = Bit B OFF Hook - Remote
        Bit 15 = Bit C OFF Hook - Remote
        Bit 16 = Bit D OFF Hook - Remote."
	DEFVAL { 'ffff'H }
        ::= { mdlPbxFramerCnfgEntry 7}

mdlPbxFraFramerSlot OBJECT-TYPE
        SYNTAX INTEGER { io1(5), io2(6), io3(7), io4(8), io5(9),
                        io6(10), io7(11), io8(12), io9(13), io10(14),
                        io11(15), io12(16) }
        MAX-ACCESS read-write
        STATUS current
        DESCRIPTION
        "Slot where is sitting the Framer."
     ::= { mdlPbxFramerCnfgEntry 8}

mdlPbxFraSignaling OBJECT-TYPE
        SYNTAX INTEGER {
            notApplicable   (1),
			endToEnd        (2),
			localTermination(3)
			}
        MAX-ACCESS read-write
        STATUS current
        DESCRIPTION
        "Signaling - describes the way the signaling ABCD bits pass from the
		             local extension to the remote extension and vice-versa.

         endToEnd = the signaling ABCD bits pass without change from local to
                    remote extension.
         localTermination = the signaling ABCD bits received from the local extension
                    are translated to different ON Hook/OFF Hook bit values and then
                    passed to remote extension. This is relevant when the Local
                    and Remote ON Hook/OFF Hook values are different."
        DEFVAL { endToEnd }
        ::= { mdlPbxFramerCnfgEntry 9}

mdlPbxFraTransSigTs OBJECT-TYPE
        SYNTAX Integer32 
        MAX-ACCESS read-write
        STATUS current
        DESCRIPTION
        "This is the Time Slot that is used for Transparent CCS signaling.
         The values of this TS are 1-24 for T1 & 1-31 for E1.
         The default for E1 is 16 & for T1 it is 24. If no signaling is used then
         the TS should be 255 (None)."
        ::= { mdlPbxFramerCnfgEntry 10}

--Protected IP Adresses list for ML-IP cards of MP-2100/4 and MP-2200
--for IP Ring Mode

mdlProtIpTable   OBJECT-TYPE
      SYNTAX SEQUENCE OF MdlProtIpEntry
      MAX-ACCESS not-accessible
      STATUS current
      DESCRIPTION
      "This table contains Protected IP Addresses for ML-IP cards
       when working in IP Ring Mode."
      ::= {cnfgMdlMux 2}

mdlProtIpEntry  OBJECT-TYPE
      SYNTAX MdlProtIpEntry
      MAX-ACCESS not-accessible
      STATUS current
	  DESCRIPTION  "An entry in table."
	  INDEX { mdlProtIpCnfgIdx, mdlProtIpSlotIdx, mdlProtIpAddress}
      ::=  {mdlProtIpTable 1}

MdlProtIpEntry ::=
      SEQUENCE {
       mdlProtIpCnfgIdx   Integer32,
       mdlProtIpSlotIdx   INTEGER,
       mdlProtIpAddress   IpAddress,
       mdlProtIpRowStatus RowStatus
	}

mdlProtIpCnfgIdx OBJECT-TYPE
      SYNTAX  Integer32 (1..255)
      MAX-ACCESS  read-only
      STATUS  current
      DESCRIPTION
      "This attribute indicates the Idx of the Cnfg being accessed.
       Idx 255 relates to the TmpCnfg.
       For Agents having several configuration, Write operation is
       allowed only to the Temporary Configuration."
      ::= { mdlProtIpEntry 1}

mdlProtIpSlotIdx OBJECT-TYPE
      SYNTAX  INTEGER
      {
       notApplicable (1),
       io1   (5),
       io2   (6),
       io3   (7),
       io4   (8),
       io5   (9),
       io6  (10),
       io7  (11),
       io8  (12),
       io9  (13),
       io10 (14),
       io11 (15),
       io12 (16)
      }
      MAX-ACCESS  read-only
      STATUS  current
      DESCRIPTION
      "This attribute indicates a unique  slot  position where
       the module is inserted.
       In the 2104 Unit the entries io6(10)..io16) are not valid."
      ::= { mdlProtIpEntry 2}

mdlProtIpAddress OBJECT-TYPE
      SYNTAX  IpAddress 
      MAX-ACCESS  read-only
      STATUS  current
      DESCRIPTION
      "A Protected IP address."
      ::= { mdlProtIpEntry 3 }

mdlProtIpRowStatus  OBJECT-TYPE
      SYNTAX  RowStatus
      MAX-ACCESS   read-create
      STATUS   current
      DESCRIPTION
      "This parameter allows creating/deleting entries of this table."
      ::= { mdlProtIpEntry 4 }


statMdlMux  OBJECT IDENTIFIER ::= {mdlMux 2}

--
-- Card status table
--
mdlStatTable  OBJECT-TYPE
    SYNTAX SEQUENCE OF MdlStatEntry
    MAX-ACCESS not-accessible
    STATUS current
	DESCRIPTION  "A table."
	::=  { statMdlMux 1 }

mdlStatEntry OBJECT-TYPE
    SYNTAX MdlStatEntry
    MAX-ACCESS not-accessible
    STATUS current
	DESCRIPTION  "An entry in table."
	INDEX { mdlStatSltIdx }
      ::= { mdlStatTable 1}

MdlStatEntry ::=
      SEQUENCE {
     mdlStatSltIdx         INTEGER,
     mdlStatHostIP         IpAddress,
     mdlStatHostMask       IpAddress,
     mdlStatDefaultGateway IpAddress
      }

mdlStatSltIdx OBJECT-TYPE
   SYNTAX  INTEGER
   {
       psA   (1),
       psB   (2),
       clA   (3),
       clB   (4),
       io1   (5),
       io2   (6),
       io3   (7),
       io4   (8),
       io5   (9),
       io6  (10),
       io7  (11),
       io8  (12),
       io9  (13),
       io10 (14),
       io11 (15),
       io12 (16)
   }
   MAX-ACCESS  read-only
   STATUS  current
   DESCRIPTION
   "A unique number to identify a slot position in the mux.
    In the 2104 Unit the entries psB(2),clB(4),io6(10)..io12(16)
    are not valid."
   ::= { mdlStatEntry 1}

mdlStatHostIP OBJECT-TYPE
    SYNTAX  IpAddress 
    MAX-ACCESS  read-only
    STATUS  current
    DESCRIPTION
    "The host interface IP address when DHCP Client=Yes.
     This object is relevant only when DHCP Client=Yes "
    ::= { mdlStatEntry 2 }

mdlStatHostMask OBJECT-TYPE
    SYNTAX  IpAddress 
    MAX-ACCESS  read-only
    STATUS  current
    DESCRIPTION
    "The host interface subnet mask when DHCP Client=Yes.
     This object is relevant only when DHCP Client=Yes "
    ::= { mdlStatEntry 3 }

mdlStatDefaultGateway OBJECT-TYPE
    SYNTAX  IpAddress
    MAX-ACCESS  read-only
    STATUS  current
    DESCRIPTION
    "Default Gateway's IP Address when DHCP Client=Yes.
     This object is relevant only when DHCP Client=Yes "
    ::= { mdlStatEntry 4 }


--
-- Specific port config for each module Type
-- *****************************************

--
-- MPCL.1 configuration parameters
--
--prtExClCnfgTable   OBJECT IDENTIFIER ::= {prtClCnfg 1}
-- prtInClInbandTable OBJECT IDENTIFIER ::= {prtClCnfg 2}

prtExClCnfgTable OBJECT-TYPE
      SYNTAX SEQUENCE OF PrtExClCnfgEntry
      MAX-ACCESS not-accessible
      STATUS current
	DESCRIPTION  "A table."
	::=  {prtClCnfg 1}

prtExClCnfgEntry OBJECT-TYPE
      SYNTAX PrtExClCnfgEntry
      MAX-ACCESS not-accessible
      STATUS current
      DESCRIPTION
      "All the entries at this table are identical (have the same
       value) for all the configurations (1..100) except the
       TmpCnfg.
       The write operation into the Table Objects is valid only
       to the TmpCnfg entry."
      INDEX {prtExClCnfgIdx, prtExClSltIdx, prtExClPrtIdx }
      ::= { prtExClCnfgTable 1}

PrtExClCnfgEntry ::=
      SEQUENCE {
      prtExClCnfgIdx         Integer32,
      prtExClSltIdx          INTEGER,
      prtExClPrtIdx          INTEGER,
   prtExClUsage           INTEGER,
   prtExClRate            INTEGER,
   prtExClDataBits        INTEGER,
   prtExClParity          INTEGER,
   prtExClStopBits        INTEGER,
   prtExClRoutingProtocol INTEGER,
   prtExClEnabled         INTEGER
      }


prtExClCnfgIdx OBJECT-TYPE
      SYNTAX  Integer32 (1..255)
      MAX-ACCESS  read-only
      STATUS  current
      DESCRIPTION
      "This attribute indicates the Idx of the Cnfg (1..100) being
       accessed.
       Idx 255 relates to the TmpCnfg."
      ::= { prtExClCnfgEntry 1}
-- In phase I only the values 1 (Cnfg1) and 255 (temp) are valid.

prtExClSltIdx OBJECT-TYPE
      SYNTAX  INTEGER
        {
       clA   (3),
       clB   (4),
       notApplicable (255)
        }
      MAX-ACCESS  read-only
      STATUS  current
      DESCRIPTION
      "This attribute indicates a unique  slot  position where
       the card is inserted. Because the second Cl is only for
       redundancy, all the parameters are identical in the two
       modules, i.e. change of any parameter in one module will
       change automatically the value of the other module..
       In the ?004 Unit the entry clB(4) is not valid."
      ::= { prtExClCnfgEntry 2}

prtExClPrtIdx OBJECT-TYPE
      SYNTAX  INTEGER
      {
  exPrt1    (1) ,
  exPrt2    (2)
      }
      MAX-ACCESS  read-only
      STATUS  current
      DESCRIPTION
      "This attribute indicates a unique  port number. "
      ::= { prtExClCnfgEntry 3}

prtExClUsage OBJECT-TYPE
      SYNTAX  INTEGER
       {
  unknown (1),
  noUse   (2),
  nmsSlip (3),
  nmsPpp  (4),
  muxSlip (5),
  muxPpp  (6),
  terminal(7)
       }
      MAX-ACCESS  read-only
      STATUS  current
      DESCRIPTION
      "This attribute indicates what is the usage of the port."
      ::= { prtExClCnfgEntry 4}

prtExClRate OBJECT-TYPE
      SYNTAX  INTEGER
       {
        r300Bps (1),
        r1200Bps (2),
        r2400Bps (3),
        r4800Bps (4),
        r9600Bps (5),
        r19200Bps (6),
        r38400Bps (7),
        r57600Bps (8),
        r115200Bps (9)
       }
      MAX-ACCESS  read-only
      STATUS  current
      DESCRIPTION
      "This attribute indicates the operation rate of the port."
      ::= { prtExClCnfgEntry 5}

prtExClDataBits OBJECT-TYPE
      SYNTAX  INTEGER
       {
        dataBits7Bits (1),
        dataBits8Bits (2)
       }
      MAX-ACCESS  read-only
      STATUS  current
      DESCRIPTION
      "This attribute indicates the number of data bits in async
       frame"
      ::= { prtExClCnfgEntry 6}

prtExClParity OBJECT-TYPE
      SYNTAX  INTEGER
       {
        odd   (1),
        even  (2),
        none  (3)
       }
      MAX-ACCESS  read-only
      STATUS  current
      DESCRIPTION
      "This attribute indicates if the parity operation mode in
       async frame"
      ::= { prtExClCnfgEntry 7}

prtExClStopBits OBJECT-TYPE
      SYNTAX  INTEGER
       {
          stopBits1Bit      (1),
          stopBits1dot5Bits (2),
          stopBits2Bits     (3)
       }
      MAX-ACCESS  read-only
      STATUS  current
      DESCRIPTION
      "This attribute indicates the minimum number of stop bits in
       the tx async frame"
      ::= { prtExClCnfgEntry 8}

prtExClRoutingProtocol OBJECT-TYPE
      SYNTAX  INTEGER
       {
       none    (1),
       rip2    (2)
       }
      MAX-ACCESS  read-only
      STATUS  current
      DESCRIPTION
      "This attribute indicates the routing protocol of the port.
       When prtExClUsage is nmsSlip or nmsPpp - all values are
                                                applicable .
       Else - only 'none' is applicable."
      ::= { prtExClCnfgEntry 9}

prtExClEnabled OBJECT-TYPE
      SYNTAX  INTEGER
       {
      notApplicable(1),
      disabled     (2),
	  enabled      (3)
       }
      MAX-ACCESS  read-only
      STATUS  current
      DESCRIPTION
      "This attribute indicates if Ethernet port of CL
       is enabled or not for management.
       It is applicable only on the ETH port of the CL, when the 
       MP includes an ML-IP card.
       disabled - will happen when there is Inband Management via
	              the ML-IP link/s
	   enabled  - will happen when ML-IP link/s is not used for Inband 
	              Management, but CL's ETH port ."
      ::= { prtExClCnfgEntry 10}

--
-- MPH1.T1, MPH1.E1, MTML.1/T1 , MTML.1/E1, ML-20
-- TDM and Hybrid(TDM & Packet) Main Link Modules
--
--prtExPh1MlCnfgTable OBJECT IDENTIFIER ::= {prtPh1MlCnfg 1}
--prtExPh1MlTsTable   OBJECT IDENTIFIER ::= {prtPh1MlCnfg 2}
--prtInPh1MlCnfgTable OBJECT IDENTIFIER ::= {prtPh1MlCnfg 3}
--prtInPh1MlDlciTable OBJECT IDENTIFIER ::= {prtPh1MlCnfg 4}
--prtPhMlCnfgTable    OBJECT IDENTIFIER ::= {prtPh1MlCnfg 5}

--
-- T1/E1 Port Objects
--
prtExPh1MlCnfgTable  OBJECT-TYPE
     SYNTAX SEQUENCE OF PrtExPh1MlCnfgEntry
     MAX-ACCESS not-accessible
     STATUS  current
     DESCRIPTION
      "- For products supporting more than one configuration, the write operation 
         into the Table is valid only to the TmpCnfg entry.
       - For products that do not support configurations, the write operation 
         into the Table will be to prtExPh1MlCnfgIdx=1."
     ::= {prtPh1MlCnfg 1}

prtExPh1MlCnfgEntry OBJECT-TYPE
      SYNTAX PrtExPh1MlCnfgEntry
      MAX-ACCESS not-accessible
      STATUS current
	DESCRIPTION  "An entry in table."
	INDEX {prtExPh1MlCnfgIdx, prtExPh1MlSltIdx, prtExPh1MlPrtIdx }
      ::= { prtExPh1MlCnfgTable 1}

PrtExPh1MlCnfgEntry ::=
      SEQUENCE {
      prtExPh1MlCnfgIdx        Integer32,
      prtExPh1MlSltIdx         INTEGER,
      prtExPh1MlPrtIdx         INTEGER,
      prtExPh1MlConnect        INTEGER,
      prtExPh1MlLineType       INTEGER,
      prtExPh1MlLineCode       INTEGER,
      prtExPh1MlLineLen        INTEGER,
      prtExPh1MlRestoreTime    INTEGER,
      prtExPh1MlTxGain         INTEGER,
      prtExPh1MlRxSensitivity  INTEGER,
      prtExPh1MlIdleCode       Integer32,
      prtExPh1MlTdmTrunk       INTEGER,
      prtExPh1MlClkMode        INTEGER,
      prtExPh1MlMfClkSrcSlt    INTEGER,
      prtExPh1MlMfClkSrcPrt    INTEGER,
      prtExPh1MlFdlType        INTEGER,
      prtExPh1MlInbandMng      INTEGER,
      prtExPh1MlInbandMngRate  INTEGER,
      prtExPh1MlRedundType     INTEGER,
      prtExPh1MlRedundSlot     INTEGER,
      prtExPh1MlRedundPort     INTEGER,
      prtExPh1MlRedundRecTime  Integer32,
   prtExPh1MlInbandMngRoutProt INTEGER,
      prtExPh1MlIfType         INTEGER,
	  prtExPh1MlMultiplier     INTEGER,
	  prtExPh1MlSupportedTS    Integer32,
	  prtExPh1MlImpedance      INTEGER,
	  prtExPh1MlQ50BwControl   INTEGER,	  
	  prtExPh1MlQ50SignalPair  INTEGER,
	  prtExPh1MlInternalSwitch INTEGER,
	  prtExPh1MlSigService     INTEGER,
	  prtExPh1MlFragmentSize   Integer32
      }

prtExPh1MlCnfgIdx OBJECT-TYPE
      SYNTAX  Integer32 (1..255)
      MAX-ACCESS  read-only
      STATUS  current
      DESCRIPTION
      "This attribute indicates the Idx of the Cnfg (1..100) being
       accessed.
       Idx 255 relates to the TmpCnfg. "
      ::= { prtExPh1MlCnfgEntry 1}
-- In phase I only the values 1 (Cnfg1) and 255 (temp) are valid.

prtExPh1MlSltIdx OBJECT-TYPE
      SYNTAX  INTEGER
     {
       notApplicable (1),
       clA   (3),
       clB   (4),
       io1   (5),
       io2   (6),
       io3   (7),
       io4   (8),
       io5   (9),
       io6  (10),
       io7  (11),
       io8  (12),
       io9  (13),
       io10 (14),
       io11 (15),
       io12 (16)
     }
      MAX-ACCESS  read-only
      STATUS  current
      DESCRIPTION
      "This attribute indicates a unique  slot  position where
       the module is inserted.
       In the ?004 Unit the entries io6(10)..io16) are not valid.
       For the Vmux2100 Main Board notApplicable (1) is used."
      ::= { prtExPh1MlCnfgEntry 2}

prtExPh1MlPrtIdx OBJECT-TYPE
      SYNTAX  INTEGER
       {
       exPrt1     (1),
       exPrt2     (2),
       exPrt3     (3),
       exPrt4     (4),
       exPrt5     (5),
       exPrt6     (6),
       exPrt7     (7),
       exPrt8     (8),
	   exPrt9     (9),
	   exPrt10   (10),
	   exPrt11   (11),
	   exPrt12   (12),
	   exPrt13   (13),
	   exPrt14   (14),
	   exPrt15   (15),
	   exPrt16   (16),
	   exPrt17   (17),
	   exPrt18   (18),
       inPrt1   (101),
	   inPrt2   (102),
	   inPrt3   (103),
	   inPrt4   (104),
       inPrt5   (105),
	   inPrt6   (106),
	   inPrt7   (107),
	   inPrt8   (108),
       inPrt9   (109),
       inPrt10  (110),
       inPrt11  (111),
       inPrt12  (112),
       inPrt13  (113),
       inPrt14  (114),
       inPrt15  (115),
       inPrt16  (116),
       inPrt17  (117),
       inPrt18  (118),
       inPrt19  (119),
       inPrt20  (120),
       inPrt21  (121),
       inPrt22  (122),
       inPrt23  (123),
       inPrt24  (124),
       inPrt25  (125),
       inPrt26  (126),
       inPrt27  (127),
       inPrt28  (128),
       inPrt29  (129),
       inPrt30  (130),
       inPrt31  (131),
       inPrt32  (132),
       inPrt33  (133),
       inPrt34  (134),
       inPrt35  (135),
       inPrt36  (136),
       inPrt37  (137),
       inPrt38  (138),
       inPrt39  (139),
       inPrt40  (140),
       inPrt41  (141),
       inPrt42  (142),
       inPrt43  (143),
       inPrt44  (144),
       inPrt45  (145),
       inPrt46  (146),
       inPrt47  (147),
       inPrt48  (148),
       inPrt49  (149),
       inPrt50  (150),
       inPrt51  (151),
       inPrt52  (152),
       inPrt53  (153),
       inPrt54  (154),
       inPrt55  (155),
       inPrt56  (156),
       inPrt57  (157),
       inPrt58  (158),
       inPrt59  (159),
       inPrt60  (160),
       inPrt61  (161),
       inPrt62  (162),
       inPrt63  (163),
       inPrt64  (164),
       inPrt65  (165),
       inPrt66  (166),
       inPrt67  (167),
       inPrt68  (168),
       inPrt69  (169),
       inPrt70  (170),
       inPrt71  (171),
       inPrt72  (172),
       inPrt73  (173),
       inPrt74  (174),
       inPrt75  (175),
       inPrt76  (176),
       inPrt77  (177),
       inPrt78  (178),
       inPrt79  (179),
       inPrt80  (180),
       inPrt81  (181),
       inPrt82  (182),
       inPrt83  (183),
       inPrt84  (184)
       }
      MAX-ACCESS  read-only
      STATUS  current
      DESCRIPTION
      "This attribute indicates a unique  port number.
	   MP-2100/2200:
       MTML-1/E1 and MTML-1/T1 cards have only one external interface.
       inPrt1, inPrt2 - for MTML-H/2E1 and HSH cards.
       inPrt1..inPrt4 - for MTML-E2 and MSL-4 cards.
       exPrt2..exPrt4 - for MTML-4 cards and others
	   exPrt1..exPrt8 - for ML-8 cards.
       inPrt1..inPrt8 - for MSL-8 and VF-30 card family.
       MP-104/204:  only exPrt3 (3) is applicable.
	   MP-4100:     intPrt1...intPrt84 - for CLX cards.
       For other products' index see their specification."
      ::= { prtExPh1MlCnfgEntry 3}

prtExPh1MlConnect OBJECT-TYPE
      SYNTAX  INTEGER
       {
        no  (2),
        yes (3)
       }
      MAX-ACCESS  read-write
      STATUS  current
      DESCRIPTION
      "This attribute indicates whether the port should be considered
       in any of the mux  algorithms. It also affects all the card
       considerations because it may indicate that the module has only
       one physical interface."
      ::= {prtExPh1MlCnfgEntry 4}

prtExPh1MlLineType OBJECT-TYPE
      SYNTAX  INTEGER
       {
        esfT1          (2), --> dsx1ESF
        sfT1           (3), --> dsx1D4
        g732nE1        (4), --> dsx1E1
        g732nE1CRC     (5), --> dsx1E1-CRC
        g732sE1        (6), --> dsx1E1-MF
        g732sE1CRC     (7), --> dsx1E1-MF-CRC
        g732unframed   (8), --> dsx1Unframed, for T1 Unframed
		e1Unframed     (9), --> dsx1E1Unframed
		framed       (101)  
       }
      MAX-ACCESS  read-write
      STATUS  current
      DESCRIPTION
      "This attribute is the line type parameter for T1/E1 interface.
       The user should select only the values which are relevant
       to the specific port:
       (2),(3), (8)  - for T1 port
       (4)..(7), (9) - for E1 port.
	   (101) framed - This value does not exist	in standard MIB and is used 
	                  for a non-standard E1 port that doesn't has real framer.
	   Note: for old devices, g732unframed(8) was used as E1 Unframed.
	         That was because at the time this value did not exist in
	         the standard MIB (RFC-1406), so we added it in private MIB.
	         Now that it was added to standard MIB, private MIB was 
	         updated as well.   
       This parameter has the same values as dsx1LineType in DS1
       MIB (RFC-3895). The parameters in dsx1LineType are:
                     other          (1)
      esfT1          dsx1ESF        (2)
      sfT1           dsx1D4         (3)
      g732nE1        dsx1E1         (4)
      g732nE1CRC     dsx1E1-CRC     (5)
      g732sE1        dsx1E1-MF      (6)
      g732sE1CRC     dsx1E1-MF-CRC  (7)
      g732unframed   dsx1Unframed   (8)	--from RFC-3895
      e1Unframed     dsx1E1Unframed (9) --from RFC-3895 "
      ::= { prtExPh1MlCnfgEntry 5}

prtExPh1MlLineCode OBJECT-TYPE
      SYNTAX  INTEGER
       {
        b7T1   (1),  --> dsx1JBZS (for E1 & T1)
        b8zsT1 (2),  --> dsx1B8ZS (for E1 & T1)
        transT1(3),  --> dsx1AMI
        hdb3E1 (4),  --> dsx1HDB3 (for E1 & T1)
        notApplicable(255)
       }
      MAX-ACCESS  read-write
      STATUS  current
      DESCRIPTION
      "This attribute is the line code parameter used for T1/E1
       interface.
       The user should select only the parameters which are relevant
       to the specific card:
       T1 line code parameters for MPH.1/T1
       E1 line code parameters for MPH.1/E1.
       This parameter has the same values as dsx1LineCoding in T1/E1
       MIB (RFC-1406).  The parameters in dsx1LineCoding are:
       dsx1JBZS  (1)
       dsx1B8ZS  (2)
       dsx1HDB3  (3)
       dsx1ZBTSI (4)
       dsx1AMI   (5)
       other     (6)"
      ::= { prtExPh1MlCnfgEntry 6}

prtExPh1MlLineLen OBJECT-TYPE
      SYNTAX  INTEGER
       {
        unknown      (1),
        len0p133ft   (2),
        len134p266ft (3),
        len267p399ft (4),
        len400p533ft (5),
        len534p655ft (6),
        lenFcc68     (7),
        notApplicable(255)
       }
      MAX-ACCESS  read-write
      STATUS  current
      DESCRIPTION
      "This attribute is the line length parameter used only for T1/DSU
       interfaces.
       lenXXXpXXXft = len-XXX-XXXft."
      ::= { prtExPh1MlCnfgEntry 7}

prtExPh1MlRestoreTime OBJECT-TYPE
      SYNTAX  INTEGER
       {
        restoreT1secFast      (2),
        restoreT10sec62411    (3),
        ccittE1                (4)
       }
      MAX-ACCESS  read-write
      STATUS  current
      DESCRIPTION
      "The time passing from the disappearance of the loss of
       synchronization condition (red alarm) to the restoration of
       normal service. The options 1secFast(2) and 10sec62411(3)
       for E1 interfaces are proprietary implementation of the T1
       standard to the E1 interface."
      ::= { prtExPh1MlCnfgEntry 8}

prtExPh1MlTxGain OBJECT-TYPE
      SYNTAX  INTEGER
       {
          notApplicable(1),
          txGain0db         (2),
          txGain7dot5db     (3),
          txGain15db        (4),
          txGain22dot5db    (5)
       }
      MAX-ACCESS  read-write
      STATUS  current
      DESCRIPTION
      "This attribute is the tx gain parameter used only for
       T1/CSU interfaces."
      ::= { prtExPh1MlCnfgEntry 9}

prtExPh1MlRxSensitivity OBJECT-TYPE
      SYNTAX  INTEGER
       {
        notApplicable(1),
        low26dBm  (2),
        high36dBm (3),
		shortHaul (4),
		longHaul  (5),
		low15dbm  (6)
       }
      MAX-ACCESS  read-write
      STATUS  current
      DESCRIPTION
      "This attribute is the rx line sensitivity parameter.
       low26dBm, high36dBm - applicable for T1-CSU
       shortHaul, longHaul - applicable for MTML-4 cards
       low15dbm was added for vmux110/210 T1 ports."
      ::= { prtExPh1MlCnfgEntry 10}

prtExPh1MlIdleCode OBJECT-TYPE
      SYNTAX  Integer32
      MAX-ACCESS  read-write
      STATUS  current
      DESCRIPTION
     "Determines the code for transmission in empty time slots.
      Type value(00-FFH), Excluding 0H,8H,10H,12H,21H,24H,42H,49H,
      84H,92H"
      ::= { prtExPh1MlCnfgEntry 11}

prtExPh1MlTdmTrunk  OBJECT-TYPE
      SYNTAX  INTEGER
       {
        linkA   (1),
        linkB   (2),
        none    (3),
        notApplicable (255)
       }
      MAX-ACCESS  read-write
      STATUS  current
      DESCRIPTION
      "This attribute indicates whether the port is used to transfer
       TDM cards data and through which Bus."
      ::= {prtExPh1MlCnfgEntry 12}

prtExPh1MlClkMode OBJECT-TYPE
      SYNTAX  INTEGER
       {
        internalLocal (1),
        loopBackLocal (2),
        nodalTiming   (3),
		loopBackFromLink (4),
		loopBackFromChannel (5),
		loopbackFromSystem (6)
       }
      MAX-ACCESS  read-write
      STATUS  current
      DESCRIPTION
      "Defines the clock operation mode of the T1/E1 interface.
       Ports that are connected to the TDM Buses must be in
       nodalTiming(3) clock mode. "
      ::= {prtExPh1MlCnfgEntry 13}

prtExPh1MlMfClkSrcSlt  OBJECT-TYPE
      SYNTAX  INTEGER
       {
          notApplicable(1),
          local (2),
          io1   (5),
          io2   (6),
          io3   (7),
          io4   (8),
          io5   (9),
          io6  (10),
          io7  (11),
          io8  (12),
          io9  (13),
          io10 (14),
          io11 (15),
          io12 (16)
       }
      MAX-ACCESS  read-write
      STATUS  current
      DESCRIPTION
      "This attribute indicates whether the port Tx multiframe is
       synchronized with Rx multiframe of another port and the slot
       position of that port.
       This operation is required in order to bypass signaling of
       PCM voice channels. Its value is always local(2) when the port
       isn't connected to any TDM bus. When it's value is local(2)
       there is no meaning to 'prtExPh1MlMfClkSrcPrt' parameter.
       In the ?004 Unit the entries io6(10)..io16) are not valid"
      ::= {prtExPh1MlCnfgEntry 14}

prtExPh1MlMfClkSrcPrt  OBJECT-TYPE
      SYNTAX  INTEGER
       {
          exPrt1         (1),
		  exPrt2         (2),
          inPrt1       (101),
          notApplicable(255)
       }
      MAX-ACCESS  read-write
      STATUS  current
      DESCRIPTION
      "A unique number to identify a port position in the mux. It
       has no effect when the prtExPh1MlMfClkSrcSlt selected is Local.
       inPrt1 - for MTML-H/E1 cards."
    ::= {prtExPh1MlCnfgEntry 15}

prtExPh1MlFdlType  OBJECT-TYPE
      SYNTAX  INTEGER
       {
          notApplicable(1),
          response   (2),
          command    (3)
       }
      MAX-ACCESS  read-write
      STATUS  current
      DESCRIPTION
      "A unique number to identify  the side of the FDL operation.
      Normal: 'response' for the user side and 'command' for the PTT
      side.
      Applicable only when working with ESF-T1 link"
      ::= {prtExPh1MlCnfgEntry 16}

prtExPh1MlInbandMng  OBJECT-TYPE
      SYNTAX  INTEGER
       {
       off                 (2),
       fdlOrTs0            (3),
       dedicatedTs         (4),
       dedicatedPpp        (5),
       dedicatedFr         (6),
       notApplicable     (255)
       }
      MAX-ACCESS  read-write
      STATUS  current
      DESCRIPTION
      "A unique number to identify an Inband management over the
       link."
      ::= {prtExPh1MlCnfgEntry 17}

prtExPh1MlInbandMngRate  OBJECT-TYPE
      SYNTAX  INTEGER
       {
          notApplicable(1),
          r4k   (2),
          r8k   (3),
          r12k  (4),
          r16k  (5),
          r32k  (6),
          r64k  (7),
          r20k  (8)
       }
      MAX-ACCESS  read-write
      STATUS  current
      DESCRIPTION
      "A unique number to identify the rate of the Inband
       management (Kbps).
       E1 port - it is not applicable when prtExPh1MlInbandMng
                 selected is off.
       T1 port - it is not applicable when prtExPh1MlInbandMng
                 selected is off OR fdlOrTs0."
      ::= {prtExPh1MlCnfgEntry 18}

prtExPh1MlRedundType  OBJECT-TYPE
      SYNTAX  INTEGER
       {
          none                (1),
          dualCableAIS        (2),
          yCable              (3),
          dualCableParallelTx (4)
       }
      MAX-ACCESS  read-write
      STATUS  current
      DESCRIPTION
      "This object determines the ML redundancy type:
       none - no ML redundacy
       dualCableAIS -        each ML card is connected by a separate
       dualCableParallelTx   cable to the other MUX (two cables
                             connect two MUXes).  There are two
                             types of dual redundancy.
       yCable - Y cable is connected to both ML cards (one cable
                connects two MUXes).
       Default=none
       When only one ML card exists, the type can be only 'none'.
       The value should be the same for both ML slots."
      ::= {prtExPh1MlCnfgEntry 19}

prtExPh1MlRedundSlot  OBJECT-TYPE
      SYNTAX  INTEGER
       {
          notApplicable (1),
          io1   (5),
          io2   (6),
          io3   (7),
          io4   (8),
          io5   (9),
          io6  (10),
          io7  (11),
          io8  (12),
          io9  (13),
          io10 (14),
          io11 (15),
          io12 (16)
       }
      MAX-ACCESS  read-write
      STATUS  current
      DESCRIPTION
      "This object indicates the slot containing the redundacy ML
       card, coupled with the current ML (prtExPh1MlSltIdx).
       When prtExPh1MlRedundType=none (no ML redundancy) this
       object will be 'notApplicable'.
       In the ?004 Unit the entries io6(10)..io12(16) are not valid
       When value is not 'none', it should be mutual to the
       redundant ML slot."
      ::= {prtExPh1MlCnfgEntry 20}

prtExPh1MlRedundPort  OBJECT-TYPE
      SYNTAX  INTEGER
       {
       exPrt1          (1),
       exPrt2          (2),
       exPrt3          (3),
       exPrt4          (4),
       inPrt1        (101),
       inPrt2        (102),
       inPrt3        (103),
       inPrt4        (104),
       notApplicable (255)
       }
      MAX-ACCESS  read-write
      STATUS  current
      DESCRIPTION
      "This object indicates the redundacy ML port, coupled with the
       current ML port (prtExPh1MlPrtIdx).
       When prtExPh1MlRedundType=none (no ML redundancy) this
       object will be 'notApplicable'.
       When value is not 'none', it should be mutual to the
       redundant ML port.
       inPrt1 - for MTML-H/E1 cards.
       inPrt1..inPrt4 - for MTML-E2 cards.
       exPrt2..exPrt4 - for MTML-4 cards."
      ::= {prtExPh1MlCnfgEntry 21}

prtExPh1MlRedundRecTime  OBJECT-TYPE
      SYNTAX  Integer32  (1..99)
      MAX-ACCESS  read-write
      STATUS  current
      DESCRIPTION
      "Redundancy Recovery Time (sec). After switching the ML card
       to the current (prtExPh1MlSltIdx), the next ML switch can
       be performed only after a minimum time, indicated by
       this object."
      ::= {prtExPh1MlCnfgEntry 22}

prtExPh1MlInbandMngRoutProt  OBJECT-TYPE
      SYNTAX  INTEGER
       {
      none    (1),
      rip2    (2),
      proprietary        (3),
	  proprietaryNoNmsTx (4)
       }
      MAX-ACCESS  read-write
      STATUS  current
      DESCRIPTION
      "This attribute indicates the Inband Mng routing protocol of
       the port."
      ::= {prtExPh1MlCnfgEntry 23}

prtExPh1MlIfType  OBJECT-TYPE
      SYNTAX  INTEGER
       {
       notApplicable (1),
       csu    (2),
       dsu    (3),
	   ltu    (4)
       }
      MAX-ACCESS  read-write
      STATUS  current
      DESCRIPTION
      "Interface type of the port.
       For T1 - csu, dsu are the valid values
       For E1 - dsu, ltu are the valid values."
      ::= {prtExPh1MlCnfgEntry 24}

prtExPh1MlMultiplier  OBJECT-TYPE
      SYNTAX  INTEGER { 
      notApplicable (1), 
      br56 (2),
      br64 (3)
      }
      MAX-ACCESS  read-write
      STATUS  current
      DESCRIPTION
      "The data rate of each TS. The multiplier values
       can be 56 kbps or 64 kbps."
      ::= {prtExPh1MlCnfgEntry 25}

prtExPh1MlSupportedTS  OBJECT-TYPE
      SYNTAX  Integer32 
      MAX-ACCESS  read-only
      STATUS  current
      DESCRIPTION
      "Number of Supported Time Slots by the agent.
       For Vmux-110 there is HW that supports less than 31/24
       Time Slots for the E1/T1 port."
      ::= {prtExPh1MlCnfgEntry 26}

prtExPh1MlImpedance  OBJECT-TYPE
      SYNTAX  INTEGER { 
      notApplicable (1), 
      unbalanced    (2),
      balanced      (3)
      }
      MAX-ACCESS  read-write
      STATUS  current
      DESCRIPTION
      "The Line Impedance.
       For T1 (always balanced), impedance is 100 ohm.
       For E1:
       - balanced   = 120 ohm
       - unbalanced =  75 ohm."
      ::= {prtExPh1MlCnfgEntry 27}

prtExPh1MlQ50BwControl  OBJECT-TYPE
      SYNTAX  INTEGER { 
      disable       (2),
      annexA        (3),
      annexB        (4)
      }
      MAX-ACCESS  read-write
      STATUS  current
      DESCRIPTION
      "This object enables configuration of Q.50 Bandwidth Control on the port.
	   If the bandwidth exceeds a certain threshold it is possible to disable
	   new calls in the PBX via Q.50 protocol.

	   Q.50 supports only E1 ports with Line Types:
	   E1-MF (G.732S), E1-CRC-MF(G.732SCRC ) 	   
	   It does not support T1 ports.
	   
	   Annex A - the basic type of Q.50 which focuses only on the bandwidth control.
       Can use one of the following pairs of signaling bits: A&B or C&D.

       Annex B - Expansion of Annex A which includes also call release messages
       and Maintenance Messages. Uses A&B bits only."
      ::= {prtExPh1MlCnfgEntry 28}

prtExPh1MlQ50SignalPair  OBJECT-TYPE
      SYNTAX  INTEGER { 
      notApplicable (1), 
      aAndB         (2),
      cAndD         (3)
      }
      MAX-ACCESS  read-write
      STATUS  current
      DESCRIPTION
      "Q.50 Signaling bits Pair that is currently in use:
       A&B bits or C&D bits. For Annex B it will always be: aAndB (2)."
      ::= {prtExPh1MlCnfgEntry 29}

 prtExPh1MlInternalSwitch  OBJECT-TYPE
      SYNTAX  INTEGER { 
      disable      (2),
      enable       (3)
      }
      MAX-ACCESS  read-write
      STATUS  current
      DESCRIPTION
      "This parameter shows whether the data will be transferred from one port to
       the other port within the same group of 2 ports.
	   The default value is: Enable.
	   Disable value might be necessary for security implementations or
	   for ring applications.
      
       For Vmux-2100 device this parameter is used on the Channelized Cards.
       Both ports in each group should have the same value for this parameter."
      ::= {prtExPh1MlCnfgEntry 30}

 prtExPh1MlSigService  OBJECT-TYPE
      SYNTAX  INTEGER {
      notApplicable(1), 
      normal       (2),
      advanced     (3)
      }
      MAX-ACCESS  read-write
      STATUS  current
      DESCRIPTION
      "Signaling Service given by this link.
       notApplicable - for T1 links 
       normal - usual Signaling
       advanced - V5 Signaling. "
      ::= {prtExPh1MlCnfgEntry 31}

prtExPh1MlFragmentSize  OBJECT-TYPE
      SYNTAX  Integer32
      MAX-ACCESS  read-write
      STATUS  current
      DESCRIPTION
      "This parameter indicates the maximum number of bytes permitted in a packet send over the Link.
      Exceeding this size will cause packet fragmentation."
      ::= {prtExPh1MlCnfgEntry 32}
--
-- MPH1.T1 & MPH1.E1
-- Time Slot Assignment Table
--
prtExPh1MlTsTable  OBJECT-TYPE
     SYNTAX SEQUENCE OF PrtExPh1MlTsEntry
     MAX-ACCESS not-accessible
     STATUS  current
     DESCRIPTION
      "The write operation into the Table Objects is valid only
       to the TmpCnfg entry, except prtExPh1MlTsTest that will be written
       directly to the Active Configuration."
     ::= {prtPh1MlCnfg 2}

prtExPh1MlTsEntry OBJECT-TYPE
      SYNTAX PrtExPh1MlTsEntry
      MAX-ACCESS not-accessible
      STATUS current
	DESCRIPTION  "An entry in table."
	INDEX {prtExPh1MlTsCnfgIdx, prtExPh1MlTsSltIdx, prtExPh1MlTsPrtIdx, prtExPh1MlTsIdx }
      ::= { prtExPh1MlTsTable 1}

PrtExPh1MlTsEntry ::=
      SEQUENCE {
      prtExPh1MlTsCnfgIdx        Integer32,
      prtExPh1MlTsSltIdx         INTEGER,
      prtExPh1MlTsPrtIdx         INTEGER,
      prtExPh1MlTsIdx            Integer32,
      prtExPh1MlTsIConSlot       INTEGER,
      prtExPh1MlTsIConPrt        Integer32,
      prtExPh1MlTsIConTs         Integer32,
      prtExPh1MlTsExt    		 OBJECT IDENTIFIER,
	  prtExPh1MlTsTest           INTEGER,
	  prtExPh1MlTsType           INTEGER,
	  prtExPh1MlTsBundle         Integer32,
	  prtExPh1MlTsTestDuration   Integer32,
	  prtExPh1MlTsSubChType      INTEGER,
	  prtExPh1MlTsSubChMask      Integer32,
	  prtExPh1MlTsChRate      	 INTEGER,
	  prtExPh1MlTsByteReversal   INTEGER,
	  prtExPh1MlTsSigProfile     INTEGER
      }

prtExPh1MlTsCnfgIdx OBJECT-TYPE
      SYNTAX  Integer32  (1..255)
      MAX-ACCESS  read-only
      STATUS  current
      DESCRIPTION
      "This attribute indicates the Idx of the Cnfg (1..100) being
       accessed.
       Idx 255 relates to the TmpCnfg. "
      ::= { prtExPh1MlTsEntry 1}
-- In phase I only the values 1 (Cnfg1) and 255 (temp) are valid.

prtExPh1MlTsSltIdx OBJECT-TYPE
      SYNTAX  INTEGER
     {
       io1   (5),
       io2   (6),
       io3   (7),
       io4   (8),
       io5   (9),
       io6  (10),
       io7  (11),
       io8  (12),
       io9  (13),
       io10 (14),
       io11 (15),
       io12 (16),
	   notApplicable (255)
     }
      MAX-ACCESS  read-only
      STATUS  current
      DESCRIPTION
      "This attribute indicates a unique  slot  position where
       the card is inserted.
       In the ?004 Unit the entries io6(10)..io16) are not valid.
       For the Vmux2100 Main Board notApplicable (255) is used."
      ::= { prtExPh1MlTsEntry 2}

prtExPh1MlTsPrtIdx OBJECT-TYPE
      SYNTAX  INTEGER
	{
          exPrt1    (1),
	  exPrt2    (2),
	  exPrt3    (3),
	  exPrt4    (4),
          exPrt5    (5),
	  exPrt6    (6),
	  exPrt7    (7),
	  exPrt8    (8),
          exPrt9    (9),
	  exPrt10    (10),
	  exPrt11    (11),
	  exPrt12    (12),
          exPrt13    (13),
	  exPrt14    (14),
	  exPrt15    (15),
	  exPrt16    (16),
	  exPrt17    (17),
	  exPrt18    (18),

	  inPrt1    (101),
	  inPrt2    (102),
	  inPrt3    (103),
	  inPrt4    (104),
          inPrt5    (105),
	  inPrt6    (106),
	  inPrt7    (107),
	  inPrt8    (108),
          inPrt9    (109),
	  inPrt10   (110),
	  inPrt11   (111),
	  inPrt12   (112),
          inPrt13   (113),
	  inPrt14   (114),
	  inPrt15   (115),
	  inPrt16   (116),
	  inPrt17   (117),
	  inPrt18   (118),
	  inPrt19   (119),
	  inPrt20   (120)	      }
      MAX-ACCESS  read-only
      STATUS  current
      DESCRIPTION
      "This attribute indicates a unique  port number.
       MPH.1/E1 and MPH.1/T1 cards have only one external interface.
	   exPrt2 - for ME1-2, MT1-2 and mhsPri cards.
	   exPrt3, exPrt4 - for mhsPri cards.
       inPrt1 - for MTML-H/E1 cards."
      ::= { prtExPh1MlTsEntry 3}

prtExPh1MlTsIdx OBJECT-TYPE
      SYNTAX  Integer32
      MAX-ACCESS  read-only
      STATUS  current
      DESCRIPTION
      "This attribute indicates a unique time slot  position.
       The valid time slots are 1..24 for T1 Card and
       1..31 for E1 interface. In G732S-E1 lines time slot 16 is not
       valid for data, it is dedicated for multiframe synchronization bits
       and voice signaling."
      ::= { prtExPh1MlTsEntry 4}

prtExPh1MlTsIConSlot OBJECT-TYPE
      SYNTAX  INTEGER
       {
          unknown   (1),		  
          noConnect (2),
          split     (4),
          io1       (5),
          io2       (6),
          io3       (7),
          io4       (8),
          io5       (9),
          io6      (10),
          io7      (11),
          io8      (12),
          io9      (13),
          io10     (14),
          io11     (15),
          io12     (16),
		  notApplicable (255)
       }
      MAX-ACCESS  read-write
      STATUS  current
      DESCRIPTION
      "This attribute indicates whether the specified time slot is
       connected/routed internally in the Agent and to which card
       it is connected.
       In the ?004 Unit the entries io6(10)..io16) are not valid.
       split - will be used when the Src TS is connected to more
               than one slot OR more than one port (each needing
               less than a whole TS)."
      ::= {prtExPh1MlTsEntry 5}

prtExPh1MlTsIConPrt OBJECT-TYPE
      SYNTAX  Integer32
      MAX-ACCESS  read-write
      STATUS  current
      DESCRIPTION
      "This attribute indicates the internally (In Mux)
       connected/routed port.
       For MP, the values will be:
       	      {
	      exPrt1    (1) ,
	      exPrt2    (2) ,
	      exPrt3    (3) ,
	      exPrt4    (4) ,
	      exPrt5    (5) ,
	      exPrt6    (6) ,
	      exPrt7    (7) ,
	      exPrt8    (8) ,
	      exPrt9    (9) ,
	      exPrt10  (10) ,
          exPrt11  (11) ,
          exPrt12  (12) ,

          noConnect (100),

	      inPrt1  (101) ,
	      inPrt2  (102) ,
	      inPrt3  (103) ,
	      inPrt4  (104) ,
	      inPrt5  (105) ,
	      inPrt6  (106) ,
	      inPrt7  (107) ,
	      inPrt8  (108) ,
	      inPrt9  (109) ,
	      inPrt10 (110)	,
		  inPrt11 (111) ,
		  inPrt12 (112)
	      }		   
	For other products see specific values at spec."
      ::= {prtExPh1MlTsEntry 6}

prtExPh1MlTsIConTs OBJECT-TYPE
      SYNTAX  Integer32
      MAX-ACCESS  read-write
      STATUS  current
      DESCRIPTION
      "This attribute indicates a unique time slot  position.
       The valid time slots are 1..24 for T1 Card and
       1..31 for E1 interface. In G732S-E1 lines time slot 16 is not
       valid for data, it is dedicated to multiframe synchronization
       and voice signaling."
      ::= {prtExPh1MlTsEntry 7}

prtExPh1MlTsExt OBJECT-TYPE
        SYNTAX  OBJECT IDENTIFIER
        MAX-ACCESS  read-only
        STATUS  current
        DESCRIPTION
             "A pointer to an extension of this table:
              prtExTsSplitTable.
              - If prtExPh1MlTsIConSlot='split', its value
                should be set to the OBJECT IDENTIFIER of the
                prtExTsSplitTable, with its relevant CnfgIdx,
                SltIdx, PrtIdx, TsIdx and 1st TsBit.
              - If prtExPh1MlTsIConSlot is not 'split', its value
                should be set to the OBJECT IDENTIFIER { 0 0 }. "
     ::= { prtExPh1MlTsEntry 8 }

prtExPh1MlTsTest OBJECT-TYPE
      SYNTAX  INTEGER
     {
       none                    (1),
       localLoop               (2),
       remoteLoop              (3),
       remoteBert              (8),	  -- BERT 
       localToneInjection      (9),	  
       remoteToneInjection     (18),  
       localBert               (30),
	   split                   (254),
       notApplicable           (255)
        }
      MAX-ACCESS  read-write
      STATUS  current
      DESCRIPTION
      "This attribute indicates a test to be activated on the selected TS.
	   It is applicable only when prtSTstCmd=testPerTS(31).
	   notApplicable - when prtSTstCmd is NOT testPerTS(31).
	   none  - no test is applied for the selected TS.
       split - when the tests are per Bit of the selected TS."
      ::= { prtExPh1MlTsEntry 9 }

prtExPh1MlTsType OBJECT-TYPE
      SYNTAX  INTEGER
     {
       noConnect               (2),
       data                    (3),
       voice                   (4),
	   cas					   (5),
	   ss7                     (6),
	   transparent             (7),
	   data2                   (8),
       data3                   (9),
	   data4                   (10),
	   ss7n2                   (11),
	   hdlcV2Compatible        (12),
	   subCh1				   (13),
	   subCh2				   (14),
	   subCh3				   (15),
	   subCh4				   (16),
	   subCh5				   (17),
	   subCh6				   (18),
	   subCh7				   (19),
	   subCh8				   (20),
	   trau					   (21),
	   qmux					   (22),
	   dynamic				   (23),
	   signaling			   (24),
	   notApplicable           (255)
        }
      MAX-ACCESS  read-write
      STATUS  current
      DESCRIPTION
      "The Time Slot Type.

       Transparent - means that the Time Slot will be Rx/Tx as is without processing it.

       If the device requires more than 1 unique data or ss7 Time Slot,
       options with numbers can be used like: data...data4.
       Each numbered Type can go to a different destination.
       ss7n2 - means the 2nd group of ss7 Time Slots.
       data2,data3, data4 mean group 2,3,4 of Data Time Slots.
       subCh1...subCh8 mean Sub Channel 1...8, respectively.
       trau, qmux, dynamic, signaling - are used by GSM devices."      
      ::= { prtExPh1MlTsEntry 10 }

prtExPh1MlTsBundle OBJECT-TYPE
      SYNTAX  Integer32
      MAX-ACCESS  read-write
      STATUS  current
      DESCRIPTION
      "The number of the bundle containing this Time Slot.
       If no bundle exists for this TS or the bundle number
       is irrelevant, the value will be 0."
      ::= { prtExPh1MlTsEntry 11 }


prtExPh1MlTsTestDuration OBJECT-TYPE
      SYNTAX  Integer32
      MAX-ACCESS  read-write
      STATUS  current
      DESCRIPTION
       "This attribute indicates the maximum duration of executing
      a test on the specific TS. This entry applies to all the
      test operations. 

      For the Vmux2100 the values are:
      0 - 60 seconds.

      A zero  value specifies no time limitation.      
      When the test isn't active, the agent initiates this object to
      2 when the duration is needed and to 0 if its not required.
      The user should set this parameter after setting the
      'prtExPh1MlTsTest' parameter."
      ::= { prtExPh1MlTsEntry 12 }

prtExPh1MlTsSubChType OBJECT-TYPE
      SYNTAX  INTEGER
     {
	hdlc			(1),
	transparent		(2),
	notApplicable	(255)
        }
      MAX-ACCESS  read-write
      STATUS  current
      DESCRIPTION
      "The Time Slot Sub-Channel Type.
	   This variable is relevant only when Time-Slot Type is SubCh
	   (e.g. prtExPh1MlTsType = subCh1...subCh8)."      
      ::= { prtExPh1MlTsEntry 13 }

prtExPh1MlTsSubChMask OBJECT-TYPE
      SYNTAX  Integer32
      MAX-ACCESS  read-write
      STATUS  current
      DESCRIPTION
      "The Sub-Channel Type Mask.
	   This variable is relevant only when Time-Slot Type is SubCh
	   (e.g. prtExPh1MlTsType = subCh1...subCh8)."      
      ::= { prtExPh1MlTsEntry 14 }
	  
prtExPh1MlTsChRate OBJECT-TYPE
      SYNTAX  INTEGER
     	{
		notApplicable	(1),
		r16Kbps			(2),
		r32Kbps			(3),
		r64Kbps			(4),
		r8Kbps			(5),
		auto			(6)	
        }
      MAX-ACCESS  read-write
      STATUS  current
      DESCRIPTION
      "The Rate of the Signaling Channel.
       notApplicable(1) when TS Type is other than Signaling or Transparent"      
      ::= { prtExPh1MlTsEntry 15 }

prtExPh1MlTsByteReversal OBJECT-TYPE
      SYNTAX  INTEGER
     	{
		notApplicable	(1),
		no				(2),
		yes				(3)
		}
      MAX-ACCESS  read-write
      STATUS  current
      DESCRIPTION
      "Byte Reversal.
	   This variable defines whether the LSB or MSB is transmitted first.
	   no(2)	- MSB is transmitted first
	   yes(3)	- LSB is transmitted first."      
      ::= { prtExPh1MlTsEntry 16 }

prtExPh1MlTsSigProfile OBJECT-TYPE
      SYNTAX  INTEGER
       {
       notApplicable (1),
--       none          (2),
       p1            (3),
       p2            (4),
       p3            (5),
       p4            (6),
       p5            (7)
       }
      MAX-ACCESS  read-write
      STATUS  current
      DESCRIPTION
      "This object indicates the Signaling Profile of the port.
       It is applicable only when prtMl4SigProfile=perTS.
       p1  = profile 1
       p2  = profile 2
       p3  = profile 3
       p4  = profile 4
       p5  = profile 5 "
      ::= { prtExPh1MlTsEntry 17 }

--
-- MPH.1/T1 & MPH.1/E1
-- Internal port objects table
-- (only for the Hybrid modules)
--
prtInPh1MlCnfgTable  OBJECT-TYPE
     SYNTAX SEQUENCE OF PrtInPh1MlCnfgEntry
     MAX-ACCESS not-accessible
     STATUS  current
     DESCRIPTION
      "The write operation into the Table Objects is valid only
       to the TmpCnfg entry."
     ::= {prtPh1MlCnfg 3}

prtInPh1MlCnfgEntry OBJECT-TYPE
      SYNTAX PrtInPh1MlCnfgEntry
      MAX-ACCESS not-accessible
      STATUS current
	DESCRIPTION  "An entry in table."
	INDEX {prtInPh1MlCnfgIdx, prtInPh1MlSltType, prtInPh1MlPrtIdx }
      ::= { prtInPh1MlCnfgTable 1}

PrtInPh1MlCnfgEntry ::=
      SEQUENCE {
      prtInPh1MlCnfgIdx            Integer32,
      prtInPh1MlSltType            INTEGER,
      prtInPh1MlPrtIdx             Integer32,
      prtInPh1MlConnect            INTEGER,
      prtInPh1MlRate               INTEGER,
      prtInPh1MlProtocol           INTEGER,
      prtInPh1MlConnectionTyp      INTEGER,
      prtInPh1MlCongResponse       INTEGER,
      prtInPh1MlCongLevel          Integer32,
      prtInPh1MlTc                 INTEGER,
      prtInPh1MlFlowControl        INTEGER,
      prtInPh1MlSegment            INTEGER,
      prtInPh1MlFrMngProt          INTEGER,
      prtInPh1MlEnqPeriod          Integer32,
      prtInPh1MlFullRptPeriod      Integer32,
      prtInPh1MlFrWindowSize       Integer32,
      prtInPh1MlErrorsThreshold    Integer32,
      prtInPh1MlMaxIdleTime        Integer32,
	  prtInPh1MlBearerCh           INTEGER,
	  prtInPh1MlAssociatedExCh     INTEGER,
	  prtInPh1MlClockEncoding      INTEGER,
	  prtInPh1MlMinSeparators      Integer32,
	  prtInPh1MlCcittCrc           INTEGER,
	  prtInPh1MlFrameSeparator     INTEGER
      }


prtInPh1MlCnfgIdx OBJECT-TYPE
      SYNTAX  Integer32 (1..255)
      MAX-ACCESS  read-only
      STATUS  current
      DESCRIPTION
      "This attribute indicates the Idx of the Cnfg (1..100) being
       accessed.
       Idx 255 relates to the TmpCnfg. "
      ::= { prtInPh1MlCnfgEntry 1}
-- In phase I only the values 1 (Cnfg1) and 255 (temp) are valid.

prtInPh1MlSltType OBJECT-TYPE
      SYNTAX  INTEGER
     {
       io1   (5),
       io2   (6),
       io3   (7),
       io4   (8),
       io5   (9),
       io6  (10),
       io7  (11),
       io8  (12),
       io9  (13),
       io10 (14),
       io11 (15),
       io12 (16),
       notApplicable(255)
     }
      MAX-ACCESS  read-only
      STATUS  current
      DESCRIPTION
      "This attribute indicates a unique  slot  position where
       the card is inserted.
       For ISDN BRI port of MX300/30:
       io1(5) = isdn1(5) and io2(6) = isdn2(6)
       In the ?004 Unit the entries io6(10)..io12(16) are not valid"
      ::= { prtInPh1MlCnfgEntry 2}

prtInPh1MlPrtIdx OBJECT-TYPE
      SYNTAX  Integer32
      MAX-ACCESS read-only
      STATUS  current
      DESCRIPTION
      "This attribute indicates a unique port number.
       MPH.1/E1 and MPH.1/T1 cards have three internal interfaces.
       MX3000 modules may have up to 50 internal ports."
      ::= { prtInPh1MlCnfgEntry 3}

prtInPh1MlConnect OBJECT-TYPE
      SYNTAX  INTEGER
       {
  no  (2),
  yes (3)
       }
      MAX-ACCESS  read-write
      STATUS  current
      DESCRIPTION
      "This attribute indicates whether the port should be
       considered in any of the mux  algorithms."
      ::= { prtInPh1MlCnfgEntry 4}

prtInPh1MlRate OBJECT-TYPE
      SYNTAX  INTEGER
       {
        r1x56eq56Kbps    (1),
        r1x64eq64Kbps    (2),
        r2x56eq112Kbps   (3),
        r2x64eq128Kbps   (4),
        r3x56eq168Kbps   (5),
        r3x64eq192Kbps   (6),
        r4x56eq224Kbps   (7),
        r4x64eq256Kbps   (8),
        r5x56eq280Kbps   (9),
        r5x64eq320Kbps  (10),
        r6x56eq336Kbps  (11),
        r6x64eq384Kbps  (12),
        r7x56eq392Kbps  (13),
        r7x64eq448Kbps  (14),
        r8x56eq448Kbps  (15),
        r8x64eq512Kbps  (16),
        r9x56eq504Kbps  (17),
        r9x64eq576Kbps  (18),
        r10x56eq560Kbps (19),
        r10x64eq640Kbps (20),
        r11x56eq616Kbps (21),
        r11x64eq704Kbps (22),
        r12x56eq672Kbps (23),
        r12x64eq768Kbps (24),
        r13x56eq728Kbps (25),
        r13x64eq832Kbps (26),
        r14x56eq784Kbps (27),
        r14x64eq896Kbps (28),
        r15x56eq840Kbps (29),
        r15x64eq960Kbps (30),
        r16x56eq896Kbps (31),
        r16x64eq1024Kbps(32),
        r17x56eq952Kbps (33),
        r17x64eq1088Kbps(34),
        r18x56eq1008Kbps(35),
        r18x64eq1152Kbps(36),
        r19x56eq1064Kbps(37),
        r19x64eq1216Kbps(38),
        r20x56eq1120Kbps(39),
        r20x64eq1280Kbps(40),
        r21x56eq1176Kbps(41),
        r21x64eq1344Kbps(42),
        r22x56eq1232Kbps(43),
        r22x64eq1408Kbps(44),
        r23x56eq1288Kbps(45),
        r23x64eq1472Kbps(46),
        r24x56eq1344Kbps(47),
        r24x64eq1536Kbps(48),
        r25x56eq1400Kbps(49),
        r25x64eq1600Kbps(50),
        r26x56eq1456Kbps(51),
        r26x64eq1664Kbps(52),
        r27x56eq1512Kbps(53),
        r27x64eq1728Kbps(54),
        r28x56eq1568Kbps(55),
        r28x64eq1792Kbps(56),
        r29x56eq1624Kbps(57),
        r29x64eq1856Kbps(58),
        r30x56eq1680Kbps(59),
        r30x64eq1920Kbps(60),
        r31x56eq1736Kbps(61),
        r31x64eq1984Kbps(62),
        r32x56eq1792Kbps(63),
        r32x64eq2048Kbps(64),
		r1x1dot5eq1dot5M(65),
		r2x1dot5eq3M    (66),
		r3x1dot5eq4dot5M(67),
		r4x1dot5eq6M    (68),
		r5x1dot5eq7dot5M(69),
		r6x1dot5eq9M    (70),
		r7x1dot5eq10dot5M(71),
		r8x1dot5eq12M   (72),
		r1x2Meq2M       (73),
		r2x2Meq4M       (74),
		r3x2Meq6M       (75),
		r4x2Meq8M       (76),
		r5x2Meq10M      (77),
		r6x2Meq12M      (78),
		r7x2Meq14M      (79),
		r8x2Meq16M      (80),
		noRate         (100)
     }
      MAX-ACCESS  read-write
      STATUS  current
      DESCRIPTION
      "This attribute indicates the port speed. "
      ::= { prtInPh1MlCnfgEntry 5}

prtInPh1MlProtocol OBJECT-TYPE
      SYNTAX  INTEGER
     {
        fr                 (1),
        frPlus             (2),
        pCellRelay         (3),
        hdlcSdlc           (4),
        transparentHdlc    (5),
		ciscoBridgedEth    (6)
     }
      MAX-ACCESS  read-write
      STATUS  current
      DESCRIPTION
      "This attribute indicates the applied protocol."
      ::= { prtInPh1MlCnfgEntry 6}

prtInPh1MlConnectionTyp OBJECT-TYPE
      SYNTAX  INTEGER
     {
	    sameNetManaged  (1),
	    sameNetNotMana  (2),
	    user            (3),
	    otherNet        (4),
	    pubNet          (5),
		notApplicable (255)
     }
      MAX-ACCESS  read-write
      STATUS  current
      DESCRIPTION
      "This attribute indicates the link connection type.
       It is required for three reasons:
     FR/CR Inband management operation (LMI,CLMM...).
     CIR check.
     NMS network management.

       SameNetManaged - indicates network internal line.
       SameNetNotMana - indicates network internal line, but the remote
               mux is not managed by the nms.

       User           - User to Network Interface.
       OtherNet       - Network To Network Interfce.
       PubNet         - Access Mux To PubNet Interface."
      ::= { prtInPh1MlCnfgEntry 7}

prtInPh1MlCongResponse OBJECT-TYPE
      SYNTAX  INTEGER
     {
     no              (2),
        flowControl     (3)
     }
      MAX-ACCESS  read-write
      STATUS  current
      DESCRIPTION
"This attribute indicates how to handle the congestion indication
 to/from the mux internal connection side (for example
 transmit/receive becn to/from the network).
   no           - do nothing
   FlowControl  - translate the congestion indication between the
                  port and the internal connection port according to
                  the definition of the prtInPh1MlFlowControl
                  parameters. The operation is done in both directions."
      ::= { prtInPh1MlCnfgEntry 8}

prtInPh1MlCongLevel OBJECT-TYPE
      SYNTAX  Integer32
      MAX-ACCESS  read-write
      STATUS  current
      DESCRIPTION
      "This attribute indicates the level of delayed data in
       precents of the total available dynamic memory,
       for which the port will start to operate .
       The resolution of the parameter is 5 percent.
	   Valid values: 10..70, 255.
       255=notApplicable."
      ::= { prtInPh1MlCnfgEntry 9}

prtInPh1MlTc OBJECT-TYPE
      SYNTAX  INTEGER
          {
          tc1sec  (1),
          tc2sec  (2),
          tc3sec  (3),
          tc4sec  (4),
		  notApplicable (255)
          }
      MAX-ACCESS  read-write
      STATUS  current
      DESCRIPTION
      "This attribute indicates the Tc parameter which is the time
       period of the sliding window in which the Bc/Be are tested.
       The value of this parameter is identical for all the ports in the
       specific card.
       255=notApplicable."
      ::= { prtInPh1MlCnfgEntry 10}

prtInPh1MlFlowControl OBJECT-TYPE
      SYNTAX  INTEGER
     {
        none                (2),
        fecnBecn            (3)
     }
      MAX-ACCESS  read-write
      STATUS  current
      DESCRIPTION
      "This attribute indicates the required flow control betweeen
       the port and the remote equipment."
      ::= { prtInPh1MlCnfgEntry 11}

prtInPh1MlSegment OBJECT-TYPE
      SYNTAX  INTEGER
   {
   notApplicable (1),
   s36Byte       (2),
   s150Byte      (3),
   s264Byte      (4),
   s378Byte      (5),
   s492Byte      (6),
   s236Byte      (7),
   s472Byte      (8),
   s708Byte      (9),
   s944Byte     (10),
   s1180Byte    (11)
   }
      MAX-ACCESS  read-write
      STATUS  current
      DESCRIPTION
      "This object is the Segmentation in Bytes.
	   In protocol FR+, ISDN internals, MX 30/300 the segmentation is:

       50 (2) ,158 (3) ,266 (4) ,376 (5), 484 (6)

       In  MX 3000/4:
       For protocol FR+ (internal ISDN ports of MHS.S, MHS.U, MHS.E1, MHS.T1
       cards) segmentation values are:

       236 (7),472 (8), 708 (9), 944 (10) ,1180 (11)"

    ::= { prtInPh1MlCnfgEntry 12}

prtInPh1MlFrMngProt OBJECT-TYPE
      SYNTAX  INTEGER
   {
   notApplicable (1),
   none          (2),
   lmi           (3),
   ansiT1        (4), --Annex D
   annexA        (5)
   }
      MAX-ACCESS  read-write
      STATUS  current
      DESCRIPTION
      "This object indicates the Frame-Relay management protocol.
       ansiT1 = ANSI T1.617 Annex D (this is the default value).
       This parameter is applicable only for FR and FR+ protocols.
       When prtInPh1MlConnectionTyp = sameNetManaged, this object
       will be RO (internally determined). "
      ::= { prtInPh1MlCnfgEntry 13}

prtInPh1MlEnqPeriod OBJECT-TYPE
      SYNTAX  Integer32 (0..30)
      MAX-ACCESS  read-write
      STATUS  current
      DESCRIPTION
      "This object is the Status Enquiry Period, in seconds.
       It determines the frequency of the Status Enquiry message
       as sent by the FR user side.
       At the FR network side, it determines the timeout for this
       message reception.
    Default = 4 seconds.
       This parameter is applicable only for FR and FR+ protocols
    AND
       only when prtInPh1MlFrMngProt is NOT (notApplicable or none).
       0=notApplicable."
    ::= { prtInPh1MlCnfgEntry 14}

prtInPh1MlFullRptPeriod OBJECT-TYPE
      SYNTAX  Integer32 (0..255)
      MAX-ACCESS  read-write
      STATUS  current
      DESCRIPTION
      "This object is the Full Report Frequency.
       It determines the number of the Status Enquiry messages
       sent by the FR user side, before a Full Report Request is
       sent.
       The units are : Status Enquiry messages (periods).
    Valid values: 1 .. 255.
       255 = infinite (never sent).
       This parameter is applicable only for FR and FR+ protocols
    AND
       only when prtInPh1MlFrMngProt is NOT (notApplicable or none).
       0=notApplicable."
    ::= { prtInPh1MlCnfgEntry 15}

prtInPh1MlFrWindowSize OBJECT-TYPE
      SYNTAX  Integer32 (0..10)
      MAX-ACCESS  read-write
      STATUS  current
      DESCRIPTION
      "This object is the FR Window Size.
       It determines the number of samplings in the sliding window
       that counts the errors.
       This parameter is applicable only for FR and FR+ protocols
    AND
       only when prtInPh1MlFrMngProt is NOT (notApplicable or none).
       0=notApplicable."
    ::= { prtInPh1MlCnfgEntry 16}

prtInPh1MlErrorsThreshold OBJECT-TYPE
      SYNTAX  Integer32 (0..10)
      MAX-ACCESS  read-write
      STATUS  current
      DESCRIPTION
      "This object is the Max Errors.
       It determines the number of Status Enquiry Errors that
       occured within the FR sliding window, before this port is
       considered DOWN (threshold).
       This parameter is applicable only for FR and FR+ protocols
    AND
       only when prtInPh1MlFrMngProt is NOT (notApplicable or none).
       0=notApplicable. "
    ::= { prtInPh1MlCnfgEntry 17}

prtInPh1MlMaxIdleTime OBJECT-TYPE
     SYNTAX  Integer32 (0..1800)
     MAX-ACCESS   read-write
     STATUS   current
     DESCRIPTION
     "Move to higher prioritized connected link	after this period of
      seconds of silence on the current link.
	  0=Never. Never move to higher prioritized connected link.
      UNIT is seconds.
      Valid values are: 0, 1, 2, 3, 4, 5, 10, 20, 30, 40, 50, 60, 120, 180, 240, 300,
      360, 420, 480, 540, 600, 900, 1200, 1500, 1800.
      Attempt to Set an invalid value will result in getting the default value."
     DEFVAL { 10 }
     ::= {prtInPh1MlCnfgEntry 18}

prtInPh1MlBearerCh OBJECT-TYPE
     SYNTAX  INTEGER
	 {
      notApplicable (1),
      channelB1     (3),
      channelB2     (4),
	  chB1andchB2   (5),
	  none          (255)
	       }
	 MAX-ACCESS   read-write
     STATUS   current
     DESCRIPTION
	 "Defines which B (bearer) channels are used for transferring ISDN data.
	  Default value is: none (255).
	  anyChannel (2) is skipped because it is not in use here."
	 ::= {prtInPh1MlCnfgEntry 19}

prtInPh1MlAssociatedExCh OBJECT-TYPE
      SYNTAX  INTEGER
     {
        exPrt1        (1),
        exPrt2        (2),
		exPrt3        (3),
		exPrt4        (4),
		notApplicable (255)
     }
      MAX-ACCESS  read-write
      STATUS  current
      DESCRIPTION
      "This object indicates the external port associated to this internal
       port. At present, it is used by the Hybrid (mp2100h), MHS-4 cards which
       can have up to 64 dynamic internal ports associated with External ports.

       For ISDN cards, the value will be: notApplicable (255).
       The associated external of an ISDN internal port is represented
       by the MIB object: prtIsdnDirectoryPrtNu."
      ::= { prtInPh1MlCnfgEntry 20}

prtInPh1MlClockEncoding OBJECT-TYPE
      SYNTAX  INTEGER
	  {
	  notApplicable (1),
	  nrz           (2),
	  nrzI          (3),
	  fm0           (4),
	  manchester    (5),
	  diffManchester(6)
	  }
      MAX-ACCESS  read-write
      STATUS  current
      DESCRIPTION
      "This object is the Encoding type of the Line.
       This parameter is applicable only for FR and FR+ protocols."
	   ::= { prtInPh1MlCnfgEntry 21}

prtInPh1MlMinSeparators OBJECT-TYPE
      SYNTAX  Integer32 (0..16)
      MAX-ACCESS  read-write
      STATUS  current
      DESCRIPTION
      "Minimum number of bytes separating between two adjacent frames (HDLC item).
       0 = notApplicable"
	   ::= { prtInPh1MlCnfgEntry 22}

prtInPh1MlCcittCrc OBJECT-TYPE
      SYNTAX  INTEGER
	  {
	  notApplicable (1),
	  crc16         (2),
	  crc32         (3)
	  }
      MAX-ACCESS  read-write
      STATUS  current
      DESCRIPTION
      "This object indicates how many Bits are used for CRC (HDLC item)."
	   ::= { prtInPh1MlCnfgEntry 23}

prtInPh1MlFrameSeparator OBJECT-TYPE
      SYNTAX  INTEGER
	  {
	  notApplicable (1),
	  idles         (2),
	  flags         (3)
	  }
      MAX-ACCESS  read-write
      STATUS  current
      DESCRIPTION
      "This object indicates what should be transferred on the line when there
       are no frames to pass (HDLC item).
       idles: mean that FF will pass on the line
       flags: mean that 7E will pass on the line."
	   ::= { prtInPh1MlCnfgEntry 24}


--
-- MPH1.T1 & MPH1.E1
-- Internal port Dlci objects table
--

prtInPh1MlDlciTable  OBJECT-TYPE
     SYNTAX SEQUENCE OF PrtInPh1MlDlciEntry
     MAX-ACCESS not-accessible
     STATUS  current
     DESCRIPTION
      "The write operation into the Table Objects is valid only
       to the TmpCnfg entry."
     ::= {prtPh1MlCnfg 4}

prtInPh1MlDlciEntry OBJECT-TYPE
      SYNTAX PrtInPh1MlDlciEntry
      MAX-ACCESS not-accessible
      STATUS current
	DESCRIPTION  "An entry in table."
	INDEX {prtInPh1MlDlciCnfgIdx, prtInPh1MlDlciSltIdx, prtInPh1MlDlciPrtIdx, prtInPh1MlDlciIdx }
      ::= { prtInPh1MlDlciTable 1}

PrtInPh1MlDlciEntry ::=
      SEQUENCE {
      prtInPh1MlDlciCnfgIdx        Integer32,
      prtInPh1MlDlciSltIdx         INTEGER,
      prtInPh1MlDlciPrtIdx         INTEGER,
      prtInPh1MlDlciIdx            Integer32,

      prtInPh1MlDlciValid          INTEGER,
      prtInPh1MlDlciIConSlt        INTEGER,
      prtInPh1MlDlciIConPrt        INTEGER,
      prtInPh1MlDlciIConDlci       Integer32,

      prtInPh1MlDlciTxBc           INTEGER,
      prtInPh1MlDlciTxBe           INTEGER,
      prtInPh1MlDlciRxBc           INTEGER,
      prtInPh1MlDlciRxBe           INTEGER,

      prtInPh1MlDlciPriority       Integer32,

      prtInPh1MlDlciStatus         INTEGER
      }


prtInPh1MlDlciCnfgIdx OBJECT-TYPE
      SYNTAX  Integer32 (1..255)
      MAX-ACCESS  read-only
      STATUS  current
      DESCRIPTION
      "This attribute indicates the Idx of the Cnfg (1..100) being
       accessed.
       Idx 255 relates to the TmpCnfg. "
      ::= { prtInPh1MlDlciEntry 1}
-- In phase I only the values 1 (Cnfg1) and 255 (temp) are valid.

prtInPh1MlDlciSltIdx OBJECT-TYPE
      SYNTAX  INTEGER
     {
       io1   (5),
       io2   (6),
       io3   (7),
       io4   (8),
       io5   (9),
       io6  (10),
       io7  (11),
       io8  (12),
       io9  (13),
       io10 (14),
       io11 (15),
       io12 (16)
     }
      MAX-ACCESS  read-only
      STATUS  current
      DESCRIPTION
      "This attribute indicates a unique  slot  position where
       the card is inserted.
       In the ?004 Unit the entries io6(10)..io16) are not valid"
      ::= { prtInPh1MlDlciEntry 2}

prtInPh1MlDlciPrtIdx OBJECT-TYPE
      SYNTAX  INTEGER
 {
       inPrt1  (101) ,
       inPrt2  (102) ,
       inPrt3  (103)
       }
      MAX-ACCESS  read-only
      STATUS  current
      DESCRIPTION
      "This attribute indicates a unique internal port number.
       MPH.1/E1 and MPH.1/T1 cards have three internal ports."
      ::= { prtInPh1MlDlciEntry 3}

prtInPh1MlDlciIdx OBJECT-TYPE
      SYNTAX  Integer32 (1..991)
      MAX-ACCESS  read-only
      STATUS  current
      DESCRIPTION
      "This attribute indicates a unique index for each possible
       used dlci(16..991). When the protocol is not Multiplexing
       protocol, then its type is 'user' and the only valid index
       is 1."
      ::= { prtInPh1MlDlciEntry 4}

prtInPh1MlDlciValid OBJECT-TYPE
      SYNTAX  INTEGER
     {
     no  (2),
     yes (3)
     }
      MAX-ACCESS  read-write
      STATUS  current
      DESCRIPTION
      "This attribute indicates whether the attributes in this entry
       are valid or not. The user can add/delete pvc (dlci to dlci
       connection) by modifing this object"
      ::= { prtInPh1MlDlciEntry 5}

prtInPh1MlDlciIConSlt OBJECT-TYPE
      SYNTAX  INTEGER
 {
          noConnect(2),
    cl    (3),
       io1   (5),
       io2   (6),
       io3   (7),
       io4   (8),
       io5   (9),
       io6  (10),
       io7  (11),
       io8  (12),
       io9  (13),
       io10 (14),
       io11 (15),
       io12 (16)
       }
      MAX-ACCESS  read-write
      STATUS  current
      DESCRIPTION
      "This attribute indicates a unique slot position In the Mux
       (Agent) where the dlci is routed to.
       In the ?004 Unit the entries io6(10)..io16) are not valid"
      ::= { prtInPh1MlDlciEntry 6}

prtInPh1MlDlciIConPrt OBJECT-TYPE
      SYNTAX  INTEGER
      {
       exPrt1    (1) ,
       exPrt2    (2) ,
       exPrt3    (3) ,
       exPrt4    (4) ,
       exPrt5    (5) ,
       exPrt6    (6) ,
       exPrt7    (7) ,
       exPrt8    (8) ,
       exPrt9    (9) ,
       exPrt10  (10) ,
    clNMS    (99) ,
          noConnect (100),
       inPrt1  (101) ,
       inPrt2  (102) ,
       inPrt3  (103) ,
       inPrt4  (104) ,
       inPrt5  (105) ,
       inPrt6  (106) ,
       inPrt7  (107) ,
       inPrt8  (108) ,
       inPrt9  (109) ,
       inPrt10 (110) ,
    inPrt11 (111) ,
    inPrt12 (112)
       }
      MAX-ACCESS  read-write
      STATUS  current
      DESCRIPTION
      "This attribute indicates a unique port id which the dlci is
       routed to."
      ::= { prtInPh1MlDlciEntry 7}


prtInPh1MlDlciIConDlci OBJECT-TYPE
      SYNTAX  Integer32    (1..991)
      MAX-ACCESS  read-write
      STATUS  current
      DESCRIPTION
      "This attribute indicates a unique internal connection dlci
       number which the src dlci is routed to."
      ::= { prtInPh1MlDlciEntry 8}

prtInPh1MlDlciTxBc OBJECT-TYPE
      SYNTAX  INTEGER
        {
         full       (1),
         zero       (2),
         txBc9600bps    (3),
        txBc14200bps    (4),
        txBc19200bps    (5),
        txBc28800bps    (6),
        txBc32000bps    (7),
        txBc38400bps    (8),
        txBc48000bps    (9),
        txBc56000bps   (10),
        txBc57600bps   (11),
          txBc64Kbps   (12),
         txBc128Kbps   (13),
         txBc192Kbps   (14),
         txBc256Kbps   (15),
         txBc320Kbps   (16),
         txBc384Kbps   (17),
         txBc448Kbps   (18),
         txBc512Kbps   (19),
         txBc768Kbps   (20),
        txBc1024Kbps   (21)
        }
      MAX-ACCESS  read-write
      STATUS  current
      DESCRIPTION
      "This attribute indicates a unique Tx committed bandwidth on
       the user transmit line or at the port receive line."
      ::= { prtInPh1MlDlciEntry 9}


prtInPh1MlDlciTxBe OBJECT-TYPE
      SYNTAX  INTEGER
        {
         full       (1),
         zero       (2),
         txBe9600bps    (3),
        txBe14200bps    (4),
        txBe19200bps    (5),
        txBe28800bps    (6),
        txBe32000bps    (7),
        txBe38400bps    (8),
        txBe48000bps    (9),
        txBe56000bps   (10),
        txBe57600bps   (11),
          txBe64Kbps   (12),
         txBe128Kbps   (13),
         txBe192Kbps   (14),
         txBe256Kbps   (15),
         txBe320Kbps   (16),
         txBe384Kbps   (17),
         txBe448Kbps   (18),
         txBe512Kbps   (19),
         txBe768Kbps   (20),
        txBe1024Kbps   (21)
        }
      MAX-ACCESS  read-write
      STATUS  current
      DESCRIPTION
      "This attribute indicates a unique Tx excess bandwidth on the
      user transmit line or at the port receive line."
      ::= { prtInPh1MlDlciEntry 10}


prtInPh1MlDlciRxBc OBJECT-TYPE
      SYNTAX  INTEGER
        {
         full       (1),
         zero       (2),
         rxBc9600bps    (3),
        rxBc14200bps    (4),
        rxBc19200bps    (5),
        rxBc28800bps    (6),
        rxBc32000bps    (7),
        rxBc38400bps    (8),
        rxBc48000bps    (9),
        rxBc56000bps   (10),
        rxBc57600bps   (11),
          rxBc64Kbps   (12),
         rxBc128Kbps   (13),
         rxBc192Kbps   (14),
         rxBc256Kbps   (15),
         rxBc320Kbps   (16),
         rxBc384Kbps   (17),
         rxBc448Kbps   (18),
         rxBc512Kbps   (19),
         rxBc768Kbps   (20),
        rxBc1024Kbps   (21)
        }
      MAX-ACCESS  read-write
      STATUS  current
      DESCRIPTION
      "This attribute indicates a unique Rx committed bandwidth on
       the user receive line or at the port transmit line."
      ::= { prtInPh1MlDlciEntry 11}


prtInPh1MlDlciRxBe OBJECT-TYPE
      SYNTAX  INTEGER
        {
         full       (1),
         zero       (2),
         rxBe9600bps    (3),
        rxBe14200bps    (4),
        rxBe19200bps    (5),
        rxBe28800bps    (6),
        rxBe32000bps    (7),
        rxBe38400bps    (8),
        rxBe48000bps    (9),
        rxBe56000bps   (10),
        rxBe57600bps   (11),
          rxBe64Kbps   (12),
         rxBe128Kbps   (13),
         rxBe192Kbps   (14),
         rxBe256Kbps   (15),
         rxBe320Kbps   (16),
         rxBe384Kbps   (17),
         rxBe448Kbps   (18),
         rxBe512Kbps   (19),
         rxBe768Kbps   (20),
        rxBe1024Kbps   (21)
        }
      MAX-ACCESS  read-write
      STATUS  current
      DESCRIPTION
      "This attribute indicates a unique Rx excess bandwidth on the
      user receive line or at the port transmit line."
      ::= { prtInPh1MlDlciEntry 12}


prtInPh1MlDlciPriority OBJECT-TYPE
      SYNTAX  Integer32  (1..8)
      MAX-ACCESS  read-write
      STATUS  current
      DESCRIPTION
      "This attribute indicates a unique priority of the pcv.
       1 is the lowest priority and 8 is the highest priority."
      ::= { prtInPh1MlDlciEntry 13}



prtInPh1MlDlciStatus OBJECT-TYPE
      SYNTAX  INTEGER
 {
          disconnected (1),
          connected    (2)
       }
      MAX-ACCESS  read-only
      STATUS  current
      DESCRIPTION
      "This attribute indicates the status of the pvc. The status is
       disconnected(1) when one of the sides is programmed as
       not connected"
      ::= { prtInPh1MlDlciEntry 14}


--
-- ML-20 - High Speed Main Link card
-- External Port Objects
--
prtPhMlCnfgTable  OBJECT-TYPE
     SYNTAX SEQUENCE OF PrtPhMlCnfgEntry
     MAX-ACCESS not-accessible
     STATUS  current
     DESCRIPTION
      "The write operation into the Table Objects is valid only
       to the TmpCnfg entry."
     ::= {prtPh1MlCnfg 5}

prtPhMlCnfgEntry OBJECT-TYPE
      SYNTAX PrtPhMlCnfgEntry
      MAX-ACCESS not-accessible
      STATUS current
	DESCRIPTION  "An entry in table."
	INDEX {prtPhMlCnfgIdx, prtPhMlSltIdx, prtPhMlPrtIdx }
      ::= { prtPhMlCnfgTable 1}

PrtPhMlCnfgEntry ::=
      SEQUENCE {
      prtPhMlCnfgIdx        Integer32,
      prtPhMlSltIdx         INTEGER,
      prtPhMlPrtIdx         INTEGER,
      prtPhMlConnect        INTEGER,
      prtPhMlRate           INTEGER,
      prtPhMlCAS            INTEGER,
      prtPhMlClockMode      INTEGER,
      prtPhMlSatBuffer      INTEGER,
      prtPhMlDialProcess    INTEGER,
      prtPhMlSyncRestore    Integer32,
      prtPhMlBus            INTEGER,
      prtPhMlMfSyncSlot     INTEGER,
	  prtPhMlClockSource    INTEGER,
	  prtPhMlErrCorrection  INTEGER,
	  prtPhMlCorrectionMode INTEGER,
	  prtPhMlControlSignals INTEGER,
	  prtPhMlInterfaceType  INTEGER,
	  prtPhMlClockPolarity 	INTEGER
      }


prtPhMlCnfgIdx OBJECT-TYPE
      SYNTAX  Integer32 (1..255)
      MAX-ACCESS  read-only
      STATUS  current
      DESCRIPTION
      "This attribute indicates the Idx of the Cnfg (1..100) being
       accessed.
       Idx 255 relates to the TmpCnfg. "
      ::= { prtPhMlCnfgEntry 1}
-- In phase I only the values 1 (Cnfg1) and 255 (temp) are valid.

prtPhMlSltIdx OBJECT-TYPE
      SYNTAX  INTEGER
     {
       notApplicable (1),
       io1   (5),
       io2   (6),
       io3   (7),
       io4   (8),
       io5   (9),
       io6  (10),
       io7  (11),
       io8  (12),
       io9  (13),
       io10 (14),
       io11 (15),
       io12 (16)
     }
      MAX-ACCESS  read-only
      STATUS  current
      DESCRIPTION
      "This attribute indicates a unique  slot  position where
       the module is inserted.
       In the ?004 Unit the entries io6(10)..io12(16) are not valid.
       
       For the Vmux2100 Main Board notApplicable (1) is used."
      ::= { prtPhMlCnfgEntry 2}

prtPhMlPrtIdx OBJECT-TYPE
      SYNTAX  INTEGER
       {
       exPrt1    (1)
       }
      MAX-ACCESS  read-only
      STATUS  current
      DESCRIPTION
      "This attribute indicates a unique  port number.
       ML-20 cards have just one external interface."
      ::= { prtPhMlCnfgEntry 3}

prtPhMlConnect OBJECT-TYPE
      SYNTAX  INTEGER
       {
  no  (2),
  yes (3)
       }
      MAX-ACCESS  read-write
      STATUS  current
      DESCRIPTION
      "This attribute indicates whether the port should be considered
       in any of the mux  algorithms."
      ::= {prtPhMlCnfgEntry 4}

prtPhMlRate     OBJECT-TYPE
      SYNTAX  INTEGER
       {
        r1x64eq64Kbps    (2),
        r2x64eq128Kbps   (4),
        r3x64eq192Kbps   (6),
        r4x64eq256Kbps   (8),
        r5x64eq320Kbps  (10),
        r6x64eq384Kbps  (12),
        r7x64eq448Kbps  (14),
        r8x64eq512Kbps  (16),
        r9x64eq576Kbps  (18),
        r10x64eq640Kbps (20),
        r11x64eq704Kbps (22),
        r12x64eq768Kbps (24),
        r13x64eq832Kbps (26),
        r14x64eq896Kbps (28),
        r15x64eq960Kbps (30),
        r16x64eq1024Kbps(32),
        r17x64eq1088Kbps(34),
        r18x64eq1152Kbps(36),
        r19x64eq1216Kbps(38),
        r20x64eq1280Kbps(40),
        r21x64eq1344Kbps(42),
        r22x64eq1408Kbps(44),
        r23x64eq1472Kbps(46),
        r24x64eq1536Kbps(48),
        r25x64eq1600Kbps(50),
        r26x64eq1664Kbps(52),
        r27x64eq1728Kbps(54),
        r28x64eq1792Kbps(56),
        r29x64eq1856Kbps(58),
        r30x64eq1920Kbps(60),
        r31x64eq1984Kbps(62),
        r32x64eq2048Kbps(64),		
		auto            (70)
       }
      MAX-ACCESS  read-write
      STATUS  current
      DESCRIPTION
      "This attribute indicates the configured port speed.
       auto - rate is adapted automatically to the attached modem rate."
      ::= {prtPhMlCnfgEntry 5}

prtPhMlCAS OBJECT-TYPE
      SYNTAX  INTEGER
       {
  no  (2),
  yes (3)
       }
      MAX-ACCESS  read-write
      STATUS  current
      DESCRIPTION
      "This attribute indicates whether Channel Associated
       Signaling (CAS) is used."
      ::= {prtPhMlCnfgEntry 6}

prtPhMlClockMode OBJECT-TYPE
      SYNTAX  INTEGER
       {
          dce     (2),
          ext-dce (3),
          dte     (4)
          }
      MAX-ACCESS  read-write
      STATUS  current
      DESCRIPTION
      "Clock mode."
      ::= { prtPhMlCnfgEntry 7}

prtPhMlSatBuffer OBJECT-TYPE
      SYNTAX  INTEGER
       {
  notApplicable (1),
  no  (2),
  yes (3)
       }
      MAX-ACCESS  read-write
      STATUS  current
      DESCRIPTION
      "Satellite Buffer (+/- 256)."
      ::= {prtPhMlCnfgEntry 8}

prtPhMlDialProcess OBJECT-TYPE
      SYNTAX  INTEGER
       {
  notApplicable (1),
  no            (2),
  callIn        (3),
  callOut       (4)
       }
      MAX-ACCESS  read-write
      STATUS  current
      DESCRIPTION
      "Dial Process."
      ::= {prtPhMlCnfgEntry 9}

prtPhMlSyncRestore OBJECT-TYPE
      SYNTAX  Integer32 (0..10)
      MAX-ACCESS  read-write
      STATUS  current
      DESCRIPTION
      "Sync Restoration time, in seconds.
       notApplicable=0. "
      ::= {prtPhMlCnfgEntry 10}

prtPhMlBus OBJECT-TYPE
      SYNTAX  INTEGER
       {
  none (1),
  busA (2),
  busB (3)
       }
      MAX-ACCESS  read-write
      STATUS  current
      DESCRIPTION
      "The TDM BUS this port is linked to."
      ::= {prtPhMlCnfgEntry 11}

prtPhMlMfSyncSlot  OBJECT-TYPE
      SYNTAX  INTEGER
       {
          none  (2),
          io1   (5),
          io2   (6),
          io3   (7),
          io4   (8),
          io5   (9),
          io6  (10),
          io7  (11),
          io8  (12),
          io9  (13),
          io10 (14),
          io11 (15),
          io12 (16)
       }
      MAX-ACCESS  read-write
      STATUS  current
      DESCRIPTION
      "This attribute indicates whether the sync is synchronized
       according to a certain card and the slot of this card.
       This operation is required in order to bypass signaling of
       PCM voice channels.
       In the ?004 Unit the entries io6(10)..io12(16) are not valid"
      ::= {prtPhMlCnfgEntry 12}

prtPhMlClockSource OBJECT-TYPE
      SYNTAX  INTEGER
       {
       notApplicable (1),
       txClock       (2),
       rxClock       (3)
       }
      MAX-ACCESS  read-write
      STATUS  current
      DESCRIPTION
      "The Clock Source: TC (Tx Clock) or RC (Rx Clock) signals."
      ::= {prtPhMlCnfgEntry 13}

prtPhMlErrCorrection OBJECT-TYPE
      SYNTAX  INTEGER
       {
       notApplicable (1),
       no            (2),
       yes           (3)
       }
      MAX-ACCESS  read-write
      STATUS  current
      DESCRIPTION
      "This object indicates if Error Correction mechanism should be applied or not.
       It will be applicable only if the interface HW includes the Error Correction 
       chip."
      ::= {prtPhMlCnfgEntry 14}

prtPhMlCorrectionMode OBJECT-TYPE
      SYNTAX  INTEGER
       {
       notApplicable (1),
       random        (2),
       bursty        (3)
       }
      MAX-ACCESS  read-write
      STATUS  current
      DESCRIPTION
      "This object is applicable only when prtPhMlErrCorrection=yes.
       random - enables to correct up to 3 random errors in an 23 bit frame
                built from 12 data bits and 11 appended parity bits.
       bursty - interleaving 3 frames, allows correcting bursts of 9 bit length."
      ::= {prtPhMlCnfgEntry 15}

   
prtPhMlControlSignals OBJECT-TYPE
      SYNTAX  INTEGER
       {
       notApplicable (1),
       ignore        (2),
       implement     (3)
       }
      MAX-ACCESS  read-write
      STATUS  current
      DESCRIPTION
      "This object shows whether the Port will ignore or implement the control signals
       like DCD, CTS, DTR."
      ::= {prtPhMlCnfgEntry 16}

prtPhMlInterfaceType OBJECT-TYPE
      SYNTAX  INTEGER
       {
       notApplicable (1),
       v35           (2),
       x21           (3), -- v.11
       rs232         (4),  -- v.28
       rs449         (5),
       ei530         (6),
       ei530a        (7)
       }
      MAX-ACCESS  read-write
      STATUS  current
      DESCRIPTION
      "The SW Configurable Interface Type."
      ::= {prtPhMlCnfgEntry 17}

prtPhMlClockPolarity  OBJECT-TYPE     
	 SYNTAX  INTEGER
       {
       notApplicable   (1),
       normal          (2),
       inverted        (3)
       }
      MAX-ACCESS  read-write
      STATUS  current
      DESCRIPTION
      "This object indicates the clock polarity."
      ::= {prtPhMlCnfgEntry 18}

-- This table is an extension for new version of MAXcess
-- modules.
prtLogicalCnfgTable  OBJECT-TYPE
     SYNTAX SEQUENCE OF PrtLogicalCnfgEntry
     MAX-ACCESS not-accessible
     STATUS  current
     DESCRIPTION
      "The write operation into the Table Objects is valid only
       to the TmpCnfg entry."
     ::= {prtLogicalCnfg 1}

prtLogicalCnfgEntry OBJECT-TYPE
      SYNTAX PrtLogicalCnfgEntry
      MAX-ACCESS not-accessible
      STATUS current
	DESCRIPTION  "An entry in table."
	INDEX {prtLogicalCnfgIdx, prtLogicalSltIdx, prtLogicalPrtIdx }
      ::= { prtLogicalCnfgTable 1}

PrtLogicalCnfgEntry ::=
      SEQUENCE {
      prtLogicalCnfgIdx   Integer32,
      prtLogicalSltIdx    INTEGER,
      prtLogicalPrtIdx   Integer32,
      prtLogicalConnect    INTEGER,
      prtLogicalFunction        INTEGER,
      prtLogicalRowStatus      RowStatus
}

prtLogicalCnfgIdx OBJECT-TYPE
      SYNTAX  Integer32 (1..255)
      MAX-ACCESS  read-only
      STATUS  current
      DESCRIPTION
      "This attribute indicates the Idx of the Cnfg (1..100) being
       accessed.
       Idx 255 relates to the TmpCnfg. "
      ::= { prtLogicalCnfgEntry 1}
-- In phase I only the values 1 (Cnfg1) and 255 (temp) are valid.

prtLogicalSltIdx OBJECT-TYPE
      SYNTAX  INTEGER
            {
              io1   (5),
              io2   (6),
              io3   (7),
              io4   (8),
              io5   (9),
              io6  (10),
              io7  (11),
              io8  (12),
              io9  (13),
              io10 (14),
              io11 (15),
              io12 (16),
       notApplicable(255)
            }
      MAX-ACCESS  read-only
      STATUS  current
      DESCRIPTION
        "Slot Index.
         For ISDN BRI Ports of MX300/30,
    io1(5) = isdn1(5) and io2(6) = isdn2(6)."
      ::= { prtLogicalCnfgEntry 2}

prtLogicalPrtIdx OBJECT-TYPE
      SYNTAX  Integer32
      MAX-ACCESS  read-only
      STATUS  current
      DESCRIPTION
      "This attribute indicates a unique  port number.
       This port number should be an internal port number:
        inPrt1(101)->inPrt50(150), linkSel1(200)->linkSel50(250),
        encaps1(300)-> encaps50(350), huntGr1(101) -> huntGr10(110)."
      ::= { prtLogicalCnfgEntry 3}

prtLogicalConnect OBJECT-TYPE
      SYNTAX  INTEGER
              {
                no  (2),
             yes (3)
              }
      MAX-ACCESS  read-create
      STATUS  current
      DESCRIPTION
      "This attribute indicates whether the port should be considered
       in any of the mux  algorithms."
      ::= { prtLogicalCnfgEntry 4}

prtLogicalFunction  OBJECT-TYPE
      SYNTAX  INTEGER
              {
                notApplicable(1),
                linkSelector(2),
         encapsulator(3),
   huntGroup(4)
              }
     MAX-ACCESS   read-create
     STATUS   current
     DESCRIPTION
     "This parameter defines the function of the relevant channel."
     ::= { prtLogicalCnfgEntry 5 }

prtLogicalRowStatus  OBJECT-TYPE
     SYNTAX  RowStatus
     MAX-ACCESS   read-create
     STATUS   current
     DESCRIPTION
     "This parameter allows the NMS to create/delete logical ports.
      The only possible supported RowStatus vaules are
      active (1) and destroy (6)."
     ::= { prtLogicalCnfgEntry 6 }


-- This group contains management information for the
-- link selector function.

linkSelectorCnfgTable  OBJECT-TYPE
     SYNTAX SEQUENCE OF LinkSelectorCnfgEntry
     MAX-ACCESS not-accessible
     STATUS  current
     DESCRIPTION
      "The write operation into the Table Objects is valid only
       to the TmpCnfg entry."
     ::= { prtLogicalCnfg 2}

linkSelectorCnfgEntry OBJECT-TYPE
      SYNTAX LinkSelectorCnfgEntry
      MAX-ACCESS not-accessible
      STATUS current
	DESCRIPTION  "An entry in table."
	INDEX {linkSelectorCnfgIdx, linkSelectorSltIdx, linkSelectorPrtIdx }
      ::= { linkSelectorCnfgTable 1}

LinkSelectorCnfgEntry ::=
      SEQUENCE {
      linkSelectorCnfgIdx      Integer32,
      linkSelectorSltIdx         INTEGER,
      linkSelectorPrtIdx         Integer32,
      linkSelectorMaxIdleTime      Integer32,
      linkSelectorMode INTEGER,
      linkSelectorRevert INTEGER,
      linkSelectorMinBUSession      Integer32 
	}

linkSelectorCnfgIdx OBJECT-TYPE
      SYNTAX  Integer32 (1..255)
      MAX-ACCESS  read-only
      STATUS  current
      DESCRIPTION
      "This attribute indicates the Idx of
      the Cnfg (1..100) being accessed.
       Idx 255 relates to the TmpCnfg. "
      ::= { linkSelectorCnfgEntry 1}
-- In phase I only the values 1 (Cnfg1) and 255 (temp) are valid.

linkSelectorSltIdx OBJECT-TYPE
      SYNTAX  INTEGER
            {
              io1   (5),
              io2   (6),
              io3   (7),
              io4   (8),
              io5   (9),
              io6  (10),
              io7  (11),
              io8  (12),
              io9  (13),
              io10 (14),
              io11 (15),
              io12 (16),
       notApplicable(255)
            }
      MAX-ACCESS  read-only
      STATUS  current
      DESCRIPTION
        "Slot Index"
      ::= { linkSelectorCnfgEntry 2}

linkSelectorPrtIdx OBJECT-TYPE
      SYNTAX  Integer32
      MAX-ACCESS  read-only
      STATUS  current
      DESCRIPTION
      "This attribute indicates a unique  port number.
       This port number should be internal port number:
       higher or equal to linkSeL1(201)."
      ::= { linkSelectorCnfgEntry 3}

linkSelectorMaxIdleTime OBJECT-TYPE
     SYNTAX  Integer32 (0..255)
     MAX-ACCESS   read-write
     STATUS   current
     DESCRIPTION
     "Move to higher prioritized connected link
     after this period of seconds of silence on the current link.
     0=move immediately to higher prioritized connected link.
     UNIT is seconds."
     DEFVAL { 0 }
::= {linkSelectorCnfgEntry 4}

linkSelectorMode OBJECT-TYPE
      SYNTAX  INTEGER { notApplicable(1),
    backup(2), bod(3)       }
      MAX-ACCESS   read-write
     STATUS   current
     DESCRIPTION
     " If the link selector is in mode:
      backup(2)=then the link with the lower priority will be
                used in case of failure of the higher priority link,
      bod(3)=bandwidth on demand or dynamic bandwidth allocation
             means that links with lower priority will be used
             whenever additional bandwidth is required. "
     DEFVAL { backup }
::= {linkSelectorCnfgEntry 5}

linkSelectorRevert OBJECT-TYPE
      SYNTAX  INTEGER { notApplicable(1),
   auto(2), manual(3)       }
      MAX-ACCESS   read-write
     STATUS   current
     DESCRIPTION
     " If the link selector is in mode backup:
      auto(2)=return automatically to Main link when it is OK.
      manual(3)=stays connected to backup link."
     DEFVAL { auto }
::= {linkSelectorCnfgEntry 6}

linkSelectorMinBUSession     OBJECT-TYPE
     SYNTAX  Integer32 (1..255)
     MAX-ACCESS   read-write
     STATUS   current
     DESCRIPTION
     "Minimum duration of a backup session before
     returning to Main Link. Relevant in Backup Mode and
     when Revert is auto(2).  Value 255 is for NEVER which
     means never return to Main Link.
     UNIT is minutes."
     DEFVAL { 10 }
::= {linkSelectorCnfgEntry 7}

-- Prioritized Links
linkSelectorPLinkTable  OBJECT-TYPE
     SYNTAX SEQUENCE OF LinkSelectorPLinkEntry
     MAX-ACCESS not-accessible
     STATUS  current
     DESCRIPTION
      "The write operation into the Table Objects is valid only
       to the TmpCnfg entry."
     ::= { prtLogicalCnfg 3}

linkSelectorPLinkEntry OBJECT-TYPE
      SYNTAX LinkSelectorPLinkEntry
      MAX-ACCESS not-accessible
      STATUS current
	DESCRIPTION  "An entry in table."
	INDEX {pLinkCnfgIdx, pLinkSltIdx, pLinkPrtIdx, pLinkIdx }
      ::= { linkSelectorPLinkTable 1}

LinkSelectorPLinkEntry ::=
      SEQUENCE {
      pLinkCnfgIdx      Integer32,
      pLinkSltIdx   INTEGER,
      pLinkPrtIdx       Integer32,
      pLinkIdx         Integer32,
      pLinkSlotNu       INTEGER,
      pLinkPortNu       Integer32,
      pLinkPrioNu       Integer32,
      pLinkVRate        INTEGER
}

pLinkCnfgIdx OBJECT-TYPE
      SYNTAX  Integer32 (1..255)
      MAX-ACCESS  read-only
      STATUS  current
      DESCRIPTION
     "This attribute indicates the Idx of the Cnfg (1..100) being
       accessed.
       Idx 255 relates to the TmpCnfg. "
      ::= { linkSelectorPLinkEntry 1}
-- In phase I only the values 1 (Cnfg1) and 255 (temp) are valid.

pLinkSltIdx OBJECT-TYPE
      SYNTAX  INTEGER
            {
              io1   (5),
              io2   (6),
              io3   (7),
              io4   (8),
              io5   (9),
              io6  (10),
              io7  (11),
              io8  (12),
              io9  (13),
              io10 (14),
              io11 (15),
              io12 (16),
       notApplicable(255)
            }
      MAX-ACCESS  read-only
      STATUS  current
      DESCRIPTION
        "Slot Index"
      ::= { linkSelectorPLinkEntry 2}

pLinkPrtIdx OBJECT-TYPE
      SYNTAX  Integer32(200..250)
      MAX-ACCESS  read-only
      STATUS  current
      DESCRIPTION
      "This attribute indicates a unique  port number.
       This port number should be the link selector number."
::= { linkSelectorPLinkEntry 3}


pLinkIdx OBJECT-TYPE
      SYNTAX  Integer32 (1..8)
      MAX-ACCESS   read-only
     STATUS   current
     DESCRIPTION
     "This index is the row number."
::= { linkSelectorPLinkEntry 4}

pLinkSlotNu OBJECT-TYPE
      SYNTAX  INTEGER {
      noConnect (2), cl(3),
        io1(5),
        io2(6),
        io3(7),
        io4(8),
        io5(9),
        io6(10),
        io7(11),
        io8(12),
        io9(13),
        io10(14),
        io11(15),
        io12(16),
        notApplicable(255)
       }
     MAX-ACCESS   read-write
     STATUS   current
     DESCRIPTION
     "The slot of the prioritized link.
     For ISDN BRI ports of MX300/30,
 io1(5) = isdn1(5) and io2(6) = isdn2(6)."
     DEFVAL { noConnect }
::= { linkSelectorPLinkEntry 5 }

pLinkPortNu OBJECT-TYPE
      SYNTAX  Integer32
      MAX-ACCESS   read-write
      STATUS   current
      DESCRIPTION
      "The port of the prioritized link.
      Value 100 is for noConnect."
      DEFVAL { 100 }
::= { linkSelectorPLinkEntry 6 }

pLinkPrioNu OBJECT-TYPE
      SYNTAX  Integer32(1..8)
      MAX-ACCESS   read-write
      STATUS   current
      DESCRIPTION
      "The priority of the prioritized link.
       MIN=1...., MAX=8."
::= { linkSelectorPLinkEntry 7 }

pLinkVRate OBJECT-TYPE
       SYNTAX INTEGER {
        r1x56eq56Kbps    (1),
        r1x64eq64Kbps    (2),
        r2x56eq112Kbps   (3),
        r2x64eq128Kbps   (4),
        r3x56eq168Kbps   (5),
        r3x64eq192Kbps   (6),
        r4x56eq224Kbps   (7),
        r4x64eq256Kbps   (8),
        r5x56eq280Kbps   (9),
        r5x64eq320Kbps  (10),
        r6x56eq336Kbps  (11),
        r6x64eq384Kbps  (12),
        r7x56eq392Kbps  (13),
        r7x64eq448Kbps  (14),
        r8x56eq448Kbps  (15),
        r8x64eq512Kbps  (16),
        r9x56eq504Kbps  (17),
        r9x64eq576Kbps  (18),
        r10x56eq560Kbps (19),
        r10x64eq640Kbps (20),
        r11x56eq616Kbps (21),
        r11x64eq704Kbps (22),
        r12x56eq672Kbps (23),
        r12x64eq768Kbps (24),
        r13x56eq728Kbps (25),
        r13x64eq832Kbps (26),
        r14x56eq784Kbps (27),
        r14x64eq896Kbps (28),
        r15x56eq840Kbps (29),
        r15x64eq960Kbps (30),
        r16x56eq896Kbps (31),
        r16x64eq1024Kbps(32),
        r17x56eq952Kbps (33),
        r17x64eq1088Kbps(34),
        r18x56eq1008Kbps(35),
        r18x64eq1152Kbps(36),
        r19x56eq1064Kbps(37),
        r19x64eq1216Kbps(38),
        r20x56eq1120Kbps(39),
        r20x64eq1280Kbps(40),
        r21x56eq1176Kbps(41),
        r21x64eq1344Kbps(42),
        r22x56eq1232Kbps(43),
        r22x64eq1408Kbps(44),
        r23x56eq1288Kbps(45),
        r23x64eq1472Kbps(46),
        r24x56eq1344Kbps(47),
        r24x64eq1536Kbps(48),
        r25x56eq1400Kbps(49),
        r25x64eq1600Kbps(50),
        r26x56eq1456Kbps(51),
        r26x64eq1664Kbps(52),
        r27x56eq1512Kbps(53),
        r27x64eq1728Kbps(54),
        r28x56eq1568Kbps(55),
        r28x64eq1792Kbps(56),
        r29x56eq1624Kbps(57),
        r29x64eq1856Kbps(58),
        r30x56eq1680Kbps(59),
        r30x64eq1920Kbps(60),
        r31x56eq1736Kbps(61),
        r31x64eq1984Kbps(62),
        noRate(100)
       }
       MAX-ACCESS   read-write
       STATUS   current
       DESCRIPTION
     "The rate to use with this link."
       DEFVAL { noRate }
::= { linkSelectorPLinkEntry 8 }


--
-- Megaplex or Kilomux ?000/?004 MPH.1/3 High speed packet data cards.
-- Megaplex or Kilomux ?000/?004 MPL.6 Low speed packet data cards.
--      (Mph1, Mph3, Mpl6)
-- Maxcess 3000/3004 MLS-3/6, MHS-1/3
--
-- prtExPhPlCnfgTable  OBJECT IDENTIFIER ::= {prtPhPlCnfg 1}
-- prtExPhPlDlciTable  OBJECT IDENTIFIER ::= {prtPhPlCnfg 2}
-- prtExPhPlModemTable OBJECT IDENTIFIER ::= {prtPhPlCnfg 3}

-- Mph.1 Mph.3 Mpl.6/ Kphs.1 Kphs.3 Mls.3 Mls.6 Mhs.1 Mhs.3
-- External port objects table

prtExPhPlCnfgTable  OBJECT-TYPE
      SYNTAX SEQUENCE OF PrtExPhPlCnfgEntry
      MAX-ACCESS not-accessible
      STATUS  current
      DESCRIPTION "The write operation into the Table Objects is
      valid only to the TmpCnfg entry."
      ::= {prtPhPlCnfg 1}

prtExPhPlCnfgEntry OBJECT-TYPE
      SYNTAX PrtExPhPlCnfgEntry
      MAX-ACCESS not-accessible
      STATUS current
	DESCRIPTION  "An entry in table."
	INDEX {prtExPhPlCnfgIdx, prtExPhPlSltIdx, prtExPhPlPrtIdx}
      ::= { prtExPhPlCnfgTable 1}

PrtExPhPlCnfgEntry ::=
      SEQUENCE {
      prtExPhPlCnfgIdx            Integer32,
      prtExPhPlSltIdx             INTEGER,
      prtExPhPlPrtIdx             INTEGER,
      prtExPhPlConnect            INTEGER,
      prtExPhPlHRate              INTEGER,
      prtExPhPlLRate              INTEGER,
      prtExPhPlProtocol           INTEGER,
      prtExPhPlConnectionTyp      INTEGER,
      prtExPhPlClkMode            INTEGER,
      prtExPhPlDceClkSrc          INTEGER,
      prtExPhPlCongResponse       INTEGER,
      prtExPhPlCongLevel          Integer32,
      prtExPhPlTc                 INTEGER,
      prtExPhPlFlowControl        INTEGER,
      prtExPhPlDcdRts             INTEGER,
      prtExPhPlDcdRtsControlPath  INTEGER,
      prtExPhPlDataBits           INTEGER,
      prtExPhPlParity             INTEGER,
      prtExPhPlStopBits           INTEGER,
      prtExPhPlLXon               Integer32,
      prtExPhPlLXoff              Integer32,
	  prtExPhPlFrMngProt          INTEGER,
	  prtExPhPlEnqPeriod          Integer32,
	  prtExPhPlFullRptPeriod      Integer32,
	  prtExPhPlFrWindowSize       Integer32,
	  prtExPhPlErrorsThreshold    Integer32,
	  prtExPhPlPvcCreateMsg       INTEGER,
	  prtExPhPlCllmMsg            INTEGER,
	  prtExPhPlProtDelayLevel     INTEGER,
	  prtExPhPlClockEncoding      INTEGER,
	  prtExPhPlMinSeparators      Integer32,
	  prtExPhPlCcittCrc           INTEGER,
	  prtExPhPlFrameSeparator     INTEGER,
	  prtExPhPlIdleCode           Integer32,
	  prtExPhPlJitter             Integer32 
	}

prtExPhPlCnfgIdx OBJECT-TYPE
      SYNTAX  Integer32 (1..255)
      MAX-ACCESS  read-only
      STATUS  current
      DESCRIPTION
      "This attribute indicates the Idx of the Cnfg (1..100) being
       accessed.
       Idx 255 relates to the TmpCnfg. "
      ::= { prtExPhPlCnfgEntry 1}
-- In phase I only the values 1 (Cnfg1) and 255 (temp) are valid.

prtExPhPlSltIdx OBJECT-TYPE
      SYNTAX  INTEGER
     {
       io1   (5),
       io2   (6),
       io3   (7),
       io4   (8),
       io5   (9),
       io6  (10),
       io7  (11),
       io8  (12),
       io9  (13),
       io10 (14),
       io11 (15),
       io12 (16),
    notApplicable (255)
     }
      MAX-ACCESS  read-only
      STATUS  current
      DESCRIPTION
      "This attribute indicates a unique  slot  position where
       the card is inserted.
       In the ?004 Unit the entries io6(10)..io12(16) are not valid"
      ::= { prtExPhPlCnfgEntry 2}

prtExPhPlPrtIdx OBJECT-TYPE
      SYNTAX  INTEGER
 {
          exPrt1  (1) ,
          exPrt2  (2) ,
          exPrt3  (3) ,
          exPrt4  (4) ,
          exPrt5  (5) ,
          exPrt6  (6)
       }
      MAX-ACCESS read-only
      STATUS  current
      DESCRIPTION
      "This attribute indicates a unique port number.
       In case of PH.1 card, only exPrt(1) is valid."
      ::= { prtExPhPlCnfgEntry 3}

prtExPhPlConnect OBJECT-TYPE
      SYNTAX  INTEGER
       {
  no  (2),
  yes (3)
       }
      MAX-ACCESS  read-write
      STATUS  current
      DESCRIPTION
      "This attribute indicates whether the port should be considered
       in any of the mux  algorithms."
      ::= { prtExPhPlCnfgEntry 4}

prtExPhPlHRate OBJECT-TYPE
      SYNTAX  INTEGER
       {
        notApplicable (1),
        r32KbpsNLE    (2),
        r48KbpsNLE    (3),
        r56KbpsNLE    (4),
        r64KbpsNLE    (5),
        r112KbpsNLE   (6),
        r128KbpsNLE   (7),
        r168KbpsNLE   (8),
        r192KbpsNLE   (9),
        r224KbpsNLE  (10),
        r256KbpsNLE  (11),
        r280KbpsE    (12),
        r320KbpsE    (13),
        r336KbpsNLE  (14),
        r384KbpsNLE  (15),
        r392KbpsE    (16),
        r448KbpsNLE  (17),
        r504KbpsLE   (18), -- r504KbpsE 
        r512KbpsE    (19), -- r512KbpsNLE			  
        r560KbpsE    (20),
        r576KbpsLE   (21), -- r576KbpsE
        r616KbpsE    (22),
        r640KbpsE    (23),
        r672KbpsNLE  (24),
        r704KbpsE    (25),
        r728KbpsE    (26),
        r768KbpsNLE  (27),
        r784KbpsE    (28),
        r832KbpsE    (29),
        r840KbpsE    (30),
        r896KbpsNLE  (31),
        r952KbpsE    (32),
        r960KbpsE    (33),
       r1008KbpsLE   (34), -- r1008KbpsE
       r1024KbpsE    (35), -- r1024KbpsNLE
       r1064KbpsE    (36),
       r1088KbpsE    (37),
       r1120KbpsE    (38),
       r1152KbpsLE   (39), -- r1152KbpsE
       r1176KbpsE    (40),
       r1216KbpsE    (41),
       r1232KbpsE    (42),
       r1280KbpsE    (43),
       r1288KbpsE    (44),
       r1344KbpsNLE  (45),
       r1400KbpsE    (46),
       r1408KbpsE    (47),
       r1456KbpsE    (48),
       r1472KbpsE    (49),
       r1512KbpsE    (50),
       r1536KbpsE    (51), -- r1536KbpsNLE
       r1568KbpsE    (52),
       r1600KbpsE    (53),
       r1624KbpsE    (54),
       r1664KbpsE    (55),
       r1680KbpsE    (56),
       r1728KbpsE    (57),
       r1736KbpsE    (58),
       r1792KbpsNLE  (59),
       r1856KbpsE    (60),
       r1920KbpsE    (61),
       r1984KbpsE    (62),
       r2048KbpsE    (63), -- r2048KbpsNLE
--
--  Additional rates for: MAXcess, MP2100h 
--
       r9d6KbpsNLE   (65),
       r14d4KbpsNLE  (66),
       r16KbpsNLE    (67),
       r19d2KbpsNLE  (68),
       r28d8KbpsNLE  (69),
       r38d4KbpsNLE  (70),
       r57d6KbpsNLE  (71), -- For Mx 30/300 Only
       r115d2KbpsNLE (72),  -- For Mx 30/300 Only
       r24000bps     (73)
       }
      MAX-ACCESS  read-write
      STATUS  current
      DESCRIPTION
      "This attribute indicates the port speed for HIGH speed cards.
       The card has limitations about the maximum sigma channel
       speeds and about the possible rates for each clock mode .
       N - The rate is valid for DCE and EXT-DCE Nodal clock mode.
       L - The rate is valid for DCE and EXT-DCE Local clock mode.
       E - The rate is valid for DTE External clock mode.
       'r9d6KbpsNLE' means rate of 9.6 Kbps ('d'=dot).
       
       Note: Some rate attributes have been changed. As the MIB was already
             released with the old attributes, the names of the options were
             not changed. The new names + attributes are in a comment.
             Example:   r2048KbpsE (63), -- r2048KbpsNLE"
      ::= { prtExPhPlCnfgEntry 5}

prtExPhPlLRate  OBJECT-TYPE
      SYNTAX  INTEGER
       {
          notApplicable  (1),
          r300bpsNLE     (2),
          r600bpsNLE     (3),
          r800bpsNLE     (4),
          r1200bpsNLE    (5),
          r2400bpsNLE    (6),
          r4800bpsNLE    (7),
          r9600bpsNLE    (8),
          r14400bpsLE    (9),  -- r14400bpsNLE
          r19200bpsNLE   (10),
          r28800bpsLE    (11), -- r28800bpsNLE
          r32000bpsNLE   (12),
          r38400bpsNLE   (13),
          r48000bpsNLE   (14),
          r56000bpsNLE   (15),
          r57600bpsLE    (16), -- r57600bpsNLE
          r64000bpsNLE   (17),
          r112000bps     (18), -- For Mx 30/300 Only: r112000bpsNLE 
          r115200bps     (19), -- For Mx 30/300 Only: r115200bpsNLE
--
-- additional rates
--
         r16000bpsNLE    (20),
         r100bpsNLE      (21), -- For Mx 30/300 Only
         r128000bps      (22), -- For Mx 30/300 Only
         r24000bps       (23)
       }
      MAX-ACCESS  read-write
      STATUS  current
      DESCRIPTION
      "This attribute indicates the port speed for LOW speed cards.
       The card has limitations about the possible rates for each
       clock mode.
       N - The rate is valid for DCE and EXT-DCE Nodal clock mode.
       L - The rate is valid for DCE and EXT-DCE Local clock mode.
       E - The rate is valid for DTE External clock mode.

       Note: Some rate attributes have been changed. As the MIB was already
             released with the old attributes, the names of the options were
             not changed. The new names + attributes are in a comment.
             Example:  r57600bpsLE (16), -- r57600bpsNLE  "

      ::= { prtExPhPlCnfgEntry 6}

prtExPhPlProtocol OBJECT-TYPE
      SYNTAX  INTEGER
     {
        fr                 (1),
        frPlus             (2),
        pCellRelay         (3),
        hdlcSdlc           (4),
        transparentHdlc    (5),
        async              (6),
        asyncReliable      (7),
        activePPP          (8),
        slip               (9),
        pppAgent           (10),
        slipAgent          (11),
        transparent        (12),
        sna                (13),
		ft1Dot2            (14) -- Standard IEC 870-5-1 for Frame Transport
     }
      MAX-ACCESS  read-write
      STATUS  current
      DESCRIPTION
      "This object indicates the applied protocol."
      ::= { prtExPhPlCnfgEntry 7}

prtExPhPlConnectionTyp OBJECT-TYPE
      SYNTAX  INTEGER
     {
     sameNetManaged  (1),
     sameNetNotMana  (2),
     user            (3),
     otherNet        (4),
     pubNet          (5),
        notApplicable (255)
     }
      MAX-ACCESS  read-write
      STATUS  current
      DESCRIPTION
      "This attribute indicates the link connection type.
       It is required for three reasons:
     FR/CR Inband management opration (LMI,CLMM...).
     CIR check.
     NMS network management.

       SameNetManaged - indicates network internal line.
       SameNetMotMana - indicates network internal line, but the
                        remote mux is not managed by the NMS.

       User           - User to Network Interface.
       OtherNet       - Network To Network Interface.
       PubNet         - Access Mux To PubNet Interface."
      ::= { prtExPhPlCnfgEntry 8}

prtExPhPlClkMode OBJECT-TYPE
      SYNTAX  INTEGER
              {
                  dce     (1),
                  extDce  (2),
                  dte     (3),
      int     (4),
      lbt     (5)
              }
      MAX-ACCESS  read-write
      STATUS  current
      DESCRIPTION
      "Clock mode."
      ::= { prtExPhPlCnfgEntry 9}

prtExPhPlDceClkSrc OBJECT-TYPE
      SYNTAX  INTEGER
              {
                  notApplicable (1),
                  local         (2),
                  nodalTiming   (3)
              }
      MAX-ACCESS  read-write
      STATUS  current
      DESCRIPTION
      "This attribute indicates the source of the clock when working
       in dce or ext-dce clock mode.
       notApplicable(1) - is applied for dte(3) and lbt(5) clock modes.
	                      When clock mode is dte, the clock source is
						  always external, therefore this object's value is
						  notApplicable.
       local(2) and nodalTiming(3) - are valid in dce(1), extDce(2)
                                     or int(4) clock modes.
       The recommended clock source is local(2)."
      ::= { prtExPhPlCnfgEntry 10}

prtExPhPlCongResponse OBJECT-TYPE
      SYNTAX  INTEGER
     {
        no                  (2),
        flowControl         (3), -- duplex, to/from flow control
        toFlowControl       (4)  -- simplex , only to flow control
     }
      MAX-ACCESS  read-write
      STATUS  current
      DESCRIPTION
"This attribute indicates how to handle the congestion indication
 to/from the mux internal connection side (for example
 transmit/received becn to/from the network).
   no           - do nothing
   flowControl  - translates the congestion indication between the
                  port and the internal connection port according
                  to the definition of the prtInPh1MlFlowControl
                  parameters. The operation is done on both
                  directions.
   toFlowControl- translates the backward congestion indication
                  received from the internal connection port
                  (normally the network side) to flow control and
                  do nothing in the other direction."
      ::= { prtExPhPlCnfgEntry 11}

prtExPhPlCongLevel OBJECT-TYPE
      SYNTAX  Integer32 (0..70)
      MAX-ACCESS  read-write
      STATUS  current
      DESCRIPTION
      "This attribute indicates the level of delayed data in
       precents of total available dynamic memory,
       for which the port will start to operate as congested.
       The resolution of the parameter is 5 percent."
      ::= { prtExPhPlCnfgEntry 12}

prtExPhPlTc OBJECT-TYPE
      SYNTAX  INTEGER
          {
          tc1sec  (1),
          tc2sec  (2),
          tc3sec  (3),
          tc4sec  (4),
    notApplicable (255)
          }
      MAX-ACCESS  read-write
      STATUS  current
      DESCRIPTION
      "This attribute indicates the Tc parameter which is the time
       period of the sliding window in which the Bc/Be are tested.
       The value of this parameter is identical for all the ports
       of a  specific card ."
      ::= { prtExPhPlCnfgEntry 13}

prtExPhPlFlowControl OBJECT-TYPE
      SYNTAX  INTEGER
     {
        none                (2),
        fecnBecn            (3),
        xonXoff             (4),
        dtrCts              (5),
        speedReduction      (6)   -- simplex response only congestion to flow control
     }
      MAX-ACCESS  read-write
      STATUS  current
      DESCRIPTION
      "This attribute indicates the required flow control betweeen
       the port and the remote equipment.
       fecnBecn - is valid only for FR, FR+ and CR protocols.
       xonXoff,dtrCts - are valid only for Async protocols.
       speedReduction - is valid only for DLC protocol when the
                        Clock Mode is DCE and the Clock Source is
                        Local."
      ::= { prtExPhPlCnfgEntry 14}

prtExPhPlDcdRts OBJECT-TYPE
      SYNTAX  INTEGER
     {
        notApplicable     (1),
        on                (2),
        endToEnd          (3)
     }
      MAX-ACCESS  read-write
      STATUS  current
      DESCRIPTION
      "Protocol may require end to end connect indication over the
       network. End to end link connection establishment over the
       FR network will be indicated to the user by using DCD or
       RTS control signals, depending on the clock mode: DCE or
       DTE respectively.
       The options are :
       - On :
              DCD(DCE)/RTS(DTE) will be constantly ON no matter
              if the End to End connection is established or not.
       - End to End:
              The DCD(DCE)/RTS(DTE) will be according to the status
              of the End to End connection."
      ::= { prtExPhPlCnfgEntry 15}

prtExPhPlDcdRtsControlPath OBJECT-TYPE
      SYNTAX  INTEGER
     {
        notApplicable     (1),
        off               (2),
        on                (3)
     }
      MAX-ACCESS  read-write
      STATUS  current
      DESCRIPTION
      "Protocol may require end to end connect indication over the
       network. This parameter defines whether to take the user
       connection status (RTS(DCE)/DCD(DTE)) and forward it to the
       network side.
      - on : Transmit active connection to the network regardless
              the RTS/DCD control lines status.
      - off: Transmit active connection to the network according
              to the status of the RTS/DCD pin. "
      ::= { prtExPhPlCnfgEntry 16}

prtExPhPlDataBits OBJECT-TYPE
      SYNTAX  INTEGER
         {
         notApplicable  (1),
         dataBits7Bits (2),
         dataBits8Bits (3)
         }
      MAX-ACCESS  read-write
      STATUS  current
      DESCRIPTION
      "This attribute indicates the number of data bits in async
       frame.
       It is relevant only for Async protocols."
      ::= { prtExPhPlCnfgEntry 17}

prtExPhPlParity OBJECT-TYPE
      SYNTAX  INTEGER
         {
         notApplicable  (1),
         odd            (2),
         even           (3),
         none           (4)
         }
      MAX-ACCESS  read-write
      STATUS  current
      DESCRIPTION
      "This attribute indicates the parity operation mode in
       async frame.
       It is relevant only for Async protocols."
      ::= { prtExPhPlCnfgEntry 18}

prtExPhPlStopBits OBJECT-TYPE
      SYNTAX  INTEGER
         {
         notApplicable  (1),
         sb1Bit           (2),
         sb1dot5Bits      (3),
         sb2Bits          (4)
         }
      MAX-ACCESS  read-write
      STATUS  current
      DESCRIPTION
      "This attribute indicates the minimum number of stop bits
       in the tx async frame.
       It is relevant only for Async protocols."
      ::= { prtExPhPlCnfgEntry 19}

prtExPhPlLXon OBJECT-TYPE
      SYNTAX  Integer32
      MAX-ACCESS  read-write
      STATUS  current
      DESCRIPTION
      "This attribute indicates the character used as X-On to
       notify receive enable.
       This parameter is valid only for async protocols.
    Valid values: 0..255.
       The value 256 indicates that it's not applicable "
      ::= { prtExPhPlCnfgEntry 20}

prtExPhPlLXoff OBJECT-TYPE
      SYNTAX  Integer32
      MAX-ACCESS  read-write
      STATUS  current
      DESCRIPTION
      "This attribute indicates the character used as X-Off to
       notify receive disable.
       This parameter is valid only for async protocols.
    Valid values: 0..255.
       The value 256 indicates that it's not applicable "
      ::= { prtExPhPlCnfgEntry 21}

prtExPhPlFrMngProt OBJECT-TYPE
      SYNTAX  INTEGER
   {
   notApplicable (1),
   none          (2),
   lmi           (3),
   ansiT1        (4),  --Annex D
   annexA        (5)
   }
      MAX-ACCESS  read-write
      STATUS  current
      DESCRIPTION
      "This object indicates the Frame-Relay management protocol.
       ansiT1 = ANSI T1.617 Annex D (this is the default value).
       This parameter is applicable only for FR and FR+ protocols.
       When prtExPhPlConnectionTyp = sameNetManaged, this object
       will be RO (internally determined). "
      ::= { prtExPhPlCnfgEntry 22}

prtExPhPlEnqPeriod OBJECT-TYPE
      SYNTAX  Integer32 (1..30)
      MAX-ACCESS  read-write
      STATUS  current
      DESCRIPTION
      "This object is the Status Enquiry Period, in seconds.
       It determines the frequency of the Status Enquiry message
       as sent by the FR user side.
       At the FR network side, it determines the timeout for this
       message reception.
    Default = 4 seconds.
       This parameter is applicable only for FR and FR+ protocols
    AND
       only when prtExPhPlFrMngProt is NOT (notApplicable or none)."
    ::= { prtExPhPlCnfgEntry 23}

prtExPhPlFullRptPeriod OBJECT-TYPE
      SYNTAX  Integer32 (1..255)
      MAX-ACCESS  read-write
      STATUS  current
      DESCRIPTION
      "This object is the Full Report Frequency.
       It determines the number of the Status Enquiry messages
       sent by the FR user side, before a Full Report Request is
       sent.
       The units are : Status Enquiry messages (periods).
    Valid values: 1 .. 255.
       255 = infinite.
       This parameter is applicable only for FR and FR+ protocols
    AND
       only when prtExPhPlFrMngProt is NOT (notApplicable or none)."
    ::= { prtExPhPlCnfgEntry 24}

prtExPhPlFrWindowSize OBJECT-TYPE
      SYNTAX  Integer32 (1..10)
      MAX-ACCESS  read-write
      STATUS  current
      DESCRIPTION
      "This object is the FR Window Size.
       It determines the number of samplings in the sliding window
       that counts the errors.
       This parameter is applicable only for FR and FR+ protocols
    AND
       only when prtExPhPlFrMngProt is NOT (notApplicable or none)."
    ::= { prtExPhPlCnfgEntry 25}

prtExPhPlErrorsThreshold OBJECT-TYPE
      SYNTAX  Integer32 (1..10)
      MAX-ACCESS  read-write
      STATUS  current
      DESCRIPTION
      "This object is the Max Errors.
       It determines the number of Status Enquiry Errors that
       occured within the FR sliding window, before this port is
       considered DOWN (threshold).
       This parameter is applicable only for FR and FR+ protocols
    AND
       only when prtExPhPlFrMngProt is NOT (notApplicable or none)."
    ::= { prtExPhPlCnfgEntry 26}

prtExPhPlPvcCreateMsg OBJECT-TYPE
      SYNTAX  INTEGER
   {
   notApplicable (1),
   no            (2),
   yes           (3)
   }
      MAX-ACCESS  read-write
      STATUS  current
      DESCRIPTION
      "This object is Update Message (if required or not).
       It determines whether a message of a New PVC Creation is
       requested or not (yes/no).
       Default = no.
       This parameter is applicable only for FR and FR+ protocols
    AND
       only when prtExPhPlFrMngProt is NOT (notApplicable or none)."
    ::= { prtExPhPlCnfgEntry 27}

prtExPhPlCllmMsg OBJECT-TYPE
      SYNTAX  INTEGER
   {
   notApplicable (1),
   no            (2),
   yes           (3)
   }
      MAX-ACCESS  read-write
      STATUS  current
      DESCRIPTION
      "This object is CLLM Message (if required or not).
       It determines whether to send (or not) a congestion message
       when the port is Rx congested.
       Default = no.
       This parameter is applicable only for FR and FR+ protocols
    AND
       only when prtExPhPlFrMngProt is NOT (notApplicable or none)."
    ::= { prtExPhPlCnfgEntry 28}

prtExPhPlProtDelayLevel OBJECT-TYPE
      SYNTAX  INTEGER
	  {
	  notApplicable (1),
	  s36Byte       (2),  --level 1
	  s150Byte      (3),  --level 2
	  s264Byte      (4),  --level 3
	  s378Byte      (5),  --level 4
	  s492Byte      (6)	  --level 5
	  }
      MAX-ACCESS  read-write
      STATUS  current

      DESCRIPTION
      "This object is the Segmentation in Bytes.
       	In some cases, the enumerated values will mean
	    other segmentation values than specified:

	   Product:    MX-3000 	    MX-3000 	   MX-300/MX-30
	   Protocol:     FR+     	Transparent		FR+
	   -----------------------------------------------------
	   level 1     50 Bytes		44 Bytes		50 Bytes
	   level 2    158 Bytes	   155 Bytes	   158 Bytes
	   level 3    266 Bytes	   266 Bytes	   266 Bytes
	   level 4    376 Bytes	   377 Bytes	   376 Bytes
	   level 5    484 Bytes	   488 Bytes	   484 Bytes

	   Defval=level 1 value

       This parameter is applicable only for FR+ and
       transparent protocols."
	   ::= { prtExPhPlCnfgEntry 29}

prtExPhPlClockEncoding OBJECT-TYPE
      SYNTAX  INTEGER
	  {
	  notApplicable (1),
	  nrz           (2),
	  nrzI          (3),
	  fm0           (4),
	  manchester    (5),
	  diffManchester(6),
	  nrzISpace     (7),
	  nrzIMark      (8)
	  }
      MAX-ACCESS  read-write
      STATUS  current
      DESCRIPTION
      "This object is the Encoding type of the Line.
       This parameter is applicable only for FR and FR+ protocols.
       For MAXCESS 3000 & MP2100H: when setting to nrzI (3) the nrzI works
       as nrzI Mark.
       For MAXCESS 30/300 when setting to nrzI (3) the nrzI works as nrzI Space."
	   ::= { prtExPhPlCnfgEntry 30}

prtExPhPlMinSeparators OBJECT-TYPE
      SYNTAX  Integer32 (0..16)
      MAX-ACCESS  read-write
      STATUS  current
      DESCRIPTION
      "Minimum number of bytes separating between two adjacent frames (HDLC item).
       0 = notApplicable"
	   ::= { prtExPhPlCnfgEntry 31}

prtExPhPlCcittCrc OBJECT-TYPE
      SYNTAX  INTEGER
	  {
	  notApplicable (1),
	  crc16         (2),
	  crc32         (3)
	  }
      MAX-ACCESS  read-write
      STATUS  current
      DESCRIPTION
      "This object indicates how many Bits are used for CRC (HDLC item)."
	   ::= { prtExPhPlCnfgEntry 32}

prtExPhPlFrameSeparator OBJECT-TYPE
      SYNTAX  INTEGER
	  {
	  notApplicable (1),
	  idles         (2),
	  flags         (3)
	  }
      MAX-ACCESS  read-write
      STATUS  current
      DESCRIPTION
      "This object indicates what should be transferred on the line when there
       are no frames to pass (HDLC item).
       idles: mean that FF will pass on the line
       flags: mean that 7E will pass on the line."
	   ::= { prtExPhPlCnfgEntry 33}

prtExPhPlIdleCode       OBJECT-TYPE
      SYNTAX  Integer32
      MAX-ACCESS  read-write
      STATUS  current
      DESCRIPTION
      "Determines the code for transmission when there are no frames to transmit 
       on the line. The value should be 0 to FFH."
	   ::= { prtExPhPlCnfgEntry 34}

prtExPhPlJitter OBJECT-TYPE
      SYNTAX  Integer32  (0..1000)
      MAX-ACCESS  read-write
      STATUS  current
      DESCRIPTION
      "Maximum variant delay of the FR network, in msec."
 	   ::= { prtExPhPlCnfgEntry 35}

--
-- PH.1 & PH.3
-- External port Dlci table
--
prtExPhPlDlciTable  OBJECT-TYPE
     SYNTAX SEQUENCE OF PrtExPhPlDlciEntry
     MAX-ACCESS not-accessible
     STATUS  current
     DESCRIPTION
      "The write operation into the Table Objects is valid only
       at the TmpCnfg entry."
     ::= {prtPhPlCnfg 2}

prtExPhPlDlciEntry OBJECT-TYPE
      SYNTAX PrtExPhPlDlciEntry
      MAX-ACCESS not-accessible
      STATUS current
	DESCRIPTION  "An entry in table."
	INDEX {prtExPhPlDlciCnfgIdx, prtExPhPlDlciSltIdx, prtExPhPlDlciPrtIdx, prtExPhPlDlciIdx }
      ::= { prtExPhPlDlciTable 1}

PrtExPhPlDlciEntry ::=
      SEQUENCE {
      prtExPhPlDlciCnfgIdx        Integer32,
      prtExPhPlDlciSltIdx         INTEGER,
      prtExPhPlDlciPrtIdx         INTEGER,
      prtExPhPlDlciIdx            Integer32,

      prtExPhPlDlciValid          INTEGER,
      prtExPhPlDlciIConSlt        INTEGER,
      prtExPhPlDlciIConPrt        INTEGER,
      prtExPhPlDlciIConDlci       Integer32,

      prtExPhPlDlciTxBc           INTEGER,
      prtExPhPlDlciTxBe           INTEGER,
      prtExPhPlDlciRxBc           INTEGER,
      prtExPhPlDlciRxBe           INTEGER,

      prtExPhPlDlciPriority       Integer32,

      prtExPhPlDlciStatus         INTEGER
      }


prtExPhPlDlciCnfgIdx OBJECT-TYPE
      SYNTAX  Integer32 (1..255)
      MAX-ACCESS  read-only
      STATUS  current
      DESCRIPTION
      "This attribute indicates the Idx of the Cnfg (1..100) being
       accessed.
       Idx 255 relates to the TmpCnfg. "
      ::= { prtExPhPlDlciEntry 1}
-- In phase I only the values 1 (Cnfg1) and 255 (temp) are valid.

prtExPhPlDlciSltIdx OBJECT-TYPE
      SYNTAX  INTEGER
     {
       io1   (5),
       io2   (6),
       io3   (7),
       io4   (8),
       io5   (9),
       io6  (10),
       io7  (11),
       io8  (12),
       io9  (13),
       io10 (14),
       io11 (15),
       io12 (16),
    notApplicable (255)
     }
      MAX-ACCESS  read-only
      STATUS  current
      DESCRIPTION
      "This attribute indicates a unique  slot  position where
       the card is inserted.
       In the ?004 Unit the entries io6(10)..io16) are not valid"
      ::= { prtExPhPlDlciEntry 2}

prtExPhPlDlciPrtIdx OBJECT-TYPE
      SYNTAX  INTEGER
 {
          exPrt1  (1) ,
          exPrt2  (2) ,
          exPrt3  (3) ,
    exPrt4  (4) ,
    exPrt5  (5) ,
    exPrt6  (6)
       }
      MAX-ACCESS  read-only
      STATUS  current
      DESCRIPTION
      "This attribute indicates a unique internal port number.
       PH.1/E1 and PH.1/T1 cards have three internal ports.
       Stand-alone units may have six such ports."
      ::= { prtExPhPlDlciEntry 3}

prtExPhPlDlciIdx OBJECT-TYPE
      SYNTAX  Integer32 (1..991)
      MAX-ACCESS  read-only
      STATUS  current
      DESCRIPTION
      "This attribute indicates a unique index for each possible
       used dlci(16..991). When the protocol is not Multiplexing
       protocol, its type is 'user' and the only valid index is 1."
      ::= { prtExPhPlDlciEntry 4}

prtExPhPlDlciValid OBJECT-TYPE
      SYNTAX  INTEGER
     {
     no  (2),
     yes (3)
     }
      MAX-ACCESS  read-write
      STATUS  current
      DESCRIPTION
      "This attribute indicates whether the attributes in this
       entry are valid or not. The user can add/delete pvc (dlci
       to dlci connection) by modifing this object"
      ::= { prtExPhPlDlciEntry 5}

prtExPhPlDlciIConSlt OBJECT-TYPE
      SYNTAX  INTEGER
 {
          noConnect (2),
    cl    (3),
       io1   (5),
       io2   (6),
       io3   (7),
       io4   (8),
       io5   (9),
       io6  (10),
       io7  (11),
       io8  (12),
       io9  (13),
       io10 (14),
       io11 (15),
       io12 (16),
    notApplicable (255)
       }
      MAX-ACCESS  read-write
      STATUS  current
      DESCRIPTION
      "This attribute indicates a unique slot position In the Mux
       (Agent) where the dlci is routed to.
    cl - will represent any of the CL slots. This value can be
         selected for multiple DLCIs of the product.
       In the ?004 Unit the entries io6(10)..io16) are not valid"
      ::= { prtExPhPlDlciEntry 6}

prtExPhPlDlciIConPrt OBJECT-TYPE
      SYNTAX  INTEGER
      {
       exPrt1    (1) ,
       exPrt2    (2) ,
       exPrt3    (3) ,
       exPrt4    (4) ,
       exPrt5    (5) ,
       exPrt6    (6) ,
       exPrt7    (7) ,
       exPrt8    (8) ,
       exPrt9    (9) ,
       exPrt10  (10) ,
    clNMS      (99),
          noConnect (100),
       inPrt1  (101) ,
       inPrt2  (102) ,
       inPrt3  (103) ,
       inPrt4  (104) ,
       inPrt5  (105) ,
       inPrt6  (106) ,
       inPrt7  (107) ,
       inPrt8  (108) ,
       inPrt9  (109) ,
       inPrt10 (110)
       }
      MAX-ACCESS  read-write
      STATUS  current
      DESCRIPTION
      "This attribute indicates a unique port id which the dlci is
       routed to.
       clNMS - will be used for NMS SNMP messages. It can be any
               port of the CL card.
               This value will be selectable only if
               prtExPhPlDlciIConSlt='cl' or 'notApplicable'."
      ::= { prtExPhPlDlciEntry 7}


prtExPhPlDlciIConDlci OBJECT-TYPE
      SYNTAX  Integer32    (1..991)
      MAX-ACCESS  read-write
      STATUS  current
      DESCRIPTION
      "This attribute indicates a unique internal connection dlci
       number,  the dlci is routed to."
      ::= { prtExPhPlDlciEntry 8}

prtExPhPlDlciTxBc OBJECT-TYPE
      SYNTAX  INTEGER
        {
         full       (1),
         zero       (2),
         txBc9600bps    (3),
        txBc14400bps    (4),
        txBc19200bps    (5),
        txBc28800bps    (6),
        txBc32000bps    (7),
        txBc38400bps    (8),
        txBc48000bps    (9),
        txBc56000bps   (10),
        txBc57600bps   (11),
          txBc64Kbps   (12),
         txBc128Kbps   (13),
         txBc192Kbps   (14),
         txBc256Kbps   (15),
         txBc320Kbps   (16),
         txBc384Kbps   (17),
         txBc448Kbps   (18),
         txBc512Kbps   (19),
         txBc768Kbps   (20),
        txBc1024Kbps   (21),
--
--KM30 ; KM300 additional rates
--
        txBc16000bps   (25),
   txBc112Kbps   (26)
        }
      MAX-ACCESS  read-write
      STATUS  current
      DESCRIPTION
      "This attribute indicates a unique Tx committed bandwidth on
       the user transmit line (or at the port receive line)."
      ::= { prtExPhPlDlciEntry 9}


prtExPhPlDlciTxBe OBJECT-TYPE
      SYNTAX  INTEGER
        {
         full       (1),
         zero       (2),
         txBe9600bps    (3),
        txBe14400bps    (4),
        txBe19200bps    (5),
        txBe28800bps    (6),
        txBe32000bps    (7),
        txBe38400bps    (8),
        txBe48000bps    (9),
        txBe56000bps   (10),
        txBe57600bps   (11),
          txBe64Kbps   (12),
         txBe128Kbps   (13),
         txBe192Kbps   (14),
         txBe256Kbps   (15),
         txBe320Kbps   (16),
         txBe384Kbps   (17),
         txBe448Kbps   (18),
         txBe512Kbps   (19),
         txBe768Kbps   (20),
        txBe1024Kbps   (21),
--
--KM30 ; KM300 additional rates
--
        txBc16000bps   (25),
   txBc112Kbps   (26)
        }
      MAX-ACCESS  read-write
      STATUS  current
      DESCRIPTION
      "This attribute indicates a unique Tx excess bandwidth on the
      user transmit line (or at the port receive line)."
      ::= { prtExPhPlDlciEntry 10}


prtExPhPlDlciRxBc OBJECT-TYPE
      SYNTAX  INTEGER
        {
         full       (1),
         zero       (2),
         rxBc9600bps    (3),
        rxBc14400bps    (4),
        rxBc19200bps    (5),
        rxBc28800bps    (6),
        rxBc32000bps    (7),
        rxBc38400bps    (8),
        rxBc48000bps    (9),
        rxBc56000bps   (10),
        rxBc57600bps   (11),
        rxBc64Kbps   (12),
         rxBc128Kbps   (13),
         rxBc192Kbps   (14),
         rxBc256Kbps   (15),
         rxBc320Kbps   (16),
         rxBc384Kbps   (17),
         rxBc448Kbps   (18),
         rxBc512Kbps   (19),
         rxBc768Kbps   (20),
        rxBc1024Kbps   (21),
--
--KM30 ; KM300 additional rates
--
        rxBc16000bps   (25),
   rxBc112Kbps   (26)
        }
      MAX-ACCESS  read-write
      STATUS  current
      DESCRIPTION
      "This attribute indicates a unique Rx committed bandwidth on the
      user receive line (or at the port transmit line)."
      ::= { prtExPhPlDlciEntry 11}


prtExPhPlDlciRxBe OBJECT-TYPE
      SYNTAX  INTEGER
        {
         full       (1),
         zero       (2),
         rxBe9600bps    (3),
        rxBe14400bps    (4),
        rxBe19200bps    (5),
        rxBe28800bps    (6),
        rxBe32000bps    (7),
        rxBe38400bps    (8),
        rxBe48000bps    (9),
        rxBe56000bps   (10),
        rxBe57600bps   (11),
          rxBe64Kbps   (12),
         rxBe128Kbps   (13),
         rxBe192Kbps   (14),
         rxBe256Kbps   (15),
         rxBe320Kbps   (16),
         rxBe384Kbps   (17),
         rxBe448Kbps   (18),
         rxBe512Kbps   (19),
         rxBe768Kbps   (20),
        rxBe1024Kbps   (21),
--
--KM30 ; KM300 additional rates
--
        rxBc16000bps   (25),
   rxBc112Kbps   (26)
        }
      MAX-ACCESS  read-write
      STATUS  current
      DESCRIPTION
      "This attribute indicates a unique Rx excess bandwidth on the
      user receive line (or at the port transmit line)."
      ::= { prtExPhPlDlciEntry 12}


prtExPhPlDlciPriority OBJECT-TYPE
      SYNTAX  Integer32  (1..8)
      MAX-ACCESS  read-write
      STATUS  current
      DESCRIPTION
      "This attribute indicates a unique priority of the pcv.
       1 is the lowest priority and 8 is the highest priority."
      ::= { prtExPhPlDlciEntry 13}


prtExPhPlDlciStatus OBJECT-TYPE
      SYNTAX  INTEGER
 {
          disconnected (1),
          connected    (2)
       }
      MAX-ACCESS  read-only
      STATUS  current
      DESCRIPTION
      "This attribute indicates the status of the pvc. The status is
       disconnected(1) when one of the sides is programmed as not
       connected"
      ::= { prtExPhPlDlciEntry 14}


-- Parameters of an external Modem which is connected to a High/Low Speed
-- Port.

prtExPhPlModemTable  OBJECT-TYPE
      SYNTAX SEQUENCE OF PrtExPhPlModemEntry
      MAX-ACCESS not-accessible
      STATUS  current
      DESCRIPTION "External Modem Parameters.
      The write operation into the
      Table Objects is valid only for the TmpCnfg entry."
      ::= {prtPhPlCnfg 3}

prtExPhPlModemEntry OBJECT-TYPE
      SYNTAX PrtExPhPlModemEntry
      MAX-ACCESS not-accessible
      STATUS current
	DESCRIPTION  "An entry in table."
	INDEX {prtExPhPlModemCnfgIdx,prtExPhPlModemSltIdx,prtExPhPlModemPrtIdx}
      ::= { prtExPhPlModemTable 1}

PrtExPhPlModemEntry ::=
      SEQUENCE {
      prtExPhPlModemCnfgIdx           Integer32,
      prtExPhPlModemSltIdx            INTEGER,
      prtExPhPlModemPrtIdx            INTEGER,
      prtExPhPlModemStatus            INTEGER,
      prtExPhPlModemActivate          INTEGER,
      prtExPhPlModemMaxIdleTime       Integer32,
      prtExPhPlModemTimeBtwnCalls     Integer32,
	  prtExPhPlModemCallDelay         Integer32 
	}

prtExPhPlModemCnfgIdx OBJECT-TYPE
      SYNTAX  Integer32 (1..255)
      MAX-ACCESS  read-only
      STATUS  current
      DESCRIPTION
      "This attribute indicates the Idx of the Cnfg (1..100) being
       accessed.
       Idx 255 relates to the TmpCnfg. "
      ::= { prtExPhPlModemEntry 1}

prtExPhPlModemSltIdx OBJECT-TYPE
      SYNTAX  INTEGER
     {
       io1   (5),
       io2   (6),
       io3   (7),
       io4   (8),
       io5   (9),
       io6  (10),
       io7  (11),
       io8  (12),
       io9  (13),
       io10 (14),
       io11 (15),
       io12 (16),
       notApplicable (255)
     }
      MAX-ACCESS  read-only
      STATUS  current
      DESCRIPTION
      "This attribute indicates a unique  slot  position where
       the card is inserted.
       In the ?004 Unit the entries io6(10)..io12(16) are not valid"
      ::= { prtExPhPlModemEntry 2}

prtExPhPlModemPrtIdx OBJECT-TYPE
      SYNTAX  INTEGER
 {
          exPrt1  (1) ,
          exPrt2  (2) ,
          exPrt3  (3) ,
          exPrt4  (4) ,
          exPrt5  (5) ,
          exPrt6  (6)
       }
      MAX-ACCESS read-only
      STATUS  current
      DESCRIPTION
      "This attribute indicates a unique port number.
       In case of PH.1 card, only exPrt(1) is valid."
      ::= { prtExPhPlModemEntry 3}

prtExPhPlModemStatus OBJECT-TYPE
      SYNTAX INTEGER
      {
       disable (2),
       enable  (3),
	   relay   (4)
      }
      MAX-ACCESS  read-write
      STATUS  current
      DESCRIPTION
      "This object indicates whether a Dial Up Modem is enabled on this port.
       Default: disable
       
       For Vmux devices this object shows whether there is Modem Relay support."       
      ::= { prtExPhPlModemEntry 4}

prtExPhPlModemActivate OBJECT-TYPE
      SYNTAX INTEGER
     {
      onFirstFrame(2),
      always    (3),
      notApplicable (255)
     }
      MAX-ACCESS  read-write
      STATUS  current
      DESCRIPTION
      "This object indicates whether the Dial Up Modem is activated when
       the first frame is received or it is always activated.
       Default: onFirstFrame"
      ::= { prtExPhPlModemEntry 5}

prtExPhPlModemMaxIdleTime OBJECT-TYPE
      SYNTAX Integer32
      MAX-ACCESS  read-write
      STATUS  current
      DESCRIPTION
      "Max Time allowed in Seconds without any traffic before the line
       is disconnected.

       Legal Values are: 1 sec, 2 sec .. 5 sec, 10 sec, 20 sec..
       1 min, 2 min .. 10 min, 15 min, 20 min, 25 min, 30 min.
       65535 sec. means that this parameter is not applicable. 

       Default: 1 sec."
       ::= { prtExPhPlModemEntry 6}

prtExPhPlModemTimeBtwnCalls OBJECT-TYPE
      SYNTAX Integer32
      MAX-ACCESS  read-write
      STATUS  current
      DESCRIPTION
      "Minimum Time in Seconds which is required after a call was
       disconnected. In this time no other call will be initiated
       from this Modem port even if there were frames transmitted
       to this port. This time is required for some Modems which
       have initializations that take a few seconds.
       
       Legal Values are:
	   0 sec. - 30 sec., 1-5 min.
       65535 sec. means that this parameter is not applicable. 

       Default: 0 sec"
       ::= { prtExPhPlModemEntry 7}

prtExPhPlModemCallDelay OBJECT-TYPE
      SYNTAX Integer32
      MAX-ACCESS  read-write
      STATUS  current
      DESCRIPTION
      "Time in Seconds that the device will wait before dialing to the remote
	   device.
	   
	   This feature is mostly used when there is a backup modem to the 
	   main link and the main link is down. In this case it is important to prevent
	   the 2 devices from dialing through the backup modems to each other at the same time.
	   It is advised to configure one side with a small call delay and the other side
	   with a large call delay.
       
       Legal Values are:
	   0 - 30, 60, 120, 180, 240, 300, 600, 900, 1200, 1500, 1800 . 
       65535 sec. means that this parameter is not applicable. 

       Default: 0 sec"
       ::= { prtExPhPlModemEntry 8}

--
-- Megaplex ?000/?004 LS-2 TDM I/O family card include:
-- Ls2-CCITT-X.50, Ls2-CCITT-X.58, Ls2-AT&T-SDM
--
--prtExLs2CnfgTable OBJECT IDENTIFIER ::= {prtLs2Cnfg 1}
--prtInLs2CnfgTable OBJECT IDENTIFIER ::= {prtLs2Cnfg 2}

prtExLs2CnfgTable OBJECT-TYPE
      SYNTAX SEQUENCE OF PrtExLs2CnfgEntry
      MAX-ACCESS not-accessible
      STATUS  current
      DESCRIPTION
       "The write operation into the Table Objects is valid only
        to the TmpCnfg entry."
      ::= {prtLs2Cnfg 1}

prtExLs2CnfgEntry OBJECT-TYPE
      SYNTAX PrtExLs2CnfgEntry
      MAX-ACCESS not-accessible
      STATUS current
	DESCRIPTION  "An entry in table."
	INDEX {prtExLs2CnfgIdx, prtExLs2SltIdx, prtExLs2PrtIdx }
      ::= {prtExLs2CnfgTable  1}

PrtExLs2CnfgEntry ::=
      SEQUENCE {
        prtExLs2CnfgIdx   Integer32,
        prtExLs2SltIdx    INTEGER,
        prtExLs2PrtIdx    INTEGER,
        prtExLs2Connect   INTEGER,
        prtExLs2Rate      INTEGER,
        prtExLs2ClkMode   INTEGER,
        prtExLs2Cts       INTEGER,
        prtExLs2Dcd       INTEGER,
        prtExLs2EnvIdx    Integer32 
	}

prtExLs2CnfgIdx OBJECT-TYPE
      SYNTAX  Integer32 (1..255)
      MAX-ACCESS  read-only
      STATUS  current
      DESCRIPTION
      "This attribute indicates the Idx of the Cnfg (1..100) being
       accessed.
       Idx  255 relates to the TmpCnfg"
      ::= {prtExLs2CnfgEntry 1}
-- In phase I only the values 1 (Cnfg1) and 255 (temp) are valid.

prtExLs2SltIdx OBJECT-TYPE
      SYNTAX  INTEGER
          {
       io1   (5),
       io2   (6),
       io3   (7),
       io4   (8),
       io5   (9),
       io6  (10),
       io7  (11),
       io8  (12),
       io9  (13),
       io10 (14),
       io11 (15),
       io12 (16)
       }
      MAX-ACCESS  read-only
      STATUS  current
      DESCRIPTION
      "This attribute indicates a unique  slot  position where
       the card is inserted.
       In the ?004 Unit the entries io6(10)..io16) are not valid."
      ::= {prtExLs2CnfgEntry 2}

prtExLs2PrtIdx OBJECT-TYPE
      SYNTAX  INTEGER
          {
          exPrt1    (1) ,
          exPrt2    (2) ,
          exPrt3    (3) ,
          exPrt4    (4) ,
          exPrt5    (5) ,
          exPrt6    (6) ,
          exPrt7    (7) ,
          exPrt8    (8) ,
          exPrt9    (9) ,
          exPrt10  (10)
          }
      MAX-ACCESS  read-only
      STATUS  current
      DESCRIPTION
      "This attribute indicates a unique  port index.
      For the Ls2/X.58 exPrt(7)..exPrt(10) are not valid."
      ::= {prtExLs2CnfgEntry 3}


prtExLs2Connect OBJECT-TYPE
      SYNTAX  INTEGER
              {
                no  (2),
                yes (3)
              }
      MAX-ACCESS  read-write
      STATUS  current
      DESCRIPTION
      "This attribute indicates whether the  port  should be
       considered in any of the mux algorithms."
      ::= {prtExLs2CnfgEntry 4}

prtExLs2Rate OBJECT-TYPE
      SYNTAX  INTEGER
       {
          r2400bps  (2),
          r4800bps  (3),
          r9600bps  (4),
          r19200bps (5)
       }
      MAX-ACCESS  read-write
      STATUS  current
      DESCRIPTION
      "Port rates."
      ::= {prtExLs2CnfgEntry 5}

prtExLs2ClkMode OBJECT-TYPE
      SYNTAX  INTEGER
       {
          dce     (1),
          ext-dce (2),
          dte     (3)
       }
      MAX-ACCESS  read-write
      STATUS  current
      DESCRIPTION
      "This attribute indicates a unique port operation clock mode."
      ::= {prtExLs2CnfgEntry 6}

prtExLs2Cts OBJECT-TYPE
      SYNTAX  INTEGER
       {
    on       (2),
    rts-min  (3),
    rts-max  (4)
       }
      MAX-ACCESS  read-write
      STATUS  current
      DESCRIPTION
      "CTS."
      ::= {prtExLs2CnfgEntry 7}

prtExLs2Dcd OBJECT-TYPE
      SYNTAX  INTEGER
       {
    on        (2),
    card-sync (3)
       }
      MAX-ACCESS  read-write
      STATUS  current
      DESCRIPTION
      "DCD."
      ::= {prtExLs2CnfgEntry 8}

prtExLs2EnvIdx OBJECT-TYPE
      SYNTAX  Integer32 (0..24)
      MAX-ACCESS  read-write
      STATUS  current
      DESCRIPTION
      "Envelope Index.
       When prtInLs2EnvAssign=auto, the value is 0 (not applicable)."
      ::= {prtExLs2CnfgEntry 9}

-- Ls2 Internal composit channel parameters
--
prtInLs2CnfgTable OBJECT-TYPE
      SYNTAX SEQUENCE OF PrtInLs2CnfgEntry
      MAX-ACCESS not-accessible
      STATUS  current
      DESCRIPTION
       "The write operation into the Table Objects is valid only
        to the TmpCnfg entry."
      ::= {prtLs2Cnfg 2}

prtInLs2CnfgEntry OBJECT-TYPE
      SYNTAX PrtInLs2CnfgEntry
      MAX-ACCESS not-accessible
      STATUS current
	DESCRIPTION  "An entry in table."
	INDEX {prtInLs2CnfgIdx, prtInLs2SltIdx, prtInLs2PrtIdx }
      ::= {prtInLs2CnfgTable 1}

PrtInLs2CnfgEntry ::=
      SEQUENCE {
        prtInLs2CnfgIdx   Integer32,
        prtInLs2SltIdx    INTEGER,
        prtInLs2PrtIdx    INTEGER,
        prtInLs2Connect   INTEGER,
        prtInLs2Group     Integer32,
        prtInLs2Member    Integer32,
        prtInLs2LinkTo    INTEGER,
        prtInLs2EnvAssign INTEGER
      }

prtInLs2CnfgIdx OBJECT-TYPE
      SYNTAX  Integer32 (1..255)
      MAX-ACCESS  read-only
      STATUS  current
      DESCRIPTION
      "This attribute indicates the Idx of the Cnfg (1..100) being
       accessed.
       Idx  255 relates to the TmpCnfg"
      ::= {prtInLs2CnfgEntry 1}
-- In phase I only the values 1 (Cnfg1) and 255 (temp) are valid.

prtInLs2SltIdx OBJECT-TYPE
      SYNTAX  INTEGER
          {
       io1   (5),
       io2   (6),
       io3   (7),
       io4   (8),
       io5   (9),
       io6  (10),
       io7  (11),
       io8  (12),
       io9  (13),
       io10 (14),
       io11 (15),
       io12 (16)
       }
      MAX-ACCESS  read-only
      STATUS  current
      DESCRIPTION
      "This attribute indicates a unique  slot  position where
       the card is inserted.
       In the ?004 Unit the entries io6(10)..io16) are not valid."
      ::= {prtInLs2CnfgEntry 2}

prtInLs2PrtIdx OBJECT-TYPE
      SYNTAX  INTEGER
          {
          inPrt1    (101),
    inPrt2    (102)
          }
      MAX-ACCESS  read-only
      STATUS  current
      DESCRIPTION
      "This attribute indicates a unique internal port index."
      ::= {prtInLs2CnfgEntry 3}

prtInLs2Connect OBJECT-TYPE
      SYNTAX  INTEGER
              {
                no  (2),
                yes (3)
              }
      MAX-ACCESS  read-write
      STATUS  current
      DESCRIPTION
      "This attribute indicates whether the port should be considered in
       any of the mux  algorithms. It also affects all the module
       considerations because the module has only one Internal
       interface which is the composite channel."
      ::= {prtInLs2CnfgEntry 4}

prtInLs2Group OBJECT-TYPE
      SYNTAX  Integer32 (1..12)
      MAX-ACCESS  read-write
      STATUS  current
      DESCRIPTION
      "This attribute indicates the group number of the port.
       LS-2 internal ports with the same group number share the same Time slot of the main
       link"
      ::= {prtInLs2CnfgEntry 5}

prtInLs2Member OBJECT-TYPE
      SYNTAX  Integer32 (1..4)
      MAX-ACCESS  read-write
      STATUS  current
      DESCRIPTION
      "This attribute indicates the group member id of the port.
       This parameter is for the automatic envelope assignment
       algorithm."
      ::= {prtInLs2CnfgEntry 6}

prtInLs2LinkTo OBJECT-TYPE
      SYNTAX  INTEGER
       {
       io1   (5),
       io2   (6),
       io3   (7),
       io4   (8),
       io5   (9),
       io6  (10),
       io7  (11),
       io8  (12),
       io9  (13),
       io10 (14),
       io11 (15),
       io12 (16)
       }
      MAX-ACCESS  read-write
      STATUS  deprecated
      DESCRIPTION
      "It indicates the slot of the main link card to which the
       LS2 card is mapped.
       STATUS  deprecated - this object is replaced by prtGenCnfgLinkToSlot
       and prtGenCnfgLinkToPort."
      ::= {prtInLs2CnfgEntry 7}

prtInLs2EnvAssign OBJECT-TYPE
      SYNTAX  INTEGER
       {
        auto    (2),
        manual  (3)
       }
      MAX-ACCESS  read-write
      STATUS  current
      DESCRIPTION
      "Envelope assignment type."
      ::= {prtInLs2CnfgEntry 8}


--
-- Megaplex?000/?004 VC-2, VC-6, VC-2/R2, VC-Q TDM I/O family port.
-- (Vc2E&m,Vc2Fxs1Plar,Vc2Fxo1,Vc2Fxs2,Vc2Fxo2,Vc2Fxs3,Vc2Fxo3)
-- Vc6E&M, Vc6Fxo, Vc6Fxs, Vc6aE&M, Vc6aFxo, Vc6aFxs
-- Vc2/R2(Fxs)
-- VC-Q
-- VC-12, VC-12/6
-- VC-8,  VC-16

prtVc2CnfgTable OBJECT-TYPE
      SYNTAX SEQUENCE OF PrtVc2CnfgEntry
      MAX-ACCESS not-accessible
      STATUS  current
      DESCRIPTION
       "- For products supporting more than one configuration, the write operation 
          into the Table is valid only to the TmpCnfg entry.
        - For products that do not support configurations, the write operation 
          into the Table will be to prtVc2CnfgIdx=1."
      ::= { cnfgPrtMux 5}

prtVc2CnfgEntry OBJECT-TYPE
      SYNTAX PrtVc2CnfgEntry
      MAX-ACCESS not-accessible
      STATUS current
	DESCRIPTION  "An entry in table."
	INDEX {prtVc2CnfgIdx, prtVc2SltIdx, prtVc2PrtIdx }
      ::= { prtVc2CnfgTable 1}

PrtVc2CnfgEntry ::=
      SEQUENCE {
        prtVc2CnfgIdx       Integer32,
        prtVc2SltIdx        INTEGER,
        prtVc2PrtIdx        Integer32,

        prtExVc2Connect     INTEGER,
        prtExVc2TransGain   Integer32,
        prtExVc2ReceiveGain Integer32,
        prtExVc2Wire        INTEGER,
        prtExVc2CodingLaw   INTEGER,
        prtExVc2Sig         INTEGER,
        prtExVc2Oos         INTEGER,
        prtExVc2LinkTo      INTEGER,
        prtExVc2OperMode    INTEGER,
        prtExVc2SigProfile  INTEGER,
        prtExVc2CallEnable  INTEGER,
        prtExVc2R2Delay     INTEGER,
        prtExVc2CasStd      INTEGER,
        prtExVc2EchoCanceler INTEGER,
        prtExVc2IfType      INTEGER,
        prtExVc2Encoding    INTEGER,
        prtExVc2TxBitCode   OCTET STRING,
        prtExVc2RxBitOutput OCTET STRING,
		prtExVc2MeterRate   INTEGER,
		prtExVc2IfSignaling INTEGER,
        prtExVc2SeizeAck    INTEGER,
        prtExVc2EandMType   INTEGER,
		prtExVc2RemType     INTEGER,
		prtExVc2ConvTime    INTEGER,
		prtExVc2SigFeedback INTEGER,
		prtExVc2EchoCancelerModule INTEGER,
		prtExVc2ReversePolarity    INTEGER,
		prtExVc2RingerFrequency    INTEGER,
		prtExVc2SigService         INTEGER,
		prtExVc2CallerIdEnable     INTEGER,
		prtExVc2CompressMethod     INTEGER,
		prtExVc2ObMode             INTEGER,
		prtExVc2VAD                INTEGER,
		prtExVc2NoiseLevelForVAD   INTEGER,
		prtExVc2WesternSigMode     INTEGER,
		prtExVc2BusProtectionPoint INTEGER,	--not used
		prtExVc2ImpedanceStandard  INTEGER
      }

prtVc2CnfgIdx OBJECT-TYPE
      SYNTAX  Integer32  (1..255)
      MAX-ACCESS  read-only
      STATUS  current
      DESCRIPTION
      "This attribute indicates the Idx of the Cnfg (1..100) being
       accessed.
       Idx  255 relates to the TmpCnfg"
      ::= {prtVc2CnfgEntry 1}
-- In phase I only the values 1 (Cnfg1) and 255 (temp) are valid.

prtVc2SltIdx OBJECT-TYPE
      SYNTAX  INTEGER
 {
       io1   (5),
       io2   (6),
       io3   (7),
       io4   (8),
       io5   (9),
       io6  (10),
       io7  (11),
       io8  (12),
       io9  (13),
       io10 (14),
       io11 (15),
       io12 (16),
       notApplicable (255)
 }
      MAX-ACCESS  read-only
      STATUS  current
      DESCRIPTION
      "This attribute indicates a unique  slot  position where
       the card is inserted.
       For Stand Alone products like WR: notApplicable (255)"
      ::= {prtVc2CnfgEntry 2}

prtVc2PrtIdx OBJECT-TYPE
      SYNTAX  Integer32
      MAX-ACCESS  read-only
      STATUS  current
      DESCRIPTION
      "A unique identifier of the port, within the card.
       For MP-2100/2200 card ports, Web Ranger and FCD-IP Voice ports 
 	   the values will be:
       exPrt1    (1) 
       exPrt2    (2) 
       exPrt3    (3) 
       exPrt4    (4) 
       exPrt5    (5) 
       exPrt6    (6) 
       exPrt7    (7) 
       exPrt8    (8) 
       exPrt9    (9) 
       exPrt10  (10) 
       exPrt11  (11) 
       exPrt12  (12)
       exPrt13  (13) 
       exPrt14  (14) 
       exPrt15  (15) 
       exPrt16  (16) 
 	   
	   For LA-240:
	     The index for fixed voice ports will be - 
	       exPrt6    (6) 
           exPrt7    (7) 
           exPrt8    (8) 
           exPrt9    (9) 
		 The index for voice card ports will be - 
		   Slot number * 100 + ch (for IO-1: 101..104, for IO-2: 201..204).
	   For other products' index see their specification."
      ::= {prtVc2CnfgEntry 3}

prtExVc2Connect OBJECT-TYPE
      SYNTAX  INTEGER
              {
                no  (2),
                yes (3),
				v51 (4),
				v52 (5) 
              }
      MAX-ACCESS  read-write
      STATUS  current
      DESCRIPTION
      "This attribute indicates whether the  port  should be
       considered in any of the mux algorithms."
      ::= {prtVc2CnfgEntry 4}

prtExVc2TransGain OBJECT-TYPE
      SYNTAX  Integer32
      MAX-ACCESS  read-write
      STATUS  current
      DESCRIPTION
      "Transmit gain in dBm.
       For ports of MP-104/204, MP-2100/2200  VC-6A, VC-6AG, VC-8
       VC-4/Omni and VC-16 cards, the units will be 0.1dBm because 
       valid values can be in 0.5dBm steps."
      ::= {prtVc2CnfgEntry 5}

prtExVc2ReceiveGain OBJECT-TYPE
      SYNTAX  Integer32
      MAX-ACCESS  read-write
      STATUS  current
      DESCRIPTION
      "Receive gain in dBm.
       For ports of MP-104/204, MP-2100/2200  VC-6A, VC-6AG, VC-8
       VC-4/Omni and VC-16 cards, the units will be 0.1dBm because 
       valid values can be in 0.5dBm steps."
      ::= {prtVc2CnfgEntry 6}

prtExVc2Wire OBJECT-TYPE
      SYNTAX  INTEGER
       {
          w2wire   (1),
          w4wire   (2),
		  notApplicable  (255)
       }
      MAX-ACCESS  read-write
      STATUS  current
      DESCRIPTION
      "For some cards, this object is equal for all the ports in the specific
       card because of HW limitations.
       For FXO & FXS this parameter is not applicable."
      ::= {prtVc2CnfgEntry 7}

prtExVc2CodingLaw OBJECT-TYPE
      SYNTAX  INTEGER
       {
          aLAW    (1),
          uLAW    (2)
       }
      MAX-ACCESS  read-write
      STATUS  current
      DESCRIPTION
      "This attribute indicates the Method/Law for decoding/encoding the voice
       information.
       aLaw(1) is the standard Law for E1 links.
       uLaw(2) is the standard Law for T1 links.

       This object is equal for all the ports in the specific module because
       of HW limitations"
      ::= {prtVc2CnfgEntry 8}

prtExVc2Sig OBJECT-TYPE
      SYNTAX  INTEGER
       {
          noSignaling           (1),
          robbedBitMultiFrame   (2),
          chAssociatedE1        (3),
          robbedBitFrame        (4)
       }
      MAX-ACCESS  read-write
      STATUS  current
      DESCRIPTION
      "This attribute indicates the method for decoding/encoding the signaling
       information(on/off hook).
       noSignaling        (1) - not using signaling (only voice).
       robbedBitMultiFrame(2) - is the standard method for T1 links and
                                proprietary method for E1 links.
       chAssociatedE1     (3) - is valid only for E1 G.732S links.
       robbedBitFrame     (4) - is proprietary method implimenting 7 bit for
                                the voice and 1 bit dedicated for signaling.

       For some cards, this object is equal for all the ports in the specific module 
       because of HW limitations."
      ::= {prtVc2CnfgEntry 9}

prtExVc2Oos OBJECT-TYPE
      SYNTAX  INTEGER
       {
          forcedIdle     (1),
          forcedBusy     (2),
          busyIdle       (3),
          idleBusy       (4),
          notApplicable  (5)
       }
      MAX-ACCESS  read-write
      STATUS  current
      DESCRIPTION
      "This object is equal for all the ports in the specific card
       because of HW limitations"
      ::= {prtVc2CnfgEntry 10}

prtExVc2LinkTo OBJECT-TYPE
      SYNTAX  INTEGER
       {
       io1   (5),
       io2   (6),
       io3   (7),
       io4   (8),
       io5   (9),
       io6  (10),
       io7  (11),
       io8  (12),
       io9  (13),
       io10 (14),
       io11 (15),
       io12 (16),
	   notApplicable  (255)
       }
      MAX-ACCESS  read-write
      STATUS  deprecated
      DESCRIPTION
      "This attribute indicates the slot of the ML card to which
       the VC card is mapped.
       STATUS  deprecated - this object is replaced by prtGenCnfgLinkToSlot
       and prtGenCnfgLinkToPort."
      ::= {prtVc2CnfgEntry 11}

prtExVc2OperMode OBJECT-TYPE
      SYNTAX  INTEGER
       {
       normal          (2),
       unidirectRx     (3),
       broadcast       (4)
       }
      MAX-ACCESS  read-write
      STATUS  current
      DESCRIPTION
      "This object indicates the operation mode of the port.
       normal = bi-directional (Tx/Rx)
       unidirectRx = unidirectional Rx.
       broadcast = Tx upon request."
      ::= {prtVc2CnfgEntry 12}


prtExVc2SigProfile OBJECT-TYPE
      SYNTAX  INTEGER
       {
       notApplicable   (1),
       manual          (2),
       p1              (3),
       p2              (4),
       p3Fxo3S3        (5),
       reversePolarity (6),	 --3RP
       meteringPulse   (7),	 --3MP
	   p4              (8)
       }
      MAX-ACCESS  read-write
      STATUS  current
      DESCRIPTION
      "This object indicates the Signaling Profile of the port.
       notApplicable - for VC-2 family and when
                       prtExVc2Sig=noSignaling(1)
       p1 = profile 1
       p2 = profile 2
       p3 = profile 3 
       p4 = profile 4 "
      ::= {prtVc2CnfgEntry 13}

prtExVc2CallEnable OBJECT-TYPE
      SYNTAX  INTEGER
       {
       notApplicable (1),
       incoming      (2),
       outgoing      (3),
       both          (4)
       }
      MAX-ACCESS  read-write
      STATUS  current
      DESCRIPTION
      "This object indicates the Enabled Call direction.
       notApplicable - for all cards except VC-2/R2.
       both     - incoming + outgoing."
      ::= {prtVc2CnfgEntry 14}

prtExVc2R2Delay OBJECT-TYPE
      SYNTAX  INTEGER
       {
       notApplicable (1),
       terrestrial   (2),
       satellite     (3)
       }
      MAX-ACCESS  read-write
      STATUS  current
      DESCRIPTION
      "This object indicates the R2 Delay.
       notApplicable - for all cards except VC-2/R2."
      ::= {prtVc2CnfgEntry 15}

prtExVc2CasStd OBJECT-TYPE
      SYNTAX  INTEGER
       {
       notApplicable (1),
       r2Q422        (2),
       specialA      (3),
       specialB      (4),
	   specialC      (5),
	   specialD      (6),
	   specialE      (7),
   	   specialF      (8),
       specialG      (9)
       }
      MAX-ACCESS  read-write
      STATUS  current
      DESCRIPTION
      "This object indicates the CAS (Channel Associated Signaling)
       Standard.
       notApplicable - for all cards except VC-2/R2."
      ::= {prtVc2CnfgEntry 16}

prtExVc2EchoCanceler OBJECT-TYPE
      SYNTAX  INTEGER
       {
       notApplicable (1),
          off    (2),
          on     (3)
       }
      MAX-ACCESS  read-write
      STATUS  current
      DESCRIPTION
      "Echo canceler activation.
       notApplicable - for VC-2 and VC-6 cards."
      ::= {prtVc2CnfgEntry 17}

prtExVc2IfType OBJECT-TYPE
      SYNTAX  INTEGER
       {
       notApplicable (1),
       w2Em     (2),
       w4Em     (3),
       fxo      (4),
       fxs      (5)
       }
      MAX-ACCESS  read-write
      STATUS  current
      DESCRIPTION
      "Interface Type."
      ::= {prtVc2CnfgEntry 18}

prtExVc2Encoding OBJECT-TYPE
      SYNTAX  INTEGER
       {
          notApplicable (1),
          pcm           (2),
          adpcm         (3),
		  linear        (4)
       }
      MAX-ACCESS  read-write
      STATUS  current
      DESCRIPTION
      "Voice Encoding Mode.
       linear - is relevant only for the ports of VC-16A card."
      ::= {prtVc2CnfgEntry 19}

prtExVc2TxBitCode OBJECT-TYPE
      SYNTAX  OCTET STRING
      MAX-ACCESS  read-write
      STATUS  current
      DESCRIPTION
      "
       - - - For MP & FCD - - -

       This object represents 4 parameters, by 2 Octets :
       Tx D Bit Code-MSB nibble,
       Tx C Bit Code-    nibble,
       Tx B Bit Code-    nibble,
       Tx A Bit Code-LSB nibble.

       Each nibble:
    0 hex = 0000 = Not Applicable
    1 hex = 0001 = M lead
    2 hex = 0010 = M lead inverse
    3 hex = 0011 = Reverse Polarity
    4 hex = 0100 = Metering Pulse
    5 hex = 0101 = Forced 1
    6 hex = 0110 = Forced 0
    7-F hex - not used (invalid values)
       This object will be RO if prtExVc2SigProfile is NOT manual.
      
       
      - - - For WR II - - -

   This object represents the following 4 parameters by 2 Octets:
   1. On/Off hook signaling transmission mode from the FXS towards the T1/E1 (MSB nibble 1).
   2. Default signaling bits that are not in use (nibble 2).
   3. Ring Detection signaling transmission mode from the FXO towards the T1/E1(nibble 3).
   4. M (Mouth) Signaling transmission mode from the E&M towards the T1/E1(LSB nibble 4). 

      Each nibble:
	---------------------------------------------------------------------------------------
	Value          On/Off Hook       Default sig.      Ring Detect.        M (Mouth)
	---------------------------------------------------------------------------------------
    0 hex = 0000   Not Applicable    Not Applicable.  Not Applicable	   Not Applicable
    1 hex = 0001   Tx A bit			 Values 1-3 are	  Tx A bit			   Tx A bit
    2 hex = 0010   Tx A bit inverse	 for On/Off Hook  Tx A bit inv.	  	   Tx A bit inv.
    3 hex = 0011   Tx B bit			 A,B,A Inv,B Inv. Tx B bit			   Tx B bit
    4 hex = 0100   Tx B bit inverse	 Values 4-7 are	  Tx B bit inv.		   Tx B bit inv.
    5 hex = 0101   not Used-invalid	 for On/Off Hook  not Used-invalid	   not Used-invalid
    6 hex = 0110   not Used-invalid	 A, A Inverse.	  not Used-invalid 	   not Used-invalid
    7 hex = 0111   not Used-invalid			 		  not Used-invalid	   not Used-invalid	 
    8 hex = 1000   not Used-invalid	 Values 8-11 are  not Used-invalid	   not Used-invalid
    9 hex = 1001   not Used-invalid	 for On/Off Hook  not Used-invalid	   not Used-invalid
	A hex = 1010   not used-invalid	 B, B Inverse.	  not Used-invalid	   not Used-invalid
	B hex = 1011   not used-invalid	 The Bits order:  not Used-invalid	   not Used-invalid
    C-F hex 	   not used-invalid	 ABCD			  not Used-invalid	   not Used-invalid
   

    Default value: 11 11 "
      ::= {prtVc2CnfgEntry 20}

prtExVc2RxBitOutput OBJECT-TYPE
      SYNTAX  OCTET STRING
      MAX-ACCESS  read-write
      STATUS  current
      DESCRIPTION
      "
       - - - For MP (VC-Q card only) & FCD - - -
       This object represents 3  parameters by 2 Octets:
       Spare       -MSB nibble, always=0 hex
       E Lead Output          -    nibble,
       Reverse Polarity Output-    nibble,
       Metering Pulse Output  -LSB nibble.

       Each nibble:
    0 hex = 0000 = Not Applicable
    1 hex = 0001 = Rx A bit
    2 hex = 0010 = Rx A bit inverse
    3 hex = 0011 = Rx B bit
    4 hex = 0100 = Rx B bit inverse
    5 hex = 0101 = Rx C bit
    6 hex = 0110 = Rx C bit inverse
    7 hex = 0111 = Rx D bit
    8 hex = 1000 = Rx D bit inverse
    9 hex = 1001 = none
    A-F hex - not used (invalid values)
       This object will be RO if prtExVc2SigProfile is NOT manual.

      - - - For MP (VC-8, VC-16, VC-16A cards) - - - 

    This object represents 4 parameters, by 2 Octets :
    Tx D Bit Code-MSB nibble,
    Tx C Bit Code-    nibble,
    Tx B Bit Code-    nibble,
    Tx A Bit Code-LSB nibble.

    Each nibble:
    0 hex = 0000 = Not Applicable
    1 hex = 0001 = not used (invalid value)
    2 hex = 0010 = not used (invalid value)
    3 hex = 0011 = not used (invalid value)
    4 hex = 0100 = not used (invalid value)
    5 hex = 0101 = Forced 1
    6 hex = 0110 = Forced 0
    7-F hex - not used (invalid values)
    This object will be RO.
       
             
      - - - For WR II - - -

   This object represents the following 2 parameters in 1 Octet:
   1. On/Off hook signaling receive mode from the T1/E1 into the FXS/FXO (MSB nibble 1).
   2. E (Ear) Signaling receive mode from the T1/E1 into the E&M (LSB nibble 2). 

      Each nibble:
	---------------------------------------------------------------------------------------
	Value          On/Off Hook       E (Ear)
	---------------------------------------------------------------------------------------
    0 hex = 0000   Not Applicable    Not Applicable
    1 hex = 0001   Rx A bit			 Rx A bit
    2 hex = 0010   Rx A bit inverse	 Rx A bit inverse
    3 hex = 0011   Rx B bit			 Rx B bit
    4 hex = 0100   Rx B bit inverse	 Rx B bit inverse
    5-F hex 	   not used-invalid	 not Used-invalid
   
	Default value: 11  "
      ::= {prtVc2CnfgEntry 21}

prtExVc2MeterRate OBJECT-TYPE
      SYNTAX  INTEGER
      {
        notApplicable(1),
        r16Khz  (2),
        r12Khz  (3),
		disabled(4)
      }
      MAX-ACCESS  read-write
      STATUS  current
      DESCRIPTION
      "This entry is applicable only for VC-6A/FXO, VC-6A/FXS, VC-8/FXO,
       VC-8/FXS, VC-16/FXO and VC-16/FXS.
       Meter Rate means rate of Call Meter in Public Phones, in KHz units.
       For some cards, the value must be the same for all card's ports."
      ::= {prtVc2CnfgEntry 22}

prtExVc2IfSignaling OBJECT-TYPE
      SYNTAX  INTEGER
      {
        notApplicable(1),
        loopStart    (2),
		groundStart  (3),
		winkStart    (4)
      }
      MAX-ACCESS  read-write
      STATUS  current
      DESCRIPTION
      "This entry is applicable only for VC-6A, VC-6AG, VC-8/FXO, VC-8/FXS,
       VC-16/FXO and VC-16/FXS cards.
       Interface Analog Signaling.
       Must be the same for all card's ports.
       loopStart - for the usual trunk/phone types.
       groundStart - for trunks that need Ground signaling .
       winkStart - for trunks that need Reverse Polarity. "
      ::= {prtVc2CnfgEntry 23}

prtExVc2SeizeAck OBJECT-TYPE
      SYNTAX INTEGER
      {
      notApplicable (1),
	  no  (2),
      yes (3)
      }
      MAX-ACCESS  read-write
      STATUS  current
      DESCRIPTION
      "This parameter shows whether the device will acknowledge
       a seize signal (On/Off Hook).
       When the value is set to yes(3) & the device receives an on/off hook signal
       it will transmit back an on/off hook signal.
	   When the value is set to no(2) & the device receives an on/off hook signal
       it will NOT transmit back an on/off hook signal.
       
       Default value for WR FXO: no(2)."
       ::= {prtVc2CnfgEntry 24}

prtExVc2EandMType OBJECT-TYPE
       SYNTAX INTEGER
	   {
       notApplicable (1),
	   type1 (2),
       type2 (3),
       type3 (4),
       type5 (5)  -- SSDC5  
       }
      MAX-ACCESS  read-write
      STATUS  current
      DESCRIPTION
      "This is the signaling type on the E&M analog side.
       The analog signaling includes voltage, no. of pins and other parameters."
       ::= {prtVc2CnfgEntry 25}

prtExVc2RemType OBJECT-TYPE
       SYNTAX INTEGER
	   {
       notApplicable (1),
	   lb  (2),
       pbx (3),
	   e1  (4),
	   t1  (5),	 --T1ESF
	   t1D4  (6)
       }
      MAX-ACCESS  read-write
      STATUS  current
      DESCRIPTION
      "Remote Type.
       Applicable for VC-6A/4LB card &
       for IPMUX-1E Far End Type - E1,T1(T1-ESF) or T1-D4 ."
       ::= {prtVc2CnfgEntry 26}

prtExVc2ConvTime OBJECT-TYPE
       SYNTAX INTEGER
	   {
       notApplicable (1),
	   m2 (2),
       m3 (3),
	   m5 (4),
	   unlimited (5)
       }
      MAX-ACCESS  read-write
      STATUS  current
      DESCRIPTION
      "Conversation Time in minutes.
       Applicable for VC-6A/4LB card."
       ::= {prtVc2CnfgEntry 27}

prtExVc2SigFeedback OBJECT-TYPE
       SYNTAX INTEGER
	   {
       notApplicable (1),
	   no  (2),
       yes (3)
       }
      MAX-ACCESS  read-write
      STATUS  current
      DESCRIPTION
      "Signaling Feedback.
       Applicable for VC-8/FXO and VC-16/FXO cards."
       ::= {prtVc2CnfgEntry 28}

prtExVc2EchoCancelerModule OBJECT-TYPE
      SYNTAX  INTEGER
       {
       notApplicable (1),
       notExist   (2),
       exist      (3)
       }
      MAX-ACCESS  read-only
      STATUS  current
      DESCRIPTION
      "This parameter indicates whether Echo canceler module exists for this port."
      ::= {prtVc2CnfgEntry 29}

prtExVc2ReversePolarity OBJECT-TYPE
      SYNTAX  INTEGER
       {
       notApplicable (1),
       disabled      (2),
       enabled       (3)
       }
      MAX-ACCESS  read-write
      STATUS  current
      DESCRIPTION
      "This object Enables/Disables Reverse Polarity for this port."
      ::= {prtVc2CnfgEntry 30}

prtExVc2RingerFrequency OBJECT-TYPE
      SYNTAX  INTEGER
       {
       notApplicable (1),
       f20Hz         (2),
       f25Hz         (3),
	   f50Hz         (4)
       }
      MAX-ACCESS  read-write
      STATUS  current
      DESCRIPTION
      "This object selects the Ringer Frequency (Hz) for this port."
      ::= {prtVc2CnfgEntry 31}

prtExVc2SigService OBJECT-TYPE
      SYNTAX  INTEGER
       {
          notApplicable (1),
          normal        (2),
          advanced      (3)
       }
      MAX-ACCESS  read-write
      STATUS  current
      DESCRIPTION
      "Signaling Service.
       advanced - is relevant only for ports of VC-8, VC-16 FXS cards.
       It is used for Signaling Services of V5.1 or R2."
      ::= {prtVc2CnfgEntry 32}

prtExVc2CallerIdEnable OBJECT-TYPE
      SYNTAX  INTEGER
       {
       notApplicable (1),
       disabled      (2),
       enabled       (3)
       }
      MAX-ACCESS  read-write
      STATUS  current
      DESCRIPTION
      "This object Enables/Disables Receiving the Caller Id number from the
       remote side, for this port/channel."
      ::= {prtVc2CnfgEntry 33}

prtExVc2CompressMethod OBJECT-TYPE
      SYNTAX  INTEGER
       {
       notApplicable (1),
       g726          (2),
       g727          (3)
       }
      MAX-ACCESS  read-write
      STATUS  current
      DESCRIPTION
      "This object is applicable only when prtExVc2Encoding=adpcm.
       It defines which method is used for Compression.
       g726 - for 4 bits (the standard method).
       g726 - for 3 bits. It is especially needed for T1 applications with signaling."
      ::= {prtVc2CnfgEntry 34}

prtExVc2ObMode OBJECT-TYPE
      SYNTAX  INTEGER
       {
       pointToPoint     (1),
       omniBus          (2),
       pointToMultiPointSrc(3),
	   pointToMultiPointDst(4)
       }
      MAX-ACCESS  read-write
      STATUS  current
      DESCRIPTION
      "This object defines the Net operation mode of the Omni-Bus card's port.
       pointToPoint - only 2 end-point ports talk; like any other voice card
       omniBus      - many talk and listen. Like conference call. 
                      All can listen to all.
       pointToMultiPointSrc - There is one Master who can be heard by all. 
                      All can talk, but only the Master can hear all. Others can hear
                      only the Master. This port is of the Master (Src).
       pointToMultiPointDst - There is one Master who can be heard by all. 
                      All can talk, but only the Master can hear all. Others can hear
                      only the Master. This port is of a Destination (NOT Master)."             
      ::= {prtVc2CnfgEntry 35}

prtExVc2VAD OBJECT-TYPE
      SYNTAX  INTEGER
       {
       notApplicable(1),
       off          (2),
       on           (3)
       }
      MAX-ACCESS  read-write
      STATUS  current
      DESCRIPTION
      "This object defines whether Voice Activation Detector (VAD)
       will be On or Off.
	   off - will be usually selected when a Modem is connected
	         to the port; not a phone.
       notApplicable - when prtExVc2DspMode=pointToPoint."
      ::= {prtVc2CnfgEntry 36}

prtExVc2NoiseLevelForVAD OBJECT-TYPE
      SYNTAX  INTEGER
       {
       notApplicable(1),
       low          (2),
       medium       (3),
	   high         (4) 
       }
      MAX-ACCESS  read-write
      STATUS  current
      DESCRIPTION
      "This object defines the Level of Noise on the line,
       the Voice Activation Detector (VAD) will have to deal with.
       notApplicable - when prtExVc2VAD=off."
      ::= {prtVc2CnfgEntry 37}

prtExVc2WesternSigMode OBJECT-TYPE
      SYNTAX  INTEGER
       {
       notApplicable(1),
       detector     (2),
       generator    (3)
       }
      MAX-ACCESS  read-write
      STATUS  current
      DESCRIPTION
      "This object defines the Western Signaling Mode.
	   detector - detects signal and passes it as is.
	   generator - generates the signal.
       notApplicable - when Western HW is not installed."
      ::= {prtVc2CnfgEntry 38}

prtExVc2BusProtectionPoint OBJECT-TYPE
      SYNTAX  INTEGER
       {
       notApplicable(1),
       no     (2),
       first  (3),
	   last   (4)
       }
      MAX-ACCESS  read-write
      STATUS  current
      DESCRIPTION
      "This object defines if the port is Bus Protection Point or not.
       notApplicable - when prtExVc2DspMode=pointToPoint.
       When we have a chain of devices where the edge devices ports are the 
       Bus Protection Point, user must configure one of these ports as 'first'
       and the other as 'last'. It does not matter which one, it just matters 
       that they will be different."
      ::= {prtVc2CnfgEntry 39}

prtExVc2ImpedanceStandard OBJECT-TYPE
      SYNTAX  INTEGER
       {
       g712     (1),
       q552ETSI (2),
       q522Italy(3)
        }
      MAX-ACCESS  read-write
      STATUS  current
      DESCRIPTION
      "This object defines the Standard used for Impedance.
       -G.712 - 600 Ohm - used in USA and other countries.
       -Q552/ETSI - used in some countries in Europe
       -Q522/Italy - used in Italy."
      ::= {prtVc2CnfgEntry 40}


--
-- Megaplex?000/?004 port specific config for HS(TDM) modules
-- HS-2,HS-3,HS-Q, HS-Q/SC, HS-6, HS-12
--
prtHsfCnfgTable OBJECT-TYPE
      SYNTAX SEQUENCE OF PrtHsfCnfgEntry
      MAX-ACCESS not-accessible
      STATUS  current
      DESCRIPTION
       "The write operation into the Table Objects is valid only
        to the TmpCnfg entry."
      ::= { cnfgPrtMux 6}

prtHsfCnfgEntry OBJECT-TYPE
      SYNTAX PrtHsfCnfgEntry
      MAX-ACCESS not-accessible
      STATUS current
	DESCRIPTION  "An entry in table."
	INDEX {prtHsfCnfgIdx, prtHsfSltIdx, prtHsfPrtIdx }
      ::= { prtHsfCnfgTable 1}

PrtHsfCnfgEntry ::=
      SEQUENCE {
        prtHsfCnfgIdx       	Integer32,
        prtHsfSltIdx        	INTEGER,
        prtHsfPrtIdx        	INTEGER,
        prtExHsfConnect     	INTEGER,
        prtExHsfRate        	INTEGER,
        prtExHsfClkMode     	INTEGER,
        prtExHsfCts        	 	INTEGER,
        prtExHsfFifoSize    	INTEGER,
        prtExHsfLinkTo      	INTEGER,
  		prtExHsfOperMode    	INTEGER,
  		prtExHsfInbandLoopback 	INTEGER,
		prtExHsfClkPolarity     INTEGER,
		prtExHsfControlSignal   INTEGER,
		prtExHsfBcastRingSrcPort INTEGER
      }

prtHsfCnfgIdx OBJECT-TYPE
      SYNTAX  Integer32 (1..255)
      MAX-ACCESS  read-only
      STATUS  current
      DESCRIPTION
      "This attribute indicates the Idx of the Cnfg (1..100) being
       accessed.
       Idx  255 relate to the TmpCnfg. "
      ::= {prtHsfCnfgEntry 1}
-- In phase I only the values 1 (Cnfg1) and 255 (temp) are valid.

prtHsfSltIdx OBJECT-TYPE
      SYNTAX  INTEGER
          {
       io1   (5),
       io2   (6),
       io3   (7),
       io4   (8),
       io5   (9),
       io6  (10),
       io7  (11),
       io8  (12),
       io9  (13),
       io10 (14),
       io11 (15),
       io12 (16)
       }
      MAX-ACCESS  read-only
      STATUS  current
      DESCRIPTION
      "This attribute indicates a unique  slot  position where
       the card is inserted.
       In the ?004 Unit the entries io6(10)..io16) are not valid."
      ::= {prtHsfCnfgEntry 2}

prtHsfPrtIdx OBJECT-TYPE
      SYNTAX  INTEGER
          {
         exPrt1    (1) ,
         exPrt2    (2) ,
         exPrt3    (3) ,
         exPrt4    (4) ,
         exPrt5    (5) ,
         exPrt6    (6) ,
         exPrt7    (7) ,
         exPrt8    (8) ,
         exPrt9    (9) ,
         exPrt10  (10) ,
         exPrt11  (11) ,
         exPrt12  (12) ,
		 inPrt1  (101) ,
		 inPrt2  (102)
          }
      MAX-ACCESS  read-only
      STATUS  current
      DESCRIPTION
      "This attribute indicates a unique  external port index.
        Hs2 has only two ports (exPrt1,exPrt2).
        Hs3 has three ports (exPrt1,exPrt2,exPrt3).
        Hsq and hsqN has four ports.
        Hs6 has six external ports.
        Hs12 has twelve external ports.
        inPrt1, inPrt2 - are relevant for VID card."
      ::= {prtHsfCnfgEntry 3}

prtExHsfConnect OBJECT-TYPE
      SYNTAX  INTEGER
              {
                no  (2),
                yes (3)
              }
      MAX-ACCESS  read-write
      STATUS  current
      DESCRIPTION
      "This attribute indicates whether the port should be
       considered in any of the mux algorithms."
      ::= {prtHsfCnfgEntry 4}

prtExHsfRate     OBJECT-TYPE
      SYNTAX  INTEGER
       {
        r1x56eq56Kbps    (1),
        r1x64eq64Kbps    (2),
        r2x56eq112Kbps   (3),
        r2x64eq128Kbps   (4),
        r3x56eq168Kbps   (5),
        r3x64eq192Kbps   (6),
        r4x56eq224Kbps   (7),
        r4x64eq256Kbps   (8),
        r5x56eq280Kbps   (9),
        r5x64eq320Kbps  (10),
        r6x56eq336Kbps  (11),
        r6x64eq384Kbps  (12),
        r7x56eq392Kbps  (13),
        r7x64eq448Kbps  (14),
        r8x56eq448Kbps  (15),
        r8x64eq512Kbps  (16),
        r9x56eq504Kbps  (17),
        r9x64eq576Kbps  (18),
        r10x56eq560Kbps (19),
        r10x64eq640Kbps (20),
        r11x56eq616Kbps (21),
        r11x64eq704Kbps (22),
        r12x56eq672Kbps (23),
        r12x64eq768Kbps (24),
        r13x56eq728Kbps (25),
        r13x64eq832Kbps (26),
        r14x56eq784Kbps (27),
        r14x64eq896Kbps (28),
        r15x56eq840Kbps (29),
        r15x64eq960Kbps (30),
        r16x56eq896Kbps (31),
        r16x64eq1024Kbps(32),
        r17x56eq952Kbps (33),
        r17x64eq1088Kbps(34),
        r18x56eq1008Kbps(35),
        r18x64eq1152Kbps(36),
        r19x56eq1064Kbps(37),
        r19x64eq1216Kbps(38),
        r20x56eq1120Kbps(39),
        r20x64eq1280Kbps(40),
        r21x56eq1176Kbps(41),
        r21x64eq1344Kbps(42),
        r22x56eq1232Kbps(43),
        r22x64eq1408Kbps(44),
        r23x56eq1288Kbps(45),
        r23x64eq1472Kbps(46),
        r24x56eq1344Kbps(47),
        r24x64eq1536Kbps(48),
        r25x56eq1400Kbps(49),
        r25x64eq1600Kbps(50),
        r26x56eq1456Kbps(51),
        r26x64eq1664Kbps(52),
        r27x56eq1512Kbps(53),
        r27x64eq1728Kbps(54),
        r28x56eq1568Kbps(55),
        r28x64eq1792Kbps(56),
        r29x56eq1624Kbps(57),
        r29x64eq1856Kbps(58),
        r30x56eq1680Kbps(59),
        r30x64eq1920Kbps(60),
        r31x56eq1736Kbps(61),
        r31x64eq1984Kbps(62),
        r32Kbps         (63)
       }
      MAX-ACCESS  read-write
      STATUS  current
      DESCRIPTION
      "This attribute indicates the port speed. "
      ::= {prtHsfCnfgEntry 5}

prtExHsfClkMode OBJECT-TYPE
      SYNTAX  INTEGER
       {
          dce     (1),
          ext-dce (2),
          dte     (3),
          none    (4)
       }
      MAX-ACCESS  read-write
      STATUS  current
      DESCRIPTION
      "This attribute indicates a unique port operation clock mode."
      ::= { prtHsfCnfgEntry 6}

prtExHsfCts OBJECT-TYPE
      SYNTAX  INTEGER
       {
     notApplicable (1),
     on            (2),
     rts           (3)
       }
      MAX-ACCESS  read-write
      STATUS  current
      DESCRIPTION
      "This attribute indicates a unique CTS control line
       operation mode."
      ::= {prtHsfCnfgEntry 7}

prtExHsfFifoSize OBJECT-TYPE
      SYNTAX  INTEGER
       {
           auto     (2),
           s16bits  (3),
           s30bits  (4),
           s52bits  (5),
           s72bits  (6)
       }
      MAX-ACCESS  read-write
      STATUS  current
      DESCRIPTION
      "Size in bits."
      ::= {prtHsfCnfgEntry 8}

prtExHsfLinkTo  OBJECT-TYPE
      SYNTAX  INTEGER
       {
       io1   (5),
       io2   (6),
       io3   (7),
       io4   (8),
       io5   (9),
       io6  (10),
       io7  (11),
       io8  (12),
       io9  (13),
       io10 (14),
       io11 (15),
       io12 (16)
       }
      MAX-ACCESS  read-write
      STATUS  deprecated
      DESCRIPTION
      "This attribute indicates a slot of Main Link module, that the
       port is linked to. This object is the same for all the
       ports in the specific card because of HW limitations.
       STATUS  deprecated - this object is replaced by prtGenCnfgLinkToSlot
       and prtGenCnfgLinkToPort."
      ::= {prtHsfCnfgEntry 9}

prtExHsfOperMode OBJECT-TYPE
      SYNTAX  INTEGER
       {
       normal          (2),
       unidirectRx     (3),
       broadcast       (4),
	   bidirBcastRing  (5)
       }
      MAX-ACCESS  read-write
      STATUS  current
      DESCRIPTION
      "This object indicates the operation mode of the port.
       normal = bi-directional (Tx/Rx)
       unidirectRx = unidirectional Rx.
       broadcast = Tx upon request.
       bidirBcastRing = Bidirectional Broadcast Ring. When this value is selected,
                AND RTS=On, the port opens its transmission channel."
      ::= {prtHsfCnfgEntry 10}

prtExHsfInbandLoopback OBJECT-TYPE
      SYNTAX  INTEGER
       {
       notApplicable   (1),
       disabled        (2),
       ft1Enabled      (3)
       }
      MAX-ACCESS  read-write
      STATUS  current
      DESCRIPTION
      "This object indicates if Inband Loopback from the Network
       should be enabled or disabled."
      ::= {prtHsfCnfgEntry 11}

prtExHsfClkPolarity OBJECT-TYPE
      SYNTAX  INTEGER
       {
       notApplicable   (1),
       normal          (2),
       invert          (3)
       }
      MAX-ACCESS  read-write
      STATUS  current
      DESCRIPTION
      "This object indicates the clock polarity.
       For FCD-M this object will be applicable only for the fixed HS port
       (the fixed port on the device)."
      ::= {prtHsfCnfgEntry 12}

prtExHsfControlSignal OBJECT-TYPE
      SYNTAX  INTEGER
       {
       notApplicable   (1),
       local           (2),
       endToEnd        (3)
       }
      MAX-ACCESS  read-write
      STATUS  current
      DESCRIPTION
      "This object indicates the Control Signal according to G.797 ITU-T standard.
       For FCD-M this object will be applicable for the fixed HS port
       (the fixed port on the device) and HS-Q/N channels.
       Local and End to End are applicable only when channel Interface type is RS-530, 
       else it will be Not Applicable."
      ::= {prtHsfCnfgEntry 13}

prtExHsfBcastRingSrcPort OBJECT-TYPE
      SYNTAX  INTEGER
          {
         exPrt1    (1) ,
         exPrt2    (2) ,
         exPrt3    (3) ,
         exPrt4    (4) ,
         exPrt5    (5) ,
         exPrt6    (6) ,
         exPrt7    (7) ,
         exPrt8    (8) ,
         exPrt9    (9) ,
         exPrt10  (10) ,
         exPrt11  (11) ,
         exPrt12  (12) ,
		 none    (100) , 
		 notApplicable  (255)
          }
      MAX-ACCESS  read-write
      STATUS  current
      DESCRIPTION
      "This object is applicable only when prtExHsfOperMode= 
       bidirBcastRing. In this case, the values mean:
       - none - this port will be connected to ML in TSA as usual.
       - exPrt1.. exPrtX ; X=maximum ports of the card in focus :
         it means that the same TS that is assigned in TSA to this port
         is actually connected also to this port, for Broadcast Ring mode.
         Therefore, this port should NOT be connected to ML in TSA."
      ::= {prtHsfCnfgEntry 14}

--
-- Megaplex?000/?004 Hs-4/1(HS4T1) HS-4/2(HS4E1) port configuration
--
--prtExHs4CnfgTable   OBJECT IDENTIFIER ::= {prtHs4Cnfg 1}
--prtExHs4TsCnfgTable OBJECT IDENTIFIER ::= {prtHs4Cnfg 2}

prtExHs4CnfgTable OBJECT-TYPE
      SYNTAX SEQUENCE OF PrtExHs4CnfgEntry
      MAX-ACCESS not-accessible
      STATUS  current
      DESCRIPTION
       "The write operation into the Table Objects is valid only
        to the TmpCnfg entry."
      ::= {prtHs4Cnfg 1}

prtExHs4CnfgEntry OBJECT-TYPE
      SYNTAX PrtExHs4CnfgEntry
      MAX-ACCESS not-accessible
      STATUS current
	DESCRIPTION  "An entry in table."
	INDEX {prtExHs4CnfgIdx, prtExHs4SltIdx,  prtExHs4PrtIdx }
      ::= { prtExHs4CnfgTable 1}

PrtExHs4CnfgEntry ::=
      SEQUENCE {
        prtExHs4CnfgIdx     Integer32,
        prtExHs4SltIdx      INTEGER,
        prtExHs4PrtIdx      INTEGER,

     prtExHs4Connect     INTEGER,
     prtExHs4LineType    INTEGER,
     prtExHs4LineCode    INTEGER,
     prtExHs4LineLen     INTEGER,
     prtExHs4RestoreT    INTEGER,
     prtExHs4OosSig      INTEGER,
     prtExHs4OosCode     INTEGER,
     prtExHs4IdleCode    Integer32,
     prtExHs4MfClkSrcSlt INTEGER,
     prtExHs4MfClkSrcPrt INTEGER
      }

prtExHs4CnfgIdx OBJECT-TYPE
      SYNTAX  Integer32  (1..255)
      MAX-ACCESS  read-only
      STATUS  current
      DESCRIPTION
      "This attribute indicates the Idx of the Cnfg (1..100) being
       accessed.
       Idx  255 relates to the TmpCnfg"
      ::= {prtExHs4CnfgEntry 1}
-- In phase I only the values 1 (Cnfg1) and 255 (temp) are valid.

prtExHs4SltIdx OBJECT-TYPE
      SYNTAX  INTEGER
     {
       io1   (5),
       io2   (6),
       io3   (7),
       io4   (8),
       io5   (9),
       io6  (10),
       io7  (11),
       io8  (12),
       io9  (13),
       io10 (14),
       io11 (15),
       io12 (16)
     }
      MAX-ACCESS  read-only
      STATUS  current
      DESCRIPTION
      "This attribute indicates a unique  slot  position where
       the card is inserted."
      ::= {prtExHs4CnfgEntry 2}

prtExHs4PrtIdx OBJECT-TYPE
      SYNTAX  INTEGER
     {
       exPrt1    (1)
     }
      MAX-ACCESS  read-only
      STATUS  current
      DESCRIPTION
      "A unique identifier of the port, within the card."
      ::= {prtExHs4CnfgEntry 3}

prtExHs4Connect OBJECT-TYPE
      SYNTAX  INTEGER
       {
  no  (2),
  yes (3)
       }
      MAX-ACCESS  read-write
      STATUS  current
      DESCRIPTION
      "This attribute indicates whether the port should be
       considered in any of the mux  algorithm. It also affects
       all the module considerations because the card has only
       one external (physical) interface."
      ::= {prtExHs4CnfgEntry 4}

prtExHs4LineType    OBJECT-TYPE
      SYNTAX  INTEGER
       {
  esfT1          (2), --> dsx1ESF
  sfT1           (3), --> dsx1D4
  g732nE1        (4), --> dsx1E1
  g732nE1CRC    (5), --> dsx1E1-CRC
  g732sE1        (6), --> dsx1E1-MF
  g732sE1CRC    (7)  --> dsx1E1-MF-CRC
       }
      MAX-ACCESS  read-write
      STATUS  current
      DESCRIPTION
      "This attribute is the line type parameter for T1/E1
       interface.
       The user should select only the parameters relevant to the
       specific card:
       T1 line code parameters for the HS-4/1 and
       E1 line code parameters for the HS-4/2.
       This parameter has the same values as dsx1LineType in T1/E1
       MIB (RFC-1406). The parameters in dsx1LineType are:
      other          (1)
      dsx1ESF        (2)
      dsx1D4         (3)
      dsx1E1         (4)
      dsx1E1-CRC     (5)
      dsx1E1-MF      (6)
      dsx1E1-MF-CRC  (7)"
      ::= {prtExHs4CnfgEntry 5}

prtExHs4LineCode OBJECT-TYPE
      SYNTAX  INTEGER
       {
  b7T1   (1),  --> dsx1JBZS
  b8zsT1 (2),  --> dsx1B8ZS
        hdb3E1 (4)   --> dsx1HDB3
       }
      MAX-ACCESS  read-write
      STATUS  current
      DESCRIPTION
      "This attribute is the line code parameter used for T1/E1
       interface.
       The user should select only the parameters relevant to the
       specific card:
       T1 line code parameters for the MPH.1/T1 and
       E1 line code parameters for the MPH.1/E1.
       This parameter has the same values as dsx1LineCoding in T1/E1
       MIB (RFC-1406).  The parameters in dsx1LineCoding are:
     dsx1JBZS  (1)
     dsx1B8ZS  (2)
     dsx1HDB3  (3)
     dsx1ZBTSI (4)
     dsx1AMI   (5)
     other     (6)"
      ::= {prtExHs4CnfgEntry 6}

prtExHs4LineLen  OBJECT-TYPE
      SYNTAX  INTEGER
       {
  unknown   (1),
        len0p133ft   (2),
        len134p266ft (3),
        len267p399ft (4),
        len400p533ft (5),
        len534p655ft (6),
        fcc68    (7)
       }
      MAX-ACCESS  read-write
      STATUS  current
      DESCRIPTION
      "This attribute is the line length parameter used only for
       T1 interfaces.
       len399p533ft=len-399-533ft "
      ::= {prtExHs4CnfgEntry 7}

prtExHs4RestoreT OBJECT-TYPE
      SYNTAX  INTEGER
       {
        restoreT1secFast      (2),
        restoreT10sec62411    (3),
  ccittE1       (4)
       }
      MAX-ACCESS  read-write
      STATUS  current
      DESCRIPTION
      "Time passing from the disappearance of the loss of
       synchronization condition (red alarm), to the restoration
       of normal service."
      ::= {prtExHs4CnfgEntry 8}

prtExHs4OosSig   OBJECT-TYPE
      SYNTAX  INTEGER
       {
        notsupported  (2),
        forcedIdle    (3),
        forcedBusy    (4),
        busyIdle      (5),
        idleBusy      (6)
       }
      MAX-ACCESS  read-write
      STATUS  current
      DESCRIPTION
      "Out of Service signal type."
      ::= {prtExHs4CnfgEntry 9}

prtExHs4OosCode  OBJECT-TYPE
      SYNTAX  INTEGER
          {
          notsupported (2),
            oosCode00H        (3),
            oosCode1aH        (4),
            oosCode54H        (5),
            oosCode7eH        (6),
            oosCode7fH        (7),
            oosCode98H        (8),
            oosCode9eH        (9),
            oosCoded5H        (10),
            oosCodee4H        (11),
            oosCodeffH        (12)
          }
      MAX-ACCESS  read-write
      STATUS  current
      DESCRIPTION
      "OOS Code"
      ::= {prtExHs4CnfgEntry 10}

prtExHs4IdleCode  OBJECT-TYPE
      SYNTAX  Integer32
      MAX-ACCESS  read-write
      STATUS  current
      DESCRIPTION
      " Type value(00 - FF HEX), excluding 0H,8H,10H,12H,21H,24H,
        42H,49H,84H,92H"
      ::= {prtExHs4CnfgEntry 11}

prtExHs4MfClkSrcSlt  OBJECT-TYPE
      SYNTAX  INTEGER
       {
          local (2),
       io1   (5),
       io2   (6),
       io3   (7),
       io4   (8),
       io5   (9),
       io6  (10),
       io7  (11),
       io8  (12),
       io9  (13),
       io10 (14),
       io11 (15),
       io12 (16)
       }
      MAX-ACCESS  read-write
      STATUS  current
      DESCRIPTION
"This attribute indicates whether the port Tx is multiframe
synchronized with Rx multiframe of another port and the slot position of that port.
This opration is required in order to bypass signaling of PCM
voice channels.
When its value is Local(2) there is no meaning to 'prtExHs4MfClkSrcPrt'
parameter.
In the ?004 Unit the entries io6(10)..io16) are not valid"
      ::= {prtExHs4CnfgEntry 12}

prtExHs4MfClkSrcPrt  OBJECT-TYPE
      SYNTAX  INTEGER
      {
       exPrt1    (1),
       exPrt2    (2),
       inPrt1  (101)
      }
      MAX-ACCESS  read-write
      STATUS  current
      DESCRIPTION
      "A unique number to identify a port position in the mux if the
       MultiFrame clock source is valid (YES).
       inPrt1 - for MTML-H/E1 cards."
      ::= {prtExHs4CnfgEntry 13}

--
-- Hs4 Time Slot Config Table
--
prtExHs4TsCnfgTable OBJECT-TYPE
     SYNTAX SEQUENCE OF PrtExHs4TsEntry
     MAX-ACCESS not-accessible
     STATUS  current
     DESCRIPTION
      "The write operation into the Table Objects is valid only
       to the TmpCnfg entry."
     ::= {prtHs4Cnfg 2}

prtExHs4TsEntry OBJECT-TYPE
      SYNTAX PrtExHs4TsEntry
      MAX-ACCESS not-accessible
      STATUS current
	DESCRIPTION  "An entry in table."
	INDEX {prtExHs4TsCnfgIdx, prtExHs4TsSltIdx, prtExHs4TsPrtIdx, prtExHs4TsIdx }
      ::= { prtExHs4TsCnfgTable 1}

PrtExHs4TsEntry ::=
      SEQUENCE {
      prtExHs4TsCnfgIdx        Integer32,
      prtExHs4TsSltIdx         INTEGER,
      prtExHs4TsPrtIdx         INTEGER,
      prtExHs4TsIdx            Integer32,
      prtExHs4TsIConSlot       INTEGER,
      prtExHs4TsIConPrt        INTEGER,
      prtExHs4TsIConTs         Integer32 
	}

prtExHs4TsCnfgIdx OBJECT-TYPE
      SYNTAX  Integer32  (1..255)
      MAX-ACCESS  read-only
      STATUS  current
      DESCRIPTION
      "This attribute indicates the Idx of the Cnfg (1..100) being
       accessed.
       Idx 255 relates to the TmpCnfg. "
      ::= { prtExHs4TsEntry 1}
-- In phase I only the values 1 (Cnfg1) and 255 (temp) are valid.

prtExHs4TsSltIdx OBJECT-TYPE
      SYNTAX  INTEGER
     {
       io1   (5),
       io2   (6),
       io3   (7),
       io4   (8),
       io5   (9),
       io6  (10),
       io7  (11),
       io8  (12),
       io9  (13),
       io10 (14),
       io11 (15),
       io12 (16)
     }
      MAX-ACCESS  read-only
      STATUS  current
      DESCRIPTION
      "This attribute indicates a unique  slot  position where
       the card is inserted.
       In the ?004 Unit the entries io6(10)..io16) are not valid"
      ::= { prtExHs4TsEntry 2}

prtExHs4TsPrtIdx OBJECT-TYPE
      SYNTAX  INTEGER
 {
          exPrt1    (1)
       }
      MAX-ACCESS  read-only
      STATUS  current
      DESCRIPTION
      "This attribute indicates a unique  port number.
       Hs4/T1 and Hs4/T1 cards have only one external interface."
      ::= { prtExHs4TsEntry 3}

prtExHs4TsIdx OBJECT-TYPE
      SYNTAX  Integer32
      MAX-ACCESS  read-only
      STATUS  current
      DESCRIPTION
      "This attribute indicates a unique time slot  position.
       The valid time slots are:
       1..24 for T1 Card and
       1..31 for E1 interface.
       In G732S-E1 lines, time slot 16 is not valid for data,
       it is dedicated to multiframe synchronization bits
       and voice signaling."
      ::= { prtExHs4TsEntry 4}

prtExHs4TsIConSlot OBJECT-TYPE
      SYNTAX  INTEGER
       {
       noConnect (2),
          io1       (5),
          io2       (6),
          io3       (7),
          io4       (8),
          io5       (9),
          io6      (10),
          io7      (11),
          io8      (12),
          io9      (13),
          io10     (14),
          io11     (15),
          io12     (16),
    split   (100)
       }
      MAX-ACCESS  read-write
      STATUS  current
      DESCRIPTION
      "This attribute indicates whether the specified time slot is
       connected/routed internally in the Agent and to which card
       it is connected.
       In the ?004 Unit the entries io6(10)..io16) are not valid.
    split - will be used when the Src TS is connected to more
               than one slot OR more than one port (each needing
               less than a whole TS)."
      ::= {prtExHs4TsEntry 5}

prtExHs4TsIConPrt OBJECT-TYPE
      SYNTAX  INTEGER
       {
       exPrt1    (1) ,
       exPrt2    (2) ,
       exPrt3    (3) ,
       exPrt4    (4) ,
       exPrt5    (5) ,
       exPrt6    (6) ,
       exPrt7    (7) ,
       exPrt8    (8) ,
       exPrt9    (9) ,
       exPrt10  (10) ,
       exPrt11  (11) ,
       exPrt12  (12) ,
       noConnect (100)
       }
      MAX-ACCESS  read-write
      STATUS  current
      DESCRIPTION
      "This attribute indicates the internally (In Mux)
       connected/routed port."
      ::= {prtExHs4TsEntry 6}

prtExHs4TsIConTs OBJECT-TYPE
      SYNTAX  Integer32
      MAX-ACCESS  read-write
      STATUS  current
      DESCRIPTION
      "This attribute indicates a unique time slot  position.
       The valid time slots are:
       1..24 for T1 Module and
       1..31 for E1 interface.
       In G732S-E1 lines time slot 16 is not valid for data,
       it is dedicated for multiframe synchronization bits
       and voice signaling."
      ::= { prtExHs4TsEntry 7}

--
-- Megaplex?000/?004 and DXC Hs-U port configuration
--
--prtExHsiCnfgTable   OBJECT IDENTIFIER ::= {prtHsiCnfg 1}

prtExHsiCnfgTable OBJECT-TYPE
      SYNTAX SEQUENCE OF PrtExHsiCnfgEntry
      MAX-ACCESS not-accessible
      STATUS  current
      DESCRIPTION
       "The write operation into the Table Objects is valid only
        to the TmpCnfg entry."
      ::= {prtHsiCnfg 1}

prtExHsiCnfgEntry OBJECT-TYPE
      SYNTAX PrtExHsiCnfgEntry
      MAX-ACCESS not-accessible
      STATUS current
	DESCRIPTION  "An entry in table."
	INDEX {prtExHsiCnfgIdx, prtExHsiSltIdx,  prtExHsiPrtIdx }
      ::= { prtExHsiCnfgTable 1}

PrtExHsiCnfgEntry ::=
      SEQUENCE {
        prtExHsiCnfgIdx     Integer32,
        prtExHsiSltIdx      INTEGER,
        prtExHsiPrtIdx      Integer32,

        prtExHsiConnect     INTEGER,
        prtExHsiRate        INTEGER,
        prtExHsiLinkTo      INTEGER,
        prtExHsiInterface   INTEGER,
		prtExHsiActType		INTEGER
      }

prtExHsiCnfgIdx OBJECT-TYPE
      SYNTAX  Integer32  (1..255)
      MAX-ACCESS  read-only
      STATUS  current
      DESCRIPTION
      "This attribute indicates the Idx of the Cnfg (1..100) being
       accessed.
       Idx 255 relates to the TmpCnfg"
      ::= {prtExHsiCnfgEntry 1}
-- In phase I only the values 1 (Cnfg1) and 255 (temp) are valid.

prtExHsiSltIdx OBJECT-TYPE
      SYNTAX  INTEGER
     {
       io1   (5),
       io2   (6),
       io3   (7),
       io4   (8),
       io5   (9),
       io6  (10),
       io7  (11),
       io8  (12),
       io9  (13),
       io10 (14),
       io11 (15),
       io12 (16),
	   io13 (17),
	   io14 (18),
	   io15 (19),
	   notApplicable (255)
     }
      MAX-ACCESS  read-only
      STATUS  current
      DESCRIPTION
      "This attribute indicates a unique  slot  position where
       the card is inserted."
      ::= {prtExHsiCnfgEntry 2}

prtExHsiPrtIdx OBJECT-TYPE
      SYNTAX  Integer32
--     {
--          exPrt1    (1),
--          exPrt2    (2),
--          exPrt3    (3),
--          exPrt4    (4),
--          exPrt5    (5),
--          exPrt6    (6),
--          exPrt7    (7),
--          exPrt8    (8),
--          exPrt9    (9),
--          exPrt10  (10),
--          exPrt11  (11),
--          exPrt12  (12)
--        }
      MAX-ACCESS  read-only
      STATUS  current
      DESCRIPTION
      "A unique port identifier within the card.
       For MP : 1..12
       For DXC: 111 .. 2531. See DXC R6 spec for port index convention.
       For FCD-A, 'S' Interface external ports: 131, 141, 151, 161."
      ::= {prtExHsiCnfgEntry 3}

prtExHsiConnect OBJECT-TYPE
      SYNTAX  INTEGER
       {
        no  (2),
        yes (3),
		v51 (4),
		v52 (5)
       }
      MAX-ACCESS  read-write
      STATUS  current
      DESCRIPTION
      "This attribute indicates whether the port should be considered in
       any of the mux  algorithms.
       v51 - this port is connected to a V5.1 interface. All rest of the
             values will be 'notApplicable' in this case. V5 MIB will be
             used instead.
       v52 - this port is connected to a V5.2 interface. All rest of the
             values will be 'notApplicable' in this case. V5 MIB will be
             used instead."
      ::= {prtExHsiCnfgEntry 4}

prtExHsiRate    OBJECT-TYPE
      SYNTAX  INTEGER
       {
          r600bps   (2),
          r1200bps  (3),
          r2400bps  (4),
          r4800bps  (5),
          r9600bps  (6),
          r19200bps (7),
          r38400bps (8),
          r48kbps   (9),
          r56kbps  (10),
          r64kbps  (11),
          r128kbps (12),
    notApplicable (255)
       }
      MAX-ACCESS  read-write
      STATUS  current
      DESCRIPTION
      "This attribute indicates the port speed."
      ::= {prtExHsiCnfgEntry 5}

prtExHsiLinkTo  OBJECT-TYPE
      SYNTAX  INTEGER
       {
       io1   (5),
       io2   (6),
       io3   (7),
       io4   (8),
       io5   (9),
       io6  (10),
       io7  (11),
       io8  (12),
       io9  (13),
       io10 (14),
       io11 (15),
       io12 (16)
       }
      MAX-ACCESS  read-write
      STATUS  deprecated
      DESCRIPTION
      "It indicates the slot of the main link card to which the HS-? card
       is mapped.
       STATUS  deprecated - this object is replaced by prtGenCnfgLinkToSlot
       and prtGenCnfgLinkToPort."
      ::= {prtExHsiCnfgEntry 6}

prtExHsiInterface  OBJECT-TYPE
      SYNTAX  INTEGER
       {
       lt   (1),
       nt   (2),
       te   (3),
	   lt1  (4),
    notApplicable (255)
       }
      MAX-ACCESS  read-write
      STATUS  current
      DESCRIPTION
      "It indicates the interface type:
       lt = line termination
       nt = network termination
       te = terminal equipment.
	   lt1 - for ASMi-31 connection (not ISDN)
	   For MP:
       For HS-U/I only 'lt' and 'nt' are applicable.
	   For HS-U/1 only 'lt' is applicable.
       For HS-S , only 'te' and 'nt' are applicable.
       For HS-U, this object is not applicable.
       For HS-U6, HS-U12, are applicable: 'lt'=lt-i,'nt'=nt-i, lt1.
       For DXC:
       For HS-U8, HS-U16, are applicable: 'lt'=LT-I,'nt'=NT-I, 'lt1'=LT-1."
      ::= {prtExHsiCnfgEntry 7}

prtExHsiActType  OBJECT-TYPE
      SYNTAX  INTEGER
       {
       notApplicable (1),
       type1 (2),
       type2 (3),
	   type3 (4)
       }
      MAX-ACCESS  read-write
      STATUS  current
      DESCRIPTION
      "It indicates the Activation Type. Activation Type is the Synchronization
	   type towards the PBX. It is applicable only when prtExHsiInterface=nt.
	   notApplicable - for cards that do not support this object, or when 
	   prtExHsiInterface is NOT nt."
      ::= {prtExHsiCnfgEntry 8}


--prtInHsiCnfgTable   OBJECT IDENTIFIER ::= {prtHsiCnfg 2}
--This table is not applicable for MP-2100 HS-U card type

prtInHsiCnfgTable OBJECT-TYPE
      SYNTAX SEQUENCE OF PrtInHsiCnfgEntry
      MAX-ACCESS not-accessible
      STATUS  current
      DESCRIPTION
       "The write operation into the Table Objects is valid only
        to the TmpCnfg entry.
        This table is not applicable for MP-2100 HS-U card type."
      ::= {prtHsiCnfg 2}

prtInHsiCnfgEntry OBJECT-TYPE
      SYNTAX PrtInHsiCnfgEntry
      MAX-ACCESS not-accessible
      STATUS current
	DESCRIPTION  "An entry in table."
	INDEX {prtInHsiCnfgIdx, prtInHsiSltIdx,  prtInHsiPrtIdx }
      ::= { prtInHsiCnfgTable 1}

PrtInHsiCnfgEntry ::=
      SEQUENCE {
        prtInHsiCnfgIdx     Integer32,
        prtInHsiSltIdx      INTEGER,
        prtInHsiPrtIdx      Integer32,

        prtInHsiConnect     INTEGER,
        prtInHsiRate        INTEGER,
		prtInHsiConcentratedTo Integer32 
	}

prtInHsiCnfgIdx OBJECT-TYPE
      SYNTAX  Integer32  (1..255)
      MAX-ACCESS  read-only
      STATUS  current
      DESCRIPTION
      "This object indicates the Idx of the Cnfg (1..100) being
       accessed.
       Idx 255 relates to the TmpCnfg"
      ::= {prtInHsiCnfgEntry 1}

prtInHsiSltIdx OBJECT-TYPE
      SYNTAX  INTEGER
     {
       io1   (5),
       io2   (6),
       io3   (7),
       io4   (8),
       io5   (9),
       io6  (10),
       io7  (11),
       io8  (12),
       io9  (13),
       io10 (14),
       io11 (15),
       io12 (16),
	   io13 (17),
	   io14 (18),
	   io15 (19),
	   notApplicable (255)
     }
      MAX-ACCESS  read-only
      STATUS  current
      DESCRIPTION
      "This object indicates a unique  slot  position where
       the card is inserted."
      ::= {prtInHsiCnfgEntry 2}

prtInHsiPrtIdx OBJECT-TYPE
      SYNTAX  Integer32
      MAX-ACCESS  read-only
      STATUS  current
      DESCRIPTION
      "A unique port identifier within the card.
       Valid values for MP: inPrt1 (101) .. inPrt48 (148).
       Valid values for DXC: 11012.. 25316. See DXC R6 spec for port index convention."
      ::= {prtInHsiCnfgEntry 3}

prtInHsiConnect OBJECT-TYPE
      SYNTAX  INTEGER
       {
       no  (2),
       yes (3)
       }
      MAX-ACCESS  read-write
      STATUS  current
      DESCRIPTION
      "This attribute indicates whether the port should be considered in
       any of the mux  algorithms."
      ::= {prtInHsiCnfgEntry 4}

prtInHsiRate    OBJECT-TYPE
      SYNTAX  INTEGER
       {
          r600bps   (2),
          r1200bps  (3),
          r2400bps  (4),
          r4800bps  (5),
          r9600bps  (6),
          r19200bps (7),
          r38400bps (8),
          r48kbps   (9),
          r56kbps  (10),
          r64kbps  (11),
          r128kbps (12),
		  concentrated  (13),
		  notConnected (100),  
          notApplicable(255)
          }
      MAX-ACCESS  read-write
      STATUS  current
      DESCRIPTION
      "This object indicates the port speed.
       For HS-U/I and HS-S ports:
       2 bit - up to 9600bps
       4 bit - 19200bps
       8 bit - 38400bps .. 64kbps.
       concentrated - this D channel goes to a Concentration channel,
                      that represents many channels that this value was
                      selected for them. The Concentrated channel is an
                      Internal D Channel of the same card. 
                      This value is applicable only for	D channels, except 
                      Concentration channel itself.
                      --for HS-S and HS-U/I cards the Concentration channel 
                        will always be: internal-13
                      --for MP-2200 HS-S12, HS-S6, HS-U12, HS-U6 and
                        DXC HS-U8 and HS-U16 cards, the Concentration channel
                        is selected via the prtInHsiConcentratedTo object.
       notConnected - same as prtInHsiConnect=no."
      ::= {prtInHsiCnfgEntry 5}

prtInHsiConcentratedTo OBJECT-TYPE
      SYNTAX  Integer32
      MAX-ACCESS  read-write
      STATUS  current
      DESCRIPTION
      "The Concentration D Channel of the prtInHsiPrtIdx port.
	   The port always belongs to the same card as prtInHsiPrtIdx port.
	   This object is applicable only when prtInHsiRate=concentrated.
       Valid values:
	   - notApplicable: 255
       - for MP-2200: HS-S12, HS-U12 cards: inPrt37 (137) .. inPrt48 (148).
                      HS-S6, HS-U6 cards: inPrt19 (119) .. inPrt24 (124).
       - for DXC:     HS-U8  cards: 112 .. 254
                      HS-U16 cards: 112 .. 258. See DXC R6 spec for port index 
                      convention."
      ::= {prtInHsiCnfgEntry 6}

--
-- Megaplex?000/?004 Hs-R and HS-U port configuration
-- DXC HS-U8, HS-U16 port configuration for Interface=LT-1
--
--prtExHsrCnfgTable   OBJECT IDENTIFIER ::= {prtHsrCnfg 1}

prtExHsrCnfgTable OBJECT-TYPE
      SYNTAX SEQUENCE OF PrtExHsrCnfgEntry
      MAX-ACCESS not-accessible
      STATUS  current
      DESCRIPTION
       "The write operation into the Table Objects is valid only
        to the TmpCnfg entry."
      ::= {prtHsrCnfg 1}

prtExHsrCnfgEntry OBJECT-TYPE
      SYNTAX PrtExHsrCnfgEntry
      MAX-ACCESS not-accessible
      STATUS current
	DESCRIPTION  "An entry in table."
	INDEX {prtExHsrCnfgIdx, prtExHsrSltIdx,  prtExHsrPrtIdx }
      ::= { prtExHsrCnfgTable 1}

PrtExHsrCnfgEntry ::=
      SEQUENCE {
        prtExHsrCnfgIdx     Integer32,
        prtExHsrSltIdx      INTEGER,
        prtExHsrPrtIdx      Integer32,

        prtExHsrConnect     INTEGER,
        prtExHsrProtocol    INTEGER,
        prtExHsrRate        INTEGER,
        prtExHsrDataBits    INTEGER,
        prtExHsrParity      INTEGER,
        prtExHsrStopBits    INTEGER,
        prtExHsrCts         INTEGER,
        prtExHsrClkMode     INTEGER,
        prtExHsrLinkTo      INTEGER,
        prtExHsrDcdDsr      INTEGER,
        prtExHsrOperMode    INTEGER,
        prtExHsrRtsDtr      INTEGER,
		prtExHsrLlbEnable   INTEGER,
		prtExHsrRlbEnable   INTEGER,
		prtExHsrRateAdapt   INTEGER,
		prtExHsrRemoteModem INTEGER ,
		prtExHsrEncapsMode  INTEGER
      }

prtExHsrCnfgIdx OBJECT-TYPE
      SYNTAX  Integer32  (1..255)
      MAX-ACCESS  read-only
      STATUS  current
      DESCRIPTION
      "This object indicates the Idx of the Cnfg (1..100) being
       accessed.
       Idx 255 relates to the TmpCnfg"
      ::= {prtExHsrCnfgEntry 1}

prtExHsrSltIdx OBJECT-TYPE
      SYNTAX  INTEGER
     {
       io1   (5),
       io2   (6),
       io3   (7),
       io4   (8),
       io5   (9),
       io6  (10),
       io7  (11),
       io8  (12),
       io9  (13),
       io10 (14),
       io11 (15),
       io12 (16),
	   io13 (17),
	   io14 (18),
	   io15 (19)
     }
      MAX-ACCESS  read-only
      STATUS  current
      DESCRIPTION
      "This object indicates a unique  slot  position where
       the card is inserted."
      ::= {prtExHsrCnfgEntry 2}

prtExHsrPrtIdx OBJECT-TYPE
      SYNTAX  Integer32
      MAX-ACCESS  read-only
      STATUS  current
      DESCRIPTION
      "A unique prt identifier within the card.
       Valid values:
	   For MP:
        - For HS-R cards: exPrt1 (1)   .. exPrt4 (4)
        - For HS-U/1 cards: inPrt1 (101) .. inPrt4 (104)
        - For HS-S12, HS-S6, HS-U12, HS-U6 cards:
          exPrt1 (1) .. exPrt12 (12). 
          This MIB table is used only for LT-1 interface.
       For DXC:
        - For HS-U8, HS-U16 cards:
          111 .. 2531 (See DXC R6 spec for port index convention). 
          This MIB table is used only for LT-1 interface."
      ::= {prtExHsrCnfgEntry 3}

prtExHsrConnect OBJECT-TYPE
      SYNTAX  INTEGER
       {
       no  (2),
       yes (3)
       }
      MAX-ACCESS  read-write
      STATUS  current
      DESCRIPTION
      "This object indicates whether the port should be considered in
       any of the mux  algorithms."
      ::= {prtExHsrCnfgEntry 4}

prtExHsrProtocol OBJECT-TYPE
      SYNTAX  INTEGER
              {
                sync  (2),
                async (3)
              }
      MAX-ACCESS  read-write
      STATUS  current
      DESCRIPTION
      "This object indicates the protocol."
      ::= {prtExHsrCnfgEntry 5}

prtExHsrRate    OBJECT-TYPE
      SYNTAX  INTEGER
       {
       r600bps    (2),
       r1200bps   (3),
       r2400bps   (4),
       r4800bps   (5),
       r9600bps   (6),
       r19200bps  (7),
       r38400bps  (8),
       r48kbps    (9),
       r56kbps   (10),
       r64kbps   (11),
       r16000bps (12),
       r32000bps (13),
       r57600bps (14),
       r115200bps(15),
       r128000bps(16),
	   r7200bps  (17),
	   r14400bps (18),
	   r28800bps (19),
	   notConnected (100)
       }
      MAX-ACCESS  read-write
      STATUS  current
      DESCRIPTION
      "This object indicates the port speed.
       The 16,32,48,56,64 and 128 kbps rates are applicable only for Sync
       protocol.
       The 57.6 and 115.2 kbps rates are applicable only for Async
       protocol.
       notConnected= 0 rate."
      ::= {prtExHsrCnfgEntry 6}

prtExHsrDataBits OBJECT-TYPE
      SYNTAX  INTEGER
       {
        d5bits    (1),
        d6bits    (2),
        d7bits    (3),
        d8bits    (4),
        notApplicable (255)
       }
      MAX-ACCESS  read-write
      STATUS  current
      DESCRIPTION
      "Data Bits.
       This object is applicable for Async protocol only."
      ::= {prtExHsrCnfgEntry 7}

prtExHsrParity OBJECT-TYPE
      SYNTAX  INTEGER
       {
        no  (2),
        yes (3),
		odd (4),
		even(5),
        notApplicable (255)
       }
      MAX-ACCESS  read-write
      STATUS  current
      DESCRIPTION
      "- For HS-R card, this object indicates if the parity bit is needed or not.
	     Therefore, the 'no' and 'yes; values are applicable. 
       - For HS-S12, HS-U12, the parity type is selected: no, odd, even.
       This object is applicable for Async protocol only."
      ::= { prtExHsrCnfgEntry 8}

prtExHsrStopBits OBJECT-TYPE
      SYNTAX  INTEGER
       {
        stopBits1Bit      (1),
        stopBits2Bits     (2),
        notApplicable   (255)
       }
      MAX-ACCESS  read-write
      STATUS  current
      DESCRIPTION
      "This object indicates the minimum number of stop bits in
       the tx async frame.
       This object is applicable for Async protocol only."
      ::= { prtExHsrCnfgEntry 9}

prtExHsrCts OBJECT-TYPE
      SYNTAX  INTEGER
       {
       on       (2),
       rts      (3),
       notApplicable   (255)
       }
      MAX-ACCESS  read-write
      STATUS  current
      DESCRIPTION
      "CTS.
       This object is applicable for Async protocol only."
      ::= {prtExHsrCnfgEntry 10}

prtExHsrClkMode OBJECT-TYPE
      SYNTAX  INTEGER
      {
      dce     (1),
      extDce  (2),
      notApplicable  (255)
      }
      MAX-ACCESS  read-write
      STATUS  current
      DESCRIPTION
      "Clock mode.
       This object is applicable for Sync protocol only."
      ::= { prtExHsrCnfgEntry 11}

prtExHsrLinkTo  OBJECT-TYPE
      SYNTAX  INTEGER
       {
	   notApplicable (1),
       io1   (5),
       io2   (6),
       io3   (7),
       io4   (8),
       io5   (9),
       io6  (10),
       io7  (11),
       io8  (12),
       io9  (13),
       io10 (14),
       io11 (15),
       io12 (16)
       }
      MAX-ACCESS  read-write
      STATUS  deprecated
      DESCRIPTION
      "It indicates the slot of the main link card to which the HS-R card
       is mapped.
       notApplicable - for HS-U/1 internal ports.
       STATUS  deprecated - this object is replaced by prtGenCnfgLinkToSlot
       and prtGenCnfgLinkToPort."
      ::= {prtExHsrCnfgEntry 12}

prtExHsrDcdDsr OBJECT-TYPE
      SYNTAX  INTEGER
       {
        notApplicable (1),
        local         (2),
        endToEnd      (3)
       }
      MAX-ACCESS  read-write
      STATUS  current
      DESCRIPTION
      "DCD & DSR."
      ::= {prtExHsrCnfgEntry 13}


prtExHsrOperMode OBJECT-TYPE
      SYNTAX  INTEGER
       {
       normal          (2),
       unidirectRx     (3),
       broadcast       (4)
       }
      MAX-ACCESS  read-write
      STATUS  current
      DESCRIPTION
      "This object indicates the operation mode of the port.
       normal = bi-directional (Tx/Rx)
       unidirectRx = unidirectional Rx.
       broadcast = Tx upon request."
      ::= {prtExHsrCnfgEntry 14}

prtExHsrRtsDtr OBJECT-TYPE
      SYNTAX  INTEGER
       {
        notApplicable (1),
        local         (2),
        endToEnd      (3)
       }
      MAX-ACCESS  read-write
      STATUS  current
      DESCRIPTION
      "RTS & DTR."
      ::= {prtExHsrCnfgEntry 15}

prtExHsrLlbEnable OBJECT-TYPE
      SYNTAX  INTEGER
       {
       notApplicable (1),
       disabled      (2),
       enabled       (3)
       }
      MAX-ACCESS  read-write
      STATUS  current
      DESCRIPTION
      "Enable/Disable LLB."
      ::= {prtExHsrCnfgEntry 16}

prtExHsrRlbEnable OBJECT-TYPE
      SYNTAX  INTEGER
       {
       notApplicable (1),
       disabled      (2),
       enabled       (3)
       }
      MAX-ACCESS  read-write
      STATUS  current
      DESCRIPTION
      "Enable/Disable RLB."
      ::= {prtExHsrCnfgEntry 17}

prtExHsrRateAdapt OBJECT-TYPE
      SYNTAX  INTEGER
       {
       notApplicable (1),
       proprietary   (2),
       v110          (3)
       }
      MAX-ACCESS  read-write
      STATUS  current
      DESCRIPTION
      "Rate Adaptation - takes a low rate and adapts it to 64Kbps.
       This object specifies the means this adaptation is done by."
      ::= {prtExHsrCnfgEntry 18}

prtExHsrRemoteModem OBJECT-TYPE
      SYNTAX  INTEGER
       {
    notApplicable (1),
    asmi31        (2),
    asmi31s2      (3)
       }
      MAX-ACCESS  read-write
      STATUS  current
      DESCRIPTION
      "Remote modem.
       asmi31s2 = ASMi-31/2 "
      ::= {prtExHsrCnfgEntry 19}

prtExHsrEncapsMode OBJECT-TYPE
      SYNTAX  INTEGER
       {
       notApplicable    (1),
       bwOptimized      (2),
	   latencyOptimized (3),
       asmi31           (4)
       }
      MAX-ACCESS  read-write
      STATUS  current
      DESCRIPTION
      "Low Speed encapsulation method over PCM.

       When Encapsulation mode is Latency optimized, only rates up to 19.2 are supported.
       In this case a double number of bits occupy the Time Slot.
       For up to 9.6 Kbps   - 4 bits are occupied.
       For 14.4 & 19.2 Kbps - 8 bits are occupied.
       
       When Encapsulation Mode is Bandwidth Optimized:
       For up to 9.6 Kbps   - 2 bits are occupied.
       For 14.4 & 19.2 Kbps - 4 bits are occupied.
       For higher rates - 8 bits are occupied."
      ::= {prtExHsrCnfgEntry 20}

--
-- Megaplex?000/?004 MBE port configuration
--

prtExMbeCnfgTable OBJECT-TYPE
      SYNTAX SEQUENCE OF PrtExMbeCnfgEntry
      MAX-ACCESS not-accessible
      STATUS  current
      DESCRIPTION
       "The write operation into the Table Objects is valid only
        to the TmpCnfg entry."
      ::= {prtMbeCnfg 1}

prtExMbeCnfgEntry OBJECT-TYPE
      SYNTAX PrtExMbeCnfgEntry
      MAX-ACCESS not-accessible
      STATUS current
	DESCRIPTION  "An entry in table."
	INDEX {prtExMbeCnfgIdx, prtExMbeSltIdx,  prtExMbePrtIdx }
      ::= { prtExMbeCnfgTable 1}

PrtExMbeCnfgEntry ::=
      SEQUENCE {
        prtExMbeCnfgIdx     Integer32,
        prtExMbeSltIdx      INTEGER,
        prtExMbePrtIdx      INTEGER,

        prtExMbeLan         INTEGER
      }

prtExMbeCnfgIdx OBJECT-TYPE
      SYNTAX  Integer32  (1..255)
      MAX-ACCESS  read-only
      STATUS  current
      DESCRIPTION
      "This attribute indicates the Idx of the Cnfg (1..100) being
       accessed.
       Idx 255 relates to the TmpCnfg"
      ::= {prtExMbeCnfgEntry 1}
-- In phase I only the values 1 (Cnfg1) and 255 (temp) are valid.

prtExMbeSltIdx OBJECT-TYPE
      SYNTAX  INTEGER
     {
       io1   (5),
       io2   (6),
       io3   (7),
       io4   (8),
       io5   (9),
       io6  (10),
       io7  (11),
       io8  (12),
       io9  (13),
       io10 (14),
       io11 (15),
       io12 (16)
     }
      MAX-ACCESS  read-only
      STATUS  current
      DESCRIPTION
      "This attribute indicates a unique  slot  position where
       the card is inserted.
       In the ?004 Unit the entries io6(10)..io16) are not valid."
      ::= {prtExMbeCnfgEntry 2}

prtExMbePrtIdx OBJECT-TYPE
      SYNTAX  INTEGER
     {
          exPrt1    (1)
     }
      MAX-ACCESS  read-only
      STATUS  current
      DESCRIPTION
      "A unique port identifier within the card."
      ::= {prtExMbeCnfgEntry 3}

prtExMbeLan OBJECT-TYPE
      SYNTAX  INTEGER
       {
        remote  (1),
        main    (2)
       }
      MAX-ACCESS  read-write
      STATUS  current
      DESCRIPTION
      "This attribute indicates whether the MBE port is operated
       as main or remote bridge."
      ::= {prtExMbeCnfgEntry 4}

prtInMbeCnfgTable OBJECT-TYPE
      SYNTAX SEQUENCE OF PrtInMbeCnfgEntry
      MAX-ACCESS not-accessible
      STATUS  current
      DESCRIPTION
       "The write operation into the Table Objects is valid only
        to the TmpCnfg entry."
      ::= {prtMbeCnfg 2}

prtInMbeCnfgEntry OBJECT-TYPE
      SYNTAX PrtInMbeCnfgEntry
      MAX-ACCESS not-accessible
      STATUS current
	DESCRIPTION  "An entry in table."
	INDEX {prtInMbeCnfgIdx, prtInMbeSltIdx,  prtInMbePrtIdx }
      ::= { prtInMbeCnfgTable 1}

PrtInMbeCnfgEntry ::=
      SEQUENCE {
        prtInMbeCnfgIdx     Integer32,
        prtInMbeSltIdx      INTEGER,
        prtInMbePrtIdx      INTEGER,

        prtInMbeConnect     INTEGER,
        prtInMbeRate        INTEGER,
        prtInMbeLinkTo      INTEGER
      }

prtInMbeCnfgIdx OBJECT-TYPE
      SYNTAX  Integer32  (1..255)
      MAX-ACCESS  read-only
      STATUS  current
      DESCRIPTION
      "This attribute indicates the Idx of the Cnfg (1..100) being
       accessed.
       Idx 255 relates to the TmpCnfg"
      ::= {prtInMbeCnfgEntry 1}
-- In phase I only the values 1 (Cnfg1) and 255 (temp) are valid.

prtInMbeSltIdx OBJECT-TYPE
      SYNTAX  INTEGER
     {
       io1   (5),
       io2   (6),
       io3   (7),
       io4   (8),
       io5   (9),
       io6  (10),
       io7  (11),
       io8  (12),
       io9  (13),
       io10 (14),
       io11 (15),
       io12 (16)
     }
      MAX-ACCESS  read-only
      STATUS  current
      DESCRIPTION
      "This attribute indicates a unique  slot  position where
       the card is inserted.
       In the ?004 Unit the entries io6(10)..io16) are not valid."
      ::= {prtInMbeCnfgEntry 2}

prtInMbePrtIdx OBJECT-TYPE
      SYNTAX  INTEGER
     {
          inPrt1    (101)
     }
      MAX-ACCESS  read-only
      STATUS  current
      DESCRIPTION
      "A unique port identifier within the card."
      ::= {prtInMbeCnfgEntry 3}

prtInMbeConnect OBJECT-TYPE
      SYNTAX  INTEGER
       {
  no  (2),
  yes (3)
       }
      MAX-ACCESS  read-write
      STATUS  current
      DESCRIPTION
      "This attribute indicates whether the port should be considered in
       any of the mux  algorithms."
      ::= {prtInMbeCnfgEntry 4}

prtInMbeRate    OBJECT-TYPE
      SYNTAX  INTEGER
	      {
        r1x64eq64Kbps    (1),
        r2x64eq128Kbps   (2),
        r3x64eq192Kbps   (3),
        r4x64eq256Kbps   (4),
        r5x64eq320Kbps   (5),
        r6x64eq384Kbps   (6),
        r7x64eq448Kbps   (7),
        r8x64eq512Kbps   (8),
        r9x64eq576Kbps   (9),
        r10x64eq640Kbps (10),
        r11x64eq704Kbps (11),
        r12x64eq768Kbps (12),
        r13x64eq832Kbps (13),
        r14x64eq896Kbps (14),
        r15x64eq960Kbps (15),
        r16x64eq1024Kbps(16),
        r17x64eq1088Kbps(17),
        r18x64eq1152Kbps(18),
        r19x64eq1216Kbps(19),
        r20x64eq1280Kbps(20),
        r21x64eq1344Kbps(21),
        r22x64eq1408Kbps(22),
        r23x64eq1472Kbps(23),
        r24x64eq1536Kbps(24)
	      }
      MAX-ACCESS  read-write
      STATUS  current
      DESCRIPTION
      "This attribute indicates the port speed."
      ::= {prtInMbeCnfgEntry 5}

prtInMbeLinkTo  OBJECT-TYPE
      SYNTAX  INTEGER
       {
       io1   (5),
       io2   (6),
       io3   (7),
       io4   (8),
       io5   (9),
       io6  (10),
       io7  (11),
       io8  (12),
       io9  (13),
       io10 (14),
       io11 (15),
       io12 (16)
       }
      MAX-ACCESS  read-write
      STATUS  deprecated
      DESCRIPTION
      "It indicates the slot of the main link card to which the
       MBE card is mapped.
       In the ?004 Unit the entries io6(10)..io16) are not valid.
       STATUS  deprecated - this object is replaced by prtGenCnfgLinkToSlot
       and prtGenCnfgLinkToPort."
      ::= {prtInMbeCnfgEntry 6}


--
-- Megaplex?000/?004 TRE port configuration
--

prtExTreCnfgTable OBJECT-TYPE
      SYNTAX SEQUENCE OF PrtExTreCnfgEntry
      MAX-ACCESS not-accessible
      STATUS  current
      DESCRIPTION
       "The write operation into the Table Objects is valid only
        to the TmpCnfg entry."
      ::= {prtTreCnfg 1}

prtExTreCnfgEntry OBJECT-TYPE
      SYNTAX PrtExTreCnfgEntry
      MAX-ACCESS not-accessible
      STATUS current
	DESCRIPTION  "An entry in table."
	INDEX {prtExTreCnfgIdx, prtExTreSltIdx,  prtExTrePrtIdx }
      ::= { prtExTreCnfgTable 1}

PrtExTreCnfgEntry ::=
      SEQUENCE {
        prtExTreCnfgIdx     Integer32,
        prtExTreSltIdx      INTEGER,
        prtExTrePrtIdx      INTEGER,

        prtExTreLan         INTEGER,
        prtExTreLanRate     INTEGER

      }

prtExTreCnfgIdx OBJECT-TYPE
      SYNTAX  Integer32  (1..255)
      MAX-ACCESS  read-only
      STATUS  current
      DESCRIPTION
      "This attribute indicates the Idx of the Cnfg (1..100) being
       accessed.
       Idx 255 relates to the TmpCnfg"
      ::= {prtExTreCnfgEntry 1}
-- In phase I only the values 1 (Cnfg1) and 255 (temp) are valid.

prtExTreSltIdx OBJECT-TYPE
      SYNTAX  INTEGER
     {
       io1   (5),
       io2   (6),
       io3   (7),
       io4   (8),
       io5   (9),
       io6  (10),
       io7  (11),
       io8  (12),
       io9  (13),
       io10 (14),
       io11 (15),
       io12 (16)
     }
      MAX-ACCESS  read-only
      STATUS  current
      DESCRIPTION
      "This attribute indicates a unique  slot  position where
       the card is inserted.
       In the ?004 Unit the entries io6(10)..io16) are not valid."
      ::= {prtExTreCnfgEntry 2}

prtExTrePrtIdx OBJECT-TYPE
      SYNTAX  INTEGER
     {
          exPrt1    (1)
     }
      MAX-ACCESS  read-only
      STATUS  current
      DESCRIPTION
      "A unique port identifier within the card."
      ::= {prtExTreCnfgEntry 3}

prtExTreLan OBJECT-TYPE
      SYNTAX  INTEGER
       {
        remote  (1),
        main    (2)
       }
      MAX-ACCESS  read-write
      STATUS  current
      DESCRIPTION
      "This attribute indicates whether the TRE port is operated
       as main or remote bridge.
       Default=remote."
      ::= {prtExTreCnfgEntry 4}

prtExTreLanRate OBJECT-TYPE
      SYNTAX  INTEGER
       {
        r4M  (1),
        r16M (2)
       }
      MAX-ACCESS  read-write
      STATUS  current
      DESCRIPTION
      "This attribute indicates the Rate of the TRE port
       in Mbit/sec.
       Default-r4M."
      ::= {prtExTreCnfgEntry 5}



prtInTreCnfgTable OBJECT-TYPE
      SYNTAX SEQUENCE OF PrtInTreCnfgEntry
      MAX-ACCESS not-accessible
      STATUS  current
      DESCRIPTION
       "The write operation into the Table Objects is valid only
        to the TmpCnfg entry."
      ::= {prtTreCnfg 2}

prtInTreCnfgEntry OBJECT-TYPE
      SYNTAX PrtInTreCnfgEntry
      MAX-ACCESS not-accessible
      STATUS current
	DESCRIPTION  "An entry in table."
	INDEX {prtInTreCnfgIdx, prtInTreSltIdx,  prtInTrePrtIdx }
      ::= { prtInTreCnfgTable 1}

PrtInTreCnfgEntry ::=
      SEQUENCE {
        prtInTreCnfgIdx     Integer32,
        prtInTreSltIdx      INTEGER,
        prtInTrePrtIdx      INTEGER,

        prtInTreConnect     INTEGER,
        prtInTreRate        INTEGER,
        prtInTreLinkTo      INTEGER
      }

prtInTreCnfgIdx OBJECT-TYPE
      SYNTAX  Integer32  (1..255)
      MAX-ACCESS  read-only
      STATUS  current
      DESCRIPTION
      "This attribute indicates the Idx of the Cnfg (1..100) being
       accessed.
       Idx 255 relates to the TmpCnfg"
      ::= {prtInTreCnfgEntry 1}
-- In phase I only the values 1 (Cnfg1) and 255 (temp) are valid.

prtInTreSltIdx OBJECT-TYPE
      SYNTAX  INTEGER
     {
       io1   (5),
       io2   (6),
       io3   (7),
       io4   (8),
       io5   (9),
       io6  (10),
       io7  (11),
       io8  (12),
       io9  (13),
       io10 (14),
       io11 (15),
       io12 (16)
     }
      MAX-ACCESS  read-only
      STATUS  current
      DESCRIPTION
      "This attribute indicates a unique  slot  position where
       the card is inserted.
       In the ?004 Unit the entries io6(10)..io16) are not valid."
      ::= {prtInTreCnfgEntry 2}

prtInTrePrtIdx OBJECT-TYPE
      SYNTAX  INTEGER
     {
          inPrt1    (101)
     }
      MAX-ACCESS  read-only
      STATUS  current
      DESCRIPTION
      "A unique port identifier within the card."
      ::= {prtInTreCnfgEntry 3}

prtInTreConnect OBJECT-TYPE
      SYNTAX  INTEGER
       {
  no  (2),
  yes (3)
       }
      MAX-ACCESS  read-write
      STATUS  current
      DESCRIPTION
      "This attribute indicates whether the port should be considered
       in any of the mux  algorithms."
      ::= {prtInTreCnfgEntry 4}

prtInTreRate    OBJECT-TYPE
      SYNTAX  INTEGER
       {
        r1x56eq56Kbps    (1),
        r1x64eq64Kbps    (2),
        r2x56eq112Kbps   (3),
        r2x64eq128Kbps   (4),
        r3x56eq168Kbps   (5),
        r3x64eq192Kbps   (6),
        r4x56eq224Kbps   (7),
        r4x64eq256Kbps   (8),
        r5x56eq280Kbps   (9),
        r5x64eq320Kbps   (10),
        r6x56eq336Kbps   (11),
        r6x64eq384Kbps   (12),
        r7x56eq392Kbps   (13),
        r7x64eq448Kbps   (14),
        r8x56eq448Kbps   (15),
        r8x64eq512Kbps   (16),
        r9x56eq504Kbps   (17)
       }
      MAX-ACCESS  read-write
      STATUS  current
      DESCRIPTION
      "This attribute indicates the port speed."
      ::= {prtInTreCnfgEntry 5}

prtInTreLinkTo  OBJECT-TYPE
      SYNTAX  INTEGER
       {
       io1   (5),
       io2   (6),
       io3   (7),
       io4   (8),
       io5   (9),
       io6  (10),
       io7  (11),
       io8  (12),
       io9  (13),
       io10 (14),
       io11 (15),
       io12 (16)
       }
      MAX-ACCESS  read-write
      STATUS  deprecated
      DESCRIPTION
      "It indicates the slot of the main link card to which the
       MBE card is mapped.
       In the ?004 Unit the entries io6(10)..io16) are not valid.
       STATUS  deprecated - this object is replaced by prtGenCnfgLinkToSlot
       and prtGenCnfgLinkToPort."
      ::= {prtInTreCnfgEntry 6}


-- Packet VC cards. 
-- This table is used for compressed voice cards with 4/8 ports.
--

prtExPVc4CnfgTable OBJECT-TYPE
      SYNTAX SEQUENCE OF PrtExPVc4CnfgEntry
      MAX-ACCESS not-accessible
      STATUS  current
      DESCRIPTION
       "The write operation into the Table Objects is valid only
        to the TmpCnfg entry."
      ::= { prtPVc4Cnfg 1}

prtExPVc4CnfgEntry OBJECT-TYPE
      SYNTAX PrtExPVc4CnfgEntry
      MAX-ACCESS not-accessible
      STATUS current
	DESCRIPTION  "An entry in table."
	INDEX {prtExPVc4CnfgIdx, prtExPVc4SltIdx, prtExPVc4PrtIdx }
      ::= { prtExPVc4CnfgTable 1}

PrtExPVc4CnfgEntry ::=
      SEQUENCE {
        prtExPVc4CnfgIdx      Integer32,
        prtExPVc4SltIdx       INTEGER,
        prtExPVc4PrtIdx       INTEGER,

		prtExPVc4PrtType      INTEGER,
        prtExPVc4Connect      INTEGER,
		prtExPVc4IfType       INTEGER,
        prtExPVc4TxGain       Integer32,
        prtExPVc4RxGain       Integer32,
		prtExPVc4MaxRate      INTEGER,
        prtExPVc4Tc           INTEGER,
        prtExPVc4Oos          INTEGER,
		prtExPVc4EchoCanceler INTEGER,
		prtExPVc4VarDelay     Integer32,
		prtExPVc4CongLevel    Integer32,
		prtExPVc4Wire         INTEGER,
		prtExPVc4ExtensionType		INTEGER,
		prtExPVc4ExtensionNumber	DisplayString,
		prtExPVc4OutPulsing 		INTEGER,
		prtExPVc4HuntGroupMb		INTEGER,
		prtExPVc4HuntGroupIdx		Integer32,
		prtExPVc4AutoFaxMode		INTEGER,
		prtExPVc4FaxRate            INTEGER,
		prtExPVc4SeizeAck           INTEGER,
		prtExPVc4SignalingProtocol  INTEGER,
		prtExPVc4DelayStart         Integer32,
		prtExPVc4WinkMinDuration    Integer32,
		prtExPVc4WinkMaxDuration    Integer32,
        prtExPVc4GenerateTone       INTEGER,
		prtExPVc4CodingLaw          INTEGER,
        prtExPVc4GenerateRingBack   INTEGER,
		prtExPVc4ChannelId          Integer32,
		prtExPVc4PortConnection     INTEGER,
		prtExPVc4CoderAndRate       INTEGER,
		prtExPVc4DestinationNum     DisplayString,
		prtExPVc4DtmfRelay          INTEGER,
		prtExPVc4DiscOnSilence      Integer32,
		prtExPVc4DynamicJitter      INTEGER,
		prtExPVc4EandMType          INTEGER,
		prtExPVc4Rate               Integer32,
		prtExPVc4FrameSize          Integer32,
		prtExPVc4MultiplexInterval  Integer32,
		prtExPVc4TransportProtocol  INTEGER,
		prtExPVc4MultiFreqRelay     INTEGER,
		prtExPVc4MinPulseWidth      Integer32,
		prtExPVc4MinPowerLevel      Integer32,
		prtExPVc4SuperTandem        INTEGER,
		prtExPVc4DestIp             IpAddress,
		prtExPVc4DestBundle         Integer32,
		prtExPVc4SrcIpAddress       IpAddress,
		prtExPVc4SrcIpMask          IpAddress,
		prtExPVc4DefaultGateway     IpAddress,
		prtExPVc4SigPacketInterval	Unsigned32
      }

prtExPVc4CnfgIdx OBJECT-TYPE
      SYNTAX  Integer32  (1..255)
      MAX-ACCESS  read-only
      STATUS  current
      DESCRIPTION
      "This attribute indicates the Idx of the Cnfg (1..100) being
       accessed.
       Idx  255 relates to the TmpCnfg"
      ::= {prtExPVc4CnfgEntry 1}
-- In phase I only the values 1 (Cnfg1) and 255 (temp) are valid.

prtExPVc4SltIdx OBJECT-TYPE
      SYNTAX  INTEGER
 {
       io1   (5),
       io2   (6),
       io3   (7),
       io4   (8),
       io5   (9),
       io6  (10),
       io7  (11),
       io8  (12),
       io9  (13),
       io10 (14),
       io11 (15),
       io12 (16),
    notApplicable (255)
 }
      MAX-ACCESS  read-only
      STATUS  current
      DESCRIPTION
      "This attribute indicates a unique  slot  position where
       the card is inserted."
      ::= {prtExPVc4CnfgEntry 2}

prtExPVc4PrtIdx OBJECT-TYPE
      SYNTAX  INTEGER
 {
       exPrt1  (1),
       exPrt2  (2),
       exPrt3  (3),
       exPrt4  (4),
       inPrt1(101),
       inPrt2(102),
       inPrt3(103),
       inPrt4(104),
	   inPrt5(105),
	   inPrt6(106),
	   inPrt7(107),
	   inPrt8(108)
 }
      MAX-ACCESS  read-only
      STATUS  current
      DESCRIPTION
      "This object indicates the port number in the selected card
       (slot)."
      ::= {prtExPVc4CnfgEntry 3}

prtExPVc4PrtType OBJECT-TYPE
      SYNTAX  INTEGER
	{
	      eAndM  (1),
	      fxo    (2),
	      fxs    (3),
	      internal(4),
	      s0      (5),
		  u       (6),
		  sQsig	  (7),
		  uQsig   (8)
	}
      MAX-ACCESS  read-write
      STATUS  current
      DESCRIPTION
      "This object indicates the type of the selected port.
	   In Mx 30/300 phase 4: s0 & u are for Voice over ISDN.
	   In MX 30/300 phase 5: sQsig & uQsig are used for Voice over ISDN with Qsig option.
	   	   
	   In MX MVC4 voice cards, each pair of ports 1-2, 3-4 may have a different type:
       E&M, FXO, FXS.
	   In MVC4 compressed voice cards ports 1..4 have the same interface for all ports.
       In MVC8 compressed voice cards each group of ports 1..4, 5..8 may have
       a different type: E&M, FXO, FXS."
      ::= {prtExPVc4CnfgEntry 4}

prtExPVc4Connect OBJECT-TYPE
      SYNTAX  INTEGER
              {
                no  (2),
                yes (3)
              }
      MAX-ACCESS  read-write
      STATUS  current
      DESCRIPTION
      "This attribute indicates whether the  port  should be
       considered in any of the mux algorithms."
      ::= {prtExPVc4CnfgEntry 5}

prtExPVc4IfType OBJECT-TYPE
      SYNTAX  INTEGER
              {
                unknown     (1),
                eAndM4wires (2),
   			    eAndM2wires (3),
                fxoGnd      (4),
                fxoLoop     (5),
                fxsGnd      (6),
				fxsLoop     (7),
				e1Framer    (8),
				e1Slave     (9),
				t1Framer   (10),
				t1Slave    (11)
              }
      MAX-ACCESS  read-write
      STATUS  current
      DESCRIPTION
      "This attribute indicates the interface type of the  port.
       eAndM4wires and eAndM2wires - are valid only for E&M
                                     port type
	   eAndM4wires - means 2/4 wires
       fxoGnd and fxoLoop - are valid only for FXO port type
       fxsGnd and fxsLoop - are valid only for FXS port type
       e1Framer, e1Slave, t1Framer, t1Slave - are applicable for the mvc4Pbx
       cards only."
      ::= {prtExPVc4CnfgEntry 6}

prtExPVc4TxGain OBJECT-TYPE
      SYNTAX  Integer32
      MAX-ACCESS  read-write
      STATUS  current
      DESCRIPTION
      "Transmission gain in dB."
      ::= {prtExPVc4CnfgEntry 7}

prtExPVc4RxGain OBJECT-TYPE
      SYNTAX  Integer32
      MAX-ACCESS  read-write
      STATUS  current
      DESCRIPTION
      "Reception gain in dBm."
      ::= {prtExPVc4CnfgEntry 8}

prtExPVc4MaxRate OBJECT-TYPE
      SYNTAX  INTEGER
       {
         notConnected  (1),
         r4800bps      (2),
         r7200bps      (3),
         r9600bps      (4),
		 notApplicatble (255)
       }
      MAX-ACCESS  read-write
      STATUS  current
      DESCRIPTION
      "Voice rate."
      ::= {prtExPVc4CnfgEntry 9}

prtExPVc4Tc OBJECT-TYPE
      SYNTAX  INTEGER
       {
          t1sec    (1),
          t2sec    (2),
          t3sec    (3),
          t4sec    (4)
       }
      MAX-ACCESS  read-write
      STATUS  current
      DESCRIPTION
      "Time interval for CIR control, in seconds. The value will
       be the same for all cards' ports."
      ::= {prtExPVc4CnfgEntry 10}

prtExPVc4Oos OBJECT-TYPE
      SYNTAX  INTEGER
       {
          notSupported   (2),
          forcedIdle     (3),
          forcedBusy     (4),
          busyIdle       (5),
          idleBusy       (6)
       }
      MAX-ACCESS  read-write
      STATUS  current
      DESCRIPTION
      "Handling type, when connection is lost."
      ::= {prtExPVc4CnfgEntry 11}

prtExPVc4EchoCanceler OBJECT-TYPE
      SYNTAX  INTEGER
       {
          off    (2),
          on     (3)
       }
      MAX-ACCESS  read-write
      STATUS  current
      DESCRIPTION
      "Echo canceler activation."
      ::= {prtExPVc4CnfgEntry 12}

prtExPVc4VarDelay OBJECT-TYPE
      SYNTAX  Integer32  (0..300)
      MAX-ACCESS  read-write
      STATUS  current
      DESCRIPTION
      "Maximum variant delay of the FR network, in msec."
      ::= {prtExPVc4CnfgEntry 13}

prtExPVc4CongLevel OBJECT-TYPE
      SYNTAX  Integer32 (0..70)
      MAX-ACCESS  read-write
      STATUS  current
      DESCRIPTION
      "This object indicates the level of delayed data in
       precents of total available dynamic memory,
       for which the port will start to operate as congested.
       The resolution of the parameter is 5%."
      ::= {prtExPVc4CnfgEntry 14}

prtExPVc4Wire OBJECT-TYPE
      SYNTAX  INTEGER
       {
          w2wire   (1),
          w4wire   (2),
    notApplicable (255)
       }
      MAX-ACCESS  read-write
      STATUS  current
      DESCRIPTION
      "This object indicates the wiring of the E&M port.
       It is applicable only for E&M card type."
      ::= {prtExPVc4CnfgEntry 15}

prtExPVc4ExtensionType OBJECT-TYPE
       SYNTAX  INTEGER
           { notApplicable(1),
             forceConnect(2),
             voiceSwitching(3),
             transparent(4),
             transparentPlus(5),
             ipForceConnect(6),
             permanentDial (7),
             autoAccept (8) }
       MAX-ACCESS  read-write
       STATUS  current
       DESCRIPTION
      "This object indicates the type of extension relevant for this port.

       ipForceConnect (6) is used for automatic connection or automatic
       dialing when the phone is off hook (hot line).
       permanentDial (7) means that the call is established upon power up. 
	   The hook may be on or off.
	   Permanent Dialing can be used when there is no signaling. 
	   autoAccept (8) means that the called party in the Permanent Dialing
	   will accept the call from the remote side automatically
	   upon on or off hook."
      ::= {prtExPVc4CnfgEntry 16}

prtExPVc4ExtensionNumber OBJECT-TYPE
       SYNTAX  DisplayString (SIZE(2))
     MAX-ACCESS  read-write
       STATUS  current
       DESCRIPTION
      "This is the extension number of this port.
      This field is relevant only when the extension
     type is voice switching and is read only if the
     port is member of a hunt group."
      ::= {prtExPVc4CnfgEntry 17}

prtExPVc4OutPulsing OBJECT-TYPE
       SYNTAX  INTEGER { notApplicable(1), no(2), yes(3) }
     MAX-ACCESS  read-write
       STATUS  current
       DESCRIPTION
      "This field indicates whether to outpulse the received
     digits. It is notApplicable(1) when the extension type
     is forceConnect(2)."
      ::= {prtExPVc4CnfgEntry 18}

prtExPVc4HuntGroupMb OBJECT-TYPE
     SYNTAX  INTEGER { notApplicable(1), no(2), yes(3) }
     MAX-ACCESS  read-write
       STATUS  current
       DESCRIPTION
      "This object indicates if this port belongs to
      an hunt group."
      ::= {prtExPVc4CnfgEntry 19}

prtExPVc4HuntGroupIdx	OBJECT-TYPE
	    SYNTAX  Integer32(0..10)
    	MAX-ACCESS  read-write
      	STATUS  current
      	DESCRIPTION
     	"If it belongs to an hunt group, this fields
	     indicates the index of the relevant hunt group.
	     0 = notApplicable "
      ::= {prtExPVc4CnfgEntry 20}

prtExPVc4AutoFaxMode	OBJECT-TYPE
    	SYNTAX  INTEGER { notApplicable(1), no(2), yes(3) }
    	MAX-ACCESS  read-write
      	STATUS  current
      	DESCRIPTION
     	"This object indicates if the system will switch automatically to
     	 FAX mode when detecting FAX activity.
     	 Default=Yes."
      ::= {prtExPVc4CnfgEntry 21}

prtExPVc4FaxRate OBJECT-TYPE
      SYNTAX  INTEGER
	      {
          notConnected  (1),
          r4800bps      (2),
		  r7200bps      (3),
		  r9600bps      (4),
		  r12000bps     (5),
		  r14400bps     (6),
          r2400bps      (7),
		  vbdFax        (8)
	      }
      MAX-ACCESS  read-write
      STATUS  current
      DESCRIPTION
      "FAX initial rate.
       Default=9600 bps."
      ::= {prtExPVc4CnfgEntry 22}

prtExPVc4SeizeAck OBJECT-TYPE
      SYNTAX INTEGER
      {
	  no   (2),
      yes  (3)
      }
      MAX-ACCESS  read-write
      STATUS  current
      DESCRIPTION
      "This parameter shows whether the device will acknowledge
       a seize signal (On/Off Hook).
       When the value is set to yes(3) & the device receives an on/off hook signal
       it will transmit back an on/off hook signal.
	   When the value is set to no(2) & the device receives an on/off hook signal
       it will NOT transmit back an on/off hook signal.
       
       Example:
       If Seize Ack Parameter = YES, when the MVC.4 receives a seize signal (Off Hook) 
       from the PBX it will send an Off Hook to the PBX.

       The Seize Parameter is relevant for all the following cards:
       MVC-4
       MVC-4/E1-Framer
       MVC-4/T1-DSU-Framer
       MVC-4/T1-CSU-Framer
       MVC-4/E1-SLAVE
       MVC-4/T1-SLAVE

       Default values:
       Analog FXS - No (value can't be changed).
       Analog FXO - Yes (value can't be changed).
       Analog E&M - No (values NO/YES).
       Digital E1/T1 Framer & Slave - No."
      ::= {prtExPVc4CnfgEntry 23}

prtExPVc4SignalingProtocol OBJECT-TYPE
      SYNTAX INTEGER
      {
	  delayStart      (2),
      immediateStart  (3),
	  winkStart       (4)
      }
      MAX-ACCESS  read-write
      STATUS  current
      DESCRIPTION
      "The signaling protocol that will be used between the PABX & the voice port.

	   Delay Start Protocol: the line is seized by sending an Off hook signal
	   and after a delay, if the called party is available (On hook)   
	   DTMF (Dual Tone Multi Frequency) digits are sent towards the called party.

       Immediate Start Protocol: the line is seized by sending an Off Hook signal
       and immediately DTMF digits are sent towards the called party.
       
       Wink start protocol: the line is seized by sending an Off Hook signal
       and then the called party sends a short Off Hook wink signal.
       Now the calling party starts sending DTMF digits."
      ::= {prtExPVc4CnfgEntry 24} 

prtExPVc4DelayStart OBJECT-TYPE
      SYNTAX Integer32
      MAX-ACCESS  read-write
      STATUS  current
      DESCRIPTION
      "This parameter is used only for Delay Protocol.
	   This is the time that the calling party will wait after sending an Off hook
	   signal and before sending DTMF digits to the called party.
       The delay values are 100..5000 msec in intervals of 100 msec."
      ::= {prtExPVc4CnfgEntry 25}

prtExPVc4WinkMinDuration OBJECT-TYPE
      SYNTAX Integer32
      MAX-ACCESS  read-write
      STATUS  current
      DESCRIPTION
      "This parameter is used only for Wink Protocol.
	   Min Duration of the Wink Signal (off hook duration from the called party).
       Legal values: 40..400 msec in intervals of 10 msec."
      ::= {prtExPVc4CnfgEntry 26}

prtExPVc4WinkMaxDuration OBJECT-TYPE
      SYNTAX Integer32
      MAX-ACCESS  read-write
      STATUS  current
      DESCRIPTION
      "This parameter is used only for Wink Protocol.
	   Max Duration of the Wink Signal (off hook duration from the called party).
       Legal values: 40..400 msec in intervals of 10 msec."
      ::= {prtExPVc4CnfgEntry 27}

prtExPVc4GenerateTone OBJECT-TYPE
      SYNTAX  INTEGER
	      {
          notApplicable  (1),
          no       (2),
		  yes      (3)
		  }
      MAX-ACCESS  read-write
      STATUS  current
      DESCRIPTION
      "This parameter indicates whether the device (MX or MPH) should generate
       dial tones for the channel.
       If the value is yes (3), it generates dial tones.
       If the value is no  (2), the connected equipment will generate dial tones.
       For example for some ISDN sets the dial tone is generated by the
       phone itself while for others sets it is generated by the MX."
      ::= {prtExPVc4CnfgEntry 28}

prtExPVc4CodingLaw OBJECT-TYPE
      SYNTAX  INTEGER
       {
          aLAW    (1),
          uLAW    (2)
       }
      MAX-ACCESS  read-write
      STATUS  current
      DESCRIPTION
      "This attribute indicates the Method/Law for decoding/encoding the voice
       information.
       aLaw(1) is the standard Law for E1 links.
       uLaw(2) is the standard Law for T1 links.

       This object is equal for all the ports in the specific module because
       of HW limitations"
      ::= {prtExPVc4CnfgEntry 29}

prtExPVc4GenerateRingBack OBJECT-TYPE
      SYNTAX  INTEGER
       {
          notApplicable  (1),
          no    (2),
          yes   (3)
       }
      MAX-ACCESS  read-write
      STATUS  current
      DESCRIPTION
      "Determines whether the Ring Back tone is generated locally or from the
       remote end.
   	   The default is - NO (Meaning coming from the remote end).
	   Yes means that the Ring Back Tone is generated locally.
       Applicable only for Force Connect."
      ::= {prtExPVc4CnfgEntry 30}

prtExPVc4ChannelId OBJECT-TYPE
      SYNTAX  Integer32 (0..256)
      MAX-ACCESS  read-write
      STATUS  current
      DESCRIPTION
      "Channel Identifier.
       According to FRF11 each voice port that works as force connect should add a
       CH Id after the DLCI in the frame header.

       Default : 1 

       Applicable only for Force Connect.
       Not Applicable value will be 0."
      ::= {prtExPVc4CnfgEntry 31}

prtExPVc4PortConnection OBJECT-TYPE
      SYNTAX  INTEGER 
       {
	      notApplicable (1),
          line    (2),
          trunk   (3)
       }
      MAX-ACCESS  read-write
      STATUS  current
      DESCRIPTION
      "Port connection determines whether the port is connected to a PABX (Trunk) or to
       Telephone set (Line) .

       It determines whether to send certain messages to the port or not.
       If the type is LINE then the port generates a
       ring back tone , if TRUNK it doesn't (The PBX does it)."
      ::= {prtExPVc4CnfgEntry 32}

prtExPVc4CoderAndRate  OBJECT-TYPE
      SYNTAX  INTEGER 
       {
       notApplicable   (1),
       g7231r6300BPS   (2),		                    
       g7231r5300BPS   (3),                
       g729A8KBPS      (4),               
       g711aLAW        (5),                    
       g711uLAW        (6),                     
       g726r16KBPS     (7),                   
       g726r24KBPS     (8),                   
       g726r32KBPS     (9),                   
       g726r40KBPS     (10),                   
       g727r16KBPS     (11),                   
       g727r24r16KBPS  (12),                
       g727r24KBPS     (13),                   
       g727r16r32KBPS  (14),                
       g727r32r24KBPS  (15),                
       g727r32KBPS     (16),                                
       g727r40r16KBPS  (17),                
       g727r40r24KBPS  (18),                
       g727r40r32KBPS  (19),                
       transparent     (20),                    
       netcoder6400BPS (21),              
       netcoder7200BPS (22),              
       netcoder8KBPS   (23),                
       netcoder8800BPS (24),              
       netcoder9600BPS (25),
       lowBitRateR2660BPS (26),
       amr4750BPS      (27), -- Adaptive Multirate Coders of GSM
	   amr5150BPS      (28),
       amr5900BPS      (29),              
       amr6700BPS      (30),
       amr7400BPS      (31),
	   amr7950BPS      (32),
	   amr10200BPS     (33),
	   amr12200BPS     (34)
      }
      MAX-ACCESS  read-write
      STATUS  current
      DESCRIPTION
      "Coder and Rate for the Voice Compression.
       In MPH: Relevant for MVC-8 card only."
      ::= {prtExPVc4CnfgEntry 33}

prtExPVc4DestinationNum  OBJECT-TYPE
      SYNTAX  DisplayString 
      MAX-ACCESS  read-write
      STATUS  current
      DESCRIPTION
      "The destination phone number: 0 to 22 digits.
       Applicable for Auto Dial - ipForceConnect(6), Permanent Dial and 
       Auto Accept Extension Types.      

       Default: Null String"
      ::= {prtExPVc4CnfgEntry 34}
		
prtExPVc4DtmfRelay  OBJECT-TYPE
      SYNTAX  INTEGER 
             {
               disable (2),
               enable  (3)
             }
      MAX-ACCESS  read-write
      STATUS  current
      DESCRIPTION
      "When DTMF RELAY is disabled, the DTMF digits (dialed by the user)
       are transmitted as compressed voice and in the remote unit are decompressed.
 
       When DTMF RELAY is enabled, the DTMF digits are detected at the near side and not
       transmitted as voice. Instead, only an indication of what digits were
       dialed are transmitted and in the far end the tone is regenerated."
      ::= {prtExPVc4CnfgEntry 35}

prtExPVc4DiscOnSilence  OBJECT-TYPE
      SYNTAX  Integer32 
      MAX-ACCESS  read-write
      STATUS  current
      DESCRIPTION
      "No. of silenced seconds after which the call will be disconected.
       A value of 0 means that there will be no disconnect when there is silence.
       Possible values: 0 - 900 sec."
      ::= {prtExPVc4CnfgEntry 36}

prtExPVc4DynamicJitter  OBJECT-TYPE
      SYNTAX  INTEGER 
             {
               disable (2),
               enable  (3)
             }
      MAX-ACCESS  read-write
      STATUS  current
      DESCRIPTION
      "The MVC8 uses two mechanisms to overcome the network delay.
       The first one is a static jitter buffer which holds a constant buffer of up
       to 300 Msec and can be controled by the JITTER parameter (prtExPVc4VarDelay).
       The second one is the dynamic jitter which calculates, in real time,
       the network delay and handles a jitter buffer dynamically.
       The dynamic mechanism that is implemented in MVC8, was intended to overcome
       network delay yet when the network bursts, the MVC8 dynamic mechanism is
       not able to overcome the delay.
       Therefore it is better not to use the dynamic jitter
       (DISABLE - should be the default) where bursts may occur often."
      ::= {prtExPVc4CnfgEntry 37}

prtExPVc4EandMType OBJECT-TYPE
       SYNTAX INTEGER
	   {
       notApplicable (1),
	   type1 (2),
       type2 (3),
       type3 (4),
       ssdc5 (5) 
       }
      MAX-ACCESS  read-write
      STATUS  current
      DESCRIPTION
      "This is the signaling type on the E&M analog side.
       The analog signaling includes voltage, no. of pins and other parameters."
       ::= {prtExPVc4CnfgEntry 38}

prtExPVc4Rate OBJECT-TYPE
      SYNTAX Integer32 (0..31)
      MAX-ACCESS  read-write
      STATUS  current
      DESCRIPTION
      "This is the Rate of the port in TS units. It is used by VF-30 card family.
       0 = NA = port is not intended to be connected; therefore, no Rate."
       ::= {prtExPVc4CnfgEntry 39}

prtExPVc4FrameSize  OBJECT-TYPE
      SYNTAX  Integer32 
      MAX-ACCESS  read-write
      STATUS  current
      DESCRIPTION
      "Defines the maximum size in Bytes of the multiplexed frame.
       In some cases this must be limited to avoid IP fragmentation,
       which makes the multiplexing useless, and can also decrease
       the damage in case of frame loss.
       Valid range: 100..1461.
       notApplicable=0."
      ::= {prtExPVc4CnfgEntry 40}

prtExPVc4MultiplexInterval  OBJECT-TYPE
      SYNTAX  Integer32                   
      MAX-ACCESS  read-write
      STATUS  current
      DESCRIPTION
      "Defines the maximum amout of time (msec.) between multiplexed frames 
       that are sent.

	   For Vmux-400/420 devices:
	   It defines the Payload Packetizing Interval.

       Valid values: 10-90 msec.
       notApplicable=0."
       ::= {prtExPVc4CnfgEntry 41}

prtExPVc4TransportProtocol OBJECT-TYPE
      SYNTAX INTEGER
	  {
      notApplicable (1),
	  ptp           (2),
      aal2oMpls     (3)
      }
      MAX-ACCESS  read-write
      STATUS  current
      DESCRIPTION
      "Transport Protocol.
       ptp = point to point.
       aal2oMpls = AAL2 over MPLS."
      ::= {prtExPVc4CnfgEntry 42}

prtExPVc4MultiFreqRelay OBJECT-TYPE
      SYNTAX INTEGER
	  {
      notApplicable (1),
	  disable       (2),
	  enable        (3)
      }
      MAX-ACCESS  read-write
      STATUS  current
      DESCRIPTION
      "This object enables/disables Multi Frequency Signaling Detection."
      ::= {prtExPVc4CnfgEntry 43}

prtExPVc4MinPulseWidth  OBJECT-TYPE
      SYNTAX  Integer32                   
      MAX-ACCESS  read-write
      STATUS  current
      DESCRIPTION
      "Defines the minimum Pulse Width in msec.
       Valid values: 45-100 msec.
       notApplicable=0."
       ::= {prtExPVc4CnfgEntry 44}

prtExPVc4MinPowerLevel  OBJECT-TYPE
      SYNTAX  Integer32                   
      MAX-ACCESS  read-write
      STATUS  current
      DESCRIPTION
      "Defines the minimum Power Level in dBm.
       Valid values: -1..-35 dBm."
      ::= {prtExPVc4CnfgEntry 45}
	     
prtExPVc4SuperTandem OBJECT-TYPE
      SYNTAX INTEGER
	  {
      notApplicable (1),
	  disable       (2),
	  enable        (3)
      }
      MAX-ACCESS  read-write
      STATUS  current
      DESCRIPTION
      "The Super Tandem feature provides end to end compression 
       over multiple hops, solving the double compression problem 
       detected in Voice compressing systems.
       The Super Tandem, when enabled, allows transmission of 
       compressed voice between a few devices and eliminates the 
       need to decompress an recompress it over each voice card and 
       PBX, thus improving voice quality and reducing delay."    
      ::= {prtExPVc4CnfgEntry 46}
		      
prtExPVc4DestIp  OBJECT-TYPE
      SYNTAX  IpAddress 
      MAX-ACCESS  read-write
      STATUS  current
      DESCRIPTION
      "This object defines the destination IP Address."
      ::= {prtExPVc4CnfgEntry 47}

prtExPVc4DestBundle  OBJECT-TYPE
      SYNTAX  Integer32 
      MAX-ACCESS  read-write
      STATUS  current
      DESCRIPTION
      "This object defines the destination Bundle at the 
       far-end device."
      ::= {prtExPVc4CnfgEntry 48}

prtExPVc4SrcIpAddress  OBJECT-TYPE
      SYNTAX  IpAddress 
      MAX-ACCESS  read-write
      STATUS  current
      DESCRIPTION
      "This object defines the Source IP Address."
      ::= {prtExPVc4CnfgEntry 49}

prtExPVc4SrcIpMask  OBJECT-TYPE
      SYNTAX  IpAddress 
      MAX-ACCESS  read-write
      STATUS  current
      DESCRIPTION
      "This object defines the Source IP Mask."
      ::= {prtExPVc4CnfgEntry 50}

prtExPVc4DefaultGateway  OBJECT-TYPE
      SYNTAX  IpAddress 
      MAX-ACCESS  read-write
      STATUS  current
      DESCRIPTION
      "This object defines the Default Gateway for this interface."
      ::= {prtExPVc4CnfgEntry 51}

prtExPVc4SigPacketInterval OBJECT-TYPE
	SYNTAX		Unsigned32                   
	MAX-ACCESS	read-write
	STATUS		current
	DESCRIPTION
	"Defines the Signaling Packetizing Interval,
	 which is the maximum time interval, measured in msec (milliseconds),
	 between multiplexed signaling frames."
	::= { prtExPVc4CnfgEntry 52 }


--
-- Packet VC4 card
-- External port Dlci table
--
prtExPVc4DlciTable  OBJECT-TYPE
     SYNTAX SEQUENCE OF PrtExPVc4DlciEntry
     MAX-ACCESS not-accessible
     STATUS  current
     DESCRIPTION
      "The write operation into the Table Objects is valid only
       at the TmpCnfg entry."
     ::= {prtPVc4Cnfg 2}

prtExPVc4DlciEntry OBJECT-TYPE
      SYNTAX PrtExPVc4DlciEntry
      MAX-ACCESS not-accessible
      STATUS current
	DESCRIPTION  "An entry in table."
	INDEX {prtExPVc4DlciCnfgIdx, prtExPVc4DlciSltIdx, prtExPVc4DlciPrtIdx}
      ::= { prtExPVc4DlciTable 1}

PrtExPVc4DlciEntry ::=
      SEQUENCE {
      prtExPVc4DlciCnfgIdx        Integer32,
      prtExPVc4DlciSltIdx         INTEGER,
      prtExPVc4DlciPrtIdx         INTEGER,

      prtExPVc4DlciValid          INTEGER,
      prtExPVc4DlciIConSlt        INTEGER,
      prtExPVc4DlciIConPrt        INTEGER,
      prtExPVc4DlciIConDlci       Integer32,

      prtExPVc4DlciTxBc           INTEGER,
      prtExPVc4DlciTxBe           INTEGER,
      prtExPVc4DlciRxBc           INTEGER,
      prtExPVc4DlciRxBe           INTEGER,

      prtExPVc4DlciPriority       Integer32,

      prtExPVc4DlciStatus         INTEGER
      }


prtExPVc4DlciCnfgIdx OBJECT-TYPE
      SYNTAX  Integer32 (1..255)
      MAX-ACCESS  read-only
      STATUS  current
      DESCRIPTION
      "This attribute indicates the Idx of the Cnfg (1..100) being
       accessed.
       Idx 255 relates to the TmpCnfg. "
      ::= { prtExPVc4DlciEntry 1}
-- In phase I only the values 1 (Cnfg1) and 255 (temp) are valid.

prtExPVc4DlciSltIdx OBJECT-TYPE
      SYNTAX  INTEGER
     {
       io1   (5),
       io2   (6),
       io3   (7),
       io4   (8),
       io5   (9),
       io6  (10),
       io7  (11),
       io8  (12),
       io9  (13),
       io10 (14),
       io11 (15),
       io12 (16),
    notApplicable (255)
     }
      MAX-ACCESS  read-only
      STATUS  current
      DESCRIPTION
      "This attribute indicates a unique  slot  position where
       the card is inserted.
       In the ?004 Unit the entries io6(10)..io16) are not valid"
      ::= { prtExPVc4DlciEntry 2}

prtExPVc4DlciPrtIdx OBJECT-TYPE
      SYNTAX  INTEGER
 {
          exPrt1  (1) ,
          exPrt2  (2) ,
          exPrt3  (3) ,
    exPrt4  (4)
       }
      MAX-ACCESS  read-only
      STATUS  current
      DESCRIPTION
      "This attribute indicates a unique internal port number.
       VC4 cards have four external ports."
      ::= { prtExPVc4DlciEntry 3}


prtExPVc4DlciValid OBJECT-TYPE
      SYNTAX  INTEGER
     {
     no  (2),
     yes (3)
     }
      MAX-ACCESS  read-write
      STATUS  current
      DESCRIPTION
      "This attribute indicates whether the attributes in this
       entry are valid or not. The user can add/delete pvc (dlci
       to dlci connection) by modifing this object"
      ::= { prtExPVc4DlciEntry 4}

prtExPVc4DlciIConSlt OBJECT-TYPE
      SYNTAX  INTEGER
 {
          noConnect (2),
       io1   (5),
       io2   (6),
       io3   (7),
       io4   (8),
       io5   (9),
       io6  (10),
       io7  (11),
       io8  (12),
       io9  (13),
       io10 (14),
       io11 (15),
       io12 (16),
    notApplicable (255)
       }
      MAX-ACCESS  read-write
      STATUS  current
      DESCRIPTION
      "This attribute indicates a unique slot position In the Mux
       (Agent) where the dlci is routed to.
       In the ?004 Unit the entries io6(10)..io16) are not valid"
      ::= { prtExPVc4DlciEntry 5}

prtExPVc4DlciIConPrt OBJECT-TYPE
      SYNTAX  INTEGER
      {
       exPrt1    (1) ,
       exPrt2    (2) ,
       exPrt3    (3) ,
       exPrt4    (4) ,
       exPrt5    (5) ,
       exPrt6    (6) ,
       exPrt7    (7) ,
       exPrt8    (8) ,
       exPrt9    (9) ,
       exPrt10  (10) ,
          noConnect (100),
       inPrt1  (101) ,
       inPrt2  (102) ,
       inPrt3  (103) ,
       inPrt4  (104) ,
       inPrt5  (105) ,
       inPrt6  (106) ,
       inPrt7  (107) ,
       inPrt8  (108) ,
       inPrt9  (109) ,
       inPrt10 (110) ,
    inPrt11 (111) ,
    inPrt12 (112)
       }
      MAX-ACCESS  read-write
      STATUS  current
      DESCRIPTION
      "This attribute indicates a unique port id which the dlci is
       routed to."
      ::= { prtExPVc4DlciEntry 6}


prtExPVc4DlciIConDlci OBJECT-TYPE
      SYNTAX  Integer32    (1..991)
      MAX-ACCESS  read-write
      STATUS  current
      DESCRIPTION
      "This attribute indicates a unique internal connection dlci
       number,  the dlci is routed to."
      ::= { prtExPVc4DlciEntry 7}

prtExPVc4DlciTxBc OBJECT-TYPE
      SYNTAX  INTEGER
        {
         full       (1),
         zero       (2),
         txBc9600bps    (3),
        txBc14400bps    (4),
        txBc19200bps    (5),
        txBc28800bps    (6),
        txBc32000bps    (7),
        txBc38400bps    (8),
        txBc48000bps    (9),
        txBc56000bps   (10),
        txBc57600bps   (11),
          txBc64Kbps   (12),
         txBc128Kbps   (13),
         txBc192Kbps   (14),
         txBc256Kbps   (15),
         txBc320Kbps   (16),
         txBc384Kbps   (17),
         txBc448Kbps   (18),
         txBc512Kbps   (19),
         txBc768Kbps   (20),
        txBc1024Kbps   (21),
--
--KM30 ; KM300 additional rates
--
        txBc16000bps   (25),
   txBc112Kbps   (26)
        }
      MAX-ACCESS  read-write
      STATUS  current
      DESCRIPTION
      "This attribute indicates a unique Tx committed bandwidth on
       the user transmit line (or at the port receive line)."
      ::= { prtExPVc4DlciEntry 8}


prtExPVc4DlciTxBe OBJECT-TYPE
      SYNTAX  INTEGER
        {
         full       (1),
         zero       (2),
         txBe9600bps    (3),
        txBe14400bps    (4),
        txBe19200bps    (5),
        txBe28800bps    (6),
        txBe32000bps    (7),
        txBe38400bps    (8),
        txBe48000bps    (9),
        txBe56000bps   (10),
        txBe57600bps   (11),
          txBe64Kbps   (12),
         txBe128Kbps   (13),
         txBe192Kbps   (14),
         txBe256Kbps   (15),
         txBe320Kbps   (16),
         txBe384Kbps   (17),
         txBe448Kbps   (18),
         txBe512Kbps   (19),
         txBe768Kbps   (20),
        txBe1024Kbps   (21),
--
--KM30 ; KM300 additional rates
--
        txBc16000bps   (25),
   txBc112Kbps   (26)
        }
      MAX-ACCESS  read-write
      STATUS  current
      DESCRIPTION
      "This attribute indicates a unique Tx excess bandwidth on the
      user transmit line (or at the port receive line)."
      ::= { prtExPVc4DlciEntry 9}


prtExPVc4DlciRxBc OBJECT-TYPE
      SYNTAX  INTEGER
        {
         full       (1),
         zero       (2),
         rxBc9600bps    (3),
        rxBc14400bps    (4),
        rxBc19200bps    (5),
        rxBc28800bps    (6),
        rxBc32000bps    (7),
        rxBc38400bps    (8),
        rxBc48000bps    (9),
        rxBc56000bps   (10),
        rxBc57600bps   (11),
        rxBc64Kbps   (12),
         rxBc128Kbps   (13),
         rxBc192Kbps   (14),
         rxBc256Kbps   (15),
         rxBc320Kbps   (16),
         rxBc384Kbps   (17),
         rxBc448Kbps   (18),
         rxBc512Kbps   (19),
         rxBc768Kbps   (20),
        rxBc1024Kbps   (21),
--
--KM30 ; KM300 additional rates
--
        rxBc16000bps   (25),
   rxBc112Kbps   (26)
        }
      MAX-ACCESS  read-write
      STATUS  current
      DESCRIPTION
      "This attribute indicates a unique Rx committed bandwidth on the
      user receive line (or at the port transmit line)."
      ::= { prtExPVc4DlciEntry 10}


prtExPVc4DlciRxBe OBJECT-TYPE
      SYNTAX  INTEGER
        {
         full       (1),
         zero       (2),
         rxBe9600bps    (3),
        rxBe14400bps    (4),
        rxBe19200bps    (5),
        rxBe28800bps    (6),
        rxBe32000bps    (7),
        rxBe38400bps    (8),
        rxBe48000bps    (9),
        rxBe56000bps   (10),
        rxBe57600bps   (11),
          rxBe64Kbps   (12),
         rxBe128Kbps   (13),
         rxBe192Kbps   (14),
         rxBe256Kbps   (15),
         rxBe320Kbps   (16),
         rxBe384Kbps   (17),
         rxBe448Kbps   (18),
         rxBe512Kbps   (19),
         rxBe768Kbps   (20),
        rxBe1024Kbps   (21),
--
--KM30 ; KM300 additional rates
--
        rxBc16000bps   (25),
   rxBc112Kbps   (26)
        }
      MAX-ACCESS  read-write
      STATUS  current
      DESCRIPTION
      "This attribute indicates a unique Rx excess bandwidth on the
      user receive line (or at the port transmit line)."
      ::= { prtExPVc4DlciEntry 11}


prtExPVc4DlciPriority OBJECT-TYPE
      SYNTAX  Integer32  (6..8)
      MAX-ACCESS  read-write
      STATUS  current
      DESCRIPTION
      "This attribute indicates a unique priority of the pvc.
       6 is the lowest priority and 8 is the highest priority."
      ::= { prtExPVc4DlciEntry 12}



prtExPVc4DlciStatus OBJECT-TYPE
      SYNTAX  INTEGER
 {
          disconnected (1),
          connected    (2)
       }
      MAX-ACCESS  read-only
      STATUS  current
      DESCRIPTION
      "This attribute indicates the status of the pvc. The status is
       disconnected(1) when one of the sides is programmed as not
       connected"
      ::= { prtExPVc4DlciEntry 13}


--
-- Megaplex ?000/?004 LS-6 TDM I/O family card include:
-- Ls6, Ls6V1/E, Ls6V1/O, Ls6V1/S, Ls6V2/E, Ls6V2/O, Ls6V2/S,
-- Ls6Vf/E, Ls6Vf/O, Ls6Vf/S
--
--prtExLs6CnfgTable OBJECT IDENTIFIER ::=  {prtLs6Cnfg 1}
--prtExLs6VCnfgTable OBJECT IDENTIFIER ::= {prtLs6Cnfg 2}
--prtInLs6CnfgTable OBJECT IDENTIFIER ::=  {prtLs6Cnfg 3}

--prtExLs6CnfgTable defines the parameters of the
-- LS-6 cards family external Data ports (1-6) ; LS-12 (1-12)

prtExLs6CnfgTable OBJECT-TYPE
      SYNTAX SEQUENCE OF PrtExLs6CnfgEntry
      MAX-ACCESS not-accessible
      STATUS  current
      DESCRIPTION
       "The write operation into the Table Objects is valid only
        to the TmpCnfg entry."
      ::= {prtLs6Cnfg 1}

prtExLs6CnfgEntry OBJECT-TYPE
      SYNTAX PrtExLs6CnfgEntry
      MAX-ACCESS not-accessible
      STATUS current
	DESCRIPTION  "An entry in table."
	INDEX {prtExLs6CnfgIdx, prtExLs6SltIdx, prtExLs6PrtIdx }
      ::= {prtExLs6CnfgTable  1}

PrtExLs6CnfgEntry ::=
      SEQUENCE {
        prtExLs6CnfgIdx    Integer32,
        prtExLs6SltIdx     INTEGER,
        prtExLs6PrtIdx     INTEGER,
        prtExLs6Connect    INTEGER,
        prtExLs6Protocol   INTEGER,
        prtExLs6Rate       INTEGER,
        prtExLs6ClkMode    INTEGER,
        prtExLs6CtrlSignal INTEGER,
        prtExLs6DataBits   INTEGER,
        prtExLs6Cts        INTEGER,
        prtExLs6LinkToInternal INTEGER
      }

prtExLs6CnfgIdx OBJECT-TYPE
      SYNTAX  Integer32 (1..255)
      MAX-ACCESS  read-only
      STATUS  current
      DESCRIPTION
      "This attribute indicates the Idx of the Cnfg (1..100) being
       accessed.
       Idx  255 relates to the TmpCnfg"
      ::= {prtExLs6CnfgEntry 1}

prtExLs6SltIdx OBJECT-TYPE
      SYNTAX  INTEGER
          {
       io1   (5),
       io2   (6),
       io3   (7),
       io4   (8),
       io5   (9),
       io6  (10),
       io7  (11),
       io8  (12),
       io9  (13),
       io10 (14),
       io11 (15),
       io12 (16),
       notApplicable (255)
       }
      MAX-ACCESS  read-only
      STATUS  current
      DESCRIPTION
      "This attribute indicates a unique  slot  position where
       the card is inserted.
       In the ?004 Unit the entries io6(10)..io12(16) are not valid."
      ::= {prtExLs6CnfgEntry 2}

prtExLs6PrtIdx OBJECT-TYPE
      SYNTAX  INTEGER
          {
          exPrt1    (1) ,
          exPrt2    (2) ,
          exPrt3    (3) ,
          exPrt4    (4) ,
          exPrt5    (5) ,
          exPrt6    (6) ,
          exPrt7    (7) ,
          exPrt8    (8) ,
          exPrt9    (9) ,
          exPrt10  (10) ,
          exPrt11  (11) ,
          exPrt12  (12)
          }
      MAX-ACCESS  read-only
      STATUS  current
      DESCRIPTION
      "This attribute indicates a unique  port index."
      ::= {prtExLs6CnfgEntry 3}

prtExLs6Connect OBJECT-TYPE
      SYNTAX  INTEGER
              {
                no  (2),
                yes (3)
              }
      MAX-ACCESS  read-write
      STATUS  current
      DESCRIPTION
      "This attribute indicates whether the  port  should be
       considered in any of the mux algorithms."
      ::= {prtExLs6CnfgEntry 4}

prtExLs6Protocol OBJECT-TYPE
      SYNTAX  INTEGER
              {
                sync  (2),
                async (3)
              }
      MAX-ACCESS  read-write
      STATUS  current
      DESCRIPTION
      "This attribute indicates the protocol.
       async - can be selected only for ports 1-2."
      ::= {prtExLs6CnfgEntry 5}

prtExLs6Rate OBJECT-TYPE
      SYNTAX  INTEGER
       {
          r300bps      (2),
          r600bps      (3),
          r1200bps     (4),
          r2400bps     (5),
          r4800bps     (6),
          r7200bps     (7),
          r8000bps     (8),
          r9600bps     (9),
          r14400bps   (10),
          r16000bps   (11),
          r19200bps   (12),
          r24000bps   (13),
          r28800bps   (14),
          r32000bps   (15),
          r38400bps   (16),
          r48000bps   (17),
          r56000bps   (18),
          r57600bps   (19),
          r64000bps   (20)
       }
      MAX-ACCESS  read-write
      STATUS  current
      DESCRIPTION
      "Port rates in bps.
       g1 - contains the values : (2)-(6),(9),(12),(16)
       g2 - contains the values : (7),(10),(14),(19)
       g3 - contains the values : (8),(11),(13),(15),(17),(18),(20);
            it is not applicable when using Async protocol.
       Rates of pair ports (1-2, 3-4, 5-6) must be from the same
       group."
      ::= {prtExLs6CnfgEntry 6}

prtExLs6ClkMode OBJECT-TYPE
      SYNTAX  INTEGER
       {
          dce     (1),
          extDce  (2),
          dte1    (3),
          notApplicable (255)
       }
      MAX-ACCESS  read-write
      STATUS  current
      DESCRIPTION
      "This attribute indicates a unique port operation clock mode.
       It is applicable for Sync protocol only ."
      ::= {prtExLs6CnfgEntry 7}

prtExLs6CtrlSignal OBJECT-TYPE
      SYNTAX  INTEGER
       {
    local     (2),
    rts       (3),
    dtrAndRts (4)
       }
      MAX-ACCESS  read-write
      STATUS  current
      DESCRIPTION
      "Control Signal."
      ::= {prtExLs6CnfgEntry 8}

prtExLs6DataBits OBJECT-TYPE
      SYNTAX  INTEGER
       {
    d6bits    (1),
    d7bits    (2),
    d8bits    (3),
    d9bits    (4),
    notApplicable (255)
       }
      MAX-ACCESS  read-write
      STATUS  current
      DESCRIPTION
      "Data Bits.
       This object is applicable for Async protocol only."
      ::= {prtExLs6CnfgEntry 9}

prtExLs6Cts OBJECT-TYPE
      SYNTAX  INTEGER
       {
     notApplicable (1),
     on            (2),
     rts           (3)
       }
      MAX-ACCESS  read-write
      STATUS  current
      DESCRIPTION
      "This object indicates the CTS control line
       operation mode."
      ::= {prtExLs6CnfgEntry 10}

prtExLs6LinkToInternal OBJECT-TYPE
      SYNTAX  INTEGER
          {
          inPrt1        (101) ,
          inPrt2        (102) ,
    notApplicable (255)
          }
      MAX-ACCESS  read-write
      STATUS  current
      DESCRIPTION
      "This object indicates which internal port of the card,
       the external port is linked to."
      ::= {prtExLs6CnfgEntry 11}


--prtExLs6VCnfgTable defines the parameters of the
-- LS-6 cards family external Voice & FAX ports (7-8)

prtExLs6VCnfgTable OBJECT-TYPE
      SYNTAX SEQUENCE OF PrtExLs6VCnfgEntry
      MAX-ACCESS not-accessible
      STATUS  current
      DESCRIPTION
       "The write operation into the Table Objects is valid only
        to the TmpCnfg entry."
      ::= {prtLs6Cnfg 2}

prtExLs6VCnfgEntry OBJECT-TYPE
      SYNTAX PrtExLs6VCnfgEntry
      MAX-ACCESS not-accessible
      STATUS current
	DESCRIPTION  "An entry in table."
	INDEX {prtExLs6VCnfgIdx, prtExLs6VSltIdx, prtExLs6VPrtIdx }
      ::= {prtExLs6VCnfgTable  1}


PrtExLs6VCnfgEntry ::=
      SEQUENCE {
        prtExLs6VCnfgIdx       Integer32,
        prtExLs6VSltIdx        INTEGER,
        prtExLs6VPrtIdx        INTEGER,

        prtExLs6VConnect       INTEGER,
        prtExLs6VRate          INTEGER,
        prtExLs6VEchoCanceler  INTEGER,
        prtExLs6VIfType        INTEGER,
        prtExLs6VTxGain        Integer32,
        prtExLs6VRxGain        Integer32,
        prtExLs6VOos           INTEGER
      }

prtExLs6VCnfgIdx OBJECT-TYPE
      SYNTAX  Integer32  (1..255)
      MAX-ACCESS  read-only
      STATUS  current
      DESCRIPTION
      "This attribute indicates the Idx of the Cnfg (1..100) being
       accessed.
       Idx  255 relates to the TmpCnfg"
      ::= {prtExLs6VCnfgEntry 1}

prtExLs6VSltIdx OBJECT-TYPE
      SYNTAX  INTEGER
 {
       io1   (5),
       io2   (6),
       io3   (7),
       io4   (8),
       io5   (9),
       io6  (10),
       io7  (11),
       io8  (12),
       io9  (13),
       io10 (14),
       io11 (15),
       io12 (16)
 }
      MAX-ACCESS  read-only
      STATUS  current
      DESCRIPTION
      "This attribute indicates a unique  slot  position where
       the card is inserted.
       In the ?004 Unit the entries io6(10)..io12(16) are not valid."
    ::= {prtExLs6VCnfgEntry 2}

prtExLs6VPrtIdx OBJECT-TYPE
      SYNTAX  INTEGER
 {
       exPrt7    (7) ,
       exPrt8    (8)
 }
      MAX-ACCESS  read-only
      STATUS  current
      DESCRIPTION
      "A unique identifier of the port, within the card."
      ::= {prtExLs6VCnfgEntry 3}

prtExLs6VConnect OBJECT-TYPE
      SYNTAX  INTEGER
              {
                no  (2),
                yes (3)
              }
      MAX-ACCESS  read-write
      STATUS  current
      DESCRIPTION
      "This attribute indicates whether the  port  should be
       considered in any of the mux algorithms."
      ::= {prtExLs6VCnfgEntry 4}


prtExLs6VRate OBJECT-TYPE
      SYNTAX  INTEGER
       {
          r6400bps      (2),
    r7200bps      (3),
    r8000bps      (4),
    r9600bps      (5),
    r16000bps     (6),
    r24000bps     (7),
    r32000bps     (8),
    r64000bps     (9)
       }
      MAX-ACCESS  read-write
      STATUS  current
      DESCRIPTION
      "Rate (bps) used for FAX transmission and Voice coding."
      ::= {prtExLs6VCnfgEntry 5}

prtExLs6VEchoCanceler OBJECT-TYPE
      SYNTAX  INTEGER
       {
          off    (2),
          on     (3)
       }
      MAX-ACCESS  read-write
      STATUS  current
      DESCRIPTION
      "Echo canceler activation."
      ::= {prtExLs6VCnfgEntry 6}

prtExLs6VIfType OBJECT-TYPE
      SYNTAX  INTEGER
              {
          w2wire   (1),
          w4wire   (2)
              }
      MAX-ACCESS  read-write
      STATUS  current
      DESCRIPTION
      "This attribute indicates the interface type of the  port.
       w4wire - is applicable only for E&M port type."
      ::= {prtExLs6VCnfgEntry 7}

prtExLs6VTxGain OBJECT-TYPE
      SYNTAX  Integer32
      MAX-ACCESS  read-write
      STATUS  current
      DESCRIPTION
      "Transmit gain in dBm.
       E&M - values range: -17 .. 8
       FXO - values range: -16 .. 4
       FXS - values range: -13 .. 8  "
      ::= {prtExLs6VCnfgEntry 8}

prtExLs6VRxGain OBJECT-TYPE
      SYNTAX  Integer32
      MAX-ACCESS  read-write
      STATUS  current
      DESCRIPTION
      "Receive gain in dBm.
       E&M - values range: -17 .. 2
       FXO - values range: -17 .. -1
       FXS - values range: -17 .. 2  "
      ::= {prtExLs6VCnfgEntry 9}

prtExLs6VOos OBJECT-TYPE
      SYNTAX  INTEGER
       {
          forcedIdle     (1),
          forcedBusy     (2),
          busyIdle       (3),
          idleBusy       (4)
       }
      MAX-ACCESS  read-write
      STATUS  current
      DESCRIPTION
      "Out of Service signaling mode."
      ::= {prtExLs6VCnfgEntry 10}



-- Ls6 and Ls12 Internal composite channel parameters
--

prtInLs6CnfgTable OBJECT-TYPE
      SYNTAX SEQUENCE OF PrtInLs6CnfgEntry
      MAX-ACCESS not-accessible
      STATUS  current
      DESCRIPTION
       "The write operation into the Table Objects is valid only
        to the TmpCnfg entry."
      ::= {prtLs6Cnfg 3}

prtInLs6CnfgEntry OBJECT-TYPE
      SYNTAX PrtInLs6CnfgEntry
      MAX-ACCESS not-accessible
      STATUS current
	DESCRIPTION  "An entry in table."
	INDEX {prtInLs6CnfgIdx, prtInLs6SltIdx, prtInLs6PrtIdx }
      ::= {prtInLs6CnfgTable 1}

PrtInLs6CnfgEntry ::=
      SEQUENCE {
        prtInLs6CnfgIdx    Integer32,
        prtInLs6SltIdx     INTEGER,
        prtInLs6PrtIdx     INTEGER,
        prtInLs6Connect    INTEGER,
        prtInLs6TandemMode INTEGER,
        prtInLs6Rate       INTEGER,
        prtInLs6RemoteType INTEGER,
        prtInLs6LinkTo     INTEGER
      }

prtInLs6CnfgIdx OBJECT-TYPE
      SYNTAX  Integer32 (1..255)
      MAX-ACCESS  read-only
      STATUS  current
      DESCRIPTION
      "This attribute indicates the Idx of the Cnfg (1..100) being
       accessed.
       Idx  255 relates to the TmpCnfg"
      ::= {prtInLs6CnfgEntry 1}

prtInLs6SltIdx OBJECT-TYPE
      SYNTAX  INTEGER
          {
       io1   (5),
       io2   (6),
       io3   (7),
       io4   (8),
       io5   (9),
       io6  (10),
       io7  (11),
       io8  (12),
       io9  (13),
       io10 (14),
       io11 (15),
       io12 (16)
       }
      MAX-ACCESS  read-only
      STATUS  current
      DESCRIPTION
      "This attribute indicates a unique  slot  position where
       the card is inserted.
       In the ?004 Unit the entries io6(10)..io12(16) are not valid."
      ::= {prtInLs6CnfgEntry 2}

prtInLs6PrtIdx OBJECT-TYPE
      SYNTAX  INTEGER
          {
          inPrt1    (101),
          inPrt2    (102)
          }
      MAX-ACCESS  read-only
      STATUS  current
      DESCRIPTION
      "This attribute indicates a unique internal port index."
      ::= {prtInLs6CnfgEntry 3}

prtInLs6Connect OBJECT-TYPE
      SYNTAX  INTEGER
              {
                no  (2),
                yes (3)
              }
      MAX-ACCESS  read-write
      STATUS  current
      DESCRIPTION
      "This attribute indicates whether the port should be considered in
       any of the mux  algorithms. It also affects all the module
       considerations because the module has only one Internal
       interface which is the composite channel."
      ::= {prtInLs6CnfgEntry 4}

prtInLs6TandemMode  OBJECT-TYPE
      SYNTAX  INTEGER
       {
     noTandem     (1),
     tandemMaster (2),
     tandemSlave  (3)
    }
      MAX-ACCESS  read-write
      STATUS  current
      DESCRIPTION
      "This object indicates the Tandem Mode.
       tandemSlave - is valid only for an LS-6 card having on
    the (current slot-1) an LS-6 card with 'tandemMaster' mode."
       ::= {prtInLs6CnfgEntry 5}

prtInLs6Rate OBJECT-TYPE
      SYNTAX  INTEGER
       {
     r32Kbps   (1),
     r56Kbps   (2),
     r64Kpbs   (3),
     r128Kbps  (4),
     r256Kbps  (5),
     r384Kbps  (6),
     r192Kbps  (7),
     r512Kbps  (8),
     r768Kbps  (9),
	 r14400bps(10) 
    }
      MAX-ACCESS  read-write
      STATUS  current
      DESCRIPTION
      "Main Rate in Kbps."
      ::= {prtInLs6CnfgEntry 6}

prtInLs6RemoteType OBJECT-TYPE
      SYNTAX  INTEGER
       {
     ls6            (1),
     km2kSlave      (2),
     km2kStandalone (3),
     notApplicable (255)
    }
      MAX-ACCESS  read-write
      STATUS  current
      DESCRIPTION
      "Remote Type.
       notApplicable - when prtInLs6TandemMode=tandemSlave "
      ::= {prtInLs6CnfgEntry 7}

prtInLs6LinkTo OBJECT-TYPE
      SYNTAX  INTEGER
       {
       io1   (5),
       io2   (6),
       io3   (7),
       io4   (8),
       io5   (9),
       io6  (10),
       io7  (11),
       io8  (12),
       io9  (13),
       io10 (14),
       io11 (15),
       io12 (16),
    notApplicable (255)
       }
      MAX-ACCESS  read-write
      STATUS  deprecated
      DESCRIPTION
      "It indicates the slot of the main link card to which the
       Ls6 card is mapped.
       In the ?004 Unit the entries io6(10)..io12(16) are not valid.
       notApplicable - when prtInLs6TandemMode=tandemSlave.
       STATUS  deprecated - this object is replaced by prtGenCnfgLinkToSlot
       and prtGenCnfgLinkToPort. "
      ::= {prtInLs6CnfgEntry 8}

--
-- Megaplex?000/?004 VC-3 TDM I/O family port.
-- (VC3/E&M,VC3/FXO,VC3/FXS)
--
--

--prtExVc3CnfgTable defines the parameters of the
-- VC-3 and VF-3 cards family external ports

prtExVc3CnfgTable OBJECT-TYPE
      SYNTAX SEQUENCE OF PrtExVc3CnfgEntry
      MAX-ACCESS not-accessible
      STATUS  current
      DESCRIPTION
       "The write operation into the Table Objects is valid only
        to the TmpCnfg entry."
      ::= { prtVc3Cnfg 1}

prtExVc3CnfgEntry OBJECT-TYPE
      SYNTAX PrtExVc3CnfgEntry
      MAX-ACCESS not-accessible
      STATUS current
	DESCRIPTION  "An entry in table."
	INDEX {prtExVc3CnfgIdx, prtExVc3SltIdx, prtExVc3PrtIdx }
      ::= { prtExVc3CnfgTable 1}

PrtExVc3CnfgEntry ::=
      SEQUENCE {
        prtExVc3CnfgIdx        Integer32,
        prtExVc3SltIdx         INTEGER,
        prtExVc3PrtIdx         INTEGER,

        prtExVc3Connect      INTEGER,
        prtExVc3TransGain    Integer32,
        prtExVc3ReceiveGain  Integer32,
        prtExVc3Wire         INTEGER,
        prtExVc3Rate         INTEGER,
        prtExVc3EchoCanceler INTEGER
      }

prtExVc3CnfgIdx OBJECT-TYPE
      SYNTAX  Integer32  (1..255)
      MAX-ACCESS  read-only
      STATUS  current
      DESCRIPTION
      "This attribute indicates the Idx of the Cnfg (1..100) being
       accessed.
       Idx  255 relates to the TmpCnfg"
      ::= {prtExVc3CnfgEntry 1}

prtExVc3SltIdx OBJECT-TYPE
      SYNTAX  INTEGER
 {
       io1   (5),
       io2   (6),
       io3   (7),
       io4   (8),
       io5   (9),
       io6  (10),
       io7  (11),
       io8  (12),
       io9  (13),
       io10 (14),
       io11 (15),
       io12 (16)
 }
      MAX-ACCESS  read-only
      STATUS  current
      DESCRIPTION
      "This attribute indicates a unique  slot  position where
       the card is inserted.
       In the ?004 Unit the entries io6(10)..io12(16) are not valid."
      ::= {prtExVc3CnfgEntry 2}

prtExVc3PrtIdx OBJECT-TYPE
      SYNTAX  INTEGER
 {
       exPrt1    (1) ,
       exPrt2    (2) ,
       exPrt3    (3)
 }
      MAX-ACCESS  read-only
      STATUS  current
      DESCRIPTION
      "A unique identifier of the port, within the card."
      ::= {prtExVc3CnfgEntry 3}

prtExVc3Connect OBJECT-TYPE
      SYNTAX  INTEGER
              {
                no  (2),
                yes (3)
              }
      MAX-ACCESS  read-write
      STATUS  current
      DESCRIPTION
      "This attribute indicates whether the  port  should be
       considered in any of the mux algorithms."
      ::= {prtExVc3CnfgEntry 4}

prtExVc3TransGain OBJECT-TYPE
      SYNTAX  Integer32
      MAX-ACCESS  read-write
      STATUS  current
      DESCRIPTION
      "Transmit gain in dBm."
      ::= {prtExVc3CnfgEntry 5}

prtExVc3ReceiveGain OBJECT-TYPE
      SYNTAX  Integer32
      MAX-ACCESS  read-write
      STATUS  current
      DESCRIPTION
      "Receive gain in dBm."
      ::= {prtExVc3CnfgEntry 6}

prtExVc3Wire OBJECT-TYPE
      SYNTAX  INTEGER
       {
          w2wire   (1),
          w4wire   (2)
       }
      MAX-ACCESS  read-write
      STATUS  current
      DESCRIPTION
      "This object is equal for all the ports in the specific
       card because of HW limitations"
      ::= {prtExVc3CnfgEntry 7}

prtExVc3Rate OBJECT-TYPE
      SYNTAX  INTEGER
       {
          r9600bps    (1),
    r4800bps    (2)
       }
      MAX-ACCESS  read-write
      STATUS  current
      DESCRIPTION
      "Rate in bps."
      ::= {prtExVc3CnfgEntry 8}

prtExVc3EchoCanceler OBJECT-TYPE
      SYNTAX  INTEGER
       {
          off    (2),
          on     (3)
       }
      MAX-ACCESS  read-write
      STATUS  current
      DESCRIPTION
      "Echo canceler activation. The value will be the same for
       all the card's external ports."
      ::= {prtExVc3CnfgEntry 9}

--prtInVc3CnfgTable defines the parameters of the
-- VC-3 or VF-3 cards family internal ports

prtInVc3CnfgTable OBJECT-TYPE
      SYNTAX SEQUENCE OF PrtInVc3CnfgEntry
      MAX-ACCESS not-accessible
      STATUS  current
      DESCRIPTION
       "The write operation into the Table Objects is valid only
        to the TmpCnfg entry."
      ::= { prtVc3Cnfg 2}

prtInVc3CnfgEntry OBJECT-TYPE
      SYNTAX PrtInVc3CnfgEntry
      MAX-ACCESS not-accessible
      STATUS current
	DESCRIPTION  "An entry in table."
	INDEX {prtInVc3CnfgIdx, prtInVc3SltIdx, prtInVc3PrtIdx }
      ::= { prtInVc3CnfgTable 1}

PrtInVc3CnfgEntry ::=
      SEQUENCE {
        prtInVc3CnfgIdx        Integer32,
        prtInVc3SltIdx         INTEGER,
        prtInVc3PrtIdx         INTEGER,

        prtInVc3Connect        INTEGER,
        prtInVc3Rate           INTEGER,
        prtInVc3Oos            INTEGER,
        prtInVc3LinkTo         INTEGER

      }

prtInVc3CnfgIdx OBJECT-TYPE
      SYNTAX  Integer32  (1..255)
      MAX-ACCESS  read-only
      STATUS  current
      DESCRIPTION
      "This attribute indicates the Idx of the Cnfg (1..100) being
       accessed.
       Idx  255 relates to the TmpCnfg"
      ::= {prtInVc3CnfgEntry 1}

prtInVc3SltIdx OBJECT-TYPE
      SYNTAX  INTEGER
 {
       io1   (5),
       io2   (6),
       io3   (7),
       io4   (8),
       io5   (9),
       io6  (10),
       io7  (11),
       io8  (12),
       io9  (13),
       io10 (14),
       io11 (15),
       io12 (16)
 }
      MAX-ACCESS  read-only
      STATUS  current
      DESCRIPTION
      "This attribute indicates a unique  slot  position where
       the card is inserted.
       In the ?004 Unit the entries io6(10)..io12(16) are not valid."
      ::= {prtInVc3CnfgEntry 2}

prtInVc3PrtIdx OBJECT-TYPE
      SYNTAX  INTEGER
 {
       inPrt1    (101)
 }
      MAX-ACCESS  read-only
      STATUS  current
      DESCRIPTION
      "A unique identifier of the port, within the card."
      ::= {prtInVc3CnfgEntry 3}

prtInVc3Connect OBJECT-TYPE
      SYNTAX  INTEGER
              {
                no  (2),
                yes (3)
              }
      MAX-ACCESS  read-write
      STATUS  current
      DESCRIPTION
      "This attribute indicates whether the  port  should be
       considered in any of the mux algorithms."
      ::= {prtInVc3CnfgEntry 4}

prtInVc3Rate OBJECT-TYPE
      SYNTAX  INTEGER
       {
          r32000bps    (1),
    r16000bps    (2)
       }
      MAX-ACCESS  read-write
      STATUS  current
      DESCRIPTION
      "Rate in bps."
      ::= {prtInVc3CnfgEntry 5}

prtInVc3Oos OBJECT-TYPE
      SYNTAX  INTEGER
       {
          forcedIdle     (1),
          forcedBusy     (2),
          busyIdle       (3),
          idleBusy       (4)
       }
      MAX-ACCESS  read-write
      STATUS  current
      DESCRIPTION
      " This object is equal for all the ports in the specific
        card because of HW limitations"
      ::= {prtInVc3CnfgEntry 6}

prtInVc3LinkTo OBJECT-TYPE
      SYNTAX  INTEGER
       {
       io1   (5),
       io2   (6),
       io3   (7),
       io4   (8),
       io5   (9),
       io6  (10),
       io7  (11),
       io8  (12),
       io9  (13),
       io10 (14),
       io11 (15),
       io12 (16)
       }
      MAX-ACCESS  read-write
      STATUS  deprecated
      DESCRIPTION
      "This attribute indicates the slot of the ML card to which
       the VC card is mapped.
       In the ?004 Unit the entries io6(10)..io12(16) are not valid.
       STATUS  deprecated - this object is replaced by prtGenCnfgLinkToSlot
       and prtGenCnfgLinkToPort."
      ::= {prtInVc3CnfgEntry 7}


--
-- Megaplex?000/?004 VC-3 TDM I/O family port.
-- (VC-PBX, VC-PBX/T1,VC-PBX/E1)
--
--

--prtExVcPbxCnfgTable defines the parameters of the
-- VC-PBX or VF-PBX cards family external ports

prtExVcPbxCnfgTable OBJECT-TYPE
      SYNTAX SEQUENCE OF PrtExVcPbxCnfgEntry
      MAX-ACCESS not-accessible
      STATUS  current
      DESCRIPTION
       "The write operation into the Table Objects is valid only
        to the TmpCnfg entry."
      ::= { prtVcPbxCnfg 1}

prtExVcPbxCnfgEntry OBJECT-TYPE
      SYNTAX PrtExVcPbxCnfgEntry
      MAX-ACCESS not-accessible
      STATUS current
	DESCRIPTION  "An entry in table."
	INDEX {prtExVcPbxCnfgIdx, prtExVcPbxSltIdx, prtExVcPbxPrtIdx }
      ::= { prtExVcPbxCnfgTable 1}

PrtExVcPbxCnfgEntry ::=
      SEQUENCE {
        prtExVcPbxCnfgIdx        Integer32,
        prtExVcPbxSltIdx         INTEGER,
        prtExVcPbxPrtIdx         INTEGER,

        prtExVcPbxConnect        INTEGER,
        prtExVcPbxGroup          INTEGER,
        prtExVcPbxTransparent    INTEGER,
        prtExVcPbxTransSignalTs  Integer32,
        prtExVcPbxFrame          INTEGER,
        prtExVcPbxRestoreTime    INTEGER,
  prtExVcPbxLineCode       INTEGER,
        prtExVcPbxLineLength     INTEGER,
        prtExVcPbxLinkTo         INTEGER,
     prtExVcPbxSignalOper     INTEGER,
  prtExVcPbxIdleCode       INTEGER
      }

prtExVcPbxCnfgIdx OBJECT-TYPE
      SYNTAX  Integer32  (1..255)
      MAX-ACCESS  read-only
      STATUS  current
      DESCRIPTION
      "This object indicates the Idx of the Cnfg (1..100) being
       accessed.
       Idx  255 relates to the TmpCnfg"
      ::= {prtExVcPbxCnfgEntry 1}

prtExVcPbxSltIdx OBJECT-TYPE
      SYNTAX  INTEGER
 {
       io1   (5),
       io2   (6),
       io3   (7),
       io4   (8),
       io5   (9),
       io6  (10),
       io7  (11),
       io8  (12),
       io9  (13),
       io10 (14),
       io11 (15),
       io12 (16)
 }
      MAX-ACCESS  read-only
      STATUS  current
      DESCRIPTION
      "This object indicates a unique  slot  position where
       the card is inserted.
       In the ?004 Unit the entries io6(10)..io12(16) are not valid."
      ::= {prtExVcPbxCnfgEntry 2}

prtExVcPbxPrtIdx OBJECT-TYPE
      SYNTAX  INTEGER
 {
       exPrt1    (1)
 }
      MAX-ACCESS  read-only
      STATUS  current
      DESCRIPTION
      "A unique identifier of the port, within the card."
      ::= {prtExVcPbxCnfgEntry 3}

prtExVcPbxConnect OBJECT-TYPE
      SYNTAX  INTEGER
              {
                no  (2),
                yes (3)
              }
      MAX-ACCESS  read-write
      STATUS  current
      DESCRIPTION
      "This object indicates whether the  port  should be
       considered in any of the mux algorithms."
      ::= {prtExVcPbxCnfgEntry 4}

prtExVcPbxGroup OBJECT-TYPE
      SYNTAX  INTEGER
 {
       io1   (5),
       io2   (6),
       io3   (7),
       io4   (8),
       io5   (9),
       io6  (10),
       io7  (11),
       io8  (12),
       io9  (13),
       io10 (14),
       io11 (15),
       io12 (16),
    notApplicable (255)
 }
      MAX-ACCESS  read-only
      STATUS  current
      DESCRIPTION
      "The group object links together several VC-PBX cards,
       concerning compression of the same input T1/E1 link
       time-slots.
       When ports of different slots have the same group, they are
       linked.
       When ports have a different group, they are not linked.
    For VC-PBX/T1 and E1 cards, this object is - their own
    IO Slot.
       In the ?004 Unit the entries io6(10)..io12(16) are not valid."
      ::= {prtExVcPbxCnfgEntry 5}

prtExVcPbxTransparent     OBJECT-TYPE
      SYNTAX  INTEGER
              {
                no  (2),
                yes (3),
    notApplicable (255)
              }
      MAX-ACCESS  read-write
      STATUS  current
      DESCRIPTION
      "This object indicates whether the Transparent transfer
       of Time-Slots is required or not.
       Time-Slots transferred by Transparent, will not be
       compressed.
       no  - applicable only for VC-PBX/T1 and VC-PBX/E1 cards
       yes - applicable only for VC-PBX/T1 and VC-PBX/E1 cards
       notApplicable - only for VC-PBX cards."
      ::= {prtExVcPbxCnfgEntry 6}

prtExVcPbxTransSignalTs     OBJECT-TYPE
      SYNTAX  Integer32
      MAX-ACCESS  read-write
      STATUS  current
      DESCRIPTION
      "This object specifies the ML Time-Slot dedicated to
       the signaling of the PABX Transparent TSs.
       None = 255.
       When prtExVcPbxTransparent=no this object's value=None (255)
       When prtExVcPbxTransparent=notApplicable, this object's
       value=None (255).
       When prtExVcPbxTransparent=yes:
    - for VC-PBX/T1 ports, this object's valid values are 1..16
      or None (255).
       - for VC-PBX/E1 ports, this object's value will be 16 or None
      (255)."
      ::= {prtExVcPbxCnfgEntry 7}

prtExVcPbxFrame OBJECT-TYPE
      SYNTAX  INTEGER
       {
  esfT1          (2), --> dsx1ESF
  sfT1           (3), --> dsx1D4
  g732nE1        (4), --> dsx1E1
  g732nE1CRC     (5), --> dsx1E1-CRC
  g732sE1        (6), --> dsx1E1-MF
  g732sE1CRC     (7),  --> dsx1E1-MF-CRC
  notApplicable  (255)
       }
      MAX-ACCESS  read-write
      STATUS  current
      DESCRIPTION
      "This object is the frame parameter for T1/E1 interface.
       The user should select only the parameters which are relevant
       to the specific card:
       T1 values for the VC-PBX/T1 card.
       E1 values for the VC-PBX/E1 card.
    notApplicable - for the VC-PBX card.
       This parameter has the same values as dsx1LineType in T1/E1
       MIB (RFC-1406). The parameters in dsx1LineType are:
                     other          (1)
      esfT1          dsx1ESF        (2)
      sfT1           dsx1D4         (3)
      g732nE1        dsx1E1         (4)
      g732nE1CRC     dsx1E1-CRC     (5)
      g732sE1        dsx1E1-MF      (6)
      g732sE1CRC     dsx1E1-MF-CRC  (7)  "
      ::= {prtExVcPbxCnfgEntry 8}

prtExVcPbxRestoreTime OBJECT-TYPE
      SYNTAX  INTEGER
       {
        restoreT1secFast      (2),
        restoreT10sec62411    (3),
        ccittE1               (4),
  notApplicable         (255)
       }
      MAX-ACCESS  read-write
      STATUS  current
      DESCRIPTION
      "The time passing from the disappearance of the loss of
       synchronization condition (red alarm) to the restoration of
       normal service. The options 1secFast(2) and 10sec62411(3)
       for E1 interfaces are proprietary implementation of the T1
       standard to the E1 interface.
       ccittE1 - is applicable only for VC-PBX/E1 card
       notApplicable - is applicable for VC-PBX card"
      ::= {prtExVcPbxCnfgEntry 9}

prtExVcPbxLineCode OBJECT-TYPE
      SYNTAX  INTEGER
       {
  b7zsT1 (1),  --> dsx1JBZS
  b8zsT1 (2),  --> dsx1B8ZS
        transT1(3),  --> dsx1AMI
        hdb3E1 (4),  --> dsx1HDB3
  notApplicable (255)
       }
      MAX-ACCESS  read-write
      STATUS  current
      DESCRIPTION
      "This object is the line code parameter used for T1/E1
       interface.
       The user should select only the parameters which are relevant
       to the specific card:
       T1 line code parameters for VC-PBX/T1
       E1 line code parameters for VC-PBX/E1
    notApplicable - for VC-PBX
       This parameter has the same values as dsx1LineCoding in T1/E1
       MIB (RFC-1406).  The parameters in dsx1LineCoding are:
     dsx1JBZS  (1)
     dsx1B8ZS  (2)
     dsx1HDB3  (3)
     dsx1ZBTSI (4)
     dsx1AMI   (5)
     other     (6)"
      ::= {prtExVcPbxCnfgEntry 10}

prtExVcPbxLineLength OBJECT-TYPE
      SYNTAX  INTEGER
       {
        unknown      (1),
        len0p133ft   (2),
        len134p266ft (3),
        len267p399ft (4),
        len400p533ft (5),
        len534p655ft (6),
        notApplicable (255)
       }
      MAX-ACCESS  read-write
      STATUS  current
      DESCRIPTION
      "This object is the line length parameter.
       It is applicable only for the VC-PBX/T1 card.
       notApplicable - for the VC-PBX and VC-PBX/E1 card.
       lenXXXpXXXft = len-XXX-XXXft."
      ::= {prtExVcPbxCnfgEntry 11}

prtExVcPbxLinkTo OBJECT-TYPE
      SYNTAX  INTEGER
       {
       io1   (5),
       io2   (6),
       io3   (7),
       io4   (8),
       io5   (9),
       io6  (10),
       io7  (11),
       io8  (12),
       io9  (13),
       io10 (14),
       io11 (15),
       io12 (16),
    notApplicable (255)
       }
      MAX-ACCESS  read-write
      STATUS  deprecated
      DESCRIPTION
      "This object indicates the slot of the ML card to which
       the VC-PBX/T1, VC-PBX/E1 card Transparent TSs are mapped.
       notApplicable - for VC-PBX card AND
       for VC-PBX/T1, VC-PBX/E1 cards, when prtExVcPbxTransparent=no .
       In the ?004 Unit the entries io6(10)..io12(16) are not valid.
       STATUS  deprecated - this object is replaced by prtGenCnfgLinkToSlot
       and prtGenCnfgLinkToPort."
      ::= {prtExVcPbxCnfgEntry 12}

prtExVcPbxSignalOper OBJECT-TYPE
      SYNTAX  INTEGER
          {
          notApplicable (1),
          normal        (2),
          bEqA          (3),
    inverseA      (4)
          }
      MAX-ACCESS  read-write
      STATUS  current
      DESCRIPTION
      "This object indicates the Signaling Operation of the
       VC-PBX/T1, VC-PBX/E1 external port.
       notApplicable - for VC-PBX card
    normal - all 4 signaling bits are transferred.
    bEqA   - copy the A bit into the B bit. Applicable only for
             VC-PBX/T1."
      ::= {prtExVcPbxCnfgEntry 13}

prtExVcPbxIdleCode OBJECT-TYPE
      SYNTAX  INTEGER
          {
          notApplicable  (1),
          hff            (2),
          he4            (3),
    hd5            (4),
    h9e            (5),
    h98            (6),
    h7f            (7),
    h7e            (8),
    h54            (9),
    h1a           (10)
          }
      MAX-ACCESS  read-write
      STATUS  current
      DESCRIPTION
      "Determines the code for transmission in empty time slots.
       notApplicable - for VC-PBX card ."
      ::= {prtExVcPbxCnfgEntry 14}



--prtIn1p6VcPbxCnfgTable defines the parameters of the
-- VC-PBX or VF-PBX cards family internal ports 1-6

prtIn1p6VcPbxCnfgTable OBJECT-TYPE
      SYNTAX SEQUENCE OF PrtIn1p6VcPbxCnfgEntry
      MAX-ACCESS not-accessible
      STATUS  current
      DESCRIPTION
       "The write operation into the Table Objects is valid only
        to the TmpCnfg entry."
      ::= { prtVcPbxCnfg 2}

prtIn1p6VcPbxCnfgEntry OBJECT-TYPE
      SYNTAX PrtIn1p6VcPbxCnfgEntry
      MAX-ACCESS not-accessible
      STATUS current
	DESCRIPTION  "An entry in table."
	INDEX {prtIn1p6VcPbxCnfgIdx, prtIn1p6VcPbxSltIdx, prtIn1p6VcPbxPrtIdx }
      ::= { prtIn1p6VcPbxCnfgTable 1}

PrtIn1p6VcPbxCnfgEntry ::=
      SEQUENCE {
        prtIn1p6VcPbxCnfgIdx        Integer32,
        prtIn1p6VcPbxSltIdx         INTEGER,
        prtIn1p6VcPbxPrtIdx         INTEGER,

        prtIn1p6VcPbxConnect      INTEGER,
        prtIn1p6VcPbxRate         INTEGER,
        prtIn1p6VcPbxEchoCanceler INTEGER,
        prtIn1p6VcPbxPabxTs       Integer32 
	}

prtIn1p6VcPbxCnfgIdx OBJECT-TYPE
      SYNTAX  Integer32  (1..255)
      MAX-ACCESS  read-only
      STATUS  current
      DESCRIPTION
      "This object indicates the Idx of the Cnfg (1..100) being
       accessed.
       Idx  255 relates to the TmpCnfg"
      ::= {prtIn1p6VcPbxCnfgEntry 1}

prtIn1p6VcPbxSltIdx OBJECT-TYPE
      SYNTAX  INTEGER
 {
       io1   (5),
       io2   (6),
       io3   (7),
       io4   (8),
       io5   (9),
       io6  (10),
       io7  (11),
       io8  (12),
       io9  (13),
       io10 (14),
       io11 (15),
       io12 (16)
 }
      MAX-ACCESS  read-only
      STATUS  current
      DESCRIPTION
      "This object indicates a unique  slot  position where
       the card is inserted.
       In the ?004 Unit the entries io6(10)..io12(16) are not valid."
      ::= {prtIn1p6VcPbxCnfgEntry 2}

prtIn1p6VcPbxPrtIdx OBJECT-TYPE
      SYNTAX  INTEGER
 {
       inPrt1  (101) ,
       inPrt2  (102) ,
       inPrt3  (103) ,
       inPrt4  (104) ,
       inPrt5  (105) ,
       inPrt6  (106)
 }
      MAX-ACCESS  read-only
      STATUS  current
      DESCRIPTION
      "A unique identifier of the port, within the card."
      ::= {prtIn1p6VcPbxCnfgEntry 3}

prtIn1p6VcPbxConnect OBJECT-TYPE
      SYNTAX  INTEGER
              {
                no  (2),
                yes (3)
              }
      MAX-ACCESS  read-write
      STATUS  current
      DESCRIPTION
      "This object indicates whether the  port  should be
       considered in any of the mux algorithms."
      ::= {prtIn1p6VcPbxCnfgEntry 4}

prtIn1p6VcPbxRate OBJECT-TYPE
      SYNTAX  INTEGER
              {
                r4800bps  (1),
                r6400bps  (2),
                r7200bps  (3),
                r8000bps  (4),
    r9600bps  (5),
    r12800bps (6)
              }
      MAX-ACCESS  read-write
      STATUS  current
      DESCRIPTION
      "This object indicates the port Rate.
       For Normal mode (prtIn7p8VcPbxMode=normal), only part of the values
       are valid (constant rate).
       For Server mode (prtIn7p8VcPbxMode=server), all values are
       applicable (user can select the desired compression rate). "
      ::= {prtIn1p6VcPbxCnfgEntry 5}

prtIn1p6VcPbxEchoCanceler OBJECT-TYPE
      SYNTAX  INTEGER
       {
          off    (2),
          on     (3)
       }
      MAX-ACCESS  read-write
      STATUS  current
      DESCRIPTION
      "Echo canceler activation."
      ::= {prtIn1p6VcPbxCnfgEntry 6}

prtIn1p6VcPbxPabxTs OBJECT-TYPE
      SYNTAX  Integer32 (1..31)
      MAX-ACCESS  read-only
      STATUS  current
      DESCRIPTION
      "This object defines the PABX Time-Slot assigned to this
       internal port.
       For a  T1 link, the valid values are: 1 .. 24.
       For an E1 link, the valid values are: 1 .. 31.
       This object is NOT applicable when prtIn1p6VcPbxConnect=no.
       This object is applicable for all cards of VC-PBX family.
       Default=the internal port index (1..6)."
      ::= {prtIn1p6VcPbxCnfgEntry 7}

--prtIn7p8VcPbxCnfgTable defines the parameters of the
-- VC-PBX or VF-PBX cards family internal ports 7-8

prtIn7p8VcPbxCnfgTable OBJECT-TYPE
      SYNTAX SEQUENCE OF PrtIn7p8VcPbxCnfgEntry
      MAX-ACCESS not-accessible
      STATUS  current
      DESCRIPTION
       "The write operation into the Table Objects is valid only
        to the TmpCnfg entry."
      ::= { prtVcPbxCnfg 3}

prtIn7p8VcPbxCnfgEntry OBJECT-TYPE
      SYNTAX PrtIn7p8VcPbxCnfgEntry
      MAX-ACCESS not-accessible
      STATUS current
	DESCRIPTION  "An entry in table."
	INDEX {prtIn7p8VcPbxCnfgIdx, prtIn7p8VcPbxSltIdx, prtIn7p8VcPbxPrtIdx }
      ::= { prtIn7p8VcPbxCnfgTable 1}

PrtIn7p8VcPbxCnfgEntry ::=
      SEQUENCE {
        prtIn7p8VcPbxCnfgIdx        Integer32,
        prtIn7p8VcPbxSltIdx         INTEGER,
        prtIn7p8VcPbxPrtIdx         INTEGER,

        prtIn7p8VcPbxConnect      INTEGER,
        prtIn7p8VcPbxMode         INTEGER,
        prtIn7p8VcPbxRate         INTEGER,
        prtIn7p8VcPbxSignalMode   INTEGER,
        prtIn7p8VcPbxOos          INTEGER,
        prtIn7p8VcPbxLinkTo       INTEGER
      }

prtIn7p8VcPbxCnfgIdx OBJECT-TYPE
      SYNTAX  Integer32  (1..255)
      MAX-ACCESS  read-only
      STATUS  current
      DESCRIPTION
      "This object indicates the Idx of the Cnfg (1..100) being
       accessed.
       Idx  255 relates to the TmpCnfg"
      ::= {prtIn7p8VcPbxCnfgEntry 1}

prtIn7p8VcPbxSltIdx OBJECT-TYPE
      SYNTAX  INTEGER
 {
       io1   (5),
       io2   (6),
       io3   (7),
       io4   (8),
       io5   (9),
       io6  (10),
       io7  (11),
       io8  (12),
       io9  (13),
       io10 (14),
       io11 (15),
       io12 (16)
 }
      MAX-ACCESS  read-only
      STATUS  current
      DESCRIPTION
      "This object indicates a unique  slot  position where
       the card is inserted.
       In the ?004 Unit the entries io6(10)..io12(16) are not valid."
      ::= {prtIn7p8VcPbxCnfgEntry 2}

prtIn7p8VcPbxPrtIdx OBJECT-TYPE
      SYNTAX  INTEGER
 {
       inPrt7  (107) ,
       inPrt8  (108)
 }
      MAX-ACCESS  read-only
      STATUS  current
      DESCRIPTION
      "A unique identifier of the port, within the card."
      ::= {prtIn7p8VcPbxCnfgEntry 3}

prtIn7p8VcPbxConnect OBJECT-TYPE
      SYNTAX  INTEGER
              {
                no  (2),
                yes (3)
              }
      MAX-ACCESS  read-write
      STATUS  current
      DESCRIPTION
      "This object indicates whether the  port  should be
       considered in any of the mux algorithms."
      ::= {prtIn7p8VcPbxCnfgEntry 4}

prtIn7p8VcPbxMode OBJECT-TYPE
      SYNTAX  INTEGER
              {
                normal  (1),
                server  (2)
              }
      MAX-ACCESS  read-write
      STATUS  current
      DESCRIPTION
      "This object indicates the working mode of the port:
       - normal - the compressed voice will be sent to an MTML
                  card inside the Mux.
       - server - the compressed voice will be sent to the Digital
                  Voice connector, as a service to an outside user."
      ::= {prtIn7p8VcPbxCnfgEntry 5}

prtIn7p8VcPbxRate OBJECT-TYPE
      SYNTAX  INTEGER
              {
                r32Kbps  (1),
    r16Kbps  (2),
                notApplicable (255)
              }
      MAX-ACCESS  read-write
      STATUS  current
      DESCRIPTION
      "This object indicates the port Main Rate.
       For Server mode (prtIn7p8VcPbxMode=server), the value will
       be notApplicable. "
      ::= {prtIn7p8VcPbxCnfgEntry 6}

prtIn7p8VcPbxSignalMode OBJECT-TYPE
      SYNTAX  INTEGER
              {
                none    (1),
                aBit    (2),
    abcBit  (3),
    abcdBit (4)
              }
      MAX-ACCESS  read-write
      STATUS  current
      DESCRIPTION
      "This object indicates the Signal Mode.
       For Server mode (prtIn7p8VcPbxMode=server), the only valid
       values are:
       - none
       - aBit "
      ::= {prtIn7p8VcPbxCnfgEntry 7}

prtIn7p8VcPbxOos OBJECT-TYPE
      SYNTAX  INTEGER
       {
          forcedIdle     (1),
          forcedBusy     (2)
       }
      MAX-ACCESS  read-write
      STATUS  current
      DESCRIPTION
      " Out of service Signaling mode."
      ::= {prtIn7p8VcPbxCnfgEntry 8}

prtIn7p8VcPbxLinkTo OBJECT-TYPE
      SYNTAX  INTEGER
       {
       io1   (5),
       io2   (6),
       io3   (7),
       io4   (8),
       io5   (9),
       io6  (10),
       io7  (11),
       io8  (12),
       io9  (13),
       io10 (14),
       io11 (15),
       io12 (16),
       notApplicable (255)
       }
      MAX-ACCESS  read-write
      STATUS  deprecated
      DESCRIPTION
      "This object indicates the slot of the ML card to which
       the VC card is mapped.
       In the ?004 Unit the entries io6(10)..io12(16) are not valid.
       For Server mode (prtIn7p8VcPbxMode=server), this object is
       not applicable.
       Both ports, 7 and 8 should be linked to the same Slot.
       STATUS  deprecated - this object is replaced by prtGenCnfgLinkToSlot
       and prtGenCnfgLinkToPort."
      ::= {prtIn7p8VcPbxCnfgEntry 9}

--prtExVcPbxTsTable defines PABX Time Slots assignment of the
-- VC-PBX E1/T1 cards, VF-PBX cards , VF-24/30/48/60 T1/E1 cards
-- and VFS cards

prtExVcPbxTsTable OBJECT-TYPE
      SYNTAX SEQUENCE OF PrtExVcPbxTsEntry
      MAX-ACCESS not-accessible
      STATUS  current
      DESCRIPTION
       "The write operation into the table objects is valid only
        to the TmpCnfg entry."
      ::= { prtVcPbxCnfg 4}

prtExVcPbxTsEntry OBJECT-TYPE
      SYNTAX PrtExVcPbxTsEntry
      MAX-ACCESS not-accessible
      STATUS current
      DESCRIPTION  "An entry in table."
	  INDEX {prtExVcPbxTsCnfgIdx, prtExVcPbxTsSltIdx, prtExVcPbxTsPrtIdx, prtExVcPbxTsIdx }
      ::= { prtExVcPbxTsTable 1}

PrtExVcPbxTsEntry ::=
      SEQUENCE {
      prtExVcPbxTsCnfgIdx        Integer32,
      prtExVcPbxTsSltIdx         INTEGER,
      prtExVcPbxTsPrtIdx         INTEGER,
      prtExVcPbxTsIdx            Integer32,
      prtExVcPbxTsMode           INTEGER,
      prtExVcPbxTsIConSlot       INTEGER,
      prtExVcPbxTsIConPrt        INTEGER,
	  prtExVcPbxTsIConTs         Integer32,
	  prtExVcPbxTsRemPrt         INTEGER,
	  prtExVcPbxTsRemTs          Integer32,
	  prtExVcPbxTsRemConnID      Unsigned32,
	  prtExVcPbxTsSourceSlot     INTEGER, 
      prtExVcPbxTsSourcePrt      Unsigned32
	  }

prtExVcPbxTsCnfgIdx OBJECT-TYPE
      SYNTAX  Integer32  (1..255)
      MAX-ACCESS  read-only
      STATUS  current
      DESCRIPTION
      "This attribute indicates the Idx of the Cnfg (1..100) being
       accessed.
       Idx 255 relates to the TmpCnfg. "
      ::= { prtExVcPbxTsEntry 1}

prtExVcPbxTsSltIdx OBJECT-TYPE
      SYNTAX  INTEGER
     {
       io1   (5),
       io2   (6),
       io3   (7),
       io4   (8),
       io5   (9),
       io6  (10),
       io7  (11),
       io8  (12),
       io9  (13),
       io10 (14),
       io11 (15),
       io12 (16)
     }
      MAX-ACCESS  read-only
      STATUS  current
      DESCRIPTION
      "This attribute indicates a unique  slot  position where
       the card is inserted.
       In the ?004 Unit the entries io6(10)..io12(16) are not valid"
      ::= { prtExVcPbxTsEntry 2}

prtExVcPbxTsPrtIdx OBJECT-TYPE
      SYNTAX  INTEGER
      {
          exPrt1    (1),
		  exPrt2    (2),
		  inPrt9  (109),
		  inPrt10 (110) 
      }
      MAX-ACCESS  read-only
      STATUS  current
      DESCRIPTION
      "This attribute indicates a unique  port number.
       VCPBX/E1, VCPBX/T1, VFPBX/E1, VFPBX/T1, VF-24/T1 and VF-30 cards 
       have only one external interface.
       VF-48/T1 and VF-60/E1 cards have two external interfaces.
       VFS cards have also internal ports."
      ::= { prtExVcPbxTsEntry 3}

prtExVcPbxTsIdx OBJECT-TYPE
      SYNTAX  Integer32
      MAX-ACCESS  read-only
      STATUS  current
      DESCRIPTION
      "This attribute indicates a unique PABX time slot  position.
       The valid time slots are 1..24 for T1 cards and
       1..31 for E1 cards."
      ::= { prtExVcPbxTsEntry 4}

prtExVcPbxTsMode OBJECT-TYPE
      SYNTAX  INTEGER
              {
                unused       (1),
                compressed   (2),  -- =compressedVoice
                transparent  (3),
				compressedCcs(4),
				mng          (5),
				ccs1        (11),
				ccs2        (12),
				ccs3        (13),
				ccs4        (14),
				ccs5        (15),
				ccs6        (16),
				ccs7        (17),
				ccs8        (18),
				ss7n1       (41),
				ss7n2       (42),
				ss7n3       (43),
				ss7n4       (44),
				ss7n5       (45),
				ss7n6       (46),
				ss7n7       (47),
				ss7n8       (48)
              }
      MAX-ACCESS  read-write
      STATUS  current
      DESCRIPTION
      "This attribute indicates the usage, process and way of the
       specific PABX TS towards its destination:
       unused - the TS is not used (no processing, no destination).
       compressed - the TS is used, sent for compression to an
                internal port (for VF-PBX cards: 1..6 for of either 
                the same card or a VF-PBX card of the same group).
				For VF-24/30/48/60 - 'compressed' represents 'compressed Voice'
				(to differentiate it from 'compressedCcs').
				In this case, the TS is compressed by an internal port (1..8). 
       transparent - the TS is used; no processing. It is sent
                directly for Bypass to a ML card the VF port/TS is linked to.
       compressedCcs - supported only by VF-24/30/48/60 cards. The TS is used;
                sent for compression to the CPU.
       mng    - the TS is used for Management (this option is used when the 
                external port is connected to another product that has to be 
                managed via this dedicated TS.
	   ccs1..ccs8 - supported only by VF-24/30/48/60 cards. Compressed TS that
	            comes from a bundle of V5.1 or V5.2 PBX.
       ss7n1..ss7n8 - supported only by VF-24/30/48/60 cards. Compressed TS that
	            comes from a bundle of V5.1 or V5.2 PBX. ss7n1 can work versus
	            Vmux having prtExPh1MlTsType=ss7(6)."
      ::= { prtExVcPbxTsEntry 5}

prtExVcPbxTsIConSlot OBJECT-TYPE
      SYNTAX  INTEGER
       {
          noConnect (2),
          io1       (5),
          io2       (6),
          io3       (7),
          io4       (8),
          io5       (9),
          io6      (10),
          io7      (11),
          io8      (12),
          io9      (13),
          io10     (14),
          io11     (15),
          io12     (16)
       }
      MAX-ACCESS  read-write
      STATUS  current
      DESCRIPTION
      "For VF-PBX cards, the io1..io12 values are applicable only when
       prtExVcPbxTsMode=compressed. Otherwise, its value should be
       noConnect.
	   For VF-24/30/48/60 cards:
	   - when prtExVcPbxTsMode=transparent or voiceTransparent, the io1..io12 values are applicable,
	     indicating the ML Slot this TS is connected to.
	   - when prtExVcPbxTsMode=compressed or compressedCcs, the	value
	     will be the same as prtExVcPbxTsSltIdx, since the compression is 
	     done within the same card.
	   - for rest of the prtExVcPbxTsMode values, the value will be: noConnect.   
       This object indicates whether the specified compressed/transparent
       time slot is connected/routed internally in the Agent and
       to which card it is connected.
       For VF-PBX card, the valid selectable slots are either the current one,
       (prtExVcPbxTsSltIdx), or a slot containing a VF-PBX card.
       In the ?004 Unit the entries io6(10)..io12(16) are not valid."
      ::= {prtExVcPbxTsEntry 6}

prtExVcPbxTsIConPrt OBJECT-TYPE
      SYNTAX  INTEGER
       {
       exPrt1      (1),
       exPrt2      (2),
	   exPrt3      (3),
	   exPrt4      (4),
	   exPrt5      (5),
	   exPrt6      (6),
	   exPrt7      (7),
	   exPrt8      (8),
       noConnect (100),
       inPrt1    (101),
       inPrt2    (102),
       inPrt3    (103),
       inPrt4    (104),
       inPrt5    (105),
       inPrt6    (106),
	   inPrt7    (107),
	   inPrt8    (108)
       }
      MAX-ACCESS  read-write
      STATUS  current
      DESCRIPTION
      "This attribute indicates the port to which this TS is connected.
	   For VF-PBX cards, only inPrt1..inPrt6 ports are valid.
	   For VF-24/30/48/60 cards:
	       - for prtExVcPbxTsMode=transparent or voiceTransparent, the valid ports are
		     ML ports (exPrt1.. exPrt8, inPrt1.. inPrt8)
	       - for prtExVcPbxTsMode=compressed or compressedCcs, the valid 
	         ports are internal ports of the same card (inPrt1..inPrt8)
       noConnect - when prtExVcPbxTsIConSlot=noConnect."
      ::= {prtExVcPbxTsEntry 7}

prtExVcPbxTsIConTs OBJECT-TYPE
      SYNTAX  Integer32	(1..255)
      MAX-ACCESS  read-write
      STATUS  current
      DESCRIPTION
      "This attribute indicates the ML TS to which this TS is connected.
	   This object is not applicable for VF-PBX cards.
	   For VF-24/30/48/60 cards it is applicable only when 
	   prtExVcPbxTsMode=transparent or voiceTransparent.
       The valid time slots are 1..24 for ML T1 cards and 1..31 for ML E1 cards.
       notApplicable - 255. "
      ::= { prtExVcPbxTsEntry 8}

prtExVcPbxTsRemPrt OBJECT-TYPE
      SYNTAX  INTEGER
      {
          exPrt1    (1),
		  exPrt2    (2),
          noConnect (100)
      }
      MAX-ACCESS  read-write
      STATUS  current
      DESCRIPTION
      "This attribute indicates the end-point port on the Remote unit.
	   VF-24/T1 and VF-30/E1 cards have one external interface.
       VF-48/T1 and VF-60/E1 cards have two external interfaces.
       noConnect - when prtExVcPbxTsMode=unused, transparent, voiceTransparent or mng."
      ::= { prtExVcPbxTsEntry 9}

prtExVcPbxTsRemTs OBJECT-TYPE
      SYNTAX  Integer32
      MAX-ACCESS  read-write
      STATUS  current
      DESCRIPTION
      "This attribute indicates the end-point TS on the Remote unit.
       The valid time slots are 1..24 for T1 ports and 1..31 for E1 ports.
       notApplicable - 255."
      ::= { prtExVcPbxTsEntry 10}

prtExVcPbxTsRemConnID OBJECT-TYPE
      SYNTAX  Unsigned32
      MAX-ACCESS  read-write
      STATUS  current
      DESCRIPTION
      "This attribute indicates the Connection ID with the Remote unit.
       notApplicable = 0."
      ::= { prtExVcPbxTsEntry 11}

prtExVcPbxTsSourceSlot OBJECT-TYPE
      SYNTAX  INTEGER
       {
          noConnect (2),
          io1       (5),
          io2       (6),
          io3       (7),
          io4       (8),
          io5       (9),
          io6      (10),
          io7      (11),
          io8      (12),
          io9      (13),
          io10     (14),
          io11     (15),
          io12     (16)
       }
      MAX-ACCESS  read-write
      STATUS  current
      DESCRIPTION
      "For VFS cards. These cards offer Compresed Voice Services for 
	   Analog Voice ports of the MP.
	   This object indicates the Source Slot of the Analog Voice port we want 
	   to compress.
       io1..io12 values are applicable only when prtExVcPbxTsMode=compressed(voice). 
       Otherwise, its value should be noConnect.
       In the ?004 Unit the entries io6(10)..io12(16) are not valid."
      ::= {prtExVcPbxTsEntry 12}

prtExVcPbxTsSourcePrt OBJECT-TYPE
      SYNTAX  Unsigned32
      MAX-ACCESS  read-write
      STATUS  current
      DESCRIPTION
      "For VFS cards. These cards offer Compresed Voice Services for 
	   Analog Voice ports of the MP.
       This object indicates the Source Port within the Slot of the Analog Voice Card, 
       we want to compress.
	   exPrt1 - exPrt16 = 1 - 16
       noConnect=100 - when prtExVcPbxTsCvServiceSlot=noConnect."
      ::= {prtExVcPbxTsEntry 13}

-- The following tables contains information specific to
-- the isdn access modules

prtIsdnCnfgTable OBJECT-TYPE
      SYNTAX SEQUENCE OF PrtIsdnCnfgEntry
      MAX-ACCESS not-accessible
      STATUS  current
      DESCRIPTION
       "The write operation into the table objects is valid only
        to the TmpCnfg entry."
      ::= { prtIsdnCnfg 1}

prtIsdnCnfgEntry OBJECT-TYPE
      SYNTAX PrtIsdnCnfgEntry
      MAX-ACCESS not-accessible
      STATUS current
	DESCRIPTION  "An entry in table."
	INDEX {prtIsdnCnfgIdx, prtIsdnSltIdx, prtIsdnPrtIdx}
      ::= { prtIsdnCnfgTable 1}

PrtIsdnCnfgEntry ::=
      SEQUENCE {
      prtIsdnCnfgIdx           Integer32,
      prtIsdnSltIdx            INTEGER,
      prtIsdnPrtIdx            Integer32,
      prtIsdnConnect           INTEGER,
      prtIsdnSignalingProtocol      INTEGER,
      prtIsdnBasicRateLineTopology  INTEGER,
      prtIsdnMode              INTEGER,
      prtIsdnFilter            INTEGER,
      prtIsdnSimultaneousCall  INTEGER,
      prtIsdnNumOfAbstractTerm Integer32,
      prtIsdnSwitchMode        INTEGER,
	  prtIsdnAbSide            INTEGER,
	  prtIsdnQsigRole          INTEGER,
	  prtIsdnInterface         INTEGER,
	  prtIsdnCallMode          INTEGER,
	  prtIsdnCallBackTimeout   Integer32
        }

prtIsdnCnfgIdx OBJECT-TYPE
      SYNTAX  Integer32  (1..255)
      MAX-ACCESS  read-only
      STATUS  current
      DESCRIPTION
      "This attribute indicates the Idx of the Cnfg (1..100) being
       accessed.
       Idx 255 relates to the TmpCnfg. "
      ::= { prtIsdnCnfgEntry 1}

prtIsdnSltIdx OBJECT-TYPE
      SYNTAX  INTEGER
            {
              io1  (5),
              io2  (6),
              io3  (7),
              io4  (8),
              io5  (9),
              io6 (10),
              io7 (11),
              io8 (12),
              io9 (13),
              io10(14),
              io11(15),
              io12(16),
              kmxMlA (103),
              kmxMlB (104),
              notApplicable(255)
            }
      MAX-ACCESS  read-only
      STATUS  current
      DESCRIPTION
      "This attribute indicates a unique  slot  position where
       the card is inserted.
       In the ?004 Unit the entries io6(10)..io12(16) are not valid
       For KM2100/4 Valid entries are 'kmxMlA ' or 'kmxMlB'"
      ::= { prtIsdnCnfgEntry 2}

prtIsdnPrtIdx OBJECT-TYPE
      SYNTAX  Integer32
      MAX-ACCESS  read-only
      STATUS  current
      DESCRIPTION
      "This attribute indicates a unique  port number.
       For MAXcess the values will be:
          exPrt1(1),
          exPrt2(2),
          exPrt3(3),
          exPrt4(4),
       For KM-2100 the port index is calculated as follows:
       100*Slot+Ch"
       ::= { prtIsdnCnfgEntry 3}

prtIsdnConnect OBJECT-TYPE
      SYNTAX  INTEGER { no(2), yes(3) }
      MAX-ACCESS  read-write
      STATUS  current
      DESCRIPTION
      "This attribute indicates if the port is connected."
      ::= { prtIsdnCnfgEntry 4 }

prtIsdnSignalingProtocol OBJECT-TYPE
      SYNTAX  INTEGER
      {
        other(1), etsi(3), ess4(5), ess5(6), dms100(7), 
        ni1(9), ni2(10), ins64(17), ins1500(18), qsig(21),
        notApplicable(255)
      }
      MAX-ACCESS  read-write
      STATUS  current
      DESCRIPTION
      "This attribute fixes which signaling protocol
        is used at this port (D-Channel).
        It is equivalent to isdnSignalingProtocol
        in the isdn MIB."
      DEFVAL { etsi }
      ::= { prtIsdnCnfgEntry 5 }

prtIsdnBasicRateLineTopology OBJECT-TYPE
      SYNTAX  INTEGER
      {
        pointToPoint(1),
        pointToMultipoint(2),
        notApplicable(255)
      }
      MAX-ACCESS  read-write
      STATUS  current
      DESCRIPTION
      "This attribute is relevant for ISDN BRI only.
        It is equivalent to isdnBasicRateLineTopology
        in the isdn MIB."
      ::= { prtIsdnCnfgEntry 6 }

prtIsdnMode OBJECT-TYPE
      SYNTAX  INTEGER
      {
        dialup(1),
        leased(2),
		syncLeased(3),
        notApplicable(255)
      }
      MAX-ACCESS  read-write
      STATUS  current
      DESCRIPTION
      "This attribute allows the user to configure the port as
       leased(2) in case of connection to a TDM network."
      ::= { prtIsdnCnfgEntry 7}

prtIsdnFilter OBJECT-TYPE
      SYNTAX  INTEGER
      { notApplicable(1),
        answerAll(2),
        rejectAll(3),
        selective(4),
		callBack (5)
      }
      MAX-ACCESS  read-write
      STATUS  current
      DESCRIPTION
      "This attribute allows the user to configure the port:
       answerAll(2): accept all incoming calls,
       rejectAll(3): reject all incoming calls,
       selective(4): accept or reject according directory table.
       callBack (5): In this mode the ISDN Ch will reject incoming calls
       and will initiate call back to the rejected phone number."
      ::= { prtIsdnCnfgEntry 8}

prtIsdnSimultaneousCall OBJECT-TYPE
      SYNTAX  INTEGER
      { notApplicable(1),
 accept(2), reject(3) }
      MAX-ACCESS  read-write
      STATUS  current
      DESCRIPTION
      "In case of simultaneous call (local,remote and remote,local):
       accept(2): accept the incoming call,
       reject(3): reject the incoming call."
      ::= { prtIsdnCnfgEntry 9}

prtIsdnNumOfAbstractTerm OBJECT-TYPE
      SYNTAX  Integer32
      MAX-ACCESS  read-write
      STATUS  current
      DESCRIPTION
      "An object for KM2100/4 agents.
    255=Not Applicable
       When ISDN Standard = ETSI or NTT (European) the value should be 255 (NotApplicable)
       else If ML speed is 64Kbps value should be 1.
       If ML speed is 128Kbps value can be either 1 or 2 (user selection)."
      ::= { prtIsdnCnfgEntry 10}

prtIsdnSwitchMode OBJECT-TYPE
      SYNTAX  INTEGER
      {
        notApplicable(1),
        auto   (2),
        manual (3),
		connect(4)
      }
      MAX-ACCESS  read-write
      STATUS  current
      DESCRIPTION
      "For KM2100.
       auto   - The call is initiated automatically by one of the IO cards connected
                to KML.10(ISDN card) having ISDN Switch Mode.
       manual - The call is initiated by the user manually,  for KML.10
                having ISDN Switch Mode (via mdlSCmd).
       connect- The call is initiated 'immediately', for KML.10 having ISDN Switch Mode.
                'immediately'- means: immediately after power-up (when product performed
                                      Reset) OR, since this value appears in the active
                 					  configuration.
                In this case, the call can be disconnected only by power-off of the
                product or by changing this object to another value (or actual Remove
                of the KML.10 relevant card).
       notApplicable - For other card types."
      ::= { prtIsdnCnfgEntry 11}

prtIsdnAbSide OBJECT-TYPE
      SYNTAX  INTEGER
      {
        notApplicable(1),
        aSide (2),
        bSide (3)
      }
      MAX-ACCESS  read-write
      STATUS  current
      DESCRIPTION
      "This parameter indicates the QSIG side in layer 3.
       This definition is from the QSIG Standard."
      ::= { prtIsdnCnfgEntry 12}

prtIsdnQsigRole OBJECT-TYPE
      SYNTAX  INTEGER
      {
        notApplicable(1),
        slave    (2),
        master   (3)
      }
      MAX-ACCESS  read-write
      STATUS  current
      DESCRIPTION
      "This parameter indicates the QSIG side in layer 1 & 2."
      ::= { prtIsdnCnfgEntry 13}

prtIsdnInterface  OBJECT-TYPE
      SYNTAX  INTEGER
       {
       lt   (1),
       nt   (2),
       te   (3),
       notApplicable (255)
       }
      MAX-ACCESS  read-write
      STATUS  current
      DESCRIPTION
      "It indicates the interface type:
       lt = line termination
       nt = network termination
       te = terminal equipment."
      ::= { prtIsdnCnfgEntry 14}

prtIsdnCallMode     OBJECT-TYPE
      SYNTAX  INTEGER  { 
                 notApplicable(1), 
                 initiate     (2), 
                 listen       (3) 
                 }
      MAX-ACCESS  read-write
      STATUS  current
      DESCRIPTION
      "This object indicates the acceptance of incoming calls.
       Initiate - Callout
       Listen   - Callin. "
      ::= { prtIsdnCnfgEntry 15}


prtIsdnCallBackTimeout  OBJECT-TYPE
      SYNTAX  Integer32 
      MAX-ACCESS  read-write
      STATUS  current
      DESCRIPTION
      "This object is applicable only if 'prtIsdnFilter' is 'CallBack'
       and determines how long to wait from receiving the incoming call
       until initiating the call back call.
       The vaules range should be '1..20 sec' and the default 10 sec."
      ::= { prtIsdnCnfgEntry 16}



prtIsdnEndpointTable OBJECT-TYPE
      SYNTAX SEQUENCE OF PrtIsdnEndpointEntry
      MAX-ACCESS not-accessible
      STATUS  current
      DESCRIPTION
       "The write operation into the table objects is valid only
        to the TmpCnfg entry."
      ::= { prtIsdnCnfg 2}

prtIsdnEndpointEntry OBJECT-TYPE
      SYNTAX PrtIsdnEndpointEntry
      MAX-ACCESS not-accessible
      STATUS current
	DESCRIPTION  "An entry in table."
	INDEX {prtIsdnEndpointCnfgIdx, prtIsdnEndpointSltIdx,
        prtIsdnEndpointPrtIdx, prtIsdnEndpointIdx }
      ::= { prtIsdnEndpointTable 1}

PrtIsdnEndpointEntry ::=
      SEQUENCE {
      prtIsdnEndpointCnfgIdx        Integer32,
      prtIsdnEndpointSltIdx         INTEGER,
      prtIsdnEndpointPrtIdx         Integer32,
      prtIsdnEndpointIdx            INTEGER,
      prtIsdnEndpointTeiType        INTEGER,
      prtIsdnEndpointTeiValue       Integer32,
      prtIsdnEndpointSpid           DisplayString,
	  prtIsdnEndpointBearerCh       INTEGER,
      prtIsdnEndpointRowStatus      RowStatus
        }

prtIsdnEndpointCnfgIdx OBJECT-TYPE
      SYNTAX  Integer32  (1..255)
      MAX-ACCESS  read-only
      STATUS  current
      DESCRIPTION
      "This attribute indicates the Idx of the Cnfg (1..100) being
       accessed.
       Idx 255 relates to the TmpCnfg. "
      ::= { prtIsdnEndpointEntry 1}

prtIsdnEndpointSltIdx OBJECT-TYPE
      SYNTAX  INTEGER
            {
              io1(5),
              io2(6),
              io3(7),
              io4(8),
              io5(9),
              io6(10),
              io7(11),
              io8(12),
              io9(13),
              io10(14),
              io11(15),
              io12(16),
              kmxMlA (103),
              kmxMlB (104),
              notApplicable(255)
            }
      MAX-ACCESS  read-only
      STATUS  current
      DESCRIPTION
      "This attribute indicates a unique  slot  position where
       the card is inserted.
       In ?004 Unit the entries io6(10)..io12(16) are not valid
       For KM2100/4 Valid entries are 'kmxMlA ' or 'kmxMlB'"
      ::= { prtIsdnEndpointEntry 2}

prtIsdnEndpointPrtIdx OBJECT-TYPE
        SYNTAX  Integer32
        MAX-ACCESS read-only
        STATUS current
        DESCRIPTION
       "This attribute indicates a unique  port number.
         For MAXcess the values will be:
          exPrt1(1),
          exPrt2(2),
          exPrt3(3),
          exPrt4(4),
         For KM-2100 the port index is calculated as follows:
         100*Slot+Ch"
       ::= { prtIsdnEndpointEntry 3}

prtIsdnEndpointIdx OBJECT-TYPE
        SYNTAX  INTEGER { atei1(1), atei2(2) }
        MAX-ACCESS read-only
        STATUS current
        DESCRIPTION
        "Since more than one endpoint may be defined per
        isdn entity, this field is a simple index.
        It corresponds to isdnEndpointIdx in the isdn MIB."
--         DEFVAL { atei1 }
        ::= { prtIsdnEndpointEntry 4}

prtIsdnEndpointTeiType OBJECT-TYPE
        SYNTAX  INTEGER { dynamic(1), static(2), notApplicable(255) }
        MAX-ACCESS read-create
        STATUS current
        DESCRIPTION
        "The type of TEI (Terminal Endpoint Identifier)
             used for this Terminal Endpoint. In case of dynamic(1),
             the TEI value is selected by the switch. In
             case of static(2), a valid TEI value has to be
             entered in the isdnEndpointTeiValue object.
             interface type as well as the Terminal Endpoint type.
             static(2). On Basic Rate interfaces the default value
             is dynamic(1) for isdn(63) Terminal Endpoints.
        It corresponds to isdnEndpointTeiType in the isdn MIB."
        ::= { prtIsdnEndpointEntry 5}

prtIsdnEndpointTeiValue OBJECT-TYPE
        SYNTAX  Integer32
        MAX-ACCESS read-create
        STATUS current
        DESCRIPTION
        "When the TEI Type is static, the value of the TEI should be
         between 0 and 63. Else, it is not selectable by user.
		 255 = notApplicable.
         It corresponds to isdnEndpointTeiValue in the isdn MIB"
        ::= { prtIsdnEndpointEntry 6 }

prtIsdnEndpointSpid OBJECT-TYPE
        SYNTAX  DisplayString
        MAX-ACCESS read-create
        STATUS current
        DESCRIPTION
        "The Service profile IDentifier (SPID) information
         for this Terminal Endpoint. It is is composed of
         9-20 numeric characters.
        It corresponds to isdnEndpointSpid in the isdn MIB."
        ::= { prtIsdnEndpointEntry 7 }

prtIsdnEndpointBearerCh OBJECT-TYPE
        SYNTAX  INTEGER {
                notApplicable(1),
                anyChannel (2),
                channelB1  (3),
                channelB2  (4) }
        MAX-ACCESS read-create
        STATUS current
        DESCRIPTION
        "This is the selected dialing channel.
         anyChannel - the system selects the dialing channel."
        ::= { prtIsdnEndpointEntry 8}

prtIsdnEndpointRowStatus OBJECT-TYPE
        SYNTAX  RowStatus
        MAX-ACCESS read-create
        STATUS current
        DESCRIPTION
        "This field indicates whether to consider this endpoint or not.
         The only possible supported RowStatus vaules are
         active (1) and destroy (6)."
        ::= { prtIsdnEndpointEntry 9}

prtIsdnDirectoryTable OBJECT-TYPE
      SYNTAX SEQUENCE OF PrtIsdnDirectoryEntry
      MAX-ACCESS not-accessible
      STATUS  current
      DESCRIPTION
       "The write operation into the table objects is valid only
        to the TmpCnfg entry."
      ::= { prtIsdnCnfg 3}

prtIsdnDirectoryEntry OBJECT-TYPE
      SYNTAX PrtIsdnDirectoryEntry
      MAX-ACCESS not-accessible
      STATUS current
	DESCRIPTION  "An entry in table."
	INDEX { prtIsdnDirectoryCnfgIdx, prtIsdnDirectorySltIdx, prtIsdnDirectoryPrtIdx }
      ::= { prtIsdnDirectoryTable 1}

PrtIsdnDirectoryEntry ::=
      SEQUENCE {
      prtIsdnDirectoryCnfgIdx   Integer32,
      prtIsdnDirectorySltIdx         INTEGER,
      prtIsdnDirectoryPrtIdx         Integer32,
      prtIsdnDirectoryLocalAddr    DisplayString,
      prtIsdnDirectoryLocalSubAddr   DisplayString,
      prtIsdnDirectoryRemoteAddr    DisplayString,
      prtIsdnDirectoryRemoteSubAddr  DisplayString,
      prtIsdnDirectoryPrtNu          Integer32,
      prtIsdnDirectoryTeiId          Integer32,
      prtIsdnDirectoryRowStatus      RowStatus,
      prtIsdnDirectoryLocalAddr2     DisplayString,
      prtIsdnDirectoryLocalSubAddr2  DisplayString,
      prtIsdnDirectoryRemoteAddr2    DisplayString,
      prtIsdnDirectoryRemoteSubAddr2 DisplayString
      }

prtIsdnDirectoryCnfgIdx OBJECT-TYPE
      SYNTAX  Integer32  (1..255)
      MAX-ACCESS  read-only
      STATUS  current
      DESCRIPTION
      "This attribute indicates the Idx of the Cnfg (1..100) being
       accessed.
       Idx 255 relates to the TmpCnfg. "
      ::= { prtIsdnDirectoryEntry 1}

prtIsdnDirectorySltIdx OBJECT-TYPE
      SYNTAX  INTEGER
            {
              io1(5),
              io2(6),
              io3(7),
              io4(8),
              io5(9),
              io6(10),
              io7(11),
              io8(12),
              io9(13),
              io10(14),
              io11(15),
              io12(16),
              kmxMlA (103),
              kmxMlB (104),
			  notApplicable (255)
            }
      MAX-ACCESS  read-only
      STATUS  current
      DESCRIPTION
      "This attribute indicates a unique  slot  position where
       the card is inserted.
       For MX300/30 ports:
       io1(5) = isdn1(5) and io2(6) = isdn2(6).
       In ?004 Unit the entries io6(10)..io12(16) are not valid
       For KM2100/4 Valid entries are 'kmxMlA ' or 'kmxMlB'"
      ::= { prtIsdnDirectoryEntry 2}

prtIsdnDirectoryPrtIdx OBJECT-TYPE
        SYNTAX  Integer32
        MAX-ACCESS read-only
        STATUS current
        DESCRIPTION
        "For MAXcess this is the internal port number: 101, 102,....
         For KM-2100 the port index is calculated as follows:
         100*Slot+Ch"
        ::= { prtIsdnDirectoryEntry 3}

prtIsdnDirectoryLocalAddr OBJECT-TYPE
        SYNTAX DisplayString (SIZE(17..20))
        MAX-ACCESS read-create
        STATUS current
        DESCRIPTION
        "This is the local address associated with this
         entry.
         - For MX: Size=17 , Default=0	(17 characters)
         - For KM: Size=20, Default=blank (20 characters) "
        ::= { prtIsdnDirectoryEntry 4}

prtIsdnDirectoryLocalSubAddr OBJECT-TYPE
        SYNTAX DisplayString (SIZE(4..6))
        MAX-ACCESS read-create
        STATUS current
        DESCRIPTION
        "This is the local subaddress associated with this
         entry.
         - For MX: Size=6 , Default=0	(6 characters)
         - For KM: Size=4 , Default=blank (4 characters)"
        ::= { prtIsdnDirectoryEntry 5}

prtIsdnDirectoryRemoteAddr OBJECT-TYPE
        SYNTAX DisplayString (SIZE(17..20))
        MAX-ACCESS read-create
        STATUS current
        DESCRIPTION
        "This is the remote address associated with this
         entry.
         - For MX: Size=17 , Default=0	(17 characters)
         - For KM: Size=20, Default=blank (20 characters)"
        ::= { prtIsdnDirectoryEntry 6}

prtIsdnDirectoryRemoteSubAddr OBJECT-TYPE
        SYNTAX  DisplayString (SIZE(4..6))
        MAX-ACCESS read-create
        STATUS current
        DESCRIPTION
        "This is the remote subaddress associated with this
         entry.
         - For MX: Size=6 , Default=0 (6 characters)
         - For KM: Size=4 , Default=blank (4 characters)"
        ::= { prtIsdnDirectoryEntry 7}


prtIsdnDirectoryPrtNu OBJECT-TYPE
        SYNTAX  Integer32
        MAX-ACCESS read-create
        STATUS current
        DESCRIPTION
        "This is the external port number connected to
         this entry."
         DEFVAL { 1 }
        ::= { prtIsdnDirectoryEntry 8}

prtIsdnDirectoryTeiId OBJECT-TYPE
        SYNTAX  Integer32
        MAX-ACCESS read-create
        STATUS current
        DESCRIPTION
        "This is the abstract terminal id if relevant,
        connected to this entry."
        DEFVAL { 1 }
        ::= { prtIsdnDirectoryEntry 9}

prtIsdnDirectoryRowStatus OBJECT-TYPE
        SYNTAX  RowStatus
        MAX-ACCESS read-create
        STATUS current
        DESCRIPTION
        "This is the status for the row. It allows to know
        whether to consider this row or not.
        The only possible supported RowStatus vaules are
        active (1) and destroy (6)."
        ::= { prtIsdnDirectoryEntry 10}

prtIsdnDirectoryLocalAddr2 OBJECT-TYPE
        SYNTAX DisplayString (SIZE(17..20))
        MAX-ACCESS read-create
        STATUS current
        DESCRIPTION
        "This is the second local address associated with this
         entry.
         - For MX: Size=17 , Default=0 (17 characters)
         - For KM: Size=20, Default=blank (20 characters)"
        ::= { prtIsdnDirectoryEntry 11}

prtIsdnDirectoryLocalSubAddr2 OBJECT-TYPE
        SYNTAX DisplayString (SIZE(4..6))
        MAX-ACCESS read-create
        STATUS current
        DESCRIPTION
        "This is the second local subaddress associated with this
         entry.
         - For MX: Size=6 , Default=0 (6 characters)
         - For KM: Size=4 , Default=blank (4 characters)"
        ::= { prtIsdnDirectoryEntry 12}

prtIsdnDirectoryRemoteAddr2 OBJECT-TYPE
        SYNTAX DisplayString (SIZE(17..20))
        MAX-ACCESS read-create
        STATUS current
        DESCRIPTION
        "This is the second remote address associated with this
         entry.
         - For MX: Size=17 , Default=0 (17 characters)
         - For KM: Size=20, Default=blank(20 characters) "
        ::= { prtIsdnDirectoryEntry 13}

prtIsdnDirectoryRemoteSubAddr2 OBJECT-TYPE
        SYNTAX  DisplayString (SIZE(4..6))
        MAX-ACCESS read-create
        STATUS current
        DESCRIPTION
        "This is the second remote subaddress associated with this
         entry.
         - For MX: Size=6 , Default=0 (6 characters)
         - For KM: Size=4 , Default=blank (4 characters) "
        ::= { prtIsdnDirectoryEntry 14}



-- This table is an extension for new version of MAXcess
-- modules.
prtFrPlusCnfgTable  OBJECT-TYPE
     SYNTAX SEQUENCE OF PrtFrPlusCnfgEntry
     MAX-ACCESS not-accessible
     STATUS  current
     DESCRIPTION
      "The write operation into the Table Objects is valid only
       to the TmpCnfg entry."
     ::= {prtFrPlusCnfg 1}

prtFrPlusCnfgEntry OBJECT-TYPE
      SYNTAX PrtFrPlusCnfgEntry
      MAX-ACCESS not-accessible
      STATUS current
	DESCRIPTION  "An entry in table."
	INDEX {prtFrPlusCnfgIdx, prtFrPlusSltIdx, prtFrPlusPrtIdx }
      ::= { prtFrPlusCnfgTable 1}

PrtFrPlusCnfgEntry ::=
      SEQUENCE {
      prtFrPlusCnfgIdx   Integer32,
      prtFrPlusSltIdx    INTEGER,
      prtFrPlusPrtIdx   Integer32,
      prtFrPlusNotSegmentedPriorities  OCTET STRING
}

prtFrPlusCnfgIdx OBJECT-TYPE
      SYNTAX  Integer32 (1..255)
      MAX-ACCESS  read-only
      STATUS  current
      DESCRIPTION
      "This attribute indicates the Idx of the Cnfg (1..100) being
       accessed.
       Idx 255 relates to the TmpCnfg. "
      ::= { prtFrPlusCnfgEntry 1}

prtFrPlusSltIdx OBJECT-TYPE
      SYNTAX  INTEGER
            {
              io1   (5),
              io2   (6),
              io3   (7),
              io4   (8),
              io5   (9),
              io6  (10),
              io7  (11),
              io8  (12),
              io9  (13),
              io10 (14),
              io11 (15),
              io12 (16),
       notApplicable(255)
            }
      MAX-ACCESS  read-only
      STATUS  current
      DESCRIPTION
        "Slot Index.
         For ISDN BRI Ports of MX300/30,
    io1(5) = isdn1(5) and io2(6) = isdn2(6)."
      ::= { prtFrPlusCnfgEntry 2}

prtFrPlusPrtIdx  OBJECT-TYPE
      SYNTAX  Integer32
      MAX-ACCESS  read-only
      STATUS  current
      DESCRIPTION
      "This attribute indicates a unique  port number.
       This port number should be:
       - for ISDN cards: inPrt1(101)->inPrt50(150)
       - for MHS1 card : exPrt1(1)
       - for MHS3, MLS3 cards: exPrt1(1)->exPrt3(3)
       - for MLS6 cards: exPrt1(1)->exPrt6(6)."
      ::= { prtFrPlusCnfgEntry 3}

prtFrPlusNotSegmentedPriorities OBJECT-TYPE
       SYNTAX OCTET STRING(SIZE(1))
       MAX-ACCESS   read-write
       STATUS   current
       DESCRIPTION
      "This parameter is relevant only for FR+ protocol and
       asks the MXcess NOT to segment data with specified
       priorities:  from LSB:
       bit 1  is for priority 1,
       bit 2  is for priority 2, .... till bit 7 for priority 7.
	   - a priority selected to be segmented : its bit will be '0'
	   - a priority not to be segmented : its bit will be '1'
       Default is 00000000; i.e, segment all priorities."
     DEFVAL { '00'H }
     ::= { prtFrPlusCnfgEntry 4 }


-- This table is an extension of prtExPh1MlCnfgTable for MTML cards
-- of MP-2200 and MP-2100

    prtMl4CnfgTable  OBJECT-TYPE
     SYNTAX SEQUENCE OF PrtMl4CnfgEntry
     MAX-ACCESS not-accessible
     STATUS  current
     DESCRIPTION
      "This is an extension table for MTML-4 card parameters."
     ::= {prtMl4Cnfg 1}

prtMl4CnfgEntry OBJECT-TYPE
      SYNTAX PrtMl4CnfgEntry
      MAX-ACCESS not-accessible
      STATUS current
	DESCRIPTION  "An entry in table."
	INDEX {prtMl4CnfgIdx, prtMl4SltIdx, prtMl4PrtIdx }
      ::= { prtMl4CnfgTable 1}

PrtMl4CnfgEntry ::=
      SEQUENCE {
      prtMl4CnfgIdx              Integer32,
      prtMl4SltIdx               INTEGER,
      prtMl4PrtIdx               INTEGER,
      prtMl4SigProfile           INTEGER,
      prtMl4CGA                  INTEGER,
      prtMl4Oos                  INTEGER,
      prtMl4VoiceOos             OCTET STRING,
      prtMl4DataOos              OCTET STRING,
	  prtMl4Service              INTEGER,
	  prtMl4IpAddress            IpAddress,
	  prtMl4IpMask               IpAddress,
	  prtMl4SignalingMode        INTEGER,
	  prtMl4EchoCanceler         INTEGER,
	  prtMl4OosErrorSource       INTEGER,
	  prtMl4OosEntryThreshold    Integer32,
	  prtMl4OosExitThreshold     Integer32,
	  prtMl4LogicalLinkId        Integer32,
	  prtMl4DedicatedTs          Integer32,
	  prtMl4RemCrc               INTEGER,
	  prtMl4CrossConnectLevel    INTEGER,
	  prtMl4PppEchoFailDetection INTEGER,
	  prtMl4EcanCasControl       INTEGER
      }


prtMl4CnfgIdx OBJECT-TYPE
      SYNTAX  Integer32 (1..255)
      MAX-ACCESS  read-only
      STATUS  current
      DESCRIPTION
      "This attribute indicates the Idx of the Cnfg (1..100) being
       accessed.
       Idx 255 relates to the TmpCnfg. The write operation is valid only
       to the TmpCnfg."
      ::= { prtMl4CnfgEntry 1}

prtMl4SltIdx OBJECT-TYPE
      SYNTAX  INTEGER
     {
       clA   (3),
       clB   (4),
       io1   (5),
       io2   (6),
       io3   (7),
       io4   (8),
       io5   (9),
       io6  (10),
       io7  (11),
       io8  (12),
       io9  (13),
       io10 (14),
       io11 (15),
       io12 (16),
	   notApplicable (255)
     }
      MAX-ACCESS  read-only
      STATUS  current
      DESCRIPTION
      "This attribute indicates a unique  slot  position where
       the module is inserted."
      ::= { prtMl4CnfgEntry 2}

prtMl4PrtIdx OBJECT-TYPE
      SYNTAX  INTEGER
       {
       exPrt1    (1),
       exPrt2    (2),
       exPrt3    (3),
       exPrt4    (4),
       exPrt5    (5),
       exPrt6    (6),
       exPrt7    (7),
       exPrt8    (8),
       inPrt1  (101),
       inPrt2  (102),
       inPrt3  (103),
       inPrt4  (104),
       inPrt5  (105),
       inPrt6  (106),
       inPrt7  (107),
       inPrt8  (108),
       inPrt9   (109),
       inPrt10  (110),
       inPrt11  (111),
       inPrt12  (112),
       inPrt13  (113),
       inPrt14  (114),
       inPrt15  (115),
       inPrt16  (116),
       inPrt17  (117),
       inPrt18  (118),
       inPrt19  (119),
       inPrt20  (120),
       inPrt21  (121),
       inPrt22  (122),
       inPrt23  (123),
       inPrt24  (124),
       inPrt25  (125),
       inPrt26  (126),
       inPrt27  (127),
       inPrt28  (128),
       inPrt29  (129),
       inPrt30  (130),
       inPrt31  (131),
       inPrt32  (132),
       inPrt33  (133),
       inPrt34  (134),
       inPrt35  (135),
       inPrt36  (136),
       inPrt37  (137),
       inPrt38  (138),
       inPrt39  (139),
       inPrt40  (140),
       inPrt41  (141),
       inPrt42  (142),
       inPrt43  (143),
       inPrt44  (144),
       inPrt45  (145),
       inPrt46  (146),
       inPrt47  (147),
       inPrt48  (148),
       inPrt49  (149),
       inPrt50  (150),
       inPrt51  (151),
       inPrt52  (152),
       inPrt53  (153),
       inPrt54  (154),
       inPrt55  (155),
       inPrt56  (156),
       inPrt57  (157),
       inPrt58  (158),
       inPrt59  (159),
       inPrt60  (160),
       inPrt61  (161),
       inPrt62  (162),
       inPrt63  (163),
       inPrt64  (164),
       inPrt65  (165),
       inPrt66  (166),
       inPrt67  (167),
       inPrt68  (168),
       inPrt69  (169),
       inPrt70  (170),
       inPrt71  (171),
       inPrt72  (172),
       inPrt73  (173),
       inPrt74  (174),
       inPrt75  (175),
       inPrt76  (176),
       inPrt77  (177),
       inPrt78  (178),
       inPrt79  (179),
       inPrt80  (180),
       inPrt81  (181),
       inPrt82  (182),
       inPrt83  (183),
       inPrt84  (184)
       }
      MAX-ACCESS  read-only
      STATUS  current
      DESCRIPTION
      "This attribute indicates a unique  port number."
      ::= { prtMl4CnfgEntry 3}

prtMl4SigProfile OBJECT-TYPE
      SYNTAX  INTEGER
       {
       notApplicable (1),
       none          (2),
       p1            (3),
       p2            (4),
       p3            (5),
       p4            (6),
       p5            (7),
	   perTS         (8) 
       }
      MAX-ACCESS  read-write
      STATUS  current
      DESCRIPTION
      "This object indicates the Signaling Profile of the port.
       none - when the Frame is G732N (no MF) or Unframed.
       p1  = profile 1
       p2  = profile 2
       p3  = profile 3
       p4  = profile 4
       p5  = profile 5 
       perTS = when Signaling Profile is selected per TS."
	  ::= {prtMl4CnfgEntry 4}

prtMl4CGA OBJECT-TYPE
    SYNTAX  INTEGER {
      none (1),
      trans(2),
      full (3)
            }
    MAX-ACCESS  read-write
    STATUS  current
    DESCRIPTION
    "This object selects the method used to signal the CGA state
     to the other end, through the main link.
     'none'  - non-transparent mode. When one of the links
               (main) will be in Out Of Service state, both
               'Data/Voice Oos' and 'Oos' will be
               transmitted to the other end.
     'trans' - when one of the links (main) will be in Out
               Of Service state, 'Data/Voice Oos' will be
               transmitted to the other end.
     'full'  - fully-transparent mode. When one of the links
                  (main) will be in Out Of Service state,
                  neither 'Data/Voice Oos' nor 'Oos' will
                  be transmitted to the other end."
 ::= { prtMl4CnfgEntry 5 }

prtMl4Oos  OBJECT-TYPE
      SYNTAX  INTEGER
       {
        notSupported  (2),
        forcedIdle    (3),
        forcedBusy    (4),
        busyIdle      (5),
        idleBusy      (6)
       }
      MAX-ACCESS  read-write
      STATUS  current
      DESCRIPTION
      "'idle' = '0' = on-hook, idle state
       'busy' = '1' = off-hook, busy state
       'forcedIdle' = SP = both A and B signaling bits are forced
                      to '0' during out-of-service periods.
       'forcedBusy' = MK = both A and B signaling bits are forced
                      to '1' during out-of-service periods.
       'busyIdle'   = MK_SP = A and B bits are forced to '1' for
                      2.5 seconds; then they are switched to '0'
                      until out-of-service condition disappears.
       'idleBusy'   = SP_MK = A and B bits are forced to '0' for
                      2.5 seconds; then they are switched to '1'
                      until out-of-service condition disappears.
       - for T1:    '0'=0   ;  '1'=1
       - for E1:    '0'=1   ;  '1'=0   "
   ::= { prtMl4CnfgEntry 6 }

prtMl4VoiceOos  OBJECT-TYPE
 SYNTAX  OCTET STRING (SIZE (0..4))
    MAX-ACCESS  read-write
    STATUS  current
    DESCRIPTION
    "Voice Out-Of-Service code. Valid range: (0 - FF HEX).
     For agents that do not support this feature, the value will
     always be 0."
   ::= { prtMl4CnfgEntry 7 }

prtMl4DataOos  OBJECT-TYPE
 SYNTAX  OCTET STRING (SIZE (0..4))
    MAX-ACCESS  read-write
    STATUS  current
    DESCRIPTION
    "Data Out-Of-Service code. Valid range: (0 - FF HEX).
     For agents that do not support this feature, the value will
     always be 0."
   ::= { prtMl4CnfgEntry 8 }

prtMl4Service OBJECT-TYPE
      SYNTAX  INTEGER
       {
       notApplicable (1),
       leasedLine    (2),
       v51           (3),
	   v52Master     (4),
	   v52Slave      (5)
       }
      MAX-ACCESS  read-write
      STATUS  current
      DESCRIPTION
      "Link Service.
       leasedLine - usual TDM interface.
       v51        - V5.1 interface.
       v52Master  - V5.2 Link to Local Exchange.
       v52Slave   - a ML that is transferred to the v52Master."
      ::= {prtMl4CnfgEntry 9}

prtMl4IpAddress OBJECT-TYPE
      SYNTAX  IpAddress
      MAX-ACCESS  read-write
      STATUS  current
      DESCRIPTION
      "IP Address of the port."
      ::= {prtMl4CnfgEntry 10}

prtMl4IpMask OBJECT-TYPE
      SYNTAX  IpAddress
      MAX-ACCESS  read-write
      STATUS  current
      DESCRIPTION
      "IP subnet mask of the port."
      ::= {prtMl4CnfgEntry 11}

prtMl4SignalingMode OBJECT-TYPE
      SYNTAX INTEGER { notApplicable(1),
		cas(2),
		ccs(3),
		robbedBit(4),
		other (5)
		}
      MAX-ACCESS read-write
      STATUS current
      DESCRIPTION
      "Refers to the signaling mode of the port (or framer module).
	  notApplicable(1)- means that no framer is needed for this port (no signaling),
	         or that this object is not relevant.
      cas(2) means Channel Associated Signaling. Used for E1 Links.
      ccs(3) is the Common Channel Signaling (the signaling is not within
             the channels time slot - a TS for signaling is used).
      robbedBit(4) is a method implementing 7 bits for the voice and 1 bit
                   dedicated for signaling. Used for T1 Links.
      other (5)- Signaling generally exists though not specifically according
              to one of the values listed ; this port uses a framer in this case."
      ::= {prtMl4CnfgEntry 12}

prtMl4EchoCanceler OBJECT-TYPE
      SYNTAX  INTEGER
       {
       notApplicable (1),
       off    (2),
       on     (3)
       }
      MAX-ACCESS  read-write
      STATUS  current
      DESCRIPTION
      "Echo canceler activation."
      ::= {prtMl4CnfgEntry 13}

prtMl4OosErrorSource OBJECT-TYPE
      SYNTAX  INTEGER
       {
       notApplicable (1),
       none          (2),
       framing       (3),
	   bpv		     (4)
       }
      MAX-ACCESS  read-write
      STATUS  current
      DESCRIPTION
      "OOS (Out-of-Service) Error Source.
       This object is applicable for T1 ports only."
      ::= {prtMl4CnfgEntry 14}

prtMl4OosEntryThreshold OBJECT-TYPE
      SYNTAX  Integer32 (0..999)
      MAX-ACCESS  read-write
      STATUS  current
      DESCRIPTION
      "This object defines the number of Errors per Second that determine the 
       minimum unacceptable noise level. This value will be the Entry Threshold
       to the OOS (Out-of-Service) state.
       This object is applicable only when prtMl4OosErrorSource=framing(3) or bpv(4).
       0=notApplicable."
      ::= { prtMl4CnfgEntry 15}

prtMl4OosExitThreshold OBJECT-TYPE
      SYNTAX  Integer32 (0..99)
      MAX-ACCESS  read-write
      STATUS  current
      DESCRIPTION
      "This object defines the number of consecutive Error-Free-Seconds before
       going from OOS state to Normal state. This value will be the Exit Threshold
       from the OOS (Out-of-Service) state.
	   Units=seconds
       This object is applicable only when prtMl4OosErrorSource=framing(3) or bpv(4).
       0=notApplicable."
      ::= { prtMl4CnfgEntry 16}

prtMl4LogicalLinkId OBJECT-TYPE
      SYNTAX  Integer32 (0..257)
      MAX-ACCESS  read-write
      STATUS  current
      DESCRIPTION
      "This object defines for a V5.2 Master ML the Logical Link Id.
       Valid values are: 0..256.
       NA=257."
      ::= { prtMl4CnfgEntry 17}

prtMl4DedicatedTs OBJECT-TYPE
      SYNTAX  Integer32 (1..255)
      MAX-ACCESS  read-write
      STATUS  current
      DESCRIPTION
      "A unique number to identify Dedicated TS of the E1 port (V5.2).
       It is applicable only when prtMl4Service=v52Slave and 
       prtExPh1MlInbandMng selected is dedicatedTs, dedicatedPpp or dedicatedFr.
       1..31 - Dedicated TS of E1
       255   - notApplicable 
       Other values are invalid."
      ::= { prtMl4CnfgEntry 18}

prtMl4RemCrc OBJECT-TYPE
      SYNTAX  INTEGER 
       {
        notApplicable	(1), 
        no              (2),
        yes             (3)
       }
      MAX-ACCESS  read-write
      STATUS  current
      DESCRIPTION
      "This object indicates whether the E1 of the Remote device
       connected to this E1 port, will have CRC-4 or not."
      ::= { prtMl4CnfgEntry 19 }

prtMl4CrossConnectLevel OBJECT-TYPE
      SYNTAX  INTEGER 
       {
        notApplicable	(1), 
        ds0             (2),
        ds1             (3)
       }
      MAX-ACCESS  read-write
      STATUS  current
      DESCRIPTION
      "This object indicates whether the cross connect is 
       on DS1 or DS0 (time-slots) level.  
       When cross connect level is ds1, Destination Slot 
       is indicated by prtGenCnfgLinkToSlot,
       Destination Port is indicated by prtGenCnfgLinkToPort. 
       For Unframed Line Type, cross connect level can be either
       notApplicable (NC=not connected) or DS1.
       Otherwise, default value is ds0."
      ::= { prtMl4CnfgEntry 20 }

prtMl4PppEchoFailDetection  OBJECT-TYPE
      SYNTAX  INTEGER 
       {
        notApplicable	(1), 
        disable         (2),
        enable          (3)
       }
      MAX-ACCESS  read-write
      STATUS  current
      DESCRIPTION
      "This object indicates whether the PPP Echo is taken into account
       for its Fail Detection.  
       This object is relevant when Inband Mng between devices is Dedicated TS PPP.
       Default=Disable.
	   Enable - will be selected mainly when a T1/E1 Ring exists and between 2 adjacent 
	            Ring devices there is another device or Net, that causes these Ring devices
	            not to sense that the PPP connection between them is lost. In this case,
	            Echo Request should be initiated by the port."
      ::= { prtMl4CnfgEntry 21 }

prtMl4EcanCasControl OBJECT-TYPE
      SYNTAX  INTEGER 
       {
        notApplicable	(1), 
        disable         (2),
        enable          (3)
       }
      MAX-ACCESS  read-write
      STATUS  current
      DESCRIPTION
      "This object enables/disables ECAN (Echo Canceller) control activation/deactivation
       sent via the A, B, C, D multiframe signaling BITs."
	  ::= { prtMl4CnfgEntry 22 }				 


--prtAcmCnfgTable defines the parameters of the
--ACM cards family external ports 1-8

prtAcmCnfgTable  OBJECT-TYPE
     SYNTAX SEQUENCE OF PrtAcmCnfgEntry
     MAX-ACCESS not-accessible
     STATUS  current
     DESCRIPTION
      "This is a table for ACM port parameters."
     ::= {prtAcmCnfg 1}

prtAcmCnfgEntry OBJECT-TYPE
      SYNTAX PrtAcmCnfgEntry
      MAX-ACCESS not-accessible
      STATUS current
	DESCRIPTION  "An entry in table."
	INDEX {prtAcmCnfgIdx, prtAcmSltIdx, prtAcmPrtIdx }
      ::= { prtAcmCnfgTable 1}

PrtAcmCnfgEntry ::=
      SEQUENCE {
      prtAcmCnfgIdx        Integer32,
      prtAcmSltIdx         INTEGER,
      prtAcmPrtIdx         INTEGER,
      prtAcmConnect        INTEGER,
      prtAcmActiveState    INTEGER,
      prtAcmAlrString      DisplayString
      }

prtAcmCnfgIdx OBJECT-TYPE
      SYNTAX  Integer32 (1..255)
      MAX-ACCESS  read-only
      STATUS  current
      DESCRIPTION
      "This attribute indicates the Idx of the Cnfg (1..100) being
       accessed.
       Idx 255 relates to the TmpCnfg. The write operation is valid only
       to the TmpCnfg."
      ::= { prtAcmCnfgEntry 1}

prtAcmSltIdx OBJECT-TYPE
      SYNTAX  INTEGER
     {
       io1   (5),
       io2   (6),
       io3   (7),
       io4   (8),
       io5   (9),
       io6  (10),
       io7  (11),
       io8  (12),
       io9  (13),
       io10 (14),
       io11 (15),
       io12 (16),
	   notApplicable (255)
     }
      MAX-ACCESS  read-only
      STATUS  current
      DESCRIPTION
      "This attribute indicates a unique  slot  position where
       the module is inserted."
      ::= { prtAcmCnfgEntry 2}

prtAcmPrtIdx OBJECT-TYPE
      SYNTAX  INTEGER
       {
       exPrt1    (1),
       exPrt2    (2),
       exPrt3    (3),
       exPrt4    (4),
       exPrt5    (5),
       exPrt6    (6),
       exPrt7    (7),
       exPrt8    (8) ,
       exPrt9    (9) ,
       exPrt10  (10) ,
       exPrt11  (11) ,
       exPrt12  (12)
       }
      MAX-ACCESS  read-only
      STATUS  current
      DESCRIPTION
      "This attribute indicates a unique  port number."
      ::= { prtAcmCnfgEntry 3}

prtAcmConnect OBJECT-TYPE
      SYNTAX  INTEGER
              {
                no  (2),
                yes (3)
              }
      MAX-ACCESS  read-write
      STATUS  current
      DESCRIPTION
      "This attribute indicates whether the port should be
       connected or not. Only a connected port can perform activity."
      ::= {prtAcmCnfgEntry 4}

prtAcmActiveState OBJECT-TYPE
      SYNTAX  INTEGER
              {
                low  (2),
                high (3)
              }
      MAX-ACCESS  read-write
      STATUS  current
      DESCRIPTION
      "This attribute indicates the Electric Active State of the port."
      ::= {prtAcmCnfgEntry 5}

prtAcmAlrString OBJECT-TYPE
        SYNTAX DisplayString (SIZE(0..35))
        MAX-ACCESS read-write
        STATUS current
        DESCRIPTION
        "Alarm string selected by user for the Inbound ports.
         This object is applicable only for the Inbound Ports: ext-5..ext-12.
         For the Outbound Ports (ext-1..ext-4), the size of this string will be 0."
      ::= {prtAcmCnfgEntry 6}

--prtE2CnfgTable defines the parameters of the
--E2 card ports 

prtE2CnfgTable  OBJECT-TYPE
     SYNTAX SEQUENCE OF PrtE2CnfgEntry
     MAX-ACCESS not-accessible
     STATUS  current
     DESCRIPTION
      "This is a table for E2 port parameters."
     ::= {prtE2Cnfg 1}

prtE2CnfgEntry OBJECT-TYPE
      SYNTAX PrtE2CnfgEntry
      MAX-ACCESS not-accessible
      STATUS current
	DESCRIPTION  "An entry in table."
	INDEX {prtE2CnfgIdx, prtE2SltIdx, prtE2PrtIdx }
      ::= { prtE2CnfgTable 1}

PrtE2CnfgEntry ::=
      SEQUENCE {
      prtE2CnfgIdx        Integer32,
      prtE2SltIdx         INTEGER,
      prtE2PrtIdx         INTEGER,
      prtE2Connect        INTEGER,
      prtE2MngOnNationalBit INTEGER
      }

prtE2CnfgIdx OBJECT-TYPE
      SYNTAX  Integer32 (1..255)
      MAX-ACCESS  read-only
      STATUS  current
      DESCRIPTION
      "This attribute indicates the Idx of the Cnfg (1..100) being
       accessed.
       Idx 255 relates to the TmpCnfg. The write operation is valid only
       to the TmpCnfg."
      ::= { prtE2CnfgEntry 1}

prtE2SltIdx OBJECT-TYPE
      SYNTAX  INTEGER
     {
       io1   (5),
       io2   (6),
       io3   (7),
       io4   (8),
       io5   (9),
       io6  (10),
       io7  (11),
       io8  (12),
       io9  (13),
       io10 (14),
       io11 (15),
       io12 (16)
     }
      MAX-ACCESS  read-only
      STATUS  current
      DESCRIPTION
      "This attribute indicates a unique  slot  position where
       the module is inserted."
      ::= { prtE2CnfgEntry 2}

prtE2PrtIdx OBJECT-TYPE
      SYNTAX  INTEGER
       {
       exPrt1    (1),
       exPrt2    (2)
       }
      MAX-ACCESS  read-only
      STATUS  current
      DESCRIPTION
      "This attribute indicates a unique  port number."
      ::= { prtE2CnfgEntry 3}

prtE2Connect OBJECT-TYPE
      SYNTAX  INTEGER
              {
                no  (2),
                yes (3)
              }
      MAX-ACCESS  read-write
      STATUS  current
      DESCRIPTION
      "This attribute indicates whether the port should be
       connected or not. Only a connected port can perform activity."
      ::= {prtE2CnfgEntry 4}

prtE2MngOnNationalBit OBJECT-TYPE
      SYNTAX  INTEGER
              {
                no  (2),
                yes (3)
              }
      MAX-ACCESS  read-write
      STATUS  current
      DESCRIPTION
      "This attribute indicates whether National Bit will be used for
       Management or not."
      ::= {prtE2CnfgEntry 5}

--prtLanWanCnfgTable defines the parameters of the Lan-Wan ports
--(for HS-ETUB MP card)

prtLanWanCnfgTable  OBJECT-TYPE
    SYNTAX SEQUENCE OF PrtLanWanCnfgEntry
    MAX-ACCESS not-accessible
    STATUS  current
    DESCRIPTION
     "This is a table for Lan-Wan port parameters."
    ::= {prtLanWanCnfg 1}

prtLanWanCnfgEntry OBJECT-TYPE
    SYNTAX PrtLanWanCnfgEntry
    MAX-ACCESS not-accessible
    STATUS current
	DESCRIPTION  "An entry in table."
	INDEX {prtLanWanCnfgIdx, prtLanWanSltIdx, prtLanWanPrtIdx }
      ::= { prtLanWanCnfgTable 1}

PrtLanWanCnfgEntry ::=
    SEQUENCE {
    prtLanWanCnfgIdx        Integer32,
    prtLanWanSltIdx         INTEGER,
    prtLanWanPrtIdx         Integer32,
    prtLanWanMode           INTEGER,
    prtLanWanDestIf         Integer32,
	prtLanWanEgressVlanMode INTEGER,
	prtLanWanL2Protocol     INTEGER,
	prtLanWanStpPriority    Integer32,
	prtLanWanStpCost        Integer32,
	prtLanWanToLanVlanMode  INTEGER,
	prtLanWanVlanId         Integer32,
	prtLanWanVlanPriority   Integer32,
	prtLanWanMtu            Integer32,
	prtLanWanVlanType		INTEGER
    }

prtLanWanCnfgIdx OBJECT-TYPE
    SYNTAX  Integer32 (1..255)
    MAX-ACCESS  not-accessible
    STATUS  current
    DESCRIPTION
    "This object indicates the Idx of the Cnfg (1..100) being
     accessed.
     Idx 255 relates to the TmpCnfg. The write operation is valid only
     to the TmpCnfg."
    ::= {prtLanWanCnfgEntry 1}

prtLanWanSltIdx OBJECT-TYPE
    SYNTAX  INTEGER
    {
       notApplicable (1),
       io1   (5),
       io2   (6),
       io3   (7),
       io4   (8),
       io5   (9),
       io6  (10),
       io7  (11),
       io8  (12),
       io9  (13),
       io10 (14),
       io11 (15),
       io12 (16)
    }
    MAX-ACCESS  not-accessible
    STATUS  current
    DESCRIPTION
    "This object indicates a unique slot position where the module is inserted."
    ::= {prtLanWanCnfgEntry 2}

prtLanWanPrtIdx OBJECT-TYPE
    SYNTAX  Integer32
    MAX-ACCESS  not-accessible
    STATUS  current
    DESCRIPTION
    "This object indicates a unique number to identify a port
     in a specific card.
     Generally, for MP-210X/2200, the Port Index will be according to the 
     external/internal port number:  
     - exPrtX : X
     - inPrtX : 100 + X
     For FCD-155, refer to device specification" 
    ::= {prtLanWanCnfgEntry 3}

prtLanWanMode OBJECT-TYPE
    SYNTAX  INTEGER
    {
     notApplicable (1),
     bridge        (2),
     bridgeAndStp  (3),
     layer3SubnetSwitch(4)
    }
    MAX-ACCESS  read-write
    STATUS  current
    DESCRIPTION
    "This object determines the working mode of this port.
    For FCD155, layer3SubnetSwitch is not applicable"
    ::= {prtLanWanCnfgEntry 4}

prtLanWanDestIf OBJECT-TYPE
    SYNTAX  Integer32
    MAX-ACCESS  read-write
    STATUS  current
    DESCRIPTION
    "This object determines the Destination Interface for the frames
     received by this port.
	 - Switching Table = 100 (it means that the destination interface
	                          will be determined by the Switching Table)
     - inPrtX (internal-X port): 100 + X .
     For FCD-155 this object is not applicable =0 " 
    ::= {prtLanWanCnfgEntry 5}

prtLanWanEgressVlanMode OBJECT-TYPE
    SYNTAX  INTEGER
    {
     notApplicable (1),
     unmodified	   (2),
	 tag           (3),
	 doubleTag 	   (4),
	 untag         (5)
    }
    MAX-ACCESS  read-write
    STATUS  current
    DESCRIPTION
    "This object determines what to do with the VLAN frames that exit
     via the WAN side of the port.
     This object is not applicable when prtLanWanMode=l3SubnetSwitch(4)."
    ::= {prtLanWanCnfgEntry 6}

prtLanWanL2Protocol OBJECT-TYPE
    SYNTAX  INTEGER
    {
     notApplicable (1),
     none   	   (2),
	 ppp           (3),
	 hdlc          (4),
	 pppoHdlc      (5),
	 mlppp         (6)
    }
    MAX-ACCESS  read-write
    STATUS  current
    DESCRIPTION
    "L2 Protocol.
     When prtLanWanMode=l3SubnetSwitch(4), the only valid value is ppp(3)."
    ::= {prtLanWanCnfgEntry 7}

prtLanWanStpPriority OBJECT-TYPE
    SYNTAX  Integer32 (0..255)
    MAX-ACCESS  read-write
    STATUS  current
    DESCRIPTION
    "The value of the priority field which is contained in the first 
     (in network byte order) octet of the (2 octet long) Port ID."
    ::= {prtLanWanCnfgEntry 8}

prtLanWanStpCost OBJECT-TYPE
    SYNTAX  Integer32 (1..65535)
    MAX-ACCESS  read-write
    STATUS  current
    DESCRIPTION
    "The contribution of this port to the path cost of paths towards 
     the spanning tree root which include this port.  802.1D-1990 recommends 
     that the default value of this parameter be in inverse	proportion 
     to the speed of the attached LAN."
    ::= {prtLanWanCnfgEntry 9}

prtLanWanToLanVlanMode OBJECT-TYPE
    SYNTAX  INTEGER
    {
     notApplicable (1),
     unmodified	   (2),
	 tag           (3),
	 doubleTag 	   (4),
	 untag         (5)
    }
    MAX-ACCESS  read-write
    STATUS  current
    DESCRIPTION
    "This object determines what to do with the VLAN frames that come from
     WAN side of the port and exit towards one of the LAN ports.
     This object is applicable only when prtLanWanDestIf=100 or 101 
     (Switching Table or inPrt1)."
    ::= {prtLanWanCnfgEntry 10}

prtLanWanVlanId OBJECT-TYPE
    SYNTAX  Integer32 (0..4095)
    MAX-ACCESS  read-write
    STATUS  current
    DESCRIPTION
    "This is the VLAN Id attached to a frame, when the relevant
     Vlan Mode (prtLanWanEgressVlanMode or prtLanWanToLanVlanMode) is
     tag or doubleTag.
     0=not applicable."
    ::= {prtLanWanCnfgEntry 11}

prtLanWanVlanPriority OBJECT-TYPE
    SYNTAX  Integer32 
    MAX-ACCESS  read-write
    STATUS  current
    DESCRIPTION
    "This is the VLAN Priority attached to a frame, when the relevant
     Vlan Mode (prtLanWanEgressVlanMode or prtLanWanToLanVlanMode) is
     tag or doubleTag.
     Valid values: 0..7
     255=not applicable."
    ::= {prtLanWanCnfgEntry 12}

prtLanWanMtu OBJECT-TYPE
    SYNTAX  Integer32 
    MAX-ACCESS  read-write
    STATUS  current
    DESCRIPTION
    "The size of the largest packet which can be sent/received on the interface, 
     specified in octets.
     Valid values change per device.
     0=not applicable."
    ::= {prtLanWanCnfgEntry 13}

prtLanWanVlanType	OBJECT-TYPE	   
      SYNTAX    INTEGER 
      {
       notApplicable          (1),
       portBasedVlan          (2),
       ieee802dot1q           (3),
	   ieee802dot1qTaggedOnly (4)
       }
      MAX-ACCESS read-write
      STATUS current
      DESCRIPTION
      "This oject indicates type of VLAN this port is assigned to.
       Port Base Vlan parameters are defined by objects under
       radBridgePortBaseVlan"
       ::= { prtLanWanCnfgEntry 14}
 
--
-- The following table includes the IP addresses of all the NMS to which
-- Traps will be sent
--

--mngTrapIpTable  OBJECT-TYPE
--      SYNTAX  SEQUENCE OF MngTrapIpEntry
--      MAX-ACCESS  not-accessible
--      STATUS current
--      DESCRIPTION
--        "This table indicates  the destination address of the traps.
--         Internally it will be limited to ten addresses. "
--      ::= { agnt 7 }
--
--mngTrapIpEntry OBJECT-TYPE
--      SYNTAX  MngTrapIpEntry
--      MAX-ACCESS  not-accessible
--      STATUS  current
--      INDEX   { mngTrapIpIdx }
--      ::= { mngTrapIpTable 1 }
--
--MngTrapIpEntry  ::=
--      SEQUENCE {
--      mngTrapIpIdx   Integer32,
--      mngTrapIpIP    IpAddress,
--      mngTrapIpIPMask IpAddress
--      }
--
--mngTrapIpIdx OBJECT-TYPE
--      SYNTAX  Integer32
--      MAX-ACCESS  read-only
--      STATUS current
--      DESCRIPTION
--      " This value indicates an index of a specific IP address"
--      ::= { mngTrapIpEntry 1 }
--
--mngTrapIpIP OBJECT-TYPE
--      SYNTAX  IpAddress
--      MAX-ACCESS  read-write
--      STATUS current
--      DESCRIPTION
--      "This value indicates  the  destination addresses of the traps. "
--      ::= { mngTrapIpEntry 2 }
--
--mngTrapIpIPMask OBJECT-TYPE
--      SYNTAX  IpAddress
--      MAX-ACCESS  read-write
--      STATUS current
--      DESCRIPTION
--      "This value indicates  the  mask of the destination addresses of the traps. "
--      ::= { mngTrapIpEntry 3 }
--
--
-- Traps

--NOTIFICATIONS

 muxHubEvents OBJECT-IDENTITY
     STATUS  current
     DESCRIPTION
     "The events for ."
     ::= { muxHub 0 }

 alarmsTrap  NOTIFICATION-TYPE
     OBJECTS       { alrBufDescription }
     STATUS current
     DESCRIPTION
     "This trap is sent whenever alarm occurs in the agent."
     ::= { muxHubEvents 1 }

  sanityTrap  NOTIFICATION-TYPE
     OBJECTS       { agnSSanityCheckStatus, agnCSaveCnfgIdxCmd }
     STATUS current
     DESCRIPTION
     "This trap is sent after a data base update.
      It returns the sanity result status and the configuration no.
      checked.
      If the result is of Flip DB Sanity Check, the configuration
      no. sent will be 0.
      If the result is of Variant Sanity Check, the configuration
      no. sent will be 100."
     ::= { muxHubEvents 2 }

  cnfgFlipTrap  NOTIFICATION-TYPE
     OBJECTS       { agnSActiveCnfg }
     STATUS current
     DESCRIPTION
     "This trap is sent upon change of the active Configuration DB.
      Attached, is the new active Configuration no."
     ::= { muxHubEvents 3 }

  flipDbChangeTrap  NOTIFICATION-TYPE
     STATUS current
     DESCRIPTION
     "This trap is sent upon change of the active Flip tables
      (Flip DB)."
     ::= { muxHubEvents 4 }

  statusChangedTrap  NOTIFICATION-TYPE
     OBJECTS       { agnLed }
     STATUS current
     DESCRIPTION
     "This trap is sent upon any change of the LEDs status."
     ::= { muxHubEvents 5 }

 


-- 
-- file :D:\Synergy\WorkArea\545\mib_rad\txt\ethIf.txt
-- 
--
-- File: EthIf.txt 	
--

--Ethernet Interface


ethIf OBJECT IDENTIFIER ::= {diverseIfWanGen 1}	  --Ethernet Interface

ethIfTable OBJECT-TYPE
      SYNTAX SEQUENCE OF EthIfEntry
      MAX-ACCESS not-accessible
      STATUS current
	DESCRIPTION  "A table."
	::=  { ethIf 1}

ethIfEntry OBJECT-TYPE
      SYNTAX EthIfEntry
      MAX-ACCESS not-accessible
      STATUS current
	DESCRIPTION  "An entry in table."
	INDEX {ethIfIdx}
      ::= {ethIfTable 1}

EthIfEntry ::=
      SEQUENCE {
      ethIfIdx                Integer32,
      ethMode                 INTEGER,
      ethBridgingMode         INTEGER,
	  ethEncapsulationCRCMode INTEGER,
	  ethBackPressure		  INTEGER,
	  ethLimit4				  INTEGER,
	  ethSkipInitReset		  INTEGER,
	  ethMulticastBlock	  	  INTEGER,
	  ethBroadcastBlock	  	  INTEGER,
	  ethSpeed				  INTEGER,
      ethRip2                 INTEGER,
      ethPortPriority         INTEGER,
	  ethPortMngEnable		  INTEGER,
	  ethFlowCtrlMacAddress   MacAddress,
	  ethRateLimit			  Integer32,
	  ethJumboFrameEnable	  INTEGER,
	  ethAutoMdiXEnable		  INTEGER,
	  ethPortDataEnable		  INTEGER,
	  ethIfUse                Integer32,
	  ethLineOam              INTEGER,
	  ethRoutingProtocol      INTEGER,
	  ethMdiXManualSwitch     INTEGER,
	  ethDot1xEnable          INTEGER,
	  ethPartnerRateMode      INTEGER,
	  ethDot1xPortRole        INTEGER
	 		   }

ethIfIdx     OBJECT-TYPE
      SYNTAX  Integer32
      MAX-ACCESS  read-only
      STATUS  current
      DESCRIPTION
      "A unique index of the ethernet interface/port."
      ::=  {ethIfEntry 1}

ethMode    OBJECT-TYPE
      SYNTAX  INTEGER
      {
      halfDuplex  (1),
      fullDuplex  (2),
	  notApplicable(255)
      }
      MAX-ACCESS  read-write
      STATUS  current
      DESCRIPTION
      "This object indicates the Ethernet mode of operation."
      ::=  {ethIfEntry 2}

ethBridgingMode  OBJECT-TYPE
      SYNTAX  INTEGER
      {
      filtered    (1),
      transparent (2)
      }
      MAX-ACCESS  read-write
      STATUS  current
      DESCRIPTION
      "This object indicates the bridging mode of the Ethernet
       interface. "
      ::=  {ethIfEntry 3}

ethEncapsulationCRCMode  OBJECT-TYPE
      SYNTAX  INTEGER
      {
	   notApplicable (1),
	   withCRC	    (2),
	   withoutCRC	(3)
      }
      MAX-ACCESS  read-write
      STATUS  current
      DESCRIPTION
       "This object define the encapsulation type requested for the
		Ethernet interface. It indicates if we transfer the Ethernet
		frame to the other side with or without the CRC. "
      ::=  {ethIfEntry 4}

ethBackPressure  OBJECT-TYPE
      SYNTAX  INTEGER
      {
	   notApplicable (1),
	   disable	    (2),
	   enable		(3)
      }
      MAX-ACCESS  read-write
      STATUS  current
      DESCRIPTION
      "This parameter defines whether to enable or disable Back pressure.
       Back Pressure is a flow control parameter. "
      ::=  {ethIfEntry 5}
      
ethLimit4  OBJECT-TYPE
      SYNTAX  INTEGER
      {
			  notApplicable (1),
			  disable	    (2),
			  enable		(3)
      }
      MAX-ACCESS  read-write
      STATUS  current
      DESCRIPTION
       "This parameter determine the Back off algorithm mode.
        Every 4 following collisions the Framer will be thrown out
        (4 times more than usuall)."
      ::=  {ethIfEntry 6}
      
ethSkipInitReset  OBJECT-TYPE
      SYNTAX  INTEGER
      {
	   notApplicable (1),
	   notSkip	    (2),
	   skip			(3)
      }
      MAX-ACCESS  read-write
      STATUS  current
      DESCRIPTION
       "This parameter defines whether read status on reset. "
      ::=  {ethIfEntry 7}
      
ethMulticastBlock  OBJECT-TYPE
      SYNTAX  INTEGER
      {
	   notApplicable (1),
	   unBlock	    (2),
	   block			(3)
      }
      MAX-ACCESS  read-write
      STATUS  current
      DESCRIPTION
       "This parameter defines whether to send multicast message to WAN from LAN or not. "
      ::=  {ethIfEntry 8}

ethBroadcastBlock  OBJECT-TYPE
      SYNTAX  INTEGER
      {
	   notApplicable (1),
	   unBlock	    (2),
	   block			(3)
      }
      MAX-ACCESS  read-write
      STATUS  current
      DESCRIPTION
       "This parameter defines whether to send broadcast message to WAN from LAN or not."
      ::=  {ethIfEntry 9}

ethSpeed  OBJECT-TYPE
      SYNTAX  INTEGER
      {
	   notApplicable (1),
	   s10Mbps	    (2),
	   s100Mbps		(3),
	   s1Gbps		(4)
      }
      MAX-ACCESS  read-write
      STATUS  current
      DESCRIPTION
       "This parameter defines the line speed."
      ::=  {ethIfEntry 10}

ethRip2  OBJECT-TYPE
      SYNTAX  INTEGER
      {
	   notApplicable (1),
	   no    	    (2),
       yes           (3)
      }
      MAX-ACCESS  read-write
      STATUS  current
      DESCRIPTION
       "This parameter defines whether to send RIP II  message 
        to WAN from LAN or not"
      ::=  {ethIfEntry 11}

ethPortPriority  OBJECT-TYPE
      SYNTAX  INTEGER
      {
      notApplicable (1),
      none    	    (2),
      fixed         (3)
      }
      MAX-ACCESS  read-write
      STATUS  current
      DESCRIPTION
       "This parameter defines if priority is to   
        be considered for this Port."
      ::=  {ethIfEntry 12}

ethPortMngEnable  OBJECT-TYPE
      SYNTAX  INTEGER
      {
      notApplicable (1),
      no	  	    (2),
      yes	        (3),
	  localOnly		(4)
      }
      MAX-ACCESS  read-write
      STATUS  current
      DESCRIPTION
       "This parameter defines whether management data can pass through this Port.
       localOnly (4) - Only local device can be managed via this port."
      ::=  {ethIfEntry 13}

ethFlowCtrlMacAddress OBJECT-TYPE
      SYNTAX  MacAddress 
      MAX-ACCESS  read-write
      STATUS  current
      DESCRIPTION
      "In case of flow control - transmit frame with this specific MAC address
       to inform the other end to stop sending frames.
       Default: 01.80.C2.00.00.01."     
      ::= {ethIfEntry 14}

ethRateLimit  OBJECT-TYPE
      SYNTAX  Integer32
      MAX-ACCESS  read-write
      STATUS  current
      DESCRIPTION
       "This parameter defines the Rate Limit of the line, in Mbps."
      ::=  {ethIfEntry 15}

ethJumboFrameEnable  OBJECT-TYPE
      SYNTAX  INTEGER
      {
	   notApplicable (1),
	   no    	     (2),
       yes           (3)
      }
      MAX-ACCESS  read-write
      STATUS  current
      DESCRIPTION
       "This parameter defines whether to support Jumbo Frame or not."
      ::=  {ethIfEntry 16}

ethAutoMdiXEnable  OBJECT-TYPE
      SYNTAX  INTEGER
      {
	   notApplicable (1),
	   no    	     (2),
       yes           (3)
      }
      MAX-ACCESS  read-write
      STATUS  current
      DESCRIPTION
       "This parameter defines whether to support 
       automatic change between MDI and MDI[X]."
      ::=  {ethIfEntry 17}

ethPortDataEnable  OBJECT-TYPE
      SYNTAX  INTEGER
      {
      notApplicable	(1),
      no			(2),
      yes			(3)
      }
      MAX-ACCESS  read-write
      STATUS  current
      DESCRIPTION
       "This parameter defines whether this port is enabled
        for data (that is not management).
        no(2)	- management can run on this port
        yes(3)	- both management and payload data can run on this port."
      ::=  {ethIfEntry 18}

ethIfUse  OBJECT-TYPE
      SYNTAX  Integer32
      MAX-ACCESS  read-write
      STATUS  current
      DESCRIPTION
       "This parameter defines the use of the port.
        1=NET
        2=USER ."
      ::=  {ethIfEntry 19}

ethLineOam  OBJECT-TYPE
      SYNTAX  INTEGER
      {
	   disable (2),
       passive (3)
      }
      MAX-ACCESS  read-write
      STATUS  current
      DESCRIPTION
       "This parameter defines the working mode of 802.AH OAM mechanism."
      ::=  {ethIfEntry 20}

ethRoutingProtocol  OBJECT-TYPE
      SYNTAX  INTEGER
      {
       notApplicable (1),
       none          (2),
       proprietary   (3),
       rip2          (4),
       rip1and2      (6)
      }
      MAX-ACCESS  read-write
      STATUS  current
      DESCRIPTION
       "This parameter defines the routing protocol 
        used above ETH port."
      ::=  {ethIfEntry 21}

ethMdiXManualSwitch  OBJECT-TYPE
      SYNTAX  INTEGER
      {
       crossOver       (1),
       straightThrough (2)
      }
      MAX-ACCESS  read-write
      STATUS  current
      DESCRIPTION
       "This parameter sets the port to be MDI-X (cross-over) or
       MDI (straight-through).  
       It is applicable only when ethAutoMdiXEnable = no, namely,
       only when the automatic MDI/MDIX crossover function is disabled."
      ::=  {ethIfEntry 22}

ethDot1xEnable    OBJECT-TYPE
      SYNTAX        INTEGER
	  {
	     notApplicable (1),
         no            (2),
         yes           (3)
      }
      MAX-ACCESS  read-write
      STATUS  current
      DESCRIPTION
      "Determines if the Port-Based Network Access Protocol
       (IEEE-802.1x) is enabled for the Ethernet Port."
      ::=  {ethIfEntry 23}

ethPartnerRateMode OBJECT-TYPE
     SYNTAX  INTEGER 
     {
  	    manual     (1),
	    automatic  (2)
     } 
     MAX-ACCESS  read-write
     STATUS  current
     DESCRIPTION
     "For converters having couples of ports, where each couple contains 
      a port with an SFP connector and a port with a RJ connector, this 
      parameter is relevant for the SFP port. It affects Rate configuration
	  of its partner (RJ port).
      manual - user can configure manually ETH parameters of RJ port (e.g 
	           Autonegotiation, Max Capability Advertised, etc...)
	  automatic - SFP Rate will be enforced on the RJ port. In this mode,
	           user cannot configure the Rate related parameters of the
	           RJ port (e.g Autonegotiation, Max Capability Advertised, etc...)"
     ::=  {ethIfEntry 24}

ethDot1xPortRole    OBJECT-TYPE
     SYNTAX  INTEGER 
     {
  	      authenticator  (1),
	      supplicant     (2)
     } 
     MAX-ACCESS  read-write
     STATUS  current
     DESCRIPTION
     "Determine the functionality of the port in 
        the Port-Based Network Access Protocol (IEEE-802.1x) - 
        either Authenticator or Supplicant."
     ::=  {ethIfEntry 25}


ethIfPerformance OBJECT IDENTIFIER ::= {ethIf 2}

ethIfCurrentTable OBJECT-TYPE
      SYNTAX SEQUENCE OF EthIfCurrentEntry
      MAX-ACCESS not-accessible
      STATUS current
	DESCRIPTION
         "The Ethernet Current table.
          When the index specifies the Ethernet interface (only), the counters
          are for an interval of 15 minutes."
	  ::=  { ethIfPerformance 1}

ethIfCurrentEntry OBJECT-TYPE
      SYNTAX EthIfCurrentEntry
      MAX-ACCESS not-accessible
      STATUS current
	DESCRIPTION
         "An entry in the Ethernet Current table."
	INDEX {ethIfCurrentIndex}
      ::= {ethIfCurrentTable 1}

EthIfCurrentEntry ::=
      SEQUENCE {
      ethIfCurrentIndex
           Integer32,
	  ethIfCurrentStatus
	       OCTET STRING,
      ethIfCurrentInFrames
      	   Gauge32,
      ethIfCurrentInOctets
      	   Gauge32,
      ethIfCurrentAlignmentErrors
      	   Gauge32,
      ethIfCurrentFCSErrors
      	   Gauge32,
      ethIfCurrentLengthError
      	   Gauge32,
      ethIfCurrentOutFrames
      	   Gauge32,
      ethIfCurrentOutOctets
      	   Gauge32,
      ethIfCurrentSingleCollisionFrames
      	   Gauge32,
      ethIfCurrentMultipleCollisionFrames
           Gauge32,
      ethIfCurrentDeferredTransmissions
      	   Gauge32,
      ethIfCurrentLateCollisions
      	   Gauge32,
      ethIfCurrentCarrierSenseErrors
      	   Gauge32,
	  ethIfCurrentInputCongestionDropped
      	   Gauge32,
	  ethIfCurrentOutputCongestionDropped
      	   Gauge32,
      ethIfCurrentOverflowInFrames
      	   Gauge32,
      ethIfCurrentOverflowInOctets
      	   Gauge32,
      ethIfCurrentOverflowFCSErrors
      	   Gauge32,
      ethIfCurrentOverflowOutFrames
      	   Gauge32,
      ethIfCurrentOverflowOutOctets
      	   Gauge32,
      ethIfCurrentOverflowMultipleCollisionFrames
      	   Gauge32,
      ethIfCurrentInUnicastFrames
      	   Gauge32,
      ethIfCurrentOutUnicastFrames
      	   Gauge32,
      ethIfCurrentInMulticastFrames
      	   Gauge32,
      ethIfCurrentOutMulticastFrames
      	   Gauge32,
      ethIfCurrentInBroadcastFrames
      	   Gauge32,
      ethIfCurrentOutBroadcastFrames
      	   Gauge32,
      ethIfCurrentInDiscardFrames
      	   Gauge32,
      ethIfCurrentOutDiscardFrames
      	   Gauge32,
      ethIfCurrentInPauseFrames
      	   Gauge32,
      ethIfCurrentOutPauseFrames
      	   Gauge32,
      ethIfCurrentOverflowInUnicastFrames
      	   Gauge32,
      ethIfCurrentOverflowOutUnicastFrames
      	   Gauge32,
      ethIfCurrentOverflowInMulticastFrames
      	   Gauge32,
      ethIfCurrentOverflowOutMulticastFrames
      	   Gauge32,
      ethIfCurrentOverflowInBroadcastFrames
      	   Gauge32,
      ethIfCurrentOverflowOutBroadcastFrames
      	   Gauge32,
      ethIfCurrentOverflowInDiscardFrames
      	   Gauge32,
      ethIfCurrentOverflowOutDiscardFrames
      	   Gauge32,
      ethIfCurrentOverflowInPauseFrames
      	   Gauge32,
      ethIfCurrentOverflowOutPauseFrames
      	   Gauge32
     }

ethIfCurrentIndex OBJECT-TYPE
      SYNTAX      Integer32
      MAX-ACCESS  read-only
      STATUS      current
      DESCRIPTION
        "The index of the Ethernet interface. 
         It may be ifIndex.
         For some devices (e.g RICi-622GE), supporting several types of 
         intervals, this index will be a concatenation of the port index 
         and interval type.
	 	 Interval type can indicate: 1 minute, 15 minutes, 1 hour, 24 hours.
         For the exact formula, see device specification."
     ::= { ethIfCurrentEntry 1 }

ethIfCurrentStatus OBJECT-TYPE
	 SYNTAX OCTET STRING  (SIZE (4))
     MAX-ACCESS  read-only
     STATUS  current
     DESCRIPTION
      "The status of the current interval:
         0 - Valid.
         1 - redundantLinkSwitch - the link has been switched 
             by a redundancy mechanism.
         2 - discontinuity - module was partialy out.
         4 - notValid - module is out."
      ::= { ethIfCurrentEntry 2 }

ethIfCurrentInFrames OBJECT-TYPE
      SYNTAX  Gauge32  
      MAX-ACCESS  read-only
      STATUS  current
      DESCRIPTION
	  "The counter associated with the number of received frames, 
	  encountered by the Ethernet interface in the current interval."
      ::= { ethIfCurrentEntry 3 }

ethIfCurrentInOctets OBJECT-TYPE
      SYNTAX  Gauge32  
      MAX-ACCESS  read-only
      STATUS  current
      DESCRIPTION
	  "The counter associated with the number of received octets, 
	  encountered by the Ethernet interface in the current interval."
      ::= { ethIfCurrentEntry 4 }

ethIfCurrentAlignmentErrors OBJECT-TYPE
      SYNTAX  Gauge32  
      MAX-ACCESS  read-only
      STATUS  current
      DESCRIPTION
	  "The counter associated with the number of received frames, 
	  which are not complete (The result of dividing the number 
	  of bits by 8 is not an Integer), encountered by the Ethernet 
	  interface in the current interval."
      ::= { ethIfCurrentEntry 5 }

ethIfCurrentFCSErrors OBJECT-TYPE
      SYNTAX  Gauge32  
      MAX-ACCESS  read-only
      STATUS  current
      DESCRIPTION
	  "The counter associated with the number of received frames 
	  that didn't pass the FCS test, encountered by the Ethernet 
	  interface in the current interval."
      ::= { ethIfCurrentEntry 6 }

ethIfCurrentLengthError OBJECT-TYPE
      SYNTAX  Gauge32  
      MAX-ACCESS  read-only
      STATUS  current
      DESCRIPTION
	  "The counter associated with the number of received frames 
	  with length error, encountered by the Ethernet interface in 
	  the current interval."
      ::= { ethIfCurrentEntry 7 }

ethIfCurrentOutFrames OBJECT-TYPE
      SYNTAX  Gauge32  
      MAX-ACCESS  read-only
      STATUS  current
      DESCRIPTION
	  "The counter associated with the number of transmitted frames, 
	  encountered by the Ethernet interface in the current interval."
      ::= { ethIfCurrentEntry 8 }

ethIfCurrentOutOctets OBJECT-TYPE
      SYNTAX  Gauge32  
      MAX-ACCESS  read-only
      STATUS  current
      DESCRIPTION
	  "The counter associated with the number of transmitted octets, 
	  encountered by the Ethernet interface in the current interval."
      ::= { ethIfCurrentEntry 9 }

ethIfCurrentSingleCollisionFrames OBJECT-TYPE
      SYNTAX  Gauge32  
      MAX-ACCESS  read-only
      STATUS  current
      DESCRIPTION
	  "The counter associated with the number of successfully
	  transmitted frames for which transmission was inhibited by
	  exactly one collision, encountered by the Ethernet interface 
	  in the current interval."
      ::= { ethIfCurrentEntry 10 }

ethIfCurrentMultipleCollisionFrames OBJECT-TYPE
      SYNTAX  Gauge32  
      MAX-ACCESS  read-only
      STATUS  current
      DESCRIPTION
	  "The counter associated with the number of successfully
	  transmitted frames for which transmission was inhibited by
	  more than one collision, encountered by the Ethernet interface 
	  in the current interval."
      ::= { ethIfCurrentEntry 11 }

ethIfCurrentDeferredTransmissions OBJECT-TYPE
      SYNTAX  Gauge32  
      MAX-ACCESS  read-only
      STATUS  current
      DESCRIPTION
	  "The counter associated with the number of transmitted frames 
	  for which the first transmission attempt was delayed due to a 
	  busy media, encountered by the Ethernet interface in the 
	  current interval."
      ::= { ethIfCurrentEntry 12 }

ethIfCurrentLateCollisions OBJECT-TYPE
      SYNTAX  Gauge32  
      MAX-ACCESS  read-only
      STATUS  current
      DESCRIPTION
	  "The counter associated with the number of times that a 
	  collision was detected later than the first 64 bytes of the 
	  frame, encountered by the Ethernet interface in the current 
	  interval."
      ::= { ethIfCurrentEntry 13 }

ethIfCurrentCarrierSenseErrors OBJECT-TYPE
      SYNTAX  Gauge32  
      MAX-ACCESS  read-only
      STATUS  current
      DESCRIPTION
	  "The counter associated with the number of times that the 
	  carrier sense condition was lost or never asserted when 
	  attempting to transmit a frame, encountered by the Ethernet 
	  interface in the current interval."
      ::= { ethIfCurrentEntry 14 }

ethIfCurrentInputCongestionDropped OBJECT-TYPE
      SYNTAX  Gauge32  
      MAX-ACCESS  read-only
      STATUS  current
      DESCRIPTION
	  "The counter associated with the number of frames dropped 
	  due to lack of buffers in ingress pool, encountered by 
	  the Ethernet interface in the current interval."
      ::= { ethIfCurrentEntry 15 }

ethIfCurrentOutputCongestionDropped OBJECT-TYPE
      SYNTAX  Gauge32  
      MAX-ACCESS  read-only
      STATUS  current
      DESCRIPTION
	  "The counter associated with the number of dropped frames 
	  due to a congestion, encountered by the Transmit direction 
	  to the Ethernet interface in the current interval."
      ::= { ethIfCurrentEntry 16 }

ethIfCurrentOverflowInFrames OBJECT-TYPE
      SYNTAX  Gauge32  
      MAX-ACCESS  read-only
      STATUS  current
      DESCRIPTION
      "The number of times the associated ethIfCurrentInFrames
       counter has overflowed in the current interval."
      ::= { ethIfCurrentEntry 17 }

ethIfCurrentOverflowInOctets OBJECT-TYPE
      SYNTAX  Gauge32  
      MAX-ACCESS  read-only
      STATUS  current
      DESCRIPTION
      "The number of times the associated ethIfCurrentInOctets
       counter has overflowed in the current interval."
      ::= { ethIfCurrentEntry 18 }

ethIfCurrentOverflowFCSErrors OBJECT-TYPE
      SYNTAX  Gauge32  
      MAX-ACCESS  read-only
      STATUS  current
      DESCRIPTION
      "The number of times the associated ethIfCurrentFCSErrors
       counter has overflowed in the current interval."
      ::= { ethIfCurrentEntry 19 }

ethIfCurrentOverflowOutFrames OBJECT-TYPE
      SYNTAX  Gauge32  
      MAX-ACCESS  read-only
      STATUS  current
      DESCRIPTION
      "The number of times the associated ethIfCurrentOutFrames
       counter has overflowed in the current interval."
      ::= { ethIfCurrentEntry 20 }

ethIfCurrentOverflowOutOctets OBJECT-TYPE
      SYNTAX  Gauge32  
      MAX-ACCESS  read-only
      STATUS  current
      DESCRIPTION
      "The number of times the associated ethIfCurrentOutOctets
       counter has overflowed in the current interval."
      ::= { ethIfCurrentEntry 21 }

ethIfCurrentOverflowMultipleCollisionFrames OBJECT-TYPE
      SYNTAX  Gauge32  
      MAX-ACCESS  read-only
      STATUS  current
      DESCRIPTION
	  "The number of times the associated ethIfCurrentMultipleCollisionFrames
       counter has overflowed in the current interval."
      ::= { ethIfCurrentEntry 22 }

ethIfCurrentInUnicastFrames OBJECT-TYPE
      SYNTAX  Gauge32  
      MAX-ACCESS  read-only
      STATUS  current
      DESCRIPTION
	  "The number of received Unicast frames, encountered by the 
	   Ethernet interface in the current interval."
      ::= { ethIfCurrentEntry 23 }

ethIfCurrentOutUnicastFrames OBJECT-TYPE
      SYNTAX  Gauge32  
      MAX-ACCESS  read-only
      STATUS  current
      DESCRIPTION
	  "The number of transmitted Unicast frames, encountered by the 
	   Ethernet interface in the current interval."
      ::= { ethIfCurrentEntry 24 }

ethIfCurrentInMulticastFrames OBJECT-TYPE
      SYNTAX  Gauge32  
      MAX-ACCESS  read-only
      STATUS  current
      DESCRIPTION
	  "The number of received Multicast frames, encountered by the 
	   Ethernet interface in the current interval."
      ::= { ethIfCurrentEntry 25 }

ethIfCurrentOutMulticastFrames OBJECT-TYPE
      SYNTAX  Gauge32  
      MAX-ACCESS  read-only
      STATUS  current
      DESCRIPTION
	  "The number of transmitted Multicast frames, encountered by the 
	   Ethernet interface in the current interval."
      ::= { ethIfCurrentEntry 26 }

ethIfCurrentInBroadcastFrames OBJECT-TYPE
      SYNTAX  Gauge32  
      MAX-ACCESS  read-only
      STATUS  current
      DESCRIPTION
	  "The number of received Broadcast frames, encountered by the 
	   Ethernet interface in the current interval."
      ::= { ethIfCurrentEntry 27 }

ethIfCurrentOutBroadcastFrames OBJECT-TYPE
      SYNTAX  Gauge32  
      MAX-ACCESS  read-only
      STATUS  current
      DESCRIPTION
	  "The number of transmitted Broadcast frames, encountered by the 
	   Ethernet interface in the current interval."
      ::= { ethIfCurrentEntry 28 }

ethIfCurrentInDiscardFrames OBJECT-TYPE
      SYNTAX  Gauge32  
      MAX-ACCESS  read-only
      STATUS  current
      DESCRIPTION
	  "The number of received Discarded frames, encountered by the 
	   Ethernet interface in the current interval."
      ::= { ethIfCurrentEntry 29 }

ethIfCurrentOutDiscardFrames OBJECT-TYPE
      SYNTAX  Gauge32  
      MAX-ACCESS  read-only
      STATUS  current
      DESCRIPTION
	  "The number of transmitted Discarded frames, encountered by the 
	   Ethernet interface in the current interval."
      ::= { ethIfCurrentEntry 30 }

ethIfCurrentInPauseFrames OBJECT-TYPE
      SYNTAX  Gauge32  
      MAX-ACCESS  read-only
      STATUS  current
      DESCRIPTION
	  "The number of received Pause frames, encountered by the 
	   Ethernet interface in the current interval."
      ::= { ethIfCurrentEntry 31 }

ethIfCurrentOutPauseFrames OBJECT-TYPE
      SYNTAX  Gauge32  
      MAX-ACCESS  read-only
      STATUS  current
      DESCRIPTION
	  "The number of transmitted Pause frames, encountered by the 
	   Ethernet interface in the current interval."
      ::= { ethIfCurrentEntry 32 }

ethIfCurrentOverflowInUnicastFrames OBJECT-TYPE
      SYNTAX  Gauge32  
      MAX-ACCESS  read-only
      STATUS  current
      DESCRIPTION
	  "The number of times the associated ethIfCurrentInUnicastFrames
       counter has overflowed in the current interval."
      ::= { ethIfCurrentEntry 33 }

ethIfCurrentOverflowOutUnicastFrames OBJECT-TYPE
      SYNTAX  Gauge32  
      MAX-ACCESS  read-only
      STATUS  current
      DESCRIPTION
	  "The number of times the associated ethIfCurrentOutUnicastFrames
       counter has overflowed in the current interval."
      ::= { ethIfCurrentEntry 34 }

ethIfCurrentOverflowInMulticastFrames OBJECT-TYPE
      SYNTAX  Gauge32  
      MAX-ACCESS  read-only
      STATUS  current
      DESCRIPTION
	  "The number of times the associated ethIfCurrentInMulticastFrames
       counter has overflowed in the current interval."
      ::= { ethIfCurrentEntry 35 }

ethIfCurrentOverflowOutMulticastFrames OBJECT-TYPE
      SYNTAX  Gauge32  
      MAX-ACCESS  read-only
      STATUS  current
      DESCRIPTION
	  "The number of times the associated ethIfCurrentOutMulticastFrames
       counter has overflowed in the current interval."
      ::= { ethIfCurrentEntry 36 }

ethIfCurrentOverflowInBroadcastFrames OBJECT-TYPE
      SYNTAX  Gauge32  
      MAX-ACCESS  read-only
      STATUS  current
      DESCRIPTION
	  "The number of times the associated ethIfCurrentInBroadcastFrames
       counter has overflowed in the current interval."
      ::= { ethIfCurrentEntry 37 }

ethIfCurrentOverflowOutBroadcastFrames OBJECT-TYPE
      SYNTAX  Gauge32  
      MAX-ACCESS  read-only
      STATUS  current
      DESCRIPTION
	  "The number of times the associated ethIfCurrentOutBroadcastFrames
       counter has overflowed in the current interval."
      ::= { ethIfCurrentEntry 38 }

ethIfCurrentOverflowInDiscardFrames OBJECT-TYPE
      SYNTAX  Gauge32  
      MAX-ACCESS  read-only
      STATUS  current
      DESCRIPTION
	  "The number of times the associated ethIfCurrentInDiscardFrames
       counter has overflowed in the current interval."
      ::= { ethIfCurrentEntry 39 }

ethIfCurrentOverflowOutDiscardFrames OBJECT-TYPE
      SYNTAX  Gauge32  
      MAX-ACCESS  read-only
      STATUS  current
      DESCRIPTION
	  "The number of times the associated ethIfCurrentOutDiscardFrames
       counter has overflowed in the current interval."
      ::= { ethIfCurrentEntry 40 }

ethIfCurrentOverflowInPauseFrames OBJECT-TYPE
      SYNTAX  Gauge32  
      MAX-ACCESS  read-only
      STATUS  current
      DESCRIPTION
	  "The number of times the associated ethIfCurrentInPauseFrames
       counter has overflowed in the current interval."
      ::= { ethIfCurrentEntry 41 }

ethIfCurrentOverflowOutPauseFrames OBJECT-TYPE
      SYNTAX  Gauge32  
      MAX-ACCESS  read-only
      STATUS  current
      DESCRIPTION
	  "The number of times the associated ethIfCurrentOutPauseFrames
       counter has overflowed in the current interval."
      ::= { ethIfCurrentEntry 42 }
      
--Interval Table

ethIfIntervalTable OBJECT-TYPE
      SYNTAX SEQUENCE OF EthIfIntervalEntry
      MAX-ACCESS not-accessible
      STATUS current
	DESCRIPTION
         "The Ethernet Interval table.
          When ethIfIntervalIndex specifies the Ethernet interface (only), 
          the counters are for an interval of 15 minutes."
	  ::=  { ethIfPerformance 2 }

ethIfIntervalEntry OBJECT-TYPE
      SYNTAX EthIfIntervalEntry
      MAX-ACCESS not-accessible
      STATUS current
	DESCRIPTION
         "An entry in the Ethernet Interval table."
    INDEX { ethIfIntervalIndex, ethIfIntervalNumber }
      ::= {ethIfIntervalTable 1}

EthIfIntervalEntry ::=
      SEQUENCE {
      ethIfIntervalIndex
           Integer32,
      ethIfIntervalNumber
           Integer32,
	  ethIfIntervalStatus
	       OCTET STRING,
      ethIfIntervalInFrames
      	   Gauge32,
      ethIfIntervalInOctets
      	   Gauge32,
      ethIfIntervalAlignmentErrors
      	   Gauge32,
      ethIfIntervalFCSErrors
      	   Gauge32,
      ethIfIntervalLengthError
      	   Gauge32,
      ethIfIntervalOutFrames
      	   Gauge32,
      ethIfIntervalOutOctets
      	   Gauge32,
      ethIfIntervalSingleCollisionFrames
      	   Gauge32,
      ethIfIntervalMultipleCollisionFrames
           Gauge32,
      ethIfIntervalDeferredTransmissions
      	   Gauge32,
      ethIfIntervalLateCollisions
      	   Gauge32,
      ethIfIntervalCarrierSenseErrors
      	   Gauge32,
	  ethIfIntervalInputCongestionDropped
		   Gauge32,
	  ethIfIntervalOutputCongestionDropped
		   Gauge32,
      ethIfIntervalOverflowInFrames
      	   Gauge32,
      ethIfIntervalOverflowInOctets
      	   Gauge32,
      ethIfIntervalOverflowFCSErrors
      	   Gauge32,
      ethIfIntervalOverflowOutFrames
      	   Gauge32,
      ethIfIntervalOverflowOutOctets
      	   Gauge32,
      ethIfIntervalOverflowMultipleCollisionFrames
      	   Gauge32,
      ethIfIntervalInUnicastFrames
      	   Gauge32,
      ethIfIntervalOutUnicastFrames
      	   Gauge32,
      ethIfIntervalInMulticastFrames
      	   Gauge32,
      ethIfIntervalOutMulticastFrames
      	   Gauge32,
      ethIfIntervalInBroadcastFrames
      	   Gauge32,
      ethIfIntervalOutBroadcastFrames
      	   Gauge32,
      ethIfIntervalInDiscardFrames
      	   Gauge32,
      ethIfIntervalOutDiscardFrames
      	   Gauge32,
      ethIfIntervalInPauseFrames
      	   Gauge32,
      ethIfIntervalOutPauseFrames
      	   Gauge32,
      ethIfIntervalOverflowInUnicastFrames
      	   Gauge32,
      ethIfIntervalOverflowOutUnicastFrames
      	   Gauge32,
      ethIfIntervalOverflowInMulticastFrames
      	   Gauge32,
      ethIfIntervalOverflowOutMulticastFrames
      	   Gauge32,
      ethIfIntervalOverflowInBroadcastFrames
      	   Gauge32,
      ethIfIntervalOverflowOutBroadcastFrames
      	   Gauge32,
      ethIfIntervalOverflowInDiscardFrames
      	   Gauge32,
      ethIfIntervalOverflowOutDiscardFrames
      	   Gauge32,
      ethIfIntervalOverflowInPauseFrames
      	   Gauge32,
      ethIfIntervalOverflowOutPauseFrames
      	   Gauge32
      }

ethIfIntervalIndex OBJECT-TYPE
    SYNTAX      Integer32
    MAX-ACCESS  read-only
    STATUS      current
    DESCRIPTION
        "The index of the Ethernet interface. 
        It may be ifIndex.
        For some devices (e.g RICi-622GE), supporting several types of 
        intervals, this index will be a concatenation of the port index and 
        interval type.
		Interval type can indicate: 1 minute, 15 minutes, 1 hour, 24 hours.
        For the exact formula, see device specification."
    ::= { ethIfIntervalEntry 1 }

ethIfIntervalNumber OBJECT-TYPE
    SYNTAX  Integer32 (1..200)
    MAX-ACCESS  read-only
    STATUS  current
    DESCRIPTION
        "The Interval Number. This number is between 1 and x, where 1 is the 
         most recently completed interval and x is the least recently 
         completed interval.
         For 15 minute intervals, usually x=96, but it can be different,
         depending on device capabilities."
    ::= { ethIfIntervalEntry 2 }

ethIfIntervalStatus OBJECT-TYPE
	 SYNTAX OCTET STRING  (SIZE (4))
     MAX-ACCESS  read-only
     STATUS  current
     DESCRIPTION
      "The status of the interval:
         0 - Valid.
         1 - redundantLinkSwitch - the link has been switched 
             by a redundancy mechanism.
         2 - discontinuity - module was partialy out.
         4 - notValid - module is out."
      ::= { ethIfIntervalEntry 3 }

ethIfIntervalInFrames OBJECT-TYPE
      SYNTAX  Gauge32  
      MAX-ACCESS  read-only
      STATUS  current
      DESCRIPTION
	  "The counter associated with the number of received frames, 
	  encountered by the Ethernet interface in the interval."
      ::= { ethIfIntervalEntry 4 }

ethIfIntervalInOctets OBJECT-TYPE
      SYNTAX  Gauge32  
      MAX-ACCESS  read-only
      STATUS  current
      DESCRIPTION
	  "The counter associated with the number of received octets, 
	  encountered by the Ethernet interface in the interval."
      ::= { ethIfIntervalEntry 5 }

ethIfIntervalAlignmentErrors OBJECT-TYPE
      SYNTAX  Gauge32  
      MAX-ACCESS  read-only
      STATUS  current
      DESCRIPTION
	  "The counter associated with the number of received frames, 
	  which are not complete (The result of dividing the number 
	  of bits by 8 is not an Integer), encountered by the Ethernet 
	  interface in the interval."
      ::= { ethIfIntervalEntry 6 }

ethIfIntervalFCSErrors OBJECT-TYPE
      SYNTAX  Gauge32  
      MAX-ACCESS  read-only
      STATUS  current
      DESCRIPTION
	  "The counter associated with the number of received frames 
	  that didn't pass the FCS test, encountered by the Ethernet 
	  interface in the interval."
      ::= { ethIfIntervalEntry 7 }

ethIfIntervalLengthError OBJECT-TYPE
      SYNTAX  Gauge32  
      MAX-ACCESS  read-only
      STATUS  current
      DESCRIPTION
	  "The counter associated with the number of received frames 
	  with length error, encountered by the Ethernet interface in 
	  the interval."
      ::= { ethIfIntervalEntry 8 }

ethIfIntervalOutFrames OBJECT-TYPE
      SYNTAX  Gauge32  
      MAX-ACCESS  read-only
      STATUS  current
      DESCRIPTION
	  "The counter associated with the number of transmitted frames, 
	  encountered by the Ethernet interface in the interval."
      ::= { ethIfIntervalEntry 9 }

ethIfIntervalOutOctets OBJECT-TYPE
      SYNTAX  Gauge32  
      MAX-ACCESS  read-only
      STATUS  current
      DESCRIPTION
	  "The counter associated with the number of transmitted octets, 
	  encountered by the Ethernet interface in the interval."
      ::= { ethIfIntervalEntry 10 }

ethIfIntervalSingleCollisionFrames OBJECT-TYPE
      SYNTAX  Gauge32  
      MAX-ACCESS  read-only
      STATUS  current
      DESCRIPTION
	  "The counter associated with the number of successfully
	  transmitted frames for which transmission was inhibited by
	  exactly one collision, encountered by the Ethernet 
	  interface in the interval."
      ::= { ethIfIntervalEntry 11 }

ethIfIntervalMultipleCollisionFrames OBJECT-TYPE
      SYNTAX  Gauge32  
      MAX-ACCESS  read-only
      STATUS  current
      DESCRIPTION
	  "The counter associated with the number of successfully
	  transmitted frames for which transmission was inhibited by
	  more than one collision, encountered by the Ethernet 
	  interface in the interval."
      ::= { ethIfIntervalEntry 12 }

ethIfIntervalDeferredTransmissions OBJECT-TYPE
      SYNTAX  Gauge32  
      MAX-ACCESS  read-only
      STATUS  current
      DESCRIPTION
	  "The counter associated with the number of transmitted frames 
	  for which the first transmission attempt was delayed due to a 
	  busy media, encountered by the Ethernet interface in the interval."
      ::= { ethIfIntervalEntry 13 }

ethIfIntervalLateCollisions OBJECT-TYPE
      SYNTAX  Gauge32  
      MAX-ACCESS  read-only
      STATUS  current
      DESCRIPTION
	  "The counter associated with the number of times that a 
	  collision was detected later than the first 64 bytes of the 
	  frame, encountered by the Ethernet interface in the interval."
      ::= { ethIfIntervalEntry 14 }

ethIfIntervalCarrierSenseErrors OBJECT-TYPE
      SYNTAX  Gauge32  
      MAX-ACCESS  read-only
      STATUS  current
      DESCRIPTION
	  "The counter associated with the number of times that the 
	  carrier sense condition was lost or never asserted when 
	  attempting to transmit a frame, encountered by the Ethernet 
	  interface in the interval."
      ::= { ethIfIntervalEntry 15 }

ethIfIntervalInputCongestionDropped OBJECT-TYPE
      SYNTAX  Gauge32  
      MAX-ACCESS  read-only
      STATUS  current
      DESCRIPTION
	  "The counter associated with the number of dropped frames 
	  due to a congestion, encountered by the Receive direction 
	  to the Ethernet interface in the interval."
	  ::= { ethIfIntervalEntry 16 }

ethIfIntervalOutputCongestionDropped OBJECT-TYPE
      SYNTAX  Gauge32  
      MAX-ACCESS  read-only
      STATUS  current
      DESCRIPTION
	  "The counter associated with the number of dropped frames 
	  due to a congestion, encountered by the Transmit direction 
	  to the Ethernet interface in the interval."
      ::= { ethIfIntervalEntry 17 }

ethIfIntervalOverflowInFrames OBJECT-TYPE
      SYNTAX  Gauge32  
      MAX-ACCESS  read-only
      STATUS  current
      DESCRIPTION
      "The number of times the associated ethIfIntervalInFrames
       counter has overflowed in the interval."
      ::= { ethIfIntervalEntry 18 }

ethIfIntervalOverflowInOctets OBJECT-TYPE
      SYNTAX  Gauge32  
      MAX-ACCESS  read-only
      STATUS  current
      DESCRIPTION
      "The number of times the associated ethIfIntervalInOctets
       counter has overflowed in the interval."
      ::= { ethIfIntervalEntry 19 }

ethIfIntervalOverflowFCSErrors OBJECT-TYPE
      SYNTAX  Gauge32  
      MAX-ACCESS  read-only
      STATUS  current
      DESCRIPTION
      "The number of times the associated ethIfIntervalFCSErrors
       counter has overflowed in the interval."
      ::= { ethIfIntervalEntry 20 }

ethIfIntervalOverflowOutFrames OBJECT-TYPE
      SYNTAX  Gauge32  
      MAX-ACCESS  read-only
      STATUS  current
      DESCRIPTION
      "The number of times the associated ethIfIntervalOutFrames
       counter has overflowed in the interval."
      ::= { ethIfIntervalEntry 21 }

ethIfIntervalOverflowOutOctets OBJECT-TYPE
      SYNTAX  Gauge32  
      MAX-ACCESS  read-only
      STATUS  current
      DESCRIPTION
      "The number of times the associated ethIfIntervalOutOctets
       counter has overflowed in the interval."
      ::= { ethIfIntervalEntry 22 }

ethIfIntervalOverflowMultipleCollisionFrames OBJECT-TYPE
      SYNTAX  Gauge32  
      MAX-ACCESS  read-only
      STATUS  current
      DESCRIPTION
      "The number of times the associated ethIfIntervalMultipleCollisionFrames
       counter has overflowed in the interval."
      ::= { ethIfIntervalEntry 23 }

ethIfIntervalInUnicastFrames OBJECT-TYPE
      SYNTAX  Gauge32  
      MAX-ACCESS  read-only
      STATUS  current
      DESCRIPTION
	  "The number of received Unicast frames, encountered by the 
	   Ethernet interface in the interval."
      ::= { ethIfIntervalEntry 24 }

ethIfIntervalOutUnicastFrames OBJECT-TYPE
      SYNTAX  Gauge32  
      MAX-ACCESS  read-only
      STATUS  current
      DESCRIPTION
	  "The number of transmitted Unicast frames, encountered by the 
	   Ethernet interface in the interval."
      ::= { ethIfIntervalEntry 25 }

ethIfIntervalInMulticastFrames OBJECT-TYPE
      SYNTAX  Gauge32  
      MAX-ACCESS  read-only
      STATUS  current
      DESCRIPTION
	  "The number of received Multicast frames, encountered by the 
	   Ethernet interface in the interval."
      ::= { ethIfIntervalEntry 26 }

ethIfIntervalOutMulticastFrames OBJECT-TYPE
      SYNTAX  Gauge32  
      MAX-ACCESS  read-only
      STATUS  current
      DESCRIPTION
	  "The number of transmitted Multicast frames, encountered by the 
	   Ethernet interface in the interval."
      ::= { ethIfIntervalEntry 27 }

ethIfIntervalInBroadcastFrames OBJECT-TYPE
      SYNTAX  Gauge32  
      MAX-ACCESS  read-only
      STATUS  current
      DESCRIPTION
	  "The number of received Broadcast frames, encountered by the 
	   Ethernet interface in the interval."
      ::= { ethIfIntervalEntry 28 }

ethIfIntervalOutBroadcastFrames OBJECT-TYPE
      SYNTAX  Gauge32  
      MAX-ACCESS  read-only
      STATUS  current
      DESCRIPTION
	  "The number of transmitted Broadcast frames, encountered by the 
	   Ethernet interface in the interval."
      ::= { ethIfIntervalEntry 29 }

ethIfIntervalInDiscardFrames OBJECT-TYPE
      SYNTAX  Gauge32  
      MAX-ACCESS  read-only
      STATUS  current
      DESCRIPTION
	  "The number of received Discarded frames, encountered by the 
	   Ethernet interface in the interval."
      ::= { ethIfIntervalEntry 30 }

ethIfIntervalOutDiscardFrames OBJECT-TYPE
      SYNTAX  Gauge32  
      MAX-ACCESS  read-only
      STATUS  current
      DESCRIPTION
	  "The number of transmitted Discarded frames, encountered by the 
	   Ethernet interface in the interval."
      ::= { ethIfIntervalEntry 31 }

ethIfIntervalInPauseFrames OBJECT-TYPE
      SYNTAX  Gauge32  
      MAX-ACCESS  read-only
      STATUS  current
      DESCRIPTION
	  "The number of received Pause frames, encountered by the 
	   Ethernet interface in the interval."
      ::= { ethIfIntervalEntry 32 }

ethIfIntervalOutPauseFrames OBJECT-TYPE
      SYNTAX  Gauge32  
      MAX-ACCESS  read-only
      STATUS  current
      DESCRIPTION
	  "The number of transmitted Pause frames, encountered by the 
	   Ethernet interface in the interval."
      ::= { ethIfIntervalEntry 33 }

ethIfIntervalOverflowInUnicastFrames OBJECT-TYPE
      SYNTAX  Gauge32  
      MAX-ACCESS  read-only
      STATUS  current
      DESCRIPTION
	  "The number of times the associated ethIfIntervalInUnicastFrames
       counter has overflowed in the interval."
      ::= { ethIfIntervalEntry 34 }

ethIfIntervalOverflowOutUnicastFrames OBJECT-TYPE
      SYNTAX  Gauge32  
      MAX-ACCESS  read-only
      STATUS  current
      DESCRIPTION
	  "The number of times the associated ethIfIntervalOutUnicastFrames
       counter has overflowed in the interval."
      ::= { ethIfIntervalEntry 35 }

ethIfIntervalOverflowInMulticastFrames OBJECT-TYPE
      SYNTAX  Gauge32  
      MAX-ACCESS  read-only
      STATUS  current
      DESCRIPTION
	  "The number of times the associated ethIfIntervalInMulticastFrames
       counter has overflowed in the interval."
      ::= { ethIfIntervalEntry 36 }

ethIfIntervalOverflowOutMulticastFrames OBJECT-TYPE
      SYNTAX  Gauge32  
      MAX-ACCESS  read-only
      STATUS  current
      DESCRIPTION
	  "The number of times the associated ethIfIntervalOutMulticastFrames
       counter has overflowed in the interval."
      ::= { ethIfIntervalEntry 37 }

ethIfIntervalOverflowInBroadcastFrames OBJECT-TYPE
      SYNTAX  Gauge32  
      MAX-ACCESS  read-only
      STATUS  current
      DESCRIPTION
	  "The number of times the associated ethIfIntervalInBroadcastFrames
       counter has overflowed in the interval."
      ::= { ethIfIntervalEntry 38 }

ethIfIntervalOverflowOutBroadcastFrames OBJECT-TYPE
      SYNTAX  Gauge32  
      MAX-ACCESS  read-only
      STATUS  current
      DESCRIPTION
	  "The number of times the associated ethIfIntervalOutBroadcastFrames
       counter has overflowed in the interval."
      ::= { ethIfIntervalEntry 39 }

ethIfIntervalOverflowInDiscardFrames OBJECT-TYPE
      SYNTAX  Gauge32  
      MAX-ACCESS  read-only
      STATUS  current
      DESCRIPTION
	  "The number of times the associated ethIfIntervalInDiscardFrames
       counter has overflowed in the interval."
      ::= { ethIfIntervalEntry 40 }

ethIfIntervalOverflowOutDiscardFrames OBJECT-TYPE
      SYNTAX  Gauge32  
      MAX-ACCESS  read-only
      STATUS  current
      DESCRIPTION
	  "The number of times the associated ethIfIntervalOutDiscardFrames
       counter has overflowed in the interval."
      ::= { ethIfIntervalEntry 41 }

ethIfIntervalOverflowInPauseFrames OBJECT-TYPE
      SYNTAX  Gauge32  
      MAX-ACCESS  read-only
      STATUS  current
      DESCRIPTION
	  "The number of times the associated ethIfIntervalInPauseFrames
       counter has overflowed in the interval."
      ::= { ethIfIntervalEntry 42 }

ethIfIntervalOverflowOutPauseFrames OBJECT-TYPE
      SYNTAX  Gauge32  
      MAX-ACCESS  read-only
      STATUS  current
      DESCRIPTION
	  "The number of times the associated ethIfIntervalOutPauseFrames
       counter has overflowed in the interval."
      ::= { ethIfIntervalEntry 43 }


ethPerformanceMode    OBJECT-TYPE
      SYNTAX  INTEGER
        {
          notApplicable  (1),
          countOK		 (2),
		  countFail		 (3)
     }
      MAX-ACCESS  read-write
      STATUS  current
      DESCRIPTION
      "This object indicates whether OK or Fail statistics will be counted."
      ::=  {ethIfPerformance 3}


ethIfPerfTable OBJECT-TYPE
      SYNTAX SEQUENCE OF EthIfPerfEntry
      MAX-ACCESS not-accessible
      STATUS current
	DESCRIPTION
         "The Ethernet Performance table."
	  ::=  { ethIfPerformance 4}

ethIfPerfEntry OBJECT-TYPE
      SYNTAX EthIfPerfEntry
      MAX-ACCESS not-accessible
      STATUS current
	DESCRIPTION
         "An entry in the Ethernet Performance table."
	INDEX {ethIfIdx}
      ::= {ethIfPerfTable 1}

EthIfPerfEntry ::=
      SEQUENCE {
      ethIfPerfInOkFrames
      	   Gauge32,
      ethIfPerfOutOkFrames
      	   Gauge32,
	  ethIfPerfTotalCollisions
		   Gauge32,
      ethIfPerfInOkOctets
      	   Gauge32 
      }

ethIfPerfInOkFrames OBJECT-TYPE
      SYNTAX  Gauge32  
      MAX-ACCESS  read-only
      STATUS  current
      DESCRIPTION
	  "The counter associated with the number of received OK frames, 
	  encountered by the Ethernet interface since ethPerformanceMode Set to countOK (2) 
	  or Reset Statistics was done."
      ::= { ethIfPerfEntry 1 }

ethIfPerfOutOkFrames OBJECT-TYPE
      SYNTAX  Gauge32  
      MAX-ACCESS  read-only
      STATUS  current
      DESCRIPTION
	  "The counter associated with the number of transmitted OK frames, 
	  encountered by the Ethernet interface since ethPerformanceMode Set to countOK (2) 
	  or Reset Statistics was done."
      ::= { ethIfPerfEntry 2 }


ethIfPerfTotalCollisions OBJECT-TYPE
      SYNTAX  Gauge32  
      MAX-ACCESS  read-only
      STATUS  current
      DESCRIPTION
	  "The counter associated with the total number of collisions 
	  of any type encountered by the Ethernet interface since 
	  ethPerformanceMode Set to countOK (2)  or Reset Statistics was done"
	  ::= { ethIfPerfEntry 3 }

ethIfPerfInOkOctets OBJECT-TYPE
      SYNTAX  Gauge32  
      MAX-ACCESS  read-only
      STATUS  current
      DESCRIPTION
	  "The counter associated with the number of received OK Octets, 
	  encountered by the Ethernet interface since ethPerformanceMode Set to countOK (2) 
	  or Reset Statistics was done."
      ::= { ethIfPerfEntry 4 }


ethIfOamCfm OBJECT IDENTIFIER ::= { ethIf 3 }

ethIfOamCfmEvents  OBJECT IDENTIFIER ::= { ethIfOamCfm 0 }

ethOamCfmDefectCondition NOTIFICATION-TYPE
	STATUS		current
	DESCRIPTION     
	"This trap indicates that a MEP has a persistent defect condition."
     ::= { ethIfOamCfmEvents 1 }

-- ETH OAM CFM Definitions  (802.1ag)


-- MEP Definition
-- ******************************************************************
-- The MEG End Point Table
-- ******************************************************************

radMepTable OBJECT-TYPE
    SYNTAX  SEQUENCE OF RadMepEntry
    MAX-ACCESS  not-accessible
    STATUS  current
    DESCRIPTION
    "MEG End Point (MEP) configuration table associated with 
     Maitenance Entity Group (MEG) End Point.
     MEP is a short name for an expanded ETH flow point that includes a compound
     ETH Segment flow termination function, which marks the end point of an ETH ME,
     and a compound ETH Diagnostic flow function."
    ::= { ethIfOamCfm 1 }

radMepEntry OBJECT-TYPE
    SYNTAX  RadMepEntry
    MAX-ACCESS  not-accessible
    STATUS  current
    DESCRIPTION
    "An entry in the table."
     INDEX  { radOamIdx1, radOamEvcIdx, radMepIdx }
    ::= { radMepTable 1 }


RadMepEntry ::=
    SEQUENCE {
	radOamIdx1			  		 Unsigned32,
    radOamEvcIdx           	     Unsigned32,
    radMepIdx             	     Unsigned32,
	radMepRowStatus              RowStatus,
   	radMepLocalMepId			 Unsigned32,
	radMepRemoteMepId  			 Unsigned32,
	radMepOamMode    			 INTEGER,
	radMepContinuityVerMode		 INTEGER,
	radMepMeLevel				 Unsigned32,
	radMepOamDestAddrType		 INTEGER,
	radMepOamDestMacAddr		 MacAddress,
	radMepDefaultPriority		 Unsigned32,
	radMepCcStatus               INTEGER,
	radMepOamProtocol            INTEGER,
	radMepMdId                   Unsigned32,
	radMepMaFormat				 INTEGER,
	radMepMaName				 OCTET STRING,
	radMepSpVlanId               Unsigned32,
	radMepCcInterval             INTEGER,
	radMepTransmitLbmDestMacAddress    MacAddress,
	radMepTransmitLbmDestMepId		   Unsigned32,
	radMepTransmitLbmDestIsMepId	   INTEGER,
	radMepTransmitLbmMassages          Integer32,
	radMepTransmitLbmVlanPriority	   Unsigned32,
	radMepTransmitLbmVlanDropEnable	   INTEGER,
	radMepLbrIn                        Counter32,
	radMepLbrInOutOfOrder			   Counter32,
	radMepLbmOut                       Counter32,
	radMepTransmitLtmTargetMacAddress  MacAddress,
	radMepTransmitLtmTargetMepId	   Unsigned32,
	radMepTransmitLtmTargetIsMepId	   INTEGER,
	radMepTransmitLtmTtl               Unsigned32,
	radMepTransmitLtmActivationCmd     INTEGER
	}

radOamIdx1 OBJECT-TYPE
    SYNTAX      Unsigned32	  
    MAX-ACCESS  not-accessible
    STATUS      current
    DESCRIPTION
     "This object may indicate the Bridge Index or Configuration index."
    ::= { radMepEntry 1 }

radOamEvcIdx OBJECT-TYPE
    SYNTAX      Unsigned32	  
    MAX-ACCESS  not-accessible
    STATUS      current
    DESCRIPTION
     "This object indicates the Index of the EVC (Ethernet Virtual Circuit) 
     that the MEP is associated to."
    ::= { radMepEntry 2 }

radMepIdx OBJECT-TYPE
    SYNTAX      Unsigned32	  
    MAX-ACCESS  not-accessible
    STATUS      current
    DESCRIPTION
     "This object indicates the ID of the MEP being accessed."
    ::= { radMepEntry 3 }

radMepRowStatus	 OBJECT-TYPE
      SYNTAX     RowStatus 
      MAX-ACCESS read-create
      STATUS     current
      DESCRIPTION
      "This attribute allows to create/delete a row in this table."
      ::= {radMepEntry 4 }

radMepLocalMepId  OBJECT-TYPE
    SYNTAX       	 Unsigned32
    MAX-ACCESS       read-create
    STATUS           current
    DESCRIPTION
     "This object indicates the local MEP ID."
    ::= { radMepEntry 5 }
  
radMepRemoteMepId  OBJECT-TYPE
    SYNTAX              Unsigned32 
    MAX-ACCESS          read-create
    STATUS              current
    DESCRIPTION
     "This atribute is currently implemneted at radMepCcTable, that
     supports multicast."
    ::= { radMepEntry 6 }

radMepOamMode  OBJECT-TYPE
    SYNTAX              INTEGER
	{
       disabled    	 (2),
       initiate   	 (3),
       react	     (4) 
    }
    MAX-ACCESS          read-create
    STATUS              current
    DESCRIPTION
     "This object determines the OAM mode of the MEP:
     disabled - no CC is initiated nor responded
     initiate - the device initiates and responds to CC
     react - the device does not initiate a CC, but responds to CC."
    ::= { radMepEntry 7 }
  
radMepContinuityVerMode  OBJECT-TYPE
    SYNTAX              INTEGER
	{
       disabled    	 (2),
       ccBased   	 (3),
       lbBased	     (4) 
    }
    MAX-ACCESS          read-create
    STATUS              current
    DESCRIPTION
     "This object determines the OAM behavior of the MEP: 
     disabled - no CC is done
     cc_based - CC is done based on incoming messages
     lb_based - CC is done based on loopback messages."
    ::= { radMepEntry 8 }

radMepMeLevel OBJECT-TYPE
     SYNTAX  Unsigned32 (0..7) 
     MAX-ACCESS  read-create
     STATUS  current
     DESCRIPTION
     "At any point in a network, ME Level is used to distinguish between OAM 
     signals belonging to different nested MEs.
     Maintenance Entity Levels are defined as follows:
     0,1,2 are assigned to customers
     3,4   are assigned to providers
     5,6,7 are assigned to operators."
    ::= { radMepEntry 9 }

radMepOamDestAddrType OBJECT-TYPE
SYNTAX  INTEGER
	{
       unicast		(1),
       multicast  	(2)
    }
    MAX-ACCESS  read-create
    STATUS  current
    DESCRIPTION
    "This object determines if the OAM messages are sent to user defined 
    unicast address, or to RAD proprietary multicast address."
    ::= { radMepEntry 10 }

radMepOamDestMacAddr OBJECT-TYPE
	SYNTAX  MacAddress 
	MAX-ACCESS  read-create
	STATUS current
	DESCRIPTION
	"This object determines the MAC address that OAM packets are sent to."
	::= { radMepEntry 11 }

radMepDefaultPriority OBJECT-TYPE
     SYNTAX  Unsigned32 (0..7) 
     MAX-ACCESS  read-create
     STATUS  current
     DESCRIPTION
     "This object defines the priority of the OAM messages sent when no 
     service is defined on EVC. If a service is defined, the OAM messages
     will get the highest service priority existing on the EVC."
    ::= { radMepEntry 12 }


radMepCcStatus OBJECT-TYPE
     SYNTAX  INTEGER 
	{
       notApplicable     (1),
	   fail	             (2),
       ok  	             (3),
	   mismerge          (4),
	   unexpectedMep     (5),
       unexpectedMeLevel (6)
    }
     MAX-ACCESS  read-only
     STATUS  current
     DESCRIPTION
     "This object indicates the Continuity Check (CC)
      status."
    ::= { radMepEntry 13 }

radMepOamProtocol  OBJECT-TYPE
     SYNTAX         INTEGER
	 {
       proprietary     (1),
	   standard        (2)	   
     }
     MAX-ACCESS  read-create
     STATUS  current
     DESCRIPTION
     "Determines whether to use proprietary OAM mechanism, 
     or to use the standard (IEEE 802.1ag, ITU-T Y.1731)."
    ::= { radMepEntry 14 }


radMepMdId   OBJECT-TYPE
     SYNTAX       Unsigned32
     MAX-ACCESS  read-create
     STATUS  current
     DESCRIPTION
     "The index of the Maintenance Domain in the radMdTable (radMdIndex)."
    ::= { radMepEntry 15 }

radMepMaFormat	OBJECT-TYPE
     SYNTAX  INTEGER 
	{
       primaryVid        (1),
       charString        (2),
       unsignedInt16     (3),
       rfc2865VpnId      (4),
	   icc               (32)  -- ITU Carrier Code
     }
     MAX-ACCESS  read-create
     STATUS  current
     DESCRIPTION
     "The type (and thereby format) of the Maintenance Association
        Name."
    ::= { radMepEntry 16 }

radMepMaName  OBJECT-TYPE
     SYNTAX   OCTET STRING (SIZE(1..45))
     MAX-ACCESS  read-create
     STATUS  current
     DESCRIPTION
     "The Short Maintenance Association name."
    ::= { radMepEntry 17 }

radMepSpVlanId  OBJECT-TYPE
     SYNTAX     Unsigned32
     MAX-ACCESS  read-create
     STATUS  current
     DESCRIPTION
     "The SP (Service Provider) VLAN used when sending an OAM message."
    ::= { radMepEntry 18 }
    	
radMepCcInterval  OBJECT-TYPE
     SYNTAX       INTEGER
	 {
       intervalInvalid   (0),  -- No CCMs are sent (disabled)
       interval300Hz     (1),  -- CCMs are sent every 3 1/3 milliseconds (300Hz)
       interval10ms      (2),  -- CCMs are sent every 10 milliseconds
       interval100ms     (3),  -- CCMs are sent every 100 milliseconds
       interval1s        (4),  -- CCMs are sent every 1 second
       interval10s       (5),  -- CCMs are sent every 10 seconds
       interval1min      (6),  -- CCMs are sent every minute
       interval10min     (7)   -- CCMs are sent every 10 minutes   
     }
     MAX-ACCESS  read-create
     STATUS  current
     DESCRIPTION
     "Indicates the interval at which CCMs are sent by a MEP
     Valid only if radMepOamMode = initiate(4)."
    ::= { radMepEntry 19 }


radMepTransmitLbmDestMacAddress OBJECT-TYPE
     SYNTAX      MacAddress
     MAX-ACCESS  read-create
     STATUS  current
     DESCRIPTION
     "The Target MAC Address Field to be transmitted in the Loopback Message: 
     For unicast MAC Address this is the unicast destination MAC address.
     For multicast MAC Address, this variable is read-only.
     This address will be used if the value of 
     radMepTransmitLbmDestIsMepId is no (2).
     802.1ag clause 12.14.7.3.2:b."
    ::= { radMepEntry 20 }

radMepTransmitLbmDestMepId	OBJECT-TYPE
     SYNTAX    	   Unsigned32
     MAX-ACCESS  read-create
     STATUS  current
     DESCRIPTION
     "The MEPID of another MEP in the same MA to which the
	  LBM is to be sent. This address will be used if the value of
      radMepTransmitLbmDestIsMepId is yes (3).
      802.1ag clause 12.14.7.3.2:b."
    ::= { radMepEntry 21 }


radMepTransmitLbmDestIsMepId	  OBJECT-TYPE
    SYNTAX      INTEGER
	{
	  no  (2),
	  yes (3)
	}
    MAX-ACCESS  read-create
    STATUS      current
    DESCRIPTION
       "yes (3) indicates that MEPID of the target MEP is used for loopback transmission.
	    no (2) indicates that unicast destination MAC address of the target MEP is used.
        802.1ag clause 12.14.7.3.2:b."
    ::= { radMepEntry 22 }


radMepTransmitLbmMassages OBJECT-TYPE
     SYNTAX      Integer32(1..1024)
     MAX-ACCESS  read-create
     STATUS  current
     DESCRIPTION
     "The number of Loopback messages to be transmitted."
    ::= { radMepEntry 23 }

radMepTransmitLbmVlanPriority	OBJECT-TYPE
     SYNTAX     Unsigned32(0..7)
     MAX-ACCESS  read-create
     STATUS  current
     DESCRIPTION
     "The priority to be used in the VLAN tag, if present,
      in the transmitted frame. 
      The default value is CCM priority.
      802.1ag clause 12.14.7.3.2:e"
    ::= { radMepEntry 24 }

radMepTransmitLbmVlanDropEnable	 OBJECT-TYPE
     SYNTAX       INTEGER
	 {
	  no  (2),
	  yes (3)
     }
     MAX-ACCESS  read-create
     STATUS  current
     DESCRIPTION
     "Drop Enable bit to be used in the VLAN tag, if present,
      in the transmitted frame. 
      802.1ag clause 12.14.7.3.2:e"
    ::= { radMepEntry 25 }


radMepLbrIn OBJECT-TYPE
    SYNTAX      Counter32
    MAX-ACCESS  read-only
    STATUS      current
    DESCRIPTION
       "Total number of valid, in-order Loopback Replies received."
    ::= { radMepEntry 26 }

radMepLbrInOutOfOrder	  OBJECT-TYPE
     SYNTAX      Counter32
    MAX-ACCESS  read-only
    STATUS      current
    DESCRIPTION
       "The total number of valid, out-of-order Loopback Replies
        received."
    ::= { radMepEntry 27 }

radMepLbmOut OBJECT-TYPE
    SYNTAX      Counter32
    MAX-ACCESS  read-only
    STATUS      current
    DESCRIPTION
       "Total number of Loopback Messages transmitted."
    ::= { radMepEntry 28 }

radMepTransmitLtmTargetMacAddress OBJECT-TYPE
     SYNTAX      MacAddress
     MAX-ACCESS  read-create
     STATUS  current
     DESCRIPTION
     "The Target MAC Address Field to be transmitted in the Link Trace Message: 
      A unicast destination MAC address.
	  This address will be used 
      if the value of radMepTransmitLtmTargetIsMepId is no (2).
      802.1ag clause 12.14.7.4.2:c."
    ::= { radMepEntry 29 }


radMepTransmitLtmTargetMepId OBJECT-TYPE
    SYNTAX      Unsigned32
	MAX-ACCESS  read-create
    STATUS      current
    DESCRIPTION
       "The MEPID of another MEP in the same MA to which 
        LTM is to be transmitted. This address will be used 
        if the value of radMepTransmitLtmTargetIsMepId is yes (3).
        802.1ag clause 12.14.7.4.2:c."
    ::= { radMepEntry 30 }

radMepTransmitLtmTargetIsMepId OBJECT-TYPE
    SYNTAX      INTEGER
	{
	  no  (2),
	  yes (3)
	}
    MAX-ACCESS  read-create
    STATUS      current
    DESCRIPTION
       "yes (3) indicates that MEPID of the target MEP is used for Linktrace transmission.
	    no (2) indicates that unicast destination MAC address of the target MEP is used.
        802.1ag clause 12.14.7.4.2:c."
    ::= { radMepEntry 31 }
   
radMepTransmitLtmTtl   OBJECT-TYPE
    SYNTAX      Unsigned32
    MAX-ACCESS  read-create
    STATUS      current
    DESCRIPTION
       "The LTM TTL field. Default value, if not specified, is 64.
       The TTL field indicates the number of hops remaining to the LTM.
       Decremented by 1 each Linktrace Responder that handles the LTM.
       The value received in the LTM is returned in the LTR.
       If 0 on input, the LTM is not transmitted to the next hop.
       802.1ag clause 12.14.7.4.2:b and 21.8.4."
    ::= { radMepEntry 32 }

radMepTransmitLtmActivationCmd   OBJECT-TYPE
    SYNTAX      INTEGER
	{
	  off  (2),
	  on   (3)
	}
    MAX-ACCESS  read-create
    STATUS      current
    DESCRIPTION
       "Activation command for starting Loop Trace. Set will be always 
        to 'on' value. After operation was finished, Agent will turn the value to 'off'."
    ::= { radMepEntry 33 }


-- ETH OAM Service Definition

 
ethOamService	OBJECT IDENTIFIER ::= { ethIfOamCfm 2 }

ethOamServiceTable OBJECT-TYPE
    SYNTAX  SEQUENCE OF EthOamServiceEntry
    MAX-ACCESS  not-accessible
    STATUS  current
    DESCRIPTION
    "Service configuration table associated with Services running on a MEP."
    ::= { ethOamService 1 }

ethOamServiceEntry OBJECT-TYPE
    SYNTAX  EthOamServiceEntry
    MAX-ACCESS  not-accessible
    STATUS  current
    DESCRIPTION
    "An entry in the table."
     INDEX  { radOamIdx1, radOamEvcIdx, radMepIdx, ethOamServiceIdx  }
    ::= { ethOamServiceTable 1 }

EthOamServiceEntry ::=
    SEQUENCE {
    ethOamServiceIdx                	Unsigned32,
	ethOamServiceRowStatus          	RowStatus,
	ethOamServicePriority  		 		Unsigned32,
	ethOamServicePmEnable    		 	INTEGER,
	ethOamServiceFrameLossRatioThresh 	Integer32,
	ethOamServiceDelayThresh		 	Integer32,
	ethOamServiceDelayVarThresh	    	Integer32,
	ethOamServiceUnavailRatioThresh    	Integer32,
	ethOamServiceTxFrames				Counter32,
	ethOamServiceOverflowTxFrames   	Counter32,
	ethOamServiceFrameLoss				Counter32,
	ethOamServiceOverflowFrameLoss		Counter32,
	ethOamServiceFrameLossRatio			Unsigned32,
	ethOamServiceElapsedTime			Counter32,
	ethOamServiceUnavailSec				Counter32,
	ethOamServiceUnavailRatio			Unsigned32,
	ethOamServiceFramesAboveDelay 				Counter32,
	ethOamServiceOverflowFramesAboveDelay   	Counter32,
    ethOamServiceFramesAboveDelayVar 			Counter32,
	ethOamServiceOverflowFramesAboveDelayVar 	Counter32,
	ethOamServiceCurrentDelay					Unsigned32,
	ethOamServiceCurrentDelayVariation			Unsigned32,
	ethOamServiceResetCounters				    INTEGER
	}

ethOamServiceIdx OBJECT-TYPE
    SYNTAX      Unsigned32	  
    MAX-ACCESS  not-accessible
    STATUS      current
    DESCRIPTION
     "This object indicates the Index of the service being accessed."
    ::= { ethOamServiceEntry 1 }

ethOamServiceRowStatus	 OBJECT-TYPE
      SYNTAX     RowStatus 
      MAX-ACCESS read-create
      STATUS     current
      DESCRIPTION
      "This attribute allows to create/delete a row in this table."
      ::= {ethOamServiceEntry 2 }

ethOamServicePriority OBJECT-TYPE
     SYNTAX  Unsigned32 (0..7) 
     MAX-ACCESS  read-create
     STATUS  current
     DESCRIPTION
     "This object determines the priority of the service. 
     It is sent as P bits in an OAM message originated by this service."
    ::= { ethOamServiceEntry 3 }

ethOamServicePmEnable  OBJECT-TYPE
    SYNTAX              INTEGER
	{
       disable    	 (2),
       enable   	 (3) 
    }
    MAX-ACCESS          read-create
    STATUS              current
    DESCRIPTION
     "This object determines PM (Performance Monitoring)
     shall be enabled or not for the service."
    ::= { ethOamServiceEntry 4 }

ethOamServiceFrameLossRatioThresh OBJECT-TYPE
    SYNTAX  Integer32  (3..10)
    MAX-ACCESS  read-create
    STATUS  current
    DESCRIPTION
    "This object determines the Frame Loss ratio threshold in exponent
     of 1/10. That is, a value of 4 means that the threshold is 1E-4."
    ::= { ethOamServiceEntry 5 }

ethOamServiceDelayThresh OBJECT-TYPE
    SYNTAX  Integer32  (0..50000)
    MAX-ACCESS  read-create
    STATUS  current
    DESCRIPTION
    "This object determines the delay threshold defined for this service, 
    in measurement unit of 0.1 msec."
    ::= { ethOamServiceEntry 6 }

ethOamServiceDelayVarThresh OBJECT-TYPE
    SYNTAX  Integer32  (0..50000)
    MAX-ACCESS  read-create
    STATUS  current
    DESCRIPTION
    "This object determines the delay variation threshold defined 
    for this service, in measurement unit of 0.1 msec."
    ::= { ethOamServiceEntry 7 }

ethOamServiceUnavailRatioThresh OBJECT-TYPE
    SYNTAX  Integer32  (3..10)
    MAX-ACCESS  read-create
    STATUS  current
    DESCRIPTION
    "This object determines the Unavailability ratio threshold in exponent 
    of 1/10. That is, a value of 4 means that the threshold is 1E-4."
    ::= { ethOamServiceEntry 8 }

ethOamServiceTxFrames  OBJECT-TYPE
    SYNTAX  Counter32  
    MAX-ACCESS  read-only
    STATUS  current
    DESCRIPTION
    "Counts the number of frames trnasmitted by since the time the service is up."
    ::= { ethOamServiceEntry 9 }

ethOamServiceOverflowTxFrames  OBJECT-TYPE
    SYNTAX  Counter32  
    MAX-ACCESS  read-only
    STATUS  current
    DESCRIPTION
    "The number of times the associated
     ethOamServiceTxFrames counter has overflowed."
    ::= { ethOamServiceEntry 10 }

ethOamServiceFrameLoss   OBJECT-TYPE
    SYNTAX  Counter32  
    MAX-ACCESS  read-only
    STATUS  current
    DESCRIPTION
    "Counts the number of frames lost since the time the service is up."
    ::= { ethOamServiceEntry 11 }

ethOamServiceOverflowFrameLoss   OBJECT-TYPE
    SYNTAX  Counter32  
    MAX-ACCESS  read-only
    STATUS  current
    DESCRIPTION
    "The number of times the associated
     ethOamServiceFrameLoss counter has overflowed."
    ::= { ethOamServiceEntry 12 }

ethOamServiceFrameLossRatio OBJECT-TYPE
    SYNTAX  Unsigned32  
    MAX-ACCESS  read-only
    STATUS  current
    DESCRIPTION
    "Indicates the ratio of the lost frames since the time the service is up.
    The value is the ratio multiplied by 1E10.
    0xFFFFFFFF will be returned for ratio greater than 4/10 (40%)."
    ::= { ethOamServiceEntry 13 }

ethOamServiceElapsedTime OBJECT-TYPE
    SYNTAX  Counter32  
    MAX-ACCESS  read-only
    STATUS  current
    DESCRIPTION
    "Indicates the time elapsed in seconds since the time the service is up."
    ::= { ethOamServiceEntry 14 }

ethOamServiceUnavailSec  OBJECT-TYPE
    SYNTAX  Counter32  
    MAX-ACCESS  read-only
    STATUS  current
    DESCRIPTION
    "Indicates the number of unavailable seconds since
     the time the service is up."
    ::= { ethOamServiceEntry 15 }

ethOamServiceUnavailRatio  OBJECT-TYPE
    SYNTAX  Unsigned32  
    MAX-ACCESS  read-only
    STATUS  current
    DESCRIPTION
    " Indicates the ratio of the unavailable seconds since the 
    time the service is up. The value is the ratio multiplied by 1E10.
    0xFFFFFFFF will be returned for ratio greater than 4/10 (40%)."
    ::= { ethOamServiceEntry 16 }

ethOamServiceFramesAboveDelay  OBJECT-TYPE
    SYNTAX  Counter32  
    MAX-ACCESS  read-only
    STATUS  current
    DESCRIPTION
    "Indicates the number of frames arrived with delay 
    greater than the delay threshold."
    ::= { ethOamServiceEntry 17 }

ethOamServiceOverflowFramesAboveDelay  OBJECT-TYPE
    SYNTAX  Counter32  
    MAX-ACCESS  read-only
    STATUS  current
    DESCRIPTION
    "Indicates the number of times the associated
     ethOamServiceFramesAboveDelay counter has overflowed."
    ::= { ethOamServiceEntry 18 }

ethOamServiceFramesAboveDelayVar  OBJECT-TYPE
    SYNTAX  Counter32  
    MAX-ACCESS  read-only
    STATUS  current
    DESCRIPTION
    "Indicates the number of frames arrived with delay variation
    greater than the delay variation threshold."
    ::= { ethOamServiceEntry 19 }

ethOamServiceOverflowFramesAboveDelayVar  OBJECT-TYPE
    SYNTAX  Counter32  
    MAX-ACCESS  read-only
    STATUS  current
    DESCRIPTION
    "Indicates the number of times the associated
     ethOamServiceFramesAboveDelayVar counter has overflowed."
    ::= { ethOamServiceEntry 20 }

ethOamServiceCurrentDelay	 OBJECT-TYPE
    SYNTAX  	Unsigned32
    MAX-ACCESS  read-only
    STATUS  current
    DESCRIPTION
    "Indicates the last measured delay sample in msec."
    ::= { ethOamServiceEntry 21 }


ethOamServiceCurrentDelayVariation	  OBJECT-TYPE
    SYNTAX  	Unsigned32
    MAX-ACCESS  read-only
    STATUS  current
    DESCRIPTION
    "Indicates the last measured delay variation sample in msec."
    ::= { ethOamServiceEntry 22 }

ethOamServiceResetCounters		 OBJECT-TYPE
    SYNTAX  	INTEGER
	{
       off(2),
       on (3)
	}
    MAX-ACCESS  read-create
    STATUS      current
    DESCRIPTION
     "Reset the running PM counters of the selected service."
    ::= { ethOamServiceEntry 23 }

-- Service Current Statistics table  

ethOamSvcCurrentStatTable OBJECT-TYPE
       SYNTAX  SEQUENCE OF EthOamSvcCurrentStatEntry
       MAX-ACCESS  not-accessible
       STATUS  current
       DESCRIPTION
       "Service Current Statistics Table."
       ::= { ethOamService 2 }
  
ethOamSvcCurrentStatEntry OBJECT-TYPE
       SYNTAX EthOamSvcCurrentStatEntry
       MAX-ACCESS not-accessible
       STATUS current
       DESCRIPTION
       "Current Statistics per service"
       INDEX   { radOamIdx1, radOamEvcIdx, 
       			 radMepIdx, ethOamServiceIdx }
       ::= { ethOamSvcCurrentStatTable 1 }

EthOamSvcCurrentStatEntry ::=
         SEQUENCE {
         ethOamSvcCurrFramesAboveDelayThresh  PerfCurrentCount,
         ethOamSvcCurrFramesBelowDelayThresh  PerfCurrentCount,
         ethOamSvcCurrFramesAboveDVarThresh   PerfCurrentCount,
		 ethOamSvcCurrFramesBelowDVarThresh   PerfCurrentCount,
		 ethOamSvcCurrFramesTxCounter	      PerfCurrentCount,
		 ethOamSvcCurrFramesLossCounter		  PerfCurrentCount,
		 ethOamSvcCurrMinRoundTripDelay		  Unsigned32,
		 ethOamSvcCurrMaxRoundTripDelay		  Unsigned32,
		 ethOamSvcCurrAvgRoundTripDelay		  Unsigned32,
		 ethOamSvcCurrMaxRoundTripDVar		  Unsigned32,
		 ethOamSvcCurrAvgRoundTripDVar		  Unsigned32,
		 ethOamSvcCurrElapsedTime	   		  Integer32,	
		 ethOamSvcCurrUnavailSec	   		  PerfCurrentCount
		 		 }

ethOamSvcCurrFramesAboveDelayThresh     OBJECT-TYPE
    SYNTAX        PerfCurrentCount
    MAX-ACCESS    read-only
    STATUS        current
    DESCRIPTION
    "Number of frames that arrived in the current interval 
     at a delay greater than the threshold value defined for the service."
     ::= { ethOamSvcCurrentStatEntry 1 }

ethOamSvcCurrFramesBelowDelayThresh     OBJECT-TYPE
    SYNTAX        PerfCurrentCount
    MAX-ACCESS    read-only
    STATUS        current
    DESCRIPTION
    "Number of frames that arrived in the current interval at a delay
     lower than or equal to the threshold value defined for the service."
     ::= { ethOamSvcCurrentStatEntry 2 }

ethOamSvcCurrFramesAboveDVarThresh     OBJECT-TYPE
    SYNTAX        PerfCurrentCount
    MAX-ACCESS    read-only
    STATUS        current
    DESCRIPTION
    "Number of frames that arrived in the current interval at a delay
    variation greater than the threshold value defined for the service."
     ::= { ethOamSvcCurrentStatEntry 3 }

ethOamSvcCurrFramesBelowDVarThresh     OBJECT-TYPE
    SYNTAX        PerfCurrentCount
    MAX-ACCESS    read-only
    STATUS        current
    DESCRIPTION
    "Number of frames that arrived in the current interval
    at a delay variation lower than or equal to the
    threshold value defined for the service."
     ::= { ethOamSvcCurrentStatEntry 4 }

ethOamSvcCurrFramesTxCounter     OBJECT-TYPE
    SYNTAX        PerfCurrentCount
    MAX-ACCESS    read-only
    STATUS        current
    DESCRIPTION
    "Number of trnasmitted frames in the current interval."
     ::= { ethOamSvcCurrentStatEntry 5 }

ethOamSvcCurrFramesLossCounter     OBJECT-TYPE
    SYNTAX        PerfCurrentCount
    MAX-ACCESS    read-only
    STATUS        current
    DESCRIPTION
    "Number of lost frames in the current interval."
     ::= { ethOamSvcCurrentStatEntry 6 }

ethOamSvcCurrMinRoundTripDelay     OBJECT-TYPE
    SYNTAX        Unsigned32
    MAX-ACCESS    read-only
    STATUS        current
    DESCRIPTION
    "The mininal value of round trip delay in the current interval.
    Values units are of 0.1 msec."
     ::= { ethOamSvcCurrentStatEntry 7 }

ethOamSvcCurrMaxRoundTripDelay     OBJECT-TYPE
    SYNTAX        Unsigned32
    MAX-ACCESS    read-only
    STATUS        current
    DESCRIPTION
    "The maximum value of round trip delay in the current interval. 
     Values units are of 0.1 msec."
     ::= { ethOamSvcCurrentStatEntry 8 }

ethOamSvcCurrAvgRoundTripDelay     OBJECT-TYPE
    SYNTAX        Unsigned32
    MAX-ACCESS    read-only
    STATUS        current
    DESCRIPTION
    "The average round trip delay in the current interval. 
     Values units are of 0.1 msec."
     ::= { ethOamSvcCurrentStatEntry 9 }

ethOamSvcCurrMaxRoundTripDVar     OBJECT-TYPE
    SYNTAX        Unsigned32
    MAX-ACCESS    read-only
    STATUS        current
    DESCRIPTION
    "The maximum value of round trip delay variation in the current interval.
     Values units are of 0.1 msec."
     ::= { ethOamSvcCurrentStatEntry 10 }

ethOamSvcCurrAvgRoundTripDVar     OBJECT-TYPE
    SYNTAX        Unsigned32
    MAX-ACCESS    read-only
    STATUS        current
    DESCRIPTION
    "The average round trip delay variation in the current interval. 
     Values units are of 0.1 msec."
     ::= { ethOamSvcCurrentStatEntry 11 }

ethOamSvcCurrElapsedTime OBJECT-TYPE
     SYNTAX  Integer32 (0..899)
     MAX-ACCESS  read-only
     STATUS  current
     DESCRIPTION
     "The number of seconds that have elapsed since
      the beginning of the  current interval."
     ::= { ethOamSvcCurrentStatEntry 12 }

ethOamSvcCurrUnavailSec OBJECT-TYPE
     SYNTAX      PerfCurrentCount
     MAX-ACCESS  read-only
     STATUS  current
     DESCRIPTION
     "The number of seconds that the service was unavailable in the current interval."
     ::= { ethOamSvcCurrentStatEntry 13 }


-- ETH OAM Service Interval Statistics table contains statistics being
-- collected by each Service over the previous 24
-- hours of operation.  The past 24 hours are broken into 96
-- completed 15 minute intervals.

ethOamSvcIntervalTable OBJECT-TYPE
       SYNTAX  SEQUENCE OF EthOamSvcIntervalEntry
       MAX-ACCESS  not-accessible
       STATUS  current
       DESCRIPTION
       "Service Interval Statistics Table."
       ::= { ethOamService 3 }
  
ethOamSvcIntervalEntry OBJECT-TYPE
       SYNTAX EthOamSvcIntervalEntry
       MAX-ACCESS not-accessible
       STATUS current
       DESCRIPTION
       "Interval Statistics per service"
       INDEX   { radOamIdx1, radOamEvcIdx, 
       			 radMepIdx, ethOamServiceIdx, ethOamSvcIntervalNum }
       ::= { ethOamSvcIntervalTable 1 }

EthOamSvcIntervalEntry ::=
         SEQUENCE {
		 ethOamSvcIntervalNum				      Integer32,
         ethOamSvcIntervalFramesAboveDelayThresh  PerfIntervalCount,
         ethOamSvcIntervalFramesBelowDelayThresh  PerfIntervalCount,
         ethOamSvcIntervalFramesAboveDVarThresh   PerfIntervalCount,
		 ethOamSvcIntervalFramesBelowDVarThresh   PerfIntervalCount,
		 ethOamSvcIntervalFramesTxCounter		  PerfIntervalCount,
		 ethOamSvcIntervalFramesLossCounter	      PerfIntervalCount,
		 ethOamSvcIntervalMinRoundTripDelay		  Unsigned32,
		 ethOamSvcIntervalMaxRoundTripDelay		  Unsigned32,
		 ethOamSvcIntervalAvgRoundTripDelay		  Unsigned32,
		 ethOamSvcIntervalMaxRoundTripDVar		  Unsigned32,
		 ethOamSvcIntervalAvgRoundTripDVar		  Unsigned32,
		 ethOamSvcIntervalUnavailSec	   		  PerfIntervalCount
		 		 }

ethOamSvcIntervalNum  OBJECT-TYPE
    SYNTAX  		Integer32 (1..96) 
    MAX-ACCESS 		not-accessible
    STATUS  		current
    DESCRIPTION
    "The Interval index, which is actualy the Interval number, 
    where 1 is the most recently completed 15 minute interval,
     and 96 is the least recently completed 15 minutes interval
     (assuming that all 96 intervals exist)."
    ::= { ethOamSvcIntervalEntry 1 }

ethOamSvcIntervalFramesAboveDelayThresh     OBJECT-TYPE
    SYNTAX        PerfIntervalCount
    MAX-ACCESS    read-only
    STATUS        current
    DESCRIPTION
    "Number of frames that arrived in a delay greater than the 
    threshold value defined for the service in the selected interval."
     ::= { ethOamSvcIntervalEntry 2 }

ethOamSvcIntervalFramesBelowDelayThresh     OBJECT-TYPE
    SYNTAX        PerfIntervalCount
    MAX-ACCESS    read-only
    STATUS        current
    DESCRIPTION
    "Number of frames that arrived in a delay lower than the 
    threshold value defined for the service in the selected interval."
     ::= { ethOamSvcIntervalEntry 3 }

ethOamSvcIntervalFramesAboveDVarThresh     OBJECT-TYPE
    SYNTAX        PerfIntervalCount
    MAX-ACCESS    read-only
    STATUS        current
    DESCRIPTION
    "Number of frames that arrived in a delay variation greater than the 
    threshold value defined for the service in the selected interval."
     ::= { ethOamSvcIntervalEntry 4 }

ethOamSvcIntervalFramesBelowDVarThresh     OBJECT-TYPE
    SYNTAX       PerfIntervalCount
    MAX-ACCESS    read-only
    STATUS        current
    DESCRIPTION
    "Number of frames that arrived in a delay variation lower than the 
    threshold value defined for the service in the selected interval."
     ::= { ethOamSvcIntervalEntry 5 }

ethOamSvcIntervalFramesTxCounter     OBJECT-TYPE
    SYNTAX        PerfIntervalCount
    MAX-ACCESS    read-only
    STATUS        current
    DESCRIPTION
    "Number of trnasmitted frames in the selected interval."
     ::= { ethOamSvcIntervalEntry 6 }

ethOamSvcIntervalFramesLossCounter     OBJECT-TYPE
    SYNTAX        PerfIntervalCount
    MAX-ACCESS    read-only
    STATUS        current
    DESCRIPTION
    "Number of lost frames in the selected interval."
     ::= { ethOamSvcIntervalEntry 7 }

ethOamSvcIntervalMinRoundTripDelay     OBJECT-TYPE
    SYNTAX        Unsigned32
    MAX-ACCESS    read-only
    STATUS        current
    DESCRIPTION
    "The mininal value of round trip delay in the selected interval. 
    Values units are of 0.1 msec."
     ::= { ethOamSvcIntervalEntry 8 }

ethOamSvcIntervalMaxRoundTripDelay     OBJECT-TYPE
    SYNTAX        Unsigned32
    MAX-ACCESS    read-only
    STATUS        current
    DESCRIPTION
    "The maximum value of round trip delay in the selected interval. 
    Values units are of 0.1 msec."
     ::= { ethOamSvcIntervalEntry 9 }

ethOamSvcIntervalAvgRoundTripDelay     OBJECT-TYPE
    SYNTAX        Unsigned32
    MAX-ACCESS    read-only
    STATUS        current
    DESCRIPTION
    "The average round trip delay in the selected interval.
    Values units are of 0.1 msec."
     ::= { ethOamSvcIntervalEntry 10 }

ethOamSvcIntervalMaxRoundTripDVar     OBJECT-TYPE
    SYNTAX        Unsigned32
    MAX-ACCESS    read-only
    STATUS        current
    DESCRIPTION
    "The maximum value of round trip delay variation in the selected interval.
    Values units are of 0.1 msec."
     ::= { ethOamSvcIntervalEntry 11 }

ethOamSvcIntervalAvgRoundTripDVar     OBJECT-TYPE
    SYNTAX        Unsigned32
    MAX-ACCESS    read-only
    STATUS        current
    DESCRIPTION
    "The average round trip delay variation in the selected interval. 
    Values units are of 0.1 msec."
     ::= { ethOamSvcIntervalEntry 12 }
 
ethOamSvcIntervalUnavailSec OBJECT-TYPE
     SYNTAX  	 PerfIntervalCount
     MAX-ACCESS  read-only
     STATUS  current
     DESCRIPTION
     "The number of seconds that the service was unavailable 
     in the selected interval."
     ::= { ethOamSvcIntervalEntry 13 }


-- ETH OAM Service Total Statistics table  

ethOamSvcTotalTable OBJECT-TYPE
       SYNTAX  SEQUENCE OF EthOamSvcTotalEntry
       MAX-ACCESS  not-accessible
       STATUS  current
       DESCRIPTION
       "ETH OAM Service Total (24H) Statistics Table."
       ::= { ethOamService 4 }
  
ethOamSvcTotalEntry OBJECT-TYPE
       SYNTAX EthOamSvcTotalEntry
       MAX-ACCESS not-accessible
       STATUS current
       DESCRIPTION
       "Total Statistics per service"
       INDEX   { radOamIdx1, radOamEvcIdx, 
       			 radMepIdx, ethOamServiceIdx }
       ::= { ethOamSvcTotalTable 1 }

EthOamSvcTotalEntry ::=
         SEQUENCE {
         ethOamSvcTotalFramesAboveDelayThresh  PerfTotalCount,
         ethOamSvcTotalFramesBelowDelayThresh  PerfTotalCount,
         ethOamSvcTotalFramesAboveDVarThresh   PerfTotalCount,
		 ethOamSvcTotalFramesBelowDVarThresh   PerfTotalCount,
		 ethOamSvcTotalFramesTxCounter		   PerfTotalCount,
		 ethOamSvcTotalFramesLossCounter	   PerfTotalCount,
		 ethOamSvcTotalMinRoundTripDelay	   Unsigned32,
		 ethOamSvcTotalMaxRoundTripDelay	   Unsigned32,
		 ethOamSvcTotalAvgRoundTripDelay	   Unsigned32,
		 ethOamSvcTotalMaxRoundTripDVar		   Unsigned32,
		 ethOamSvcTotalAvgRoundTripDVar		   Unsigned32,
		 ethOamSvcTotalUnavailSec	   		   PerfTotalCount
		 		 }

ethOamSvcTotalFramesAboveDelayThresh     OBJECT-TYPE
    SYNTAX        PerfTotalCount
    MAX-ACCESS    read-only
    STATUS        current
    DESCRIPTION
    "Number of frames that arrived in a delay greater than the 
    threshold value defined for the service in the last 24H."
     ::= { ethOamSvcTotalEntry 1 }

ethOamSvcTotalFramesBelowDelayThresh     OBJECT-TYPE
    SYNTAX        PerfTotalCount
    MAX-ACCESS    read-only
    STATUS        current
    DESCRIPTION
    "Number of frames that arrived in a delay lower than the 
    threshold value defined for the service in the last 24H."
     ::= { ethOamSvcTotalEntry 2 }

ethOamSvcTotalFramesAboveDVarThresh     OBJECT-TYPE
    SYNTAX        PerfTotalCount
    MAX-ACCESS    read-only
    STATUS        current
    DESCRIPTION
    "Number of frames that arrived in a delay variation greater than the 
    threshold value defined for the service in the last 24H."
     ::= { ethOamSvcTotalEntry 3 }

ethOamSvcTotalFramesBelowDVarThresh     OBJECT-TYPE
    SYNTAX        PerfTotalCount
    MAX-ACCESS    read-only
    STATUS        current
    DESCRIPTION
    "Number of frames that arrived in a delay variation lower than the 
    threshold value defined for the service in the last 24H."
     ::= { ethOamSvcTotalEntry 4 }

ethOamSvcTotalFramesTxCounter     OBJECT-TYPE
    SYNTAX        PerfTotalCount
    MAX-ACCESS    read-only
    STATUS        current
    DESCRIPTION
    "Number of trnasmitted frames in the last 24H."
     ::= { ethOamSvcTotalEntry 5 }

ethOamSvcTotalFramesLossCounter     OBJECT-TYPE
    SYNTAX        PerfTotalCount
    MAX-ACCESS    read-only
    STATUS        current
    DESCRIPTION
    "Number of lost frames in the last 24H."
     ::= { ethOamSvcTotalEntry 6 }

ethOamSvcTotalMinRoundTripDelay     OBJECT-TYPE
    SYNTAX        Unsigned32
    MAX-ACCESS    read-only
    STATUS        current
    DESCRIPTION
    "The mininal value of round trip delay in the last 24H. 
    Values units are of 0.1 msec."
     ::= { ethOamSvcTotalEntry 7 }

ethOamSvcTotalMaxRoundTripDelay     OBJECT-TYPE
    SYNTAX        Unsigned32
    MAX-ACCESS    read-only
    STATUS        current
    DESCRIPTION
    "The maximum value of round trip delay in the last 24H. 
    Values units are of 0.1 msec."
     ::= { ethOamSvcTotalEntry 8 }

ethOamSvcTotalAvgRoundTripDelay     OBJECT-TYPE
    SYNTAX        Unsigned32
    MAX-ACCESS    read-only
    STATUS        current
    DESCRIPTION
    "The average round trip delay in the last 24H. 
    Values units are of 0.1 msec."
     ::= { ethOamSvcTotalEntry 9 }

ethOamSvcTotalMaxRoundTripDVar     OBJECT-TYPE
    SYNTAX        Unsigned32
    MAX-ACCESS    read-only
    STATUS        current
    DESCRIPTION
    "The maximum value of round trip delay variation in the last 24H. 
    Values units are of 0.1 msec."
     ::= { ethOamSvcTotalEntry 10 }

ethOamSvcTotalAvgRoundTripDVar     OBJECT-TYPE
    SYNTAX        Unsigned32
    MAX-ACCESS    read-only
    STATUS        current
    DESCRIPTION
    "The average round trip delay variation in the last 24H. 
    Values units are of 0.1 msec."
     ::= { ethOamSvcTotalEntry 11 }

ethOamSvcTotalUnavailSec OBJECT-TYPE
     SYNTAX  	 PerfTotalCount 
     MAX-ACCESS  read-only
     STATUS  current
     DESCRIPTION
     "The number of seconds that the service was unavailable 
     in the last 24H."
     ::= { ethOamSvcTotalEntry 12 }

-- MD (Maintenance Domain) Definition
-- ******************************************************************
-- The Maintenance Domain Table
-- ******************************************************************
radMdTable  OBJECT-TYPE
    SYNTAX  SEQUENCE OF RadMdEntry
    MAX-ACCESS  not-accessible
    STATUS  current
    DESCRIPTION
    "The MaintenanceDomain table. Each row in the table represents
        a different maintenance domain.

        A Maintenance domain is described in 802.1ag (3.22) as the
        network or the part of the network for which faults in
        connectivity are to be managed. The boundary of a Maintenance
        Domain is defined by a set of DSAPs, each of which can become
        a point of connectivity to a service instance."
    ::= { ethIfOamCfm 3 }

radMdEntry OBJECT-TYPE
    SYNTAX  RadMdEntry
    MAX-ACCESS  not-accessible
    STATUS  current
    DESCRIPTION
    "The Maintenance Domain table entry. This entry is not lost
        upon reboot. It is backed up by stable storage"
     INDEX  { radMdIndex }
    ::= { radMdTable 1 }

RadMdEntry ::= SEQUENCE {
      radMdIndex                Unsigned32,
      radMdFormat               INTEGER,
      radMdName                 OCTET STRING,
      radMdRowStatus            RowStatus
    }

radMdIndex OBJECT-TYPE
    SYNTAX      Unsigned32	  
    MAX-ACCESS  not-accessible
    STATUS      current
    DESCRIPTION
     "The index to the maintenance domain table."
    ::= { radMdEntry 1 }

radMdFormat OBJECT-TYPE
    SYNTAX      INTEGER
    {
      none              (1),
      dnsLikeName       (2),
      macAddressAndUint (3),
      charString        (4)
    }
    MAX-ACCESS  read-create
    STATUS      current
    DESCRIPTION
       "The type (and thereby format) of the Maintenance Domain Name."
    ::= { radMdEntry 2 }

radMdName OBJECT-TYPE
    SYNTAX      OCTET STRING (SIZE(1..43))
    MAX-ACCESS  read-create
    STATUS      current
    DESCRIPTION
       "The Maintenance Domain name. The type/format of this object
        is determined by the value of the radMdNameType object.
          
        Each Maintenance Domain has unique name amongst all those
        used or available to a service provider or operator.  It
        facilitates easy identification of administrative
        responsibility for each Maintenance Domain."
    ::= { radMdEntry 3 }


radMdRowStatus	 OBJECT-TYPE
      SYNTAX     RowStatus 
      MAX-ACCESS read-create
      STATUS     current
      DESCRIPTION
         "This attribute allows to create/delete a row in this table.
         
         The writable columns in a row can not be changed if the row
         is active. All columns must have a valid value before a row
         can be activated."
      ::= { radMdEntry 4 }


-- ******************************************************************
-- The Linktrace Reply Table
-- ******************************************************************

radMepLtrTable OBJECT-TYPE
    SYNTAX      SEQUENCE OF RadMepLtrEntry
    MAX-ACCESS  not-accessible
    STATUS      current
    DESCRIPTION
       "This table contains a list of Linktrace replies 
       received by a specific MEP in response to
       a linktrace message.
       "
    ::= { ethIfOamCfm 4 }

radMepLtrEntry OBJECT-TYPE
    SYNTAX      RadMepLtrEntry
    MAX-ACCESS  not-accessible
    STATUS      current
    DESCRIPTION
       "The LinktraceReply table entry."
    INDEX { radOamIdx1, radMepIdx, radMepLtrReceiveOrder }
    ::= { radMepLtrTable 1 }


RadMepLtrEntry ::= SEQUENCE {
      radMepLtrReceiveOrder         Unsigned32,
      radMepLtrTtl                  Unsigned32,
      radMepLtrMacAddr              MacAddress,
	  radMepLtrRelay                INTEGER,
	  radMepLtrIngress				INTEGER,
	  radMepLtrIngressPortIdSubtype	LldpPortIdSubtype,
	  radMepLtrIngressPortId        OCTET STRING,
   	  radMepLtrEgress				INTEGER,
	  radMepLtrEgressPortIdSubtype	LldpPortIdSubtype,
	  radMepLtrEgressPortId         OCTET STRING
}

radMepLtrReceiveOrder  OBJECT-TYPE
    SYNTAX      Unsigned32	  
    MAX-ACCESS  not-accessible
    STATUS      current
    DESCRIPTION
     "An index to distinguish among multiple LTRs with the same LTR
        Transaction Identifier field value.  radMepLtrReceiveOrder
        are assigned sequentially from 1, in the order that the
        Linktrace Initiator received the LTRs."
    ::= { radMepLtrEntry 1 }


radMepLtrTtl   OBJECT-TYPE
    SYNTAX      Unsigned32 (0..255)
    MAX-ACCESS  read-only
    STATUS      current
    DESCRIPTION
       "TTL field value for a returned LTR."
    ::= { radMepLtrEntry 2 }

radMepLtrMacAddr  OBJECT-TYPE
    SYNTAX        MacAddress
    MAX-ACCESS    read-only
    STATUS        current
    DESCRIPTION
       "The MAC address in the header of the returned LTR."
    ::= { radMepLtrEntry 3 }

radMepLtrRelay    OBJECT-TYPE
    SYNTAX        INTEGER
	{
         rlyHit     (1),
         rlyFdb     (2),
         rlyMpdb    (3)
  	}
    MAX-ACCESS    read-only
    STATUS        current
    DESCRIPTION
       "The value returned in the Relay Action field:
        rlyHit - the LTM reached an MP whose MAC address matches the target MAC address.
        rlyFdb - the Egress Port was determined by consulting the Filtering Database.
        rlyMpdb - the Egress Port was determined by consulting the MIP CCM Database.
        802.1ag clauses 12.14.7.5.3:g and 20.36.2.5"
    ::= { radMepLtrEntry 4 }

radMepLtrIngress    OBJECT-TYPE
    SYNTAX        	INTEGER
	{
          ingNoTlv    (1),
          ingOk       (2),
          ingDown     (3),
          ingBlocked  (4),
          ingVid      (5)
	}
    MAX-ACCESS    read-only
    STATUS        current
    DESCRIPTION
       "The value returned in the Ingress Action Field of the LTM.
        ingNoTlv - no Reply Ingress TLV was returned in the LTM.
        ingOK - the target data frame would be passed through to the MAC Relay Entity.
        ingDown - the Bridge Port's MAC_Operational parameter is false.
        ingBlocked - the target data frame would not be forwarded if received on this port.
        ingVid - the ingress port is not in the members of the LTM's VID,
        and ingress filtering is enabled, so the target data frame would be 
        filtered by the ingress filtering.
        802.1ag clauses 12.14.7.5.3:k and 20.36.2.6"
    ::= { radMepLtrEntry 5 }

radMepLtrIngressPortIdSubtype	OBJECT-TYPE
    SYNTAX        LldpPortIdSubtype
	MAX-ACCESS    read-only
    STATUS        current
    DESCRIPTION
       "The format of the Ingress Port ID.
	   If the radMepLtrIngress object contains the value
       egrNoTlv(1), then the contents of this object are meaningless.
       802.1ag clauses 12.14.7.5.3:m and 20.36.2.8"
    ::= { radMepLtrEntry 6 }

radMepLtrIngressPortId	OBJECT-TYPE
    SYNTAX      OCTET STRING (SIZE (1..255))
    MAX-ACCESS  read-only
    STATUS      current
    DESCRIPTION
       "Ingress Port ID. This is an alpha-numeric string that contains a
       specific identifier for the port.
       The format of this object is determined by
        the value of the radMepLtrIngressPortIdSubtype object.
        If the radMepLtrIngress object contains the value
        ingNoTlv(1), then the contents of this object are meaningless.
        802.1ag clauses 12.14.7.5.3:n and 20.36.2.9"
    ::= { radMepLtrEntry 7 }

radMepLtrEgress	OBJECT-TYPE
    SYNTAX     		INTEGER
    {
        egrNoTlv    (1),
        egrOK       (2),
        egrDown     (3),
        egrBlocked  (4),
        egrVid      (5)
    }
    MAX-ACCESS  read-only
    STATUS      current
    DESCRIPTION
       "The value returned in the Egress Action Field of the LTM.
        The value egrNoTlv(1) indicates that no Reply Egress TLV was
        returned in the LTM.
        802.1ag clauses 12.14.7.5.3:o and 20.36.2.10"
    ::= { radMepLtrEntry 8 }


radMepLtrEgressPortIdSubtype  OBJECT-TYPE
    SYNTAX     	  LldpPortIdSubtype
	MAX-ACCESS    read-only
    STATUS        current
    DESCRIPTION
       "The format of the egress Port ID.
        If the radMepLtrEgress object contains the value
        egrNoTlv(1), then the contents of this object are meaningless.
        802.1ag clauses 12.14.7.5.3:q and 20.36.2.12"
    ::= { radMepLtrEntry 9 }

radMepLtrEgressPortId      OBJECT-TYPE
    SYNTAX     	  OCTET STRING (SIZE (1..255))
	MAX-ACCESS    read-only
    STATUS        current
    DESCRIPTION
       "Egress Port ID. The format of this object is determined by
        the value of the radMepLtrEgressPortIdSubtype object.
        If the radMepLtrEgress object contains the value
        egrNoTlv(1), then the contents of this object are meaningless.
        802.1ag clauses 12.14.7.5.3:r and 20.36.2.13"
    ::= { radMepLtrEntry 10 }


-- ******************************************************************
-- The MEP CC Status Table
-- ******************************************************************

radMepCcStatusTable OBJECT-TYPE
    SYNTAX      SEQUENCE OF RadMepCcStatusEntry
    MAX-ACCESS  not-accessible
    STATUS      current
    DESCRIPTION
       "This table contains a list of CC Status  
       received by a specific MEP from different Remote MEPs. 
       "
    ::= { ethIfOamCfm 5 }

radMepCcStatusEntry OBJECT-TYPE
    SYNTAX      RadMepCcStatusEntry
    MAX-ACCESS  not-accessible
    STATUS      current
    DESCRIPTION
       "An entry in the CC Status Table."
    INDEX { radOamIdx1, radMepIdx, radMepRemoteMepIdx }
    ::= { radMepCcStatusTable 1 }

RadMepCcStatusEntry ::= SEQUENCE {
      radMepRemoteMepIdx        Unsigned32,
	  radMepCcStatusRemMepId	Unsigned32,
      radMepCcStat              INTEGER,
      radMepCcStatusMacAddr     MacAddress
      }

radMepRemoteMepIdx  OBJECT-TYPE
    SYNTAX      Unsigned32	  
    MAX-ACCESS  not-accessible
    STATUS      current
    DESCRIPTION
     "This is a running index for arriving CC messages (from different Remote MEPs)
      for a specific MEP ID."
    ::= { radMepCcStatusEntry 1 }

radMepCcStatusRemMepId		OBJECT-TYPE
     SYNTAX   Unsigned32
     MAX-ACCESS  read-create
     STATUS  current
     DESCRIPTION
     "This attribute indicates the Remote MEP ID from which the CC 
      messages has arrived."
    ::= { radMepCcStatusEntry 2 }

radMepCcStat OBJECT-TYPE
     SYNTAX  INTEGER 
	{
       notApplicable     (1),
	   fail	             (2),
       ok  	             (3),
	   mismerge          (4),
	   unexpectedMep     (5),
       unexpectedMeLevel (6),
	   unexpectedPeriod  (7),
	   rdi               (8)
    }
     MAX-ACCESS  read-only
     STATUS  current
     DESCRIPTION
     "This object indicates the Continuity Check (CC) status (ITU-T Y.1731, Appendix I):
     mismerge - A MEP detects a Mismerge condition when a CCM frame arrives with the 
       correct MEG level, but incorrect MEG ID.
	 unexpectedMep -A MEP detects an Unexpected MEP condition when a CCM frame arrives with the 
       correct MEG level, the correct MEG ID, but an unexpected MEP ID,
       which includes the MEP's own MEP ID.
     unexpectedMeLevel - A MEP detects an Unexpected MEG Level condition when a CCM frame
       arrives with incorrect MEG Level. Incorrect MEG Level is less than the MEP's 
       own MEG level.
     unexpectedPeriod - A MEP detects an Unexpected Period condition when a CCM frame
       arrives with a correct MEG level. a correct MEG ID, a correct MEP ID, 
       but with the Period field value different from the MEP's own CCM
       transmission period.
     rdi - A MEP detects RDI when it receives a CCM frame with the RDI field set."
    ::= { radMepCcStatusEntry 3 }

radMepCcStatusMacAddr   OBJECT-TYPE
     SYNTAX   MacAddress
     MAX-ACCESS  read-only
     STATUS  current
     DESCRIPTION
     "This object indicates the MAC Address in the 
     CC Status message received."
    ::= { radMepCcStatusEntry 4 }


--Ethernet Type at system level
ethOamStdEtherType  OBJECT-TYPE
     SYNTAX      Unsigned32
     MAX-ACCESS  read-write
     STATUS  current
     DESCRIPTION
     "The Standard Ether Type in an OAM message.
      This object will be RW until a formal value will be issued for standard Ethernet Type.
      When such Standard will exist, this object will be supported RO to reflect 
      the Standard value."
    ::= { ethIfOamCfm 6 }


--MAC Address at system level
ethOamStdMacAddress  OBJECT-TYPE
     SYNTAX      MacAddress
     MAX-ACCESS  read-write
     STATUS  current
     DESCRIPTION
     "The Standard MAC Address in an OAM message.
      This object will be RW until a formal value will be issued for standard MAC Address.
      When such Standard will exist, this object will be supported RO to reflect 
      the Standard value."
    ::= { ethIfOamCfm 7 }

-- ******************************************************************
-- The Extension for the Maintenance Domain Table
-- ******************************************************************

dot1agXCfmMdTable
OBJECT-TYPE
    SYNTAX  SEQUENCE OF Dot1agXCfmMdEntry
    MAX-ACCESS  not-accessible
    STATUS  current
    DESCRIPTION
    	"The Maintenance Domain table. Each row in the table represents
        a different maintenance association."
    ::= { ethIfOamCfm 8 }

dot1agXCfmMdEntry OBJECT-TYPE
    SYNTAX  Dot1agXCfmMdEntry
    MAX-ACCESS  not-accessible
    STATUS  current
    DESCRIPTION
    "The Maintenance Domain table entry."
--   AUGMENTS  { dot1agCfmMdEntry }
     INDEX  { dot1agCfmMdIndex }
    ::= { dot1agXCfmMdTable 1 }

Dot1agXCfmMdEntry ::= SEQUENCE 
     {
	   dot1agXCfmMdProtocol   INTEGER
     }

dot1agXCfmMdProtocol  OBJECT-TYPE
     SYNTAX         INTEGER
	 {
       preStandard     (1),
	   standard        (2)	   
     }
     MAX-ACCESS  read-create
     STATUS  current
     DESCRIPTION
     "
     ."
::= { dot1agXCfmMdEntry 1 }


-- ******************************************************************
-- The Extension for the MEP Table
-- ******************************************************************

dot1agXCfmMepTable
OBJECT-TYPE
    SYNTAX      SEQUENCE OF Dot1agXCfmMepEntry
    MAX-ACCESS  not-accessible
    STATUS      current
    DESCRIPTION
       "The Maintenance Association End Point (MEP) table."
	::= { ethIfOamCfm 9 }

dot1agXCfmMepEntry OBJECT-TYPE
    SYNTAX      Dot1agXCfmMepEntry
    MAX-ACCESS  not-accessible
    STATUS      current
    DESCRIPTION
       "The MEP table entry
       "
 -- AUGMENTS    { dot1agCfmMepEntry }
    INDEX { dot1agCfmMdIndex,
            dot1agCfmMaIndex,
            dot1agCfmMepIdentifier
          }
    ::= { dot1agXCfmMepTable 1 }

Dot1agXCfmMepEntry ::= SEQUENCE 
    {
    	dot1agXCfmMepContinuityVerMode  INTEGER,
		dot1agXCfmMepDestAddrType       INTEGER,
		dot1agXCfmMepDestMacAddr        MacAddress,
		dot1agXCfmMepMappingProfile	    Unsigned32
			 
			     }

dot1agXCfmMepContinuityVerMode  OBJECT-TYPE
    SYNTAX              INTEGER
	{
       disabled    	 (2),
       ccBased   	 (3),
       lbBased	     (4) 
    }
    MAX-ACCESS          read-create
    STATUS              current
    DESCRIPTION
     "This object determines the OAM behavior of the MEP: 
     disabled - no Continuity Verification is done
     cc_based - Continuity Verification is done based on incoming CC messages
     lb_based - Continuity Verification is done based on loopback messages."
    ::= { dot1agXCfmMepEntry 1 }

dot1agXCfmMepDestAddrType OBJECT-TYPE
SYNTAX  INTEGER
	{
       unicast		(1),
       multicast  	(2)
    }
    MAX-ACCESS  read-create
    STATUS  current
    DESCRIPTION
    "This object determines if the OAM messages are sent to user defined 
    unicast address, or to RAD proprietary multicast address."
    ::= { dot1agXCfmMepEntry 2 }

dot1agXCfmMepDestMacAddr OBJECT-TYPE
	SYNTAX  MacAddress 
	MAX-ACCESS  read-create
	STATUS current
	DESCRIPTION
	"This object determines the MAC address that OAM packets are sent to."
	::= { dot1agXCfmMepEntry 3 }

dot1agXCfmMepMappingProfile   OBJECT-TYPE
    SYNTAX       Unsigned32
    MAX-ACCESS   read-create
    STATUS       current
    DESCRIPTION
	"This attribute defines the Mapping/classification profile (flowMappingProfileTable )
	 assigned to this Mep."
     ::= { dot1agXCfmMepEntry 4}  

-- ******************************************************************
-- The Extension for the MEP Database Table
-- ******************************************************************

dot1agXCfmMepDbTable  OBJECT-TYPE
    SYNTAX      SEQUENCE OF Dot1agXCfmMepDbEntry
    MAX-ACCESS  not-accessible
    STATUS      current
    DESCRIPTION
       "The MEP DB table" 
    ::= { ethIfOamCfm 10 }

dot1agXCfmMepDbEntry OBJECT-TYPE
    SYNTAX      Dot1agXCfmMepDbEntry
    MAX-ACCESS  not-accessible
    STATUS      current
    DESCRIPTION
    "The MEP Database table entry.
    "
-- AUGMENTS    dot1agCfmMepDbEntry
    INDEX { dot1agCfmMdIndex,
            dot1agCfmMaIndex,
            dot1agCfmMepIdentifier,
            dot1agCfmMepDbRMepIdentifier
          }
    ::= { dot1agXCfmMepDbTable 1 }

Dot1agXCfmMepDbEntry ::= SEQUENCE 
{
  dot1agXCfmMepCcStat INTEGER
}

dot1agXCfmMepCcStat OBJECT-TYPE
    SYNTAX  INTEGER 
	{
       notApplicable     (1),
	   fail	             (2),
       ok  	             (3),
	   mismerge          (4),
	   unexpectedMep     (5),
       unexpectedMeLevel (6),
	   unexpectedPeriod  (7),
	   rdi               (8)
    }
     MAX-ACCESS  read-only
     STATUS  current
     DESCRIPTION
     "This object indicates the Continuity Check (CC) status (ITU-T Y.1731, Appendix I):
     mismerge - A MEP detects a Mismerge condition when a CCM frame arrives with the 
       correct MEG level, but incorrect MEG ID.
	 unexpectedMep -A MEP detects an Unexpected MEP condition when a CCM frame arrives with the 
       correct MEG level, the correct MEG ID, but an unexpected MEP ID,
       which includes the MEP's own MEP ID.
     unexpectedMeLevel - A MEP detects an Unexpected MEG Level condition when a CCM frame
       arrives with incorrect MEG Level. Incorrect MEG Level is less than the MEP's 
       own MEG level.
     unexpectedPeriod - A MEP detects an Unexpected Period condition when a CCM frame
       arrives with a correct MEG level. a correct MEG ID, a correct MEP ID, 
       but with the Period field value different from the MEP's own CCM
       transmission period.
     rdi - A MEP detects RDI when it receives a CCM frame with the RDI field set."
    ::= { dot1agXCfmMepDbEntry 1 }


-- ETH Ring Definition

ethIfRing OBJECT IDENTIFIER ::= { ethIf 4 }

ethIfRingEvents  OBJECT IDENTIFIER ::= { ethIfRing 0 }

ethIfRingTable OBJECT-TYPE
    SYNTAX  SEQUENCE OF EthIfRingEntry
    MAX-ACCESS  not-accessible
    STATUS  current
    DESCRIPTION
    "Ethernet Ring Table."
    ::= { ethIfRing 1 }

ethIfRingEntry OBJECT-TYPE
    SYNTAX  EthIfRingEntry
    MAX-ACCESS  not-accessible
    STATUS  current
    DESCRIPTION
    "An entry in the table."
     INDEX  { ethIfRingIdx }
    ::= { ethIfRingTable 1 }

EthIfRingEntry ::=
    SEQUENCE {
	ethIfRingIdx 		        Unsigned32,
	ethIfRingAdminStatus        INTEGER,
	ethIfRingPorts              PortList,
 	ethIfRingOperStatus         INTEGER,
 	ethIfRingKeepAliveInterval  Unsigned32,
	ethIfRingKeepAliveThresh	Unsigned32,
	ethIfRingKeepAliveVlanId	Unsigned32,
	ethIfRingMultiCastVlanId	Unsigned32,
	ethIfRingRowStatus			INTEGER
	}

ethIfRingIdx OBJECT-TYPE
    SYNTAX      Unsigned32	  
    MAX-ACCESS  not-accessible
    STATUS      current
    DESCRIPTION
     "This object is an Index that can indicate
     Slot, Ring, Cnfg etc., according to the device used.
     When NA, 1 will be used."
    ::= { ethIfRingEntry 1 }

ethIfRingAdminStatus OBJECT-TYPE
     SYNTAX  INTEGER 
	{
       down      (2),
       up  	     (3)
    }
     MAX-ACCESS  read-write
     STATUS  current
     DESCRIPTION
     "This object denotes the Ethernet Ring administrative status."
    ::= { ethIfRingEntry 2 }

ethIfRingPorts  OBJECT-TYPE
    SYNTAX      PortList
	MAX-ACCESS  read-write
    STATUS      current
    DESCRIPTION
   "The set of ports which are assigned to be ring members.  
    The default value of this object is a string of zeros."
    ::= {ethIfRingEntry 3}
			

ethIfRingOperStatus OBJECT-TYPE
     SYNTAX  INTEGER 
	{
       notApplicable (1),
	   open	         (2),
       close  	     (3)
    }
     MAX-ACCESS  read-only
     STATUS  current
     DESCRIPTION
     "This object indicates the Ethernet Ring operational status."
    ::= { ethIfRingEntry 4 }

ethIfRingKeepAliveInterval   OBJECT-TYPE
     SYNTAX  Unsigned32
     MAX-ACCESS  read-write
     STATUS  current
     DESCRIPTION
     "This parameter indicates the period of time (in msec.) 
     between two consequent Keep Alive messages."
     ::= { ethIfRingEntry 5 }

ethIfRingKeepAliveThresh	 OBJECT-TYPE
     SYNTAX  Unsigned32
     MAX-ACCESS  read-write
     STATUS  current
     DESCRIPTION
     "This parameter indicates the maximum number of 
     missed Keep Alive answer messages acceptable, after which link status will be failed."
     ::= { ethIfRingEntry 6 }

ethIfRingKeepAliveVlanId OBJECT-TYPE
     SYNTAX  Unsigned32 
     MAX-ACCESS  read-write
     STATUS  current
     DESCRIPTION
     "Dedicated VLAN ID for keep alive messages."
     ::= { ethIfRingEntry 7 }

ethIfRingMultiCastVlanId	OBJECT-TYPE
     SYNTAX  	Unsigned32
     MAX-ACCESS  read-write
     STATUS  current
     DESCRIPTION
     "Dedicated VLAN ID for multicast messages."
     ::= { ethIfRingEntry 8 }

ethIfRingRowStatus	  OBJECT-TYPE
     SYNTAX  			INTEGER
	 {
	    active(1),
		createAndGo(4),
        destroy(6)
	 }
	 MAX-ACCESS  read-write
     STATUS  current
     DESCRIPTION
     "Implement creation/deletion of rings in the device."
     ::= { ethIfRingEntry 9 }


--ETH RING NOTIFICATIONS

ethIfRingStatusChange  NOTIFICATION-TYPE
	OBJECTS     {ethIfRingOperStatus}
	STATUS		current
	DESCRIPTION     
	"This trap indicates that the status of the 
	Ethernet Ring has been changed."
     ::= { ethIfRingEvents 1 }



-- ETH Storming

ethIfStorming OBJECT IDENTIFIER ::= { ethIf 5 }

ethIfStormTable OBJECT-TYPE
    SYNTAX  SEQUENCE OF EthIfStormEntry
    MAX-ACCESS  not-accessible
    STATUS  current
    DESCRIPTION
    "Ethernet Storming Table."
    ::= { ethIfStorming 1 }

ethIfStormEntry OBJECT-TYPE
    SYNTAX  EthIfStormEntry
    MAX-ACCESS  not-accessible
    STATUS  current
    DESCRIPTION
    "An entry in the table."
     INDEX  {ethIfStormCnfgIdx, ethIfStormIfIdx, ethIfStormDirection, ethIfStormPacketType }
    ::= { ethIfStormTable 1 }

EthIfStormEntry ::=
    SEQUENCE {
	ethIfStormCnfgIdx	 Unsigned32,
	ethIfStormIfIdx 	 Unsigned32,
	ethIfStormDirection     INTEGER,
	ethIfStormPacketType       BITS,
	ethIfStormCtrlEnable    INTEGER,
	ethIfStormMaxRate    Unsigned32
	}

ethIfStormCnfgIdx OBJECT-TYPE
     SYNTAX Unsigned32 (1..255)
     MAX-ACCESS not-accessible
     STATUS current
     DESCRIPTION
     "This attribute indicates the Idx of the Cnfg(1..255) being 
      accessed ; Idx of 255 relates to the TmpCnfg."
     ::= {ethIfStormEntry 1}

ethIfStormIfIdx     OBJECT-TYPE
      SYNTAX  Unsigned32
      MAX-ACCESS  not-accessible
      STATUS  current
      DESCRIPTION
      "A unique index of the ethernet interface/port."
      ::=  {ethIfStormEntry 2}

ethIfStormDirection OBJECT-TYPE
    SYNTAX		INTEGER {
		all			(1),
		ingress		(2),
		egress		(3)
	}
    MAX-ACCESS	not-accessible
    STATUS		current
    DESCRIPTION
    "This object indicates the port's Storm Direction."
    ::= { ethIfStormEntry 3 }

ethIfStormPacketType  OBJECT-TYPE
     SYNTAX   BITS
     {
	   unknownUnicast (0), --Flooded Unicast
	   broadcast      (1),
	   multicast      (2)
     }
     MAX-ACCESS  not-accessible
     STATUS  current
     DESCRIPTION
	 "Packet Type on which Storming operations will be performed." 
     ::= { ethIfStormEntry 4 }

ethIfStormCtrlEnable OBJECT-TYPE
     SYNTAX  INTEGER 
	{
       disable       (2),
       enable  	     (3)
    }
     MAX-ACCESS  read-write
     STATUS  current
     DESCRIPTION
     "This object indicates if the Storm Controling is Enabled or Disabled 
      for the relevant entry."
    ::= { ethIfStormEntry 5 }

ethIfStormMaxRate OBJECT-TYPE
    SYNTAX		Unsigned32
    MAX-ACCESS	read-write
    STATUS		current
    DESCRIPTION
    "This object indicates the Maximum Rate at which Storming packets are forwarded, 
     in Kbps.For some devices the units are PPS(Packets Per Second ) or kilobytes 
     per second."      
    ::= { ethIfStormEntry 6 }

ethIfOamEfm OBJECT IDENTIFIER ::= { ethIf 6 }
-- ETH OAM EFM: 802.3ah

dot3OamEvents OBJECT IDENTIFIER ::= { ethIfOamEfm 0 }

dot3OamOperStatusChange  NOTIFICATION-TYPE
	OBJECTS     { dot3OamOperStatus }
	STATUS		current
	DESCRIPTION     
	"This trap is sent when OAM EFM Link goes Up or Down.
	 Up - is considered when dot3OamOperStatus value changes to operational(9) 
	      from any other value.
	 Down - is considered when dot3OamOperStatus value changes from operational(9) 
	      to any other value."
     ::= { dot3OamEvents 1 }

dot3OamPeerEvent  NOTIFICATION-TYPE
	OBJECTS     { dot3OamXPeerState }
	STATUS		current
	DESCRIPTION     
	"This trap is sent when value of dot3OamXPeerState changes from any value
	 to one of the following values: linkFault, dyingGasp, criticalEvent.
	 This trap has no recovery (clearing value)."
     ::= { dot3OamEvents 2 }

dot3OamDescrTable OBJECT-TYPE
    SYNTAX      SEQUENCE OF Dot3OamDescrEntry
    MAX-ACCESS  not-accessible
    STATUS      current
    DESCRIPTION
     "This table supports definitions of Descriptors (profiles) of OAM EFM Links."
   ::= {ethIfOamEfm 1}

dot3OamDescrEntry OBJECT-TYPE
    SYNTAX      Dot3OamDescrEntry
    MAX-ACCESS  not-accessible
    STATUS      current
    DESCRIPTION
    "Each entry corresponds to a single OAM EFM Descriptor (profile).  
     Each Descriptor contains a set of OAM EFM Link configuration
     parameters.  The configuration parameters are applied to the 
     OAM EFM Links referencing this Descriptor (see dot3OamXDescrId
     object).  Descriptors may be created/deleted using the row creation/deletion 
     mechanism via dot3OamDescrRowStatus. If an active entry is referenced 
     in dot3OamXDescrId, the entry MUST remain active until all references are removed."
    INDEX { dot3OamDescrId }
    ::= { dot3OamDescrTable 1 }

Dot3OamDescrEntry ::=
     SEQUENCE {
     dot3OamDescrId            Unsigned32,
     dot3OamDescrRowStatus     RowStatus,
     dot3OamDescrMode          INTEGER,
	 dot3OamDescrLbRxOperation INTEGER,
     dot3OamDescrRateLimit     Unsigned32
     }

dot3OamDescrId OBJECT-TYPE
    SYNTAX      Unsigned32 (1..4294967295)
    MAX-ACCESS  not-accessible
    STATUS      current
    DESCRIPTION
    "This object is the unique index associated with this Descriptor (profile).
     Entries in this table are referenced via the object dot3OamXDescrId
     in dot3OamXEntry."
    ::= { dot3OamDescrEntry 1 }

dot3OamDescrRowStatus OBJECT-TYPE
    SYNTAX      RowStatus
    MAX-ACCESS  read-create
    STATUS      current
    DESCRIPTION
    "This object controls creation/deletion of the associated entry in this table 
     per the semantics of RowStatus.  If an active entry is referenced in 
     dot3OamXDescrId, the	entry MUST remain active until all references are removed."
    ::= { dot3OamDescrEntry 2 }

dot3OamDescrMode OBJECT-TYPE
    SYNTAX  INTEGER {
      passive(1),
      active (2)
                    }
    MAX-ACCESS  read-create
    STATUS      current
    DESCRIPTION
    "This object controls the mode of OAM operation for an Ethernet-like interface
     referencing this Descriptor.  
     OAM on Ethernet interfaces may be in 'active' mode or 'passive' mode.  
     These two modes differ in that active mode provides additional capabilities 
     to initiate monitoring activities with the remote OAM peer entity, while
     passive mode generally waits for the peer to initiate OAM actions with it.  
     As an example, an active OAM entity can put the remote OAM entity in a 
     loopback state, where a passive OAM entity cannot."
    ::= { dot3OamDescrEntry 3 }

dot3OamDescrLbRxOperation OBJECT-TYPE
     SYNTAX      INTEGER { 
       ignore(1), 
       process(2) 
                         }
     MAX-ACCESS  read-create
     STATUS      current
     DESCRIPTION
     "Since OAM loopback is a disruptive operation (user traffic does not pass), 
      this object provides a mechanism to provide control: whether received OAM 
      loopback commands are	processed or ignored, for the OAM Link referencing
      this Descriptor.  
      When the value is ignore(1),  received loopback commands are ignored.  
      When the value is process(2),	received loopback commands are processed.  
      The default value is to ignore loopback commands (ignore(1))."
     ::= { dot3OamDescrEntry 4 }

dot3OamDescrRateLimit OBJECT-TYPE
    SYNTAX      Unsigned32
    MAX-ACCESS  read-create
    STATUS      current
    DESCRIPTION
    "This object defines how many OAM frames can be sent per second (maximum)
     for an OAM EFM Link referencing this Descriptor."
    ::= { dot3OamDescrEntry 5 }

dot3OamXTable OBJECT-TYPE
    SYNTAX      SEQUENCE OF Dot3OamXEntry
    MAX-ACCESS  not-accessible
    STATUS      current
    DESCRIPTION
    "This table is an extension of dot3OamTable of standard DOT3-OAM-MIB."
    ::= { ethIfOamEfm 2 }

dot3OamXEntry OBJECT-TYPE
    SYNTAX     Dot3OamXEntry
    MAX-ACCESS not-accessible
    STATUS     current
    DESCRIPTION
      "An entry in dot3OamXTable."
    AUGMENTS { dot3OamEntry }
        ::= { dot3OamXTable 1 }

Dot3OamXEntry ::=
    SEQUENCE {
      dot3OamXDescrId   Unsigned32,
	  dot3OamXPeerState INTEGER
             }

dot3OamXDescrId OBJECT-TYPE
    SYNTAX      Unsigned32 (1..4294967295)
    MAX-ACCESS  read-write
    STATUS      current
    DESCRIPTION
    "This object points to an entry of dot3OamDescrTable (dot3OamDescrId), 
     which defines part of the configuration parameters for this OAM EFM Link.
     As long as one of the OAM EFM Links refers an entry in the dot3OamDescrTable,
     this entry cannot be removed.
     When an OAM EFM Link supports this object (RW), the standard MIB objects of:
     dot3OamMode (parallel to dot3OamDescrMode) and dot3OamLoopbackIgnoreRx
	 (parallel to dot3OamDescrLbRxOperation) will be supported by Agent RO."
    ::= { dot3OamXEntry 1 }

dot3OamXPeerState OBJECT-TYPE
    SYNTAX  INTEGER {
	  unknown      (1),
      operational  (2),
      linkFault    (3),
	  dyingGasp    (4),
	  criticalEvent(5)
                    }
    MAX-ACCESS  read-only
    STATUS      current
    DESCRIPTION
    "This object reports the state of the Peer of the OAM EFM Link.
	 unknown - at the initialization of the device, or after Reset, when 
	           there is still no data about the peer's state. 
     operational - usually after unknown state, when device senses that
	           peer is OK.
     linkFault - Loss of Signal is detected by the receiver.
     dyingGasp - Unrecoverable condition has occurred (e.g power failure)
     criticalEvent - Unspecified Critical Event has occured."
    ::= { dot3OamXEntry 2 }


ethIfMacLayer OBJECT IDENTIFIER ::= {ethIf 7}

ethIfMacLayerEvents OBJECT IDENTIFIER ::= { ethIfMacLayer 0 }

ethIfSrcMacCtrlTable OBJECT-TYPE
    SYNTAX      SEQUENCE OF EthIfSrcMacCtrlEntry
    MAX-ACCESS  not-accessible
    STATUS      current
    DESCRIPTION
     "This table supports source MAC addresses control parameters per interface.
      Source MAC control will be used mainly for security. Only packets with certain source MAC
      Addresses will be allowed to access the device. The source MAC addresses can be static or learned.
      The static addresses will be defined by the user in another table: ethIfSrcMacCtrlAddrTable.
      The learned addresses will exist in the ethIfSrcMacCtrlAddrTable as well."
   ::= {ethIfMacLayer 1}

ethIfSrcMacCtrlEntry OBJECT-TYPE
    SYNTAX      EthIfSrcMacCtrlEntry
    MAX-ACCESS  not-accessible
    STATUS      current
    DESCRIPTION
    "An entry in the table."
    INDEX { ethIfSrcMacCtrlIndex, ethIfSrcMacCtrlIdx2 }
    ::= { ethIfSrcMacCtrlTable 1 }


EthIfSrcMacCtrlEntry ::=
     SEQUENCE {
     ethIfSrcMacCtrlIndex               Unsigned32,
	 ethIfSrcMacCtrlIdx2                Unsigned32,     
     ethIfSrcMacCtrl                    INTEGER,
	 ethIfSrcMacCtrlMaxPermitAddr       Unsigned32,
	 ethIfSrcMacCtrlCurNumPermitAddr    Unsigned32,
     ethIfSrcMacCtrlFlushAddrCmd        INTEGER,
	 ethIfSrcMacCtrlAging               Unsigned32,
	 ethIfSrcMacCtrlLocking             INTEGER,
	 ethIfSrcMacCtrlViolationAction     INTEGER,
	 ethIfSrcMacCtrlLastViolatingAddr   MacAddress,
	 ethIfSrcMacCtrlPortStatus          INTEGER
     }

ethIfSrcMacCtrlIndex OBJECT-TYPE
      SYNTAX      Unsigned32
      MAX-ACCESS  not-accessible
      STATUS      current
      DESCRIPTION
        "The index of the MAC Layer interface supporting source MAC control feature. 
        It may be the ifIndex of the ETH/Bridge Port."
     ::= { ethIfSrcMacCtrlEntry 1 }

ethIfSrcMacCtrlIdx2 OBJECT-TYPE
      SYNTAX      Unsigned32
      MAX-ACCESS  not-accessible
      STATUS      current
      DESCRIPTION
        "A second index that can be used. For example: The VLAN ID for which the source MAC
         control feature is supported. When this index is not in use, its value will be: 9999." 
     ::= { ethIfSrcMacCtrlEntry 2 }

ethIfSrcMacCtrl OBJECT-TYPE
      SYNTAX      INTEGER
      {
	   disable	     (2),
	   enable		 (3)
      }				 
      MAX-ACCESS  read-write
      STATUS      current
      DESCRIPTION
        "Enable or disable the source MAC control on the current interface.
		 The device should not enable source MAC control if for the current interface there
		 are more than ethIfSrcMacCtrlMaxPermitAddr addresses in the ethIfSrcMacCtrlAddrTable.
		 Default value will be: disable (2)."
     ::= { ethIfSrcMacCtrlEntry 3 }

ethIfSrcMacCtrlMaxPermitAddr OBJECT-TYPE
      SYNTAX      Unsigned32
      MAX-ACCESS  read-write
      STATUS      current
      DESCRIPTION
        "This is the maximum number of permitted MAC addresses (static and learned) for the
         current interface."
     ::= { ethIfSrcMacCtrlEntry 4 }

ethIfSrcMacCtrlCurNumPermitAddr OBJECT-TYPE
      SYNTAX      Unsigned32
      MAX-ACCESS  read-only
      STATUS      current
      DESCRIPTION
        "This is the number of source MAC addresses currently permitted for the
         current interface."
     ::= { ethIfSrcMacCtrlEntry 5 }

ethIfSrcMacCtrlFlushAddrCmd OBJECT-TYPE
      SYNTAX      INTEGER	   
	{
	  off (2),
	  on  (3)
	}
      MAX-ACCESS  read-write
      STATUS      current
      DESCRIPTION
        "When set to on (3) this command will erase all the learned addresses and invalid
         addresses of the selected interface in the ethIfSrcMacCtrlAddrTable.
         After operation is finished, Agent will turn the value to 'off'."
     ::= { ethIfSrcMacCtrlEntry 6 }

ethIfSrcMacCtrlAging OBJECT-TYPE
      SYNTAX      Unsigned32
      MAX-ACCESS  read-write
      STATUS      current
      DESCRIPTION
        "The timeout period in seconds for aging out dynamically learned source MAC addresses. 
         Valid Values:
         0 - disable
         10-1000000"
     ::= { ethIfSrcMacCtrlEntry 7 }

ethIfSrcMacCtrlLocking OBJECT-TYPE
      SYNTAX      INTEGER	   
	{
	  unlock (2),
	  lock   (3)
	}
      MAX-ACCESS  read-write
      STATUS      current
      DESCRIPTION
        "When set to lock (3) this command will lock the Source MAC Address learning.
         No more learned addresses will be added to the ethIfSrcMacCtrlAddrTable.
         When set to unlock (2) this command will unlock the Source MAC Address learning.
		 Learned addresses will be added to the ethIfSrcMacCtrlAddrTable but the number of
		 addresses in the table will not exceed ethIfSrcMacCtrlMaxPermitAddr.
		 Default value is: unlock (2)."
     ::= { ethIfSrcMacCtrlEntry 8 }

ethIfSrcMacCtrlViolationAction OBJECT-TYPE
      SYNTAX      INTEGER	   
	{
	  drop       (2),
	  dropNotify (3),
	  shutdown   (4)
	}
      MAX-ACCESS  read-write
      STATUS      current
      DESCRIPTION
      "Determines the action that the device will take upon security violation.        
       drop(2)       - the violating packets will be dropped.
       dropNotify (3)- the violating packets will be dropped and notifications
                       will be generated. Notifications may be for example:
                       SNMP Traps, Syslog messages and log file new entries.
       shutdown (4)  - the interface will be forced to shut down."
     ::= { ethIfSrcMacCtrlEntry 9 }

ethIfSrcMacCtrlLastViolatingAddr OBJECT-TYPE
      SYNTAX      MacAddress	   
      MAX-ACCESS  read-write
      STATUS      current
      DESCRIPTION
      "This object indicates the last MAC address that violated the security
       on the current interface. If no violation, the agent will return:
       00-00-00-00-00-00 ."
     ::= { ethIfSrcMacCtrlEntry 10 }

ethIfSrcMacCtrlPortStatus OBJECT-TYPE
      SYNTAX      INTEGER	   
	{
	  shutdown       (2),
	  secureActive   (3),
	  secureInactive (4)
	}
      MAX-ACCESS  read-only
      STATUS      current
      DESCRIPTION
      "This object represents the operational status of the MAC Control feature
       on an interface.
       shutdown(2)       - This indicates that the port is shutdown due to security
                           violation.
       secureActive (3)  - This indicates that the MAC Control interface security
                           is operational and this interface is not shutdown due to
                           security violation.
	   secureInactive (4)- This indicates that the MAC Control is not operational."
       ::= { ethIfSrcMacCtrlEntry 11 }

									 

ethIfSrcMacCtrlAddrTable OBJECT-TYPE
    SYNTAX      SEQUENCE OF EthIfSrcMacCtrlAddrEntry
    MAX-ACCESS  not-accessible
    STATUS      current
    DESCRIPTION
    "This table shows which MAC Addresses are permitted when the source MAC control
     is enabled and which non permitted MAC Addresses attempted to access the
     current interface. It contains static source MAC Addresses as well as learned
     MAC Addresses. The user can configure Static permitted source MAC Addresses via this table."
     ::= {ethIfMacLayer 2}

ethIfSrcMacCtrlAddrEntry OBJECT-TYPE
    SYNTAX      EthIfSrcMacCtrlAddrEntry
    MAX-ACCESS  not-accessible
    STATUS      current
    DESCRIPTION
    "An entry in the table."
    INDEX {ethIfSrcMacCtrlAddrIndex, ethIfSrcMacCtrlAddr, ethIfSrcMacCtrlAddrIdx3 }
    ::= { ethIfSrcMacCtrlAddrTable 1 }

EthIfSrcMacCtrlAddrEntry ::=
     SEQUENCE {
     ethIfSrcMacCtrlAddrIndex          Unsigned32,
	 ethIfSrcMacCtrlAddr               MacAddress,
	 ethIfSrcMacCtrlAddrIdx3           Unsigned32,
     ethIfSrcMacCtrlAddrRowStatus      INTEGER,
     ethIfSrcMacCtrlAddrStatus         INTEGER
     }


ethIfSrcMacCtrlAddrIndex OBJECT-TYPE
      SYNTAX      Unsigned32
      MAX-ACCESS  not-accessible
      STATUS      current
      DESCRIPTION
        "The index of the interface for which the source MAC addresses exist in this table. 
        It may be the ifIndex of the ETH/Bridge Port."
     ::= { ethIfSrcMacCtrlAddrEntry 1 }

ethIfSrcMacCtrlAddr  OBJECT-TYPE
      SYNTAX      MacAddress
      MAX-ACCESS  not-accessible
      STATUS      current
      DESCRIPTION
        "A unicast source MAC address that was learned or statically configured for the current
         interface. Packets with this source MAC address will be accepted by the device."
     ::= { ethIfSrcMacCtrlAddrEntry 2 }

ethIfSrcMacCtrlAddrIdx3 OBJECT-TYPE
      SYNTAX      Unsigned32
      MAX-ACCESS  not-accessible
      STATUS      current
      DESCRIPTION
        "A third index that can be used. For example: The VLAN ID for which the source MAC control
         feature is supported. When this index is not in use, its value will be: 9999." 
     ::= { ethIfSrcMacCtrlAddrEntry 3 }

ethIfSrcMacCtrlAddrRowStatus OBJECT-TYPE
      SYNTAX  INTEGER
	       {  active (1),
		      createAndGo (4),
		      destroy (6) }     
      MAX-ACCESS  read-write
      STATUS      current
      DESCRIPTION
        "This MIB object will be used in order to create/delete a static row
         or delete an address that is not allowed to access the current interface
         (ethIfSrcMacCtrlAddrStatus= invalid(2)).
		 Device will add the learned addresses to this table.
         It will not be possible to add a new static entry to this table while the
         number of existing rows is equal or more than ethIfSrcMacCtrlMaxPermitAddr.
         When ethIfSrcMacCtrl = enabled (3), the device will add learned entries only
         up to ethIfSrcMacCtrlMaxPermitAddr."
     ::= { ethIfSrcMacCtrlAddrEntry 4 }

ethIfSrcMacCtrlAddrStatus OBJECT-TYPE
      SYNTAX      INTEGER
       {                    
         invalid (2),
         learned(3),
         mgmt(5)  -- static
       }
      MAX-ACCESS  read-only
      STATUS      current
      DESCRIPTION
        "The status of this entry.  The meanings of the values are:
         invalid (2) - the current address is not allowed to access this interface.		 	  
		 learned(3) - the current address was learned.
		 mgmt (5) - the current address is static. It may exist in the MAC Table."
     ::= { ethIfSrcMacCtrlAddrEntry 5 }

-- ethIfMacLayerNotifications

ethIfMacAccessViolation NOTIFICATION-TYPE
    OBJECTS     {ifDescr, ethIfSrcMacCtrlLastViolatingAddr}
	STATUS		current
	DESCRIPTION     
	"This trap indicates that an Access Violation occurred."
     ::= { ethIfMacLayerEvents 1 }
-- 
-- file :D:\Synergy\WorkArea\545\mib_rad\txt\tsa.txt
-- 

--Title:  RAD's WAN TSA (Time-Slot Assignment) MIB
--By:     Smadar Tauber
--Date :  30.11.1998

--Last Update: 28/11/04   
--By: Smadar Tauber
--File:  v:\doc\rdv\mib\ver525\tsa.txt

--***********************************************************************
--Products that use this file WITHOUT the MPMX.TXT file,have to add the
--following definitions to their *.pkb files:
--
--wanGen   OBJECT IDENTIFIER ::= {radWan 1}
--agnWanGen   OBJECT IDENTIFIER ::= {wanGen 2}
--agnSystemTs      OBJECT IDENTIFIER ::= {agnWanGen 11}
--***********************************************************************

--
-- TS Assignment Table from system point of view
--

agnTsTable  OBJECT-TYPE
     SYNTAX SEQUENCE OF AgnTsEntry
     MAX-ACCESS not-accessible
     STATUS  current
     DESCRIPTION
     "The write operation into the Table Objects is valid only
      to the TmpCnfg entry."
     ::= { agnSystemTs 1}

agnTsEntry OBJECT-TYPE
      SYNTAX AgnTsEntry
      MAX-ACCESS not-accessible
      STATUS current
	DESCRIPTION  "An entry in table."
	INDEX {agnTsCnfgIdx, agnTsSltIdx, agnTsPrtIdx, agnTsIdx,
             agnTsBitIdx, agnTsConSltIdx, agnTsConPrtIdx, agnTsConIdx }
      ::= { agnTsTable 1}

AgnTsEntry ::=
      SEQUENCE {
     agnTsCnfgIdx   Integer32,
     agnTsSltIdx    INTEGER,
     agnTsPrtIdx    Integer32,
     agnTsIdx       Integer32,
     agnTsBitIdx    Integer32,
     agnTsConSltIdx INTEGER,
     agnTsConPrtIdx Integer32,
     agnTsConIdx    Integer32,
     agnTsType      INTEGER,
     agnTsRowStatus RowStatus,
	 agnTsDirection INTEGER
      }

agnTsCnfgIdx OBJECT-TYPE
      SYNTAX  Integer32 (1..255)
      MAX-ACCESS  read-only
      STATUS  current
      DESCRIPTION
      "This attribute indicates the Idx of the Cnfg (1..100) being
       accessed.
       Idx 255 relates to the TmpCnfg. "
      ::= { agnTsEntry 1}

agnTsSltIdx OBJECT-TYPE
      SYNTAX  INTEGER
     { clA   (3),
	   clB   (4),
       io1   (5),
       io2   (6),
       io3   (7),
       io4   (8),
       io5   (9),
       io6  (10),
       io7  (11),
       io8  (12),
       io9  (13),
       io10 (14),
       io11 (15),
       io12 (16),
       io13 (17),
       io14 (18),
       io15 (19),
       notApplicable(255)
     }
      MAX-ACCESS  read-only
      STATUS  current
      DESCRIPTION
      "This attribute indicates a unique  slot  position where
       the card is inserted."
      ::= { agnTsEntry 2}

agnTsPrtIdx OBJECT-TYPE
      SYNTAX  Integer32
      MAX-ACCESS  read-only
      STATUS  current
      DESCRIPTION
      "This attribute indicates a unique external or internal port number.
       For MP-2100, the valid values will be (for MLs only):
       -  exPrt1(1)..exPrt8(8) 
       -  inPrt1(101)..inPrt8(108).
       For other products' index see their specification."
      ::= { agnTsEntry 3}

agnTsIdx OBJECT-TYPE
      SYNTAX  Integer32 (1..32)
      MAX-ACCESS  read-only
      STATUS  current
      DESCRIPTION
      "This attribute indicates a unique index for TS (Time-Slot).
       - for T1 ports - 1..24, Fbit(25)
       - for E1 ports - 1..31
       - for HDSL ports - 1..32 ; 32 will represent TS0."
      ::= { agnTsEntry 4}

agnTsBitIdx OBJECT-TYPE
      SYNTAX  Integer32
      MAX-ACCESS  read-only
      STATUS  current
      DESCRIPTION
      "This attribute indicates a unique index for the Bit
       of each TS (Time-Slot).
       1..8 - Bit 1.. Bit 8
       255  - notApplicable
       This object is applicable only in Split Time-Slot cases."
      ::= { agnTsEntry 5}

agnTsConSltIdx OBJECT-TYPE
      SYNTAX  INTEGER
   {   clA   (3),
   	   clB   (4),
       io1   (5),
       io2   (6),
       io3   (7),
       io4   (8),
       io5   (9),
       io6  (10),
       io7  (11),
       io8  (12),
       io9  (13),
       io10 (14),
       io11 (15),
       io12 (16),
       io13 (17),
       io14 (18),
       io15 (19),
       notApplicable(255)
       }
      MAX-ACCESS  read-only
      STATUS  current
      DESCRIPTION
      "This attribute indicates a unique slot position In the Mux
       where the TS is routed to."
      ::= { agnTsEntry 6}

agnTsConPrtIdx OBJECT-TYPE
      SYNTAX  Integer32
      MAX-ACCESS  read-only
      STATUS  current
      DESCRIPTION
      "This attribute indicates a unique port id the TS is 
       routed to.
	   notApplicable - when agnTsType=mng or spare
       For MP-2100/2200:
       exPrt1    (1) .. exPrt16  (16) ,  notApplicable(100),
       inPrt1  (101) .. inPrt48 (148).
       For other products' index see their specification. "
      ::= { agnTsEntry 7}

agnTsConIdx OBJECT-TYPE
      SYNTAX  Integer32    (1..255)
      MAX-ACCESS  read-only
      STATUS  current
      DESCRIPTION
      "This attribute indicates a unique TS number the Src TS is 
       routed to.
	   Valid values:
       - for T1 ports - 1..24, Fbit(25)
       - for E1 ports - 1..31
       - for HDSL ports - 1..32 ; 32 will represent TS0.
       - notApplicable - 255 (for ports that don't have TSs)."
      ::= { agnTsEntry 8}

agnTsType  OBJECT-TYPE
      SYNTAX  INTEGER
      {
       unknown   (1),
       voice     (2),
       data      (3),
       vcMP      (4),
       mng       (6),
	   spare     (7),
	   reserved  (8),
	   dChannel  (9)     
      }
      MAX-ACCESS  read-create
      STATUS  current
      DESCRIPTION
      "Time-Slot Type - regarding its connection and media type.
       voice, data, vcMP - connected and the media is specified.
       mng - management. This TS is Dedicated to Management (not
             disconnected, but not connected to another port).
       spare - applicable for ML-20, ML-20N and MSL cards only. 
             These TSs should be reserved for future connection, 
             though at the moment are not connected.
       reserved - these TSs are not connected, but they are Reserved for 
             Protection (back-up) of a certain Path. Therefore, should 
             NOT be used for connection of other Paths.
       dChannel - is used only when the TS is connected to a V5.1 ML (Bypass)
                  and it contains ISDN D Channel data. In this case, 
                  agnTsConSltIdx, agnTsConPrtIdx and agnTsConIdx, will
                  be 'notApplicable', since no TS is assigned for D Ch in V5.1 ML."
   ::= { agnTsEntry 9}

agnTsRowStatus OBJECT-TYPE
      SYNTAX  RowStatus
      MAX-ACCESS  read-create
      STATUS  current
      DESCRIPTION
      "This attribute allows to create/delete a row in this table.
        For creating a row, the NMS should set
        agnTsRowStatus.255.id2.id3.id4.id5.id6.id7.id8 = active(1).
        For destroying a row, the NMS should set:
        agnTsRowStatus.255.id2.id3.id4.id5.id6.id7.id8 = destroy(6).
        Only rows with status active(1) are relevant.
        The only possible supported RowStatus values are
        active (1) and destroy (6)."
      ::= { agnTsEntry 10}

agnTsDirection  OBJECT-TYPE
      SYNTAX  INTEGER
      {
       notApplicable (1),
       rx            (2),
       tx            (3),
       both          (4),
       bcastSrc      (5),
	   bcastDst      (6),
	   internal      (7)
      }
      MAX-ACCESS  read-create
      STATUS  current
      DESCRIPTION
      "Direction of the connection. This parameter is especially important
	   when in MP a Selected Port is connected to a Connected Port that has 
	   no TSs, so it doesn't appear in the TS Assignment for the first 5 indexes.
	   notApplicable - for products that do not support this object	or for
	        certain TS Types (for example: mng, spare)
       rx - the Selected Port only Receives from the Connected Port (the Selected Port 
            will appear in the first 5 indexes).
       tx - the Selected Port only Transmits to the Connected Port (the Selected Port 
            will appear in the first 5 indexes). Nothing is received back.
       both - the Selected Port Receives and Transmits to the Connected Port 
           (the Selected Port will appear in the first 5 indexes).
       bcastSrc - the ML is a Broadcast-Bidirectional Source. It Transmits to
            one or several IO Ports (including the one that appears in the last
            3 indexes) and sometimes receives.
            The Port that responds is dynamic (it can be another each time).
            The ML will appear in the first 5 indexes.
       bcastDst - the ML is a Broadcast-Bidirectional Destination. Therefore,
             it Receives and sometimes Transmits.  The ML will appear in the
             first 5 indexes.
       internal - for connection of TSs internally, within the same card. Such an
             assignment has no effect on the external TS connections of the same
             TS. A TS can be connected with 'internal' direction to a port
             of the same card and at the same time, connected by another direction
             to ports (and TSs) of other cards."
      ::= { agnTsEntry 11}

-- 
-- file :D:\Synergy\WorkArea\545\mib_rad\txt\sps5.txt
-- 

-- Title:   PS MIB
--
--
-- Version:  1.0
-- Date:       February  1, 95
-- By:         Debby Koren
-- Updated:  Orly Nicklass, Smadar Tauber, Yair Arian, Liora Gafni
-- Last update: 19-Sep-06
-- By:	        Ilana Schvetz

-- Comments:  This is the Packet Switching branch in the RAD MIB



--	  X121Address ::= OCTET STRING (SIZE(0..17))
	   -- 0 to 17 bytes in length containing the ASCII
	   -- characters [0-9], each octet contains one digit
	   -- of the address.

-- radPS        OBJECT IDENTIFIER ::= { rad 8 }

-- The groups in this MIB are the PS System Group, the Async Group, the Link Table, X.25 Group,
-- HDLC Table, STM Table.   Whenever an object appears twice with only the final
-- character in the object name differing, the object whose name ends with S is read-write, and represents
-- a scratch value that will take effect upon an activate imperitive action.  The object whose name ends
-- with A represents the current active value and is read-only.   This was done to protect the user against
-- inadvertantly disturbing active communications and to allow switchover to a different set of parameters
-- in real time.

-- The PS System Group contains all the PS system wide cofiguration parameters
-- and the Routing Table


pktSwchSystem    OBJECT IDENTIFIER ::= { radPS 1}

pktSwchSysParam  OBJECT IDENTIFIER ::= { pktSwchSystem 1 }

pktSwchSysSParam  OBJECT IDENTIFIER ::= { pktSwchSysParam 1 }

pktSwchSysX28PromptS  OBJECT-TYPE
    SYNTAX DisplayString (SIZE (0..10))
    MAX-ACCESS  read-write
    STATUS  current
    DESCRIPTION
	"This specifies a different PAD prompt, instead of the standard default character, the *.
		 Up to 10 characters can be entered."
    ::= { pktSwchSysSParam 1 }

pktSwchSysHeraldS  OBJECT-TYPE
    SYNTAX DisplayString (SIZE (0..32))
    MAX-ACCESS  read-write
    STATUS  current
    DESCRIPTION
	"This specifies the PAD herald message for the SPS-6 and SPS-12.  Up to 32 characters
		can be entered.  Other devices will return a zero length octet string and will send an error
		 if this object is set to a string of any other length."
    ::= { pktSwchSysSParam 2 }

pktSwchSysBulletinS  OBJECT-TYPE
    SYNTAX DisplayString (SIZE (0..32))
    MAX-ACCESS  read-write
    STATUS  current
    DESCRIPTION
	"This specifies the PAD bulletin message.  Up to 32 characters can be entered."
    ::= { pktSwchSysSParam 3 }

pktSwchSysComPortSubAddS  OBJECT-TYPE
    SYNTAX Integer32 (0..255)
    MAX-ACCESS  read-write
    STATUS  current
    DESCRIPTION
	"This is the scratch command port with the desired subaddress."
    ::= { pktSwchSysSParam 4 }


pktSwchSysComPortAltSubAddS  OBJECT-TYPE
    SYNTAX Integer32 (0..255)
    MAX-ACCESS  read-write
    STATUS  current
    DESCRIPTION
	"This configures the command port with the second subaddress."
    ::= { pktSwchSysSParam 5 }

pktSwchSysInnerCommLenS  OBJECT-TYPE
    SYNTAX Integer32 (1..5)
    MAX-ACCESS  read-write
    STATUS  current
    DESCRIPTION
	"This specifies the address length in digits for Inner Communication."
    ::= {  pktSwchSysSParam 6 }

pktSwchSysXOnCharS OBJECT-TYPE
    SYNTAX Integer32 (0..127)
    MAX-ACCESS  read-write
    STATUS  current
    DESCRIPTION
	"The ASCII code of the software flow control character that will be used to start/renew the data
		 transfer."
    ::= {  pktSwchSysSParam 7 }


pktSwchSysXOffCharS OBJECT-TYPE
    SYNTAX Integer32 (0..127)
    MAX-ACCESS  read-write
    STATUS  current
    DESCRIPTION
	"The ASCII code of the software flow control character that will be used to stop the data
		 transfer."
    ::= {  pktSwchSysSParam 8 }

pktSwchSysMaxLcnS OBJECT-TYPE
    SYNTAX Integer32
    MAX-ACCESS  read-write
    STATUS  current
    DESCRIPTION
	"The maximum number of LCNs on the device."
    ::= {  pktSwchSysSParam 9 }


pktSwchSysMaxAIDS OBJECT-TYPE
    SYNTAX Integer32
    MAX-ACCESS  read-write
    STATUS  current
    DESCRIPTION
	"The maximum number of AIDs on the device."
    ::= {  pktSwchSysSParam 10 }

pktSwchSysDeviceIdS OBJECT-TYPE
    SYNTAX DisplayString
    MAX-ACCESS  read-write
    STATUS  current
    DESCRIPTION
	"The device Id."
    ::= {  pktSwchSysSParam 11 }

pktSwchSysDtrPollPeriodS OBJECT-TYPE
    SYNTAX Integer32 (300..20000)
    MAX-ACCESS  read-write
    STATUS  current
    DESCRIPTION
	"Polling interval for DTR signal, in miliseconds. DTR signal 
	 may be used as trigger	for opening and closing calls.
	 The value should be Set in steps of 50 msec, else it will be
	 rounded to the nearest 50 msec multiple (e.g 380 will be rounded to 400).
	 Default value: 3000 msec."
    ::= {  pktSwchSysSParam 12 }


pktSwchSysAParam  OBJECT IDENTIFIER ::= { pktSwchSysParam 2 }

pktSwchSysX28PromptA  OBJECT-TYPE
    SYNTAX DisplayString (SIZE (0..10))
    MAX-ACCESS  read-only
    STATUS  current
    DESCRIPTION
	"This specifies the active PAD prompt."
    ::= { pktSwchSysAParam 1 }

pktSwchSysHeraldA  OBJECT-TYPE
    SYNTAX DisplayString (SIZE (0..32))
    MAX-ACCESS  read-only
    STATUS  current
    DESCRIPTION
	"This specifies the active PAD herald message for the SPS-6 and SPS-12.  Other devices will
		return a zero length string."
    ::= { pktSwchSysAParam 2 }

pktSwchSysBulletinA  OBJECT-TYPE
    SYNTAX DisplayString (SIZE (0..32))
    MAX-ACCESS  read-only
    STATUS  current
    DESCRIPTION
	"This indicates the active PAD bulletin message."
    ::= { pktSwchSysAParam 3 }

pktSwchSysComPortSubAddA  OBJECT-TYPE
    SYNTAX Integer32 (0..255)
    MAX-ACCESS  read-only
    STATUS  current
    DESCRIPTION
	"This is the active command port with the desired subaddress."
    ::= { pktSwchSysAParam 4 }

pktSwchSysComPortAltSubAddA  OBJECT-TYPE
    SYNTAX Integer32 (0..255)
    MAX-ACCESS  read-only
    STATUS  current
    DESCRIPTION
	"This is the active command port with the second subaddress."
    ::= {  pktSwchSysAParam 5 }


pktSwchSysInnerCommLenA  OBJECT-TYPE
    SYNTAX Integer32 (1..5)
    MAX-ACCESS  read-only
    STATUS  current
    DESCRIPTION
	"This specifies the active address length in digits for Inner Communication."
    ::= {  pktSwchSysAParam 6 }

pktSwchSysXOnCharA OBJECT-TYPE
    SYNTAX Integer32 (0..127)
    MAX-ACCESS  read-only
    STATUS  current
    DESCRIPTION
	"The activeASCII code of the software flow control character that is used to start/renew the data
		 transfer."
    ::= {  pktSwchSysAParam 7 }

pktSwchSysXOffCharA OBJECT-TYPE
    SYNTAX Integer32 (0..127)
    MAX-ACCESS  read-only
    STATUS  current
    DESCRIPTION
	"The active ASCII code of the software flow control character that is used to stop the data
		 transfer."
    ::= {  pktSwchSysAParam 8 }

pktSwchSysMaxLcnA OBJECT-TYPE
    SYNTAX Integer32
    MAX-ACCESS  read-only
    STATUS  current
    DESCRIPTION
	"The active maximum number of LCNs on the device."
    ::= {  pktSwchSysAParam 9 }

pktSwchSysMaxAIDA OBJECT-TYPE
    SYNTAX Integer32
    MAX-ACCESS  read-only
    STATUS  current
    DESCRIPTION
	"The active maximum number of AIDs on the device."
    ::= {  pktSwchSysAParam 10 }

pktSwchSysDeviceIdA OBJECT-TYPE
    SYNTAX DisplayString
    MAX-ACCESS  read-only
    STATUS  current
    DESCRIPTION
	"The device Id."
    ::= {  pktSwchSysAParam 11 }

pktSwchSysDtrPollPeriodA OBJECT-TYPE
    SYNTAX Integer32 (300..20000)
    MAX-ACCESS  read-only
    STATUS  current
    DESCRIPTION
	"Polling interval for DTR signal, in miliseconds. DTR signal 
	 may be used as trigger	for opening and closing calls.
	 The value is in steps of 50 msec; if user sets it differently, it is
	 rounded to the nearest 50 msec multiple (e.g 380 will be rounded to 400).
	 Default value: 3000 msec."
    ::= {  pktSwchSysAParam 12 }



pktSwchSysEvRepS  OBJECT IDENTIFIER ::= { pktSwchSysParam 3 }

pktSwchSysEvRepAdd1S  OBJECT-TYPE
    SYNTAX DisplayString
    MAX-ACCESS  read-write
    STATUS  current
    DESCRIPTION
	"This specifies the X.25 address to which the reports selected by means of
		 pktSwchSysEvRepMask1S and pktSwchSysEvRepPeriod1S will be sent."
    ::= { pktSwchSysEvRepS 1 }

pktSwchSysEvRepAdd2S  OBJECT-TYPE
    SYNTAX DisplayString
    MAX-ACCESS  read-write
    STATUS  current
    DESCRIPTION
	"This specifies the X.25 address to which the reports selected by means of
		 pktSwchSysEvRepMask2S and pktSwchSysEvRepPeriod2S will be sent."
    ::= { pktSwchSysEvRepS 2 }

pktSwchSysEvRepMask1S  OBJECT-TYPE
    SYNTAX Integer32 (0..15)
    MAX-ACCESS  read-write
    STATUS  current
    DESCRIPTION
	"This specifies the conditions on which reports are sent to the address specified in
		 pktSwchSysEvRepAdd1S.  The value is a sum of values (powers of two), where each
		 value in the sum represents a condition.  The values that may be included in the sum and
		 their meanings are:
		0 Disable event reports
		1 Send report when SYNC status has changed
		2 Send report when RTS status has changed
		4 Send report at Power On (Reset)
		8 Report charging information at CLR."
    ::= { pktSwchSysEvRepS 3 }

pktSwchSysEvRepPeriod1S  OBJECT-TYPE
    SYNTAX Integer32 (0..255)
    MAX-ACCESS  read-write
    STATUS  current
    DESCRIPTION
        "This specifies the time interval in minutes at which periodic
reports are sent to the address specified in pktSwchSysEvRepAdd1S.  A value of
                 zero indicates that periodic reports are disabled." ::= {
    pktSwchSysEvRepS 4 }


pktSwchSysEvRepMask2S  OBJECT-TYPE
    SYNTAX Integer32 (0..15)
    MAX-ACCESS  read-write
    STATUS  current
    DESCRIPTION
	"This specifies the conditions on which reports are sent to the address specified in
		 pktSwchSysEvRepAdd2S.  The value is a sum of values (powers of two), where each
		 value in the sum represents a condition.  The values that may be included in the sum and
		  their meanings are:
		0 Disable event reports
		1 Send report when SYNC status has changed
		2 Send report when RTS status has changed
		4 Send report at Power On (Reset)
		8 Report charging information at CLR."
    ::= { pktSwchSysEvRepS 5 }

pktSwchSysEvRepPeriod2S  OBJECT-TYPE
    SYNTAX Integer32 (0..255)
    MAX-ACCESS  read-write
    STATUS  current
    DESCRIPTION
	"This specifies the time interval in minutes at which periodic reports are sent to
		 the address specified in pktSwchSysEvRepAdd2S.  A value of zero indicates that
		 periodic reports are disabled."
    ::= { pktSwchSysEvRepS 6 }


pktSwchSysEvRepRetryCntS  OBJECT-TYPE
    SYNTAX Integer32
	MAX-ACCESS read-write
	STATUS  current
	DESCRIPTION
	"Number of retries to send Event Reports to each port.
	 Possible values:
	 0     - Disable retry mechanism
	 1-255 - Number of retries "
	::= { pktSwchSysEvRepS 7 }

pktSwchSysEvRepRetryDelayS  OBJECT-TYPE
    SYNTAX Integer32
	MAX-ACCESS read-write
	STATUS  current
	DESCRIPTION
	"Time interval between retries (in minutes).
	 Valid values: 1-255 "
	::= { pktSwchSysEvRepS 8 }

pktSwchSysEvRepRetryOptionsS  OBJECT-TYPE
    SYNTAX Integer32
	MAX-ACCESS read-write
	STATUS  current
	DESCRIPTION
	"Event report options. The value is a sum of values (powers of
	two), where each value in the sum represents an option. The
	values that may be included in the sum and their meanings are:
	0 - No Options
	1 - Alternate Mode: Port 1 reports are readdressed to Port 2
	    on failure. (Port 2 mask is not used).
    2 - Condensed Format
	X - Any combination of the above values "
	::= { pktSwchSysEvRepS 9 }



pktSwchSysEvRepA  OBJECT IDENTIFIER ::= { pktSwchSysParam 4 }

pktSwchSysEvRepAdd1A  OBJECT-TYPE
    SYNTAX DisplayString
    MAX-ACCESS  read-only
    STATUS  current
    DESCRIPTION
	"This specifies the active X.25 address to which the reports selected by means of
		 pktSwchSysEvRepMask1A and pktSwchSysEvRepPeriod1A will be sent."
    ::= { pktSwchSysEvRepA 1 }

pktSwchSysEvRepAdd2A  OBJECT-TYPE
    SYNTAX DisplayString
    MAX-ACCESS  read-only
    STATUS  current
    DESCRIPTION
	"This specifies the active X.25 address to which the reports selected by means of
		 pktSwchSysEvRepMask2A and pktSwchSysEvRepPeriod2A will be sent."
    ::= { pktSwchSysEvRepA 2 }


pktSwchSysEvRepMask1A  OBJECT-TYPE
    SYNTAX Integer32 (0..15)
    MAX-ACCESS  read-only
    STATUS  current
    DESCRIPTION
	"This specifies the active conditions on which reports are sent to the address specified in
		 pktSwchSysEvRepAdd1A.  The value is a sum of values (powers of two), where each
		 value in the sum represents a condition.  The values that may be included in the sum and
		 their meanings are:
		0 Disable event reports
		1 Send report when SYNC status has changed
		2 Send report when RTS status has changed
		4 Send report at Power On (Reset)
	  	8 Report charging information at CLR."
    ::= { pktSwchSysEvRepA 3 }


pktSwchSysEvRepPeriod1A  OBJECT-TYPE
    SYNTAX Integer32 (1..255)
    MAX-ACCESS  read-only
    STATUS  current
    DESCRIPTION
	"This specifies the active time interval in minutes at which periodic reports are sent to
		 the address specified in pktSwchSysEvRepAdd1A.  A value of zero indicates that
		 periodic reports are disabled."
    ::= { pktSwchSysEvRepA 4 }

pktSwchSysEvRepMask2A  OBJECT-TYPE
    SYNTAX Integer32 (0..15)
    MAX-ACCESS  read-only
    STATUS  current
    DESCRIPTION
	"This specifies the active conditions on which reports are sent to the address specified in
		 pktSwchSysEvRepAdd2A.  The value is a sum of values (powers of two), where each
		 value in the sum represents a condition.  The values that may be included in the sum and
		  their meanings are:
		0 Disable event reports
		1 Send report when SYNC status has changed
		2 Send report when RTS status has changed
		4 Send report at Power On (Reset)
	  	8 Report charging information at CLR."
    ::= { pktSwchSysEvRepA 5 }

pktSwchSysEvRepPeriod2A  OBJECT-TYPE
    SYNTAX Integer32 (1..255)
    MAX-ACCESS  read-only
    STATUS  current
    DESCRIPTION
	"This specifies the active time interval in minutes at which periodic reports are sent to
		 the address specified in pktSwchSysEvRepAdd2A.  A value of zero indicates that
		 periodic reports are disabled."
    ::= { pktSwchSysEvRepA 6 }

pktSwchSysEvRepRetryCntA  OBJECT-TYPE
    SYNTAX Integer32
	MAX-ACCESS read-only
	STATUS  current
	DESCRIPTION
	"Number of retries to send Event Reports to each port.
	 Possible values:
	 0     - Disable retry mechanism
	 1-255 - Number of retries "
	::= { pktSwchSysEvRepA 7 }

pktSwchSysEvRepRetryDelayA  OBJECT-TYPE
    SYNTAX Integer32
	MAX-ACCESS read-only
	STATUS  current
	DESCRIPTION
	"Time interval between retries (in minutes).
	 Valid values: 1-255 "
	::= { pktSwchSysEvRepA 8 }

pktSwchSysEvRepRetryOptionsA  OBJECT-TYPE
    SYNTAX Integer32
	MAX-ACCESS read-only
	STATUS  current
	DESCRIPTION
	"Event report options. The value is a sum of values (powers of
	two), where each value in the sum represents an option. The
	values that may be included in the sum and their meanings are:
	0 - No Options
	1 - Alternate Mode: Port 1 reports are readdressed to Port 2
	    on failure. (Port 2 mask is not used).
    2 - Condensed Format
	X - Any combination of the above values "
	::= { pktSwchSysEvRepA 9 }


pktSwchSysGen  OBJECT IDENTIFIER ::= { pktSwchSysParam 5 }

pktSwchSysDate OBJECT-TYPE
    SYNTAX DisplayString
    MAX-ACCESS  read-write
    STATUS  current
    DESCRIPTION
	"This is used to update the date on the device."
    ::= {  pktSwchSysGen 1 }


pktSwchSysTime OBJECT-TYPE
    SYNTAX DisplayString
    MAX-ACCESS  read-write
    STATUS  current
    DESCRIPTION
	"This is used to update the time on the device."
    ::= {  pktSwchSysGen 2 }

pktSwchSysAction OBJECT-TYPE
    SYNTAX INTEGER {
       noOp(1),
       reset(2),
       resetStat(3),
       rearrangeNovram(4),
       setDefaultConfig(5)     }
    MAX-ACCESS  read-write
    STATUS  current
    DESCRIPTION
	"This is used to perform imperitive commands on the device.
	 The reset command resets the device with the scratch values."
    ::= {  pktSwchSysGen 3 }

pktSwchSysRamSize OBJECT-TYPE
    SYNTAX Integer32
    MAX-ACCESS  read-only
    STATUS  current
    DESCRIPTION
	"The RAM size on the device."
    ::= {  pktSwchSysGen 4 }

pktSwchSysNovramSize OBJECT-TYPE
    SYNTAX Integer32
    MAX-ACCESS  read-only
    STATUS  current
    DESCRIPTION
	"The NOVRAM size on the device."
    ::= {  pktSwchSysGen 5 }

pktSwchSysNovramUtil OBJECT-TYPE
    SYNTAX Integer32
    MAX-ACCESS  read-only
    STATUS  current
    DESCRIPTION
	"The NOVRAM utilization on the device."
    ::= {  pktSwchSysGen 6 }

pktSwchSysFreeDataBuff OBJECT-TYPE
    SYNTAX Integer32
    MAX-ACCESS  read-only
    STATUS  current
    DESCRIPTION
	"The free data buffers on the device."
    ::= {  pktSwchSysGen 7 }

pktSwchSysMinDataBuffInPool OBJECT-TYPE
    SYNTAX Integer32
    MAX-ACCESS  read-only
    STATUS  current
    DESCRIPTION
	"The minimum data buffers in the pool on the device."
    ::= {  pktSwchSysGen 8 }

pktSwchSysProtocols OBJECT-TYPE
    SYNTAX Integer32
    MAX-ACCESS  read-only
    STATUS  current
    DESCRIPTION
	"The protocols the device can support. The value is a sum of values
	 (powers of two), where each value in the sum represents a protocol.
	 The values that may be included in the sum and their
	 meanings are:
		1     X.25
		2     Frame Relay
		4     HDLC
	  	8     SDLC
		16    MPE
		32    ASYNC
		64    STM-4
        128   STM-8
        256   STM-16
        512   STM-24
		1024  BISYNC
		2048  SLIP
        4096  ETHERNET
        8192  PPP
       16384  ISDN
	  	XX - Any combination of the values specified above ."
       ::= {  pktSwchSysGen 9 }


pktSwchSysChannelProtocols OBJECT-TYPE
    SYNTAX Integer32
    MAX-ACCESS  read-only
    STATUS  current
    DESCRIPTION
        "The protocols the device can support on the async channels.
		1     ASYNC
		2     SLIP
                3     PPP  "
       ::= {  pktSwchSysGen 10 }


pktSwchSysStatus OBJECT-TYPE
    SYNTAX  INTEGER {
       valid(1),
       createRequest(2),
       underCreation(3),
       invalid(4)
     }
    MAX-ACCESS  read-write
    STATUS  current
    DESCRIPTION
	"The status of the System data.  The choices are those defined in the SNMPv2 Textual Conventions
		 for RowStatus.  This will allow easy replacement of the INTEGER syntax with the RowStatus
		 textual convention SYNTAX."
  ::= { pktSwchSysParam 6 }



-- The routing subgroup in the pktSwch System Group contains the routing table, the local PVC table
-- and the net PVC table

pktSwchRouting  OBJECT IDENTIFIER ::= {  pktSwchSystem 2}

pktSwchRoutSTable    OBJECT-TYPE
    SYNTAX  SEQUENCE  OF PktSwchRoutSEntry
    MAX-ACCESS  not-accessible
    STATUS  current
    DESCRIPTION
	"The Scratch Routing Table defines the routes for incoming and
	 outgoing data on the device."
    ::=  { pktSwchRouting 1 }

pktSwchRoutSEntry OBJECT-TYPE
    SYNTAX  PktSwchRoutSEntry
    MAX-ACCESS  not-accessible
    STATUS  current
    DESCRIPTION
	"Defines the contents of each line in the Scratch Routing Table."
    INDEX   { pktSwchRoutIdS }
    ::=  { pktSwchRoutSTable 1  }

PktSwchRoutSEntry ::=  SEQUENCE {
	pktSwchRoutIdS
	 Integer32,
    pktSwchRoutAddressS
     DisplayString,
    pktSwchRoutDestLink1S
     DisplayString,
	pktSwchRoutDestLink2S
     DisplayString,
	pktSwchRoutDestLink3S
     DisplayString,
    pktSwchRoutLinkPrio1S
     Integer32,
	pktSwchRoutLinkPrio2S
     Integer32,
	pktSwchRoutLinkPrio3S
     Integer32,
	pktSwchRoutSearchStatusS
	 INTEGER,
    pktSwchRoutStatusS
     INTEGER
    }

pktSwchRoutIdS OBJECT-TYPE
    SYNTAX Integer32 (1..2000)
	MAX-ACCESS  read-only
	STATUS  current
	DESCRIPTION
	"Index of the pktSwchRoutSTable."
	::= { pktSwchRoutSEntry 1 }

pktSwchRoutAddressS OBJECT-TYPE
    SYNTAX DisplayString
    MAX-ACCESS  read-write
    STATUS  current
    DESCRIPTION
	"The address to which the entry applies.  The use of the octet
	 string syntax allows the use of the letter x as a wild card in
	 the addresses."
    ::= { pktSwchRoutSEntry 2 }

pktSwchRoutDestLink1S OBJECT-TYPE
    SYNTAX 	DisplayString -- (SIZE(6))
    MAX-ACCESS  read-write
    STATUS  current
    DESCRIPTION
        "First destination link through which the data will be routed.
         For X.25 destination: any valid x.25 link no.
         For Frame Relay Link: any valid dlci with an x.25 encapsulation
                               protocol, presented in the form of {port:dlci}.
         For a local destination: 100 .
         For ISDN:             ISDN routing entry number preceeded by the
                               letter 'I' (example: I4)"
    ::= { pktSwchRoutSEntry 3 }

pktSwchRoutDestLink2S OBJECT-TYPE
    SYNTAX DisplayString -- (SIZE(6))
    MAX-ACCESS  read-write
    STATUS  current
    DESCRIPTION
        "Second destination link through which the data will be routed.
         For X.25 destination: any valid x.25 link no.
         For Frame Relay Link: any valid dlci with an x.25 encapsulation
                               protocol, presented in the form of {port:dlci}.
         For a local destination: 100 .
         For ISDN:             ISDN routing entry number preceeded by the
                               letter 'I' (example: I4)"
    ::= { pktSwchRoutSEntry 4 }

pktSwchRoutDestLink3S OBJECT-TYPE
    SYNTAX DisplayString -- (SIZE(6))
    MAX-ACCESS  read-write
    STATUS  current
    DESCRIPTION
        "Third destination link through which the data will be routed.
         For X.25 destination: any valid x.25 link no.
         For Frame Relay Link: any valid dlci with an x.25 encapsulation
                               protocol, presented in the form of {port:dlci}.
         For a local destination: 100 .
         For ISDN:             ISDN routing entry number preceeded by the
                               letter 'I' (example: I4)"
    ::= { pktSwchRoutSEntry 5 }


pktSwchRoutLinkPrio1S OBJECT-TYPE
    SYNTAX Integer32
    MAX-ACCESS  read-write
    STATUS  current
    DESCRIPTION
	"A priority of the associated destination of link 1."
    ::= { pktSwchRoutSEntry 6 }

pktSwchRoutLinkPrio2S OBJECT-TYPE
    SYNTAX Integer32
    MAX-ACCESS  read-write
    STATUS  current
    DESCRIPTION
	"A priority of the associated destination of link 2."
    ::= { pktSwchRoutSEntry 7 }

pktSwchRoutLinkPrio3S OBJECT-TYPE
    SYNTAX Integer32
    MAX-ACCESS  read-write
    STATUS  current
    DESCRIPTION
	"A priority of the associated destination of link 3."
    ::= { pktSwchRoutSEntry 8 }

pktSwchRoutSearchStatusS OBJECT-TYPE
    SYNTAX  INTEGER {
       off(2),
       on(3)
    }
    MAX-ACCESS  read-write
    STATUS  current
    DESCRIPTION
	" off - The device stops searching for a matching address.
	  on - The device continues searching for a matching address in the
	       links of the next entry."
  ::= { pktSwchRoutSEntry 9 }


pktSwchRoutStatusS OBJECT-TYPE
    SYNTAX  INTEGER {
       valid(1),
       createRequest(2),
       underCreation(3),
       invalid(4)
    }
    MAX-ACCESS  read-write
    STATUS  current
    DESCRIPTION
	"The status of this routing table entry.  The choices are those defined in the SNMPv2 Textual
		 Conventions for RowStatus.  This will allow easy replacement of the INTEGER syntax with
		 the RowStatus textual convention SYNTAX."
  ::= { pktSwchRoutSEntry 10 }

pktSwchRoutATable    OBJECT-TYPE
    SYNTAX  SEQUENCE  OF PktSwchRoutAEntry
    MAX-ACCESS  not-accessible
    STATUS  current
    DESCRIPTION
	"The Active Routing Table defines the active routes for incoming and outgoing data
		on the device."
    ::=  { pktSwchRouting 2 }

pktSwchRoutAEntry OBJECT-TYPE
    SYNTAX  PktSwchRoutAEntry
    MAX-ACCESS  not-accessible
    STATUS  current
    DESCRIPTION
	"Defines the contents of each line in the Active Routing Table."
    INDEX   { pktSwchRoutIdA }
    ::=  { pktSwchRoutATable 1  }

PktSwchRoutAEntry ::= SEQUENCE {
    pktSwchRoutIdA
	 Integer32,
    pktSwchRoutAddressA
     DisplayString,
    pktSwchRoutDestLink1A
     DisplayString,
	pktSwchRoutDestLink2A
     DisplayString,
	pktSwchRoutDestLink3A
     DisplayString,
    pktSwchRoutLinkPrio1A
     Integer32,
	pktSwchRoutLinkPrio2A
     Integer32,
	pktSwchRoutLinkPrio3A
     Integer32,
	pktSwchRoutSearchStatusA
	 INTEGER
    }

pktSwchRoutIdA OBJECT-TYPE
    SYNTAX Integer32 (1..2000)
	MAX-ACCESS  read-only
	STATUS  current
	DESCRIPTION
	"Index of the pktSwchRoutATable."
	::= { pktSwchRoutAEntry 1 }


pktSwchRoutAddressA OBJECT-TYPE
    SYNTAX DisplayString
    MAX-ACCESS  read-only
    STATUS  current
    DESCRIPTION
	"The address to which the entry applies.  The use of the octet string syntax allows
		 the use of the letter x as a wild card in the addresses."
    ::= { pktSwchRoutAEntry 2 }

pktSwchRoutDestLink1A OBJECT-TYPE
    SYNTAX DisplayString -- (SIZE(6))
    MAX-ACCESS  read-only
    STATUS  current
    DESCRIPTION
        "First destination link through which the data will be routed.
         For X.25 destination: any valid x.25 link no.
         For Frame Relay Link: any valid dlci with an x.25 encapsulation
                               protocol, presented in the form of {port:dlci}.
         For a local destination: 100 .
         For ISDN:             ISDN routing entry number preceeded by the
                               letter 'I' (example: I4)"
    ::= { pktSwchRoutAEntry 3 }

pktSwchRoutDestLink2A OBJECT-TYPE
    SYNTAX DisplayString -- (SIZE(6))
    MAX-ACCESS  read-only
    STATUS  current
    DESCRIPTION
        "Second destination link through which the data will be routed.
         For X.25 destination: any valid x.25 link no.
         For Frame Relay Link: any valid dlci with an x.25 encapsulation
                               protocol, presented in the form of {port:dlci}.
         For a local destination: 100 .
         For ISDN:             ISDN routing entry number preceeded by the
                               letter 'I' (example: I4)"
    ::= { pktSwchRoutAEntry 4 }

pktSwchRoutDestLink3A OBJECT-TYPE
    SYNTAX DisplayString -- (SIZE(6))
    MAX-ACCESS  read-only
    STATUS  current
    DESCRIPTION
        "Third destination link through which the data will be routed.
         For X.25 destination: any valid x.25 link no.
         For Frame Relay Link: any valid dlci with an x.25 encapsulation
                               protocol, presented in the form of {port:dlci}.
         For a local destination: 100 .
         For ISDN:             ISDN routing entry number preceeded by the
                               letter 'I' (example: I4)"
    ::= { pktSwchRoutAEntry 5 }


pktSwchRoutLinkPrio1A OBJECT-TYPE
    SYNTAX Integer32
    MAX-ACCESS  read-only
    STATUS  current
    DESCRIPTION
	"A priority of the associated destination of link 1."
    ::= { pktSwchRoutAEntry 6 }

pktSwchRoutLinkPrio2A OBJECT-TYPE
    SYNTAX Integer32
    MAX-ACCESS  read-only
    STATUS  current
    DESCRIPTION
	"A priority of the associated destination of link 2."
    ::= { pktSwchRoutAEntry 7 }

pktSwchRoutLinkPrio3A OBJECT-TYPE
    SYNTAX Integer32
    MAX-ACCESS  read-only
    STATUS  current
    DESCRIPTION
	"A priority of the associated destination of link 3."
    ::= { pktSwchRoutAEntry 8 }

pktSwchRoutSearchStatusA OBJECT-TYPE
    SYNTAX  INTEGER {
       off(2),
       on(3)
    }
    MAX-ACCESS  read-only
    STATUS  current
    DESCRIPTION
	" off - The device stops searching for a matching address.
	  on - The device continues searching for a matching address in the
	       links of the next entry."
  ::= { pktSwchRoutAEntry 9 }



pktSwchPvcSTable    OBJECT-TYPE
    SYNTAX  SEQUENCE  OF PktSwchPvcSEntry
    MAX-ACCESS  not-accessible
    STATUS  current
    DESCRIPTION
	"The Scratch Network PVC Table defines the network PVCs."
    ::=  { pktSwchRouting 3 }

pktSwchPvcSEntry OBJECT-TYPE
    SYNTAX  PktSwchPvcSEntry
    MAX-ACCESS  not-accessible
    STATUS  current
    DESCRIPTION
	"Defines the contents of each line in the Scratch Network PVC table."
    INDEX   { pktSwchPvcNumS }
    ::=  { pktSwchPvcSTable 1  }

PktSwchPvcSEntry ::= SEQUENCE {
    pktSwchPvcNumS
     Integer32,
    pktSwchPvcSrcLinkS
     Integer32,
    pktSwchPvcSrcLcnS
     DisplayString,
    pktSwchPvcDstLinkS
     Integer32,
    pktSwchPvcDstLcnS
     Integer32,
    pktSwchPvcStatusS
     INTEGER
    }

pktSwchPvcNumS OBJECT-TYPE
    SYNTAX Integer32 (1..200)
    MAX-ACCESS  read-only
    STATUS  current
    DESCRIPTION
	"The PVC number corresponding to this entry."
    ::= { pktSwchPvcSEntry 1 }

pktSwchPvcSrcLinkS OBJECT-TYPE
    SYNTAX Integer32 (0..100)
    MAX-ACCESS  read-write
    STATUS  current
    DESCRIPTION
	"The number of the link (1 through 6 for SPS-6 and 1 through 12 for SPS-12) that will be
		 used as a source link to create a connection by means of the PVC.
		  0 means that the PVC will not be active, 100 means that this pvc is Local."
    ::= { pktSwchPvcSEntry 2 }

pktSwchPvcSrcLcnS OBJECT-TYPE
    SYNTAX DisplayString -- (SIZE(1..6))
    MAX-ACCESS  read-write
    STATUS  current
    DESCRIPTION
	"    Network pvc:
    The number of the logical channel (0-255) that will be used as the source
    logical channel to create a connection by means of the PVC.

    Local pvc:
    For asynchronous channel to X.25 PVC,
      Any valid Async Channel number.

   For encapsulation of transparent HDLC over X25 PVC,
     valid Channel numbers are:
        HxM - for the main PVC.
        HxB - for the backup PVC.
              x is a valid HDLC link number.

   For encapsulation of Multi Point Encapsulator (MPE) over X25 PVC,
     valid channel numbers are:
        Nx - where x is a valid MPE link number.

   For encapsulation of IP Over X.25 PVC, Enter IP."
    ::= { pktSwchPvcSEntry 3 }

pktSwchPvcDstLinkS OBJECT-TYPE
    SYNTAX Integer32 (0..12)
    MAX-ACCESS  read-write
    STATUS  current
    DESCRIPTION
	"The number of the destination link that will be used.
	 0 means that the PVC will not be active."
    ::= { pktSwchPvcSEntry 4 }

pktSwchPvcDstLcnS OBJECT-TYPE
    SYNTAX Integer32 (0..255)
    MAX-ACCESS  read-write
    STATUS  current
    DESCRIPTION
	"The number of the logical channel for the destination link."
    ::= { pktSwchPvcSEntry 5 }

pktSwchPvcStatusS OBJECT-TYPE
    SYNTAX  INTEGER {
       valid(1),
       createRequest(2),
       underCreation(3),
       invalid(4)
     }
    MAX-ACCESS  read-write
    STATUS  current
    DESCRIPTION
	"The status of this Network PVC table entry.  The choices are those defined in the SNMPv2
		 Textual Conventions for RowStatus.  This will allow easy replacement of the INTEGER syntax
		 with the RowStatus textual convention SYNTAX."
  ::= { pktSwchPvcSEntry 6 }

pktSwchPvcATable   OBJECT-TYPE
    SYNTAX  SEQUENCE  OF PktSwchPvcAEntry
    MAX-ACCESS  not-accessible
    STATUS  current
    DESCRIPTION
	"The Active Network PVC Table defines the active network PVCs."
    ::=  { pktSwchRouting 4 }

pktSwchPvcAEntry OBJECT-TYPE
    SYNTAX  PktSwchPvcAEntry
    MAX-ACCESS  not-accessible
    STATUS  current
    DESCRIPTION
	"Defines the contents of each line in the Active Network PVC table."
    INDEX   { pktSwchPvcNumA }
    ::=  { pktSwchPvcATable 1  }

PktSwchPvcAEntry ::= SEQUENCE {
    pktSwchPvcNumA
     Integer32,
    pktSwchPvcSrcLinkA
     Integer32,
    pktSwchPvcSrcLcnA
     DisplayString,
    pktSwchPvcDstLinkA
     Integer32,
    pktSwchPvcDstLcnA
     Integer32
    }

pktSwchPvcNumA OBJECT-TYPE
    SYNTAX Integer32 (1..200)
    MAX-ACCESS  read-only
    STATUS  current
    DESCRIPTION
	"The PVC number corresponding to this entry."
    ::= { pktSwchPvcAEntry 1 }

pktSwchPvcSrcLinkA OBJECT-TYPE
    SYNTAX Integer32 (0..100)
    MAX-ACCESS  read-only
    STATUS  current
    DESCRIPTION
	"The number of the link (1 through 6 for SPS-6 and 1 through 12 for SPS-12) that is
		 used as a source link to create a connection by means of the PVC.
		  0 means that the PVC will not be active, 100 means that this pvc is Local."
    ::= { pktSwchPvcAEntry 2 }

pktSwchPvcSrcLcnA OBJECT-TYPE
    SYNTAX DisplayString -- (SIZE(1..6))
    MAX-ACCESS  read-only
    STATUS  current
    DESCRIPTION
	"    Network pvc:
    The number of the logical channel (0-255) that will be used as the source
    logical channel to create a connection by means of the PVC.

    Local pvc:
    For asynchronous channel to X.25 PVC,
      Any valid Async Channel number.

   For encapsulation of transparent HDLC over X25 PVC,
     valid Channel numbers are:
        HxM - for the main PVC.
        HxB - for the backup PVC.
              x is a valid HDLC link number.

   For encapsulation of Multi Point Encapsulator (MPE) over X25 PVC,
     valid channel numbers are:
        Nx - where x is a valid MPE link number.

   For encapsulation of IP Over X.25 PVC, Enter IP."
    ::= { pktSwchPvcAEntry 3 }

pktSwchPvcDstLinkA OBJECT-TYPE
    SYNTAX Integer32 (0..12)
    MAX-ACCESS  read-only
    STATUS  current
    DESCRIPTION
	"The number of the destination link that is used.
	0 means that the PVC will not be active."
    ::= { pktSwchPvcAEntry 4 }

pktSwchPvcDstLcnA OBJECT-TYPE
    SYNTAX Integer32 (0..255)
    MAX-ACCESS  read-only
    STATUS  current
    DESCRIPTION
	"The number of the logical channel for the destination link."
    ::= { pktSwchPvcAEntry 5 }


-- NUI Table

pktSwchNui  OBJECT IDENTIFIER ::= { pktSwchSystem 3 }

-- The NUI Table contains the Network User Identification
-- password information.

pktSwchNuiSTable    OBJECT-TYPE
    SYNTAX  SEQUENCE  OF PktSwchNuiSEntry
    MAX-ACCESS  not-accessible
    STATUS  current
    DESCRIPTION
	"The NUI Table defines the NUIs that can be used by the device."
    ::=  {  pktSwchNui 1 }

pktSwchNuiSEntry OBJECT-TYPE
    SYNTAX  PktSwchNuiSEntry
    MAX-ACCESS  not-accessible
    STATUS  current
    DESCRIPTION
	"Defines the contents of each line in the NUI Table."
    INDEX   { pktSwchNuiIndexS }
    ::=  { pktSwchNuiSTable 1  }

PktSwchNuiSEntry ::= SEQUENCE {
    pktSwchNuiIndexS
     Integer32,
    pktSwchNuiGroupIdS
     Integer32,
    pktSwchNuiInPasswdS
     DisplayString,
    pktSwchNuiOutPasswdPointerS
     Integer32,
    pktSwchNuiInAddrS
     DisplayString,
    pktSwchNuiOutAddrPointerS
     Integer32,
    pktSwchNuiStatusS
     INTEGER
    }

pktSwchNuiIndexS OBJECT-TYPE
    SYNTAX Integer32
    MAX-ACCESS  read-only
    STATUS  current
    DESCRIPTION
	"The index of this entry."
    ::= { pktSwchNuiSEntry 1 }

pktSwchNuiGroupIdS OBJECT-TYPE
    SYNTAX  Integer32
    MAX-ACCESS  read-write
    STATUS  current
    DESCRIPTION
	"The group Id for this NUI entry."
    ::= { pktSwchNuiSEntry 2 }

pktSwchNuiInPasswdS OBJECT-TYPE
    SYNTAX  DisplayString
    MAX-ACCESS  read-write
    STATUS  current
    DESCRIPTION
	"The password for the incoming call. 15 chars."
    ::= { pktSwchNuiSEntry 3 }

pktSwchNuiOutPasswdPointerS OBJECT-TYPE
    SYNTAX  Integer32
    MAX-ACCESS  read-write
    STATUS  current
    DESCRIPTION
	"A pointer to the password in the OutPasswdTable for an outgoing call."
    ::= { pktSwchNuiSEntry 4 }

pktSwchNuiInAddrS OBJECT-TYPE
    SYNTAX  DisplayString
    MAX-ACCESS  read-write
    STATUS  current
    DESCRIPTION
	"The addresss for the incoming call. 15 digits."
    ::= { pktSwchNuiSEntry 5 }

pktSwchNuiOutAddrPointerS OBJECT-TYPE
    SYNTAX  Integer32
    MAX-ACCESS  read-write
    STATUS  current
    DESCRIPTION
	"A pointer to the address in the OutAddrTable for an outgoing call."
    ::= { pktSwchNuiSEntry 6 }

pktSwchNuiStatusS OBJECT-TYPE
    SYNTAX  INTEGER {
       valid(1),
       createRequest(2),
       underCreation(3),
       invalid(4)
     }
    MAX-ACCESS  read-write
    STATUS  current
    DESCRIPTION
	"The status of this NUI table entry.  The choices are those defined in the SNMPv2 Textual
		 Conventions for RowStatus.  This will allow easy replacement of the INTEGER syntax with
		 the RowStatus textual convention SYNTAX."
  ::= { pktSwchNuiSEntry 7 }


pktSwchNuiATable    OBJECT-TYPE
    SYNTAX  SEQUENCE  OF PktSwchNuiAEntry
    MAX-ACCESS  not-accessible
    STATUS  current
    DESCRIPTION
	"The NUI Table defines the NUIs that can be used by the device."
    ::=  {  pktSwchNui 2 }

pktSwchNuiAEntry OBJECT-TYPE
    SYNTAX  PktSwchNuiAEntry
    MAX-ACCESS  not-accessible
    STATUS  current
    DESCRIPTION
	"Defines the contents of each line in the NUI Table."
    INDEX   { pktSwchNuiIndexA }
    ::=  { pktSwchNuiATable 1  }

PktSwchNuiAEntry ::= SEQUENCE {
    pktSwchNuiIndexA
     Integer32,
    pktSwchNuiGroupIdA
     Integer32,
    pktSwchNuiInPasswdA
     DisplayString,
    pktSwchNuiOutPasswdPointerA
     Integer32,
    pktSwchNuiInAddrA
     DisplayString,
    pktSwchNuiOutAddrPointerA
     Integer32,
    pktSwchNuiStatusA
     INTEGER
    }

pktSwchNuiIndexA OBJECT-TYPE
    SYNTAX Integer32
    MAX-ACCESS  read-only
    STATUS  current
    DESCRIPTION
	"The index of this entry."
    ::= { pktSwchNuiAEntry 1 }

pktSwchNuiGroupIdA OBJECT-TYPE
    SYNTAX  Integer32
    MAX-ACCESS  read-only
    STATUS  current
    DESCRIPTION
	"The group Id for this NUI entry."
    ::= { pktSwchNuiAEntry 2 }

pktSwchNuiInPasswdA OBJECT-TYPE
    SYNTAX  DisplayString
    MAX-ACCESS  read-only
    STATUS  current
    DESCRIPTION
	"The password for the incoming call. 15 chars."
    ::= { pktSwchNuiAEntry 3 }

pktSwchNuiOutPasswdPointerA OBJECT-TYPE
    SYNTAX  Integer32
    MAX-ACCESS  read-only
    STATUS  current
    DESCRIPTION
	"A pointer to the password in the OutPasswdTable for an outgoing call."
    ::= { pktSwchNuiAEntry 4 }

pktSwchNuiInAddrA OBJECT-TYPE
    SYNTAX  DisplayString
    MAX-ACCESS  read-only
    STATUS  current
    DESCRIPTION
	"The addresss for the incoming call. 15 digits."
    ::= { pktSwchNuiAEntry 5 }

pktSwchNuiOutAddrPointerA OBJECT-TYPE
    SYNTAX  Integer32
    MAX-ACCESS  read-only
    STATUS  current
    DESCRIPTION
	"A pointer to the address in the OutAddrTable for an outgoing call."
    ::= { pktSwchNuiAEntry 6 }

pktSwchNuiStatusA OBJECT-TYPE
    SYNTAX  INTEGER {
       valid(1),
       createRequest(2),
       underCreation(3),
       invalid(4)
     }
    MAX-ACCESS  read-only
    STATUS  current
    DESCRIPTION
	"The status of this NUI table entry.  The choices are those defined in the SNMPv2 Textual
		 Conventions for RowStatus.  This will allow easy replacement of the INTEGER syntax with
		 the RowStatus textual convention SYNTAX."
  ::= { pktSwchNuiAEntry 7 }


pktSwchNuiOutPasswdSTable    OBJECT-TYPE
    SYNTAX  SEQUENCE  OF PktSwchNuiOutPasswdSEntry
    MAX-ACCESS  not-accessible
    STATUS  current
    DESCRIPTION
	"The table defines the passwords that can be used by the device."
    ::=  {  pktSwchNui 3 }

pktSwchNuiOutPasswdSEntry OBJECT-TYPE
    SYNTAX  PktSwchNuiOutPasswdSEntry
    MAX-ACCESS  not-accessible
    STATUS  current
    DESCRIPTION
	"Defines the contents of each line in OutPasswd Table."
    INDEX   { pktSwchNuiOutPasswdIndexS }
    ::=  { pktSwchNuiOutPasswdSTable 1  }

PktSwchNuiOutPasswdSEntry ::= SEQUENCE {
    pktSwchNuiOutPasswdIndexS
     Integer32,
    pktSwchNuiOutPasswdValueS
     DisplayString,
    pktSwchNuiOutPasswdStatusS
     INTEGER
    }

pktSwchNuiOutPasswdIndexS OBJECT-TYPE
    SYNTAX Integer32
    MAX-ACCESS  read-only
    STATUS  current
    DESCRIPTION
	"The index of this entry."
    ::= { pktSwchNuiOutPasswdSEntry 1 }

pktSwchNuiOutPasswdValueS OBJECT-TYPE
    SYNTAX DisplayString
    MAX-ACCESS  read-write
    STATUS  current
    DESCRIPTION
	"The password of this entry. 15 chars."
    ::= { pktSwchNuiOutPasswdSEntry 2 }

pktSwchNuiOutPasswdStatusS OBJECT-TYPE
    SYNTAX  INTEGER {
       valid(1),
       createRequest(2),
       underCreation(3),
       invalid(4)
     }
    MAX-ACCESS  read-write
    STATUS  current
    DESCRIPTION
	"The status of this NuiOutPasswd table entry."
  ::= { pktSwchNuiOutPasswdSEntry 3 }


pktSwchNuiOutPasswdATable    OBJECT-TYPE
    SYNTAX  SEQUENCE  OF PktSwchNuiOutPasswdAEntry
    MAX-ACCESS  not-accessible
    STATUS  current
    DESCRIPTION
	"The table defines the passwords that can be used by the device."
    ::=  {  pktSwchNui 4 }

pktSwchNuiOutPasswdAEntry OBJECT-TYPE
    SYNTAX  PktSwchNuiOutPasswdAEntry
    MAX-ACCESS  not-accessible
    STATUS  current
    DESCRIPTION
	"Defines the contents of each line in OutPasswd Table."
    INDEX   { pktSwchNuiOutPasswdIndexA }
    ::=  { pktSwchNuiOutPasswdATable 1  }

PktSwchNuiOutPasswdAEntry ::= SEQUENCE {
    pktSwchNuiOutPasswdIndexA
     Integer32,
    pktSwchNuiOutPasswdValueA
     DisplayString,
    pktSwchNuiOutPasswdStatusA
     INTEGER
    }

pktSwchNuiOutPasswdIndexA OBJECT-TYPE
    SYNTAX Integer32
    MAX-ACCESS  read-only
    STATUS  current
    DESCRIPTION
	"The index of this entry."
    ::= { pktSwchNuiOutPasswdAEntry 1 }

pktSwchNuiOutPasswdValueA OBJECT-TYPE
    SYNTAX DisplayString
    MAX-ACCESS  read-only
    STATUS  current
    DESCRIPTION
	"The password of this entry. 15 chars."
    ::= { pktSwchNuiOutPasswdAEntry 2 }

pktSwchNuiOutPasswdStatusA OBJECT-TYPE
    SYNTAX  INTEGER {
       valid(1),
       createRequest(2),
       underCreation(3),
       invalid(4)
     }
    MAX-ACCESS  read-only
    STATUS  current
    DESCRIPTION
	"The status of this NuiOutPasswd table entry."
  ::= { pktSwchNuiOutPasswdAEntry 3 }


pktSwchNuiOutAddrSTable    OBJECT-TYPE
    SYNTAX  SEQUENCE  OF PktSwchNuiOutAddrSEntry
    MAX-ACCESS  not-accessible
    STATUS  current
    DESCRIPTION
	"The table defines the Addresses that can be used by the device."
    ::=  {  pktSwchNui 5 }

pktSwchNuiOutAddrSEntry OBJECT-TYPE
    SYNTAX  PktSwchNuiOutAddrSEntry
    MAX-ACCESS  not-accessible
    STATUS  current
    DESCRIPTION
	"Defines the contents of each line in OutAddr Table."
    INDEX   { pktSwchNuiOutAddrIndexS }
    ::=  { pktSwchNuiOutAddrSTable 1  }

PktSwchNuiOutAddrSEntry ::= SEQUENCE {
    pktSwchNuiOutAddrIndexS
     Integer32,
    pktSwchNuiOutAddrValueS
     DisplayString,
    pktSwchNuiOutAddrStatusS
     INTEGER
    }

pktSwchNuiOutAddrIndexS OBJECT-TYPE
    SYNTAX Integer32
    MAX-ACCESS  read-only
    STATUS  current
    DESCRIPTION
	"The index of this entry."
    ::= { pktSwchNuiOutAddrSEntry 1 }

pktSwchNuiOutAddrValueS OBJECT-TYPE
    SYNTAX DisplayString
    MAX-ACCESS  read-write
    STATUS  current
    DESCRIPTION
	"The address of this entry. 15 digits."
    ::= { pktSwchNuiOutAddrSEntry 2 }

pktSwchNuiOutAddrStatusS OBJECT-TYPE
    SYNTAX  INTEGER {
       valid(1),
       createRequest(2),
       underCreation(3),
       invalid(4)
     }
    MAX-ACCESS  read-write
    STATUS  current
    DESCRIPTION
	"The status of this NuiOutAddr table entry."
  ::= { pktSwchNuiOutAddrSEntry 3 }


pktSwchNuiOutAddrATable    OBJECT-TYPE
    SYNTAX  SEQUENCE  OF PktSwchNuiOutAddrAEntry
    MAX-ACCESS  not-accessible
    STATUS  current
    DESCRIPTION
	"The table defines the Addresses that can be used by the device."
    ::=  {  pktSwchNui 6 }

pktSwchNuiOutAddrAEntry OBJECT-TYPE
    SYNTAX  PktSwchNuiOutAddrAEntry
    MAX-ACCESS  not-accessible
    STATUS  current
    DESCRIPTION
	"Defines the contents of each line in OutAddr Table."
    INDEX   { pktSwchNuiOutAddrIndexA }
    ::=  { pktSwchNuiOutAddrATable 1  }

PktSwchNuiOutAddrAEntry ::= SEQUENCE {
    pktSwchNuiOutAddrIndexA
     Integer32,
    pktSwchNuiOutAddrValueA
     DisplayString,
    pktSwchNuiOutAddrStatusA
     INTEGER
    }

pktSwchNuiOutAddrIndexA OBJECT-TYPE
    SYNTAX Integer32
    MAX-ACCESS  read-only
    STATUS  current
    DESCRIPTION
	"The index of this entry."
    ::= { pktSwchNuiOutAddrAEntry 1 }

pktSwchNuiOutAddrValueA OBJECT-TYPE
    SYNTAX DisplayString
    MAX-ACCESS  read-only
    STATUS  current
    DESCRIPTION
	"The address of this entry. 15 digits."
    ::= { pktSwchNuiOutAddrAEntry 2 }

pktSwchNuiOutAddrStatusA OBJECT-TYPE
    SYNTAX  INTEGER {
       valid(1),
       createRequest(2),
       underCreation(3),
       invalid(4)
     }
    MAX-ACCESS  read-only
    STATUS  current
    DESCRIPTION
	"The status of this NuiOutAddr table entry."
  ::= { pktSwchNuiOutAddrAEntry 3 }


-- X25 Manager Table

pktSwchMng  OBJECT IDENTIFIER ::= { pktSwchSystem 4 }

pktSwchMngX25TrapIpTable  OBJECT-TYPE
	SYNTAX  SEQUENCE OF PktSwchMngX25Entry
	MAX-ACCESS  not-accessible
	STATUS current
	DESCRIPTION
	"This table indicates  the destination address of the traps.
	  Internally it will be limited to ten addresses. "
	::= { pktSwchMng 1 }

pktSwchMngX25Entry OBJECT-TYPE
	SYNTAX PktSwchMngX25Entry
	MAX-ACCESS  not-accessible
	STATUS current
    DESCRIPTION
	"An entry in table pktSwchMngX25TrapIpTable."
	INDEX {  pktSwchMngID }
	::= {pktSwchMngX25TrapIpTable  1 }


PktSwchMngX25Entry  ::=
	    SEQUENCE {
	pktSwchMngID
	  Integer32,
	pktSwchMngIP
	  IpAddress,
	pktSwchMngPhyAddr
	  DisplayString,
	pktSwchTrapEnable
	  Integer32,
	pktSwchEncapsulationMode
	  INTEGER
	}

pktSwchMngID OBJECT-TYPE
	SYNTAX  Integer32
	MAX-ACCESS  read-only
	STATUS current
	DESCRIPTION
	" This value indicates an index of a specific IP address"
	::= { pktSwchMngX25Entry 1 }

pktSwchMngIP OBJECT-TYPE
	SYNTAX  IpAddress
	MAX-ACCESS  read-write
        STATUS  current
	DESCRIPTION
	"This value indicates  the  destination address of the traps. IP 0.0.0.0 removes the entry. "
	::= { pktSwchMngX25Entry 2 }

pktSwchMngPhyAddr OBJECT-TYPE
	SYNTAX  DisplayString
	MAX-ACCESS  read-write
	STATUS  deprecated
	DESCRIPTION
	"This value indicates  the  physical destination  address of the traps."
	::= { pktSwchMngX25Entry 3 }

pktSwchTrapEnable OBJECT-TYPE
	SYNTAX  Integer32
	MAX-ACCESS  read-write
        STATUS  current
	DESCRIPTION
	"This value indicates which traps should be sent.
	 The value is a sum of values (powers of two), where each value in
	 the sum represents	a trap that should be reported to the Management
	 Station. The values that may be included in the sum and their meanings are:
		0   No traps would be reported.
		1   Link Down
		2   Link Up
		4   rtsChange
		8   resetX25
		16  restartX25
		32  frDLCIStatusChange
		64  coldStart
		128 linkProtocolChanged
        256 enrollmentPS
		512 ledStatusChange         "
	::= { pktSwchMngX25Entry 4 }

pktSwchEncapsulationMode OBJECT-TYPE
    SYNTAX  INTEGER	{
	 ipPid(1),
	 snapPid(2)
	 }
	MAX-ACCESS  read-write
        STATUS  deprecated
	DESCRIPTION
	"Format type for IP over X25"
	::= { pktSwchMngX25Entry 5 }


-- XID Table

pktSwchXid  OBJECT IDENTIFIER ::= { pktSwchSystem 5 }

pktSwchXidSTable  OBJECT-TYPE
	SYNTAX  SEQUENCE OF PktSwchXidSEntry
	MAX-ACCESS  not-accessible
	STATUS current
	DESCRIPTION
	"The Exchange Id table contains a list of 13 incoming pairs of allowed
	 dial-up phone numbers and passwords. Also included is one pair of
	 outgoing phone number and password (InternalIndex=14)."
	::= { pktSwchXid 1 }

pktSwchXidSEntry OBJECT-TYPE
	SYNTAX PktSwchXidSEntry
	MAX-ACCESS  not-accessible
	STATUS current
	DESCRIPTION
	"An entry in table pktSwchXidSTable."
	INDEX {  pktSwchXidIndexS, pktSwchXidInternalIndexS }
	::= {pktSwchXidSTable  1 }


PktSwchXidSEntry  ::=
	    SEQUENCE {
	pktSwchXidIndexS
	  Integer32,
	pktSwchXidInternalIndexS
	  Integer32,
	pktSwchXidPasswdS
	  DisplayString,
	pktSwchXidPhoneS
	  DisplayString,
	pktSwchXidStatusS
	  INTEGER
	}

pktSwchXidIndexS OBJECT-TYPE
	SYNTAX  Integer32
	MAX-ACCESS  read-only
	STATUS current
	DESCRIPTION
	" This Index of the XID table."
	::= { pktSwchXidSEntry 1 }

pktSwchXidInternalIndexS OBJECT-TYPE
	SYNTAX  Integer32
	MAX-ACCESS  read-only
	STATUS current
	DESCRIPTION
	"An internal index for each XidIndex of the table. The first 13 entries
	 refer to Incoming calls. The 14th entry refers to an Outgoing call."
	::= { pktSwchXidSEntry 2 }

pktSwchXidPasswdS OBJECT-TYPE
	SYNTAX  DisplayString
	MAX-ACCESS  read-write
	STATUS current
	DESCRIPTION
	"Password of size 16 chars."
	::= { pktSwchXidSEntry 3 }

pktSwchXidPhoneS OBJECT-TYPE
	SYNTAX  DisplayString
	MAX-ACCESS  read-write
	STATUS current
	DESCRIPTION
	"Phone number of size 16 digits."
	::= { pktSwchXidSEntry 4 }

pktSwchXidStatusS OBJECT-TYPE
    SYNTAX  INTEGER {
       valid(1),
       createRequest(2),
       underCreation(3),
       invalid(4)
     }
    MAX-ACCESS  read-write
    STATUS  current
    DESCRIPTION
	"The status of the XID table entry. The status applies to the XidIndex,
	 i.e., setting the staus to invalid results in the removal of all
	 the InternalIndex entries (1..14) belonging to the relevant XidIndex."
  ::= { pktSwchXidSEntry 5 }


pktSwchXidATable  OBJECT-TYPE
	SYNTAX  SEQUENCE OF PktSwchXidAEntry
	MAX-ACCESS  not-accessible
	STATUS current
	DESCRIPTION
	"The Exchange Id table contains a list of 13 incoming pairs of allowed
	 dial-up phone numbers and passwords. Also included is one pair of
	 outgoing phone number and password (InternalIndex=14)."
	::= { pktSwchXid 2 }

pktSwchXidAEntry OBJECT-TYPE
	SYNTAX PktSwchXidAEntry
	MAX-ACCESS  not-accessible
	STATUS current
	DESCRIPTION
	"An entry in table pktSwchXidATable."
	INDEX {  pktSwchXidIndexA, pktSwchXidInternalIndexA }
	::= {pktSwchXidATable  1 }


PktSwchXidAEntry  ::=
	    SEQUENCE {
	pktSwchXidIndexA
	  Integer32,
	pktSwchXidInternalIndexA
	  Integer32,
	pktSwchXidPasswdA
	  DisplayString,
	pktSwchXidPhoneA
	  DisplayString,
	pktSwchXidStatusA
	  INTEGER
	}

pktSwchXidIndexA OBJECT-TYPE
	SYNTAX  Integer32
	MAX-ACCESS  read-only
	STATUS current
	DESCRIPTION
	" This Index of the XID table."
	::= { pktSwchXidAEntry 1 }

pktSwchXidInternalIndexA OBJECT-TYPE
	SYNTAX  Integer32
	MAX-ACCESS  read-only
	STATUS current
	DESCRIPTION
	"An internal index for each XidIndex of the table. The first 13 entries
	 refer to Incoming calls. The 14th entry refers to an Outgoing call."
	::= { pktSwchXidAEntry 2 }

pktSwchXidPasswdA OBJECT-TYPE
	SYNTAX  DisplayString
	MAX-ACCESS  read-only
	STATUS current
	DESCRIPTION
	"Password of size 16 chars."
	::= { pktSwchXidAEntry 3 }

pktSwchXidPhoneA OBJECT-TYPE
	SYNTAX  DisplayString
	MAX-ACCESS  read-only
	STATUS current
	DESCRIPTION
	"Phone number of size 16 digits."
	::= { pktSwchXidAEntry 4 }

pktSwchXidStatusA OBJECT-TYPE
    SYNTAX  INTEGER {
       valid(1),
       createRequest(2),
       underCreation(3),
       invalid(4)
     }
    MAX-ACCESS  read-only
    STATUS  current
    DESCRIPTION
	"The status of the XID table entry. The status applies to the XidIndex,
	 i.e., setting the staus to invalid results in the removal of all
	 the InternalIndex entries (1..14) belonging to the relevant XidIndex."
  ::= { pktSwchXidAEntry 5 }


pktSwchIpRouting  OBJECT IDENTIFIER ::= { pktSwchSystem 6 }

pktSwchIpRoutSTable    OBJECT-TYPE
    SYNTAX  SEQUENCE  OF PktSwchIpRoutSEntry
    MAX-ACCESS  not-accessible
    STATUS  current
    DESCRIPTION
	"The Scratch Routing Table defines the routes for incoming and
	 outgoing ip datagrams on the device."
    ::=  { pktSwchIpRouting 1 }

pktSwchIpRoutSEntry OBJECT-TYPE
    SYNTAX  PktSwchIpRoutSEntry
    MAX-ACCESS  not-accessible
    STATUS  current
    DESCRIPTION
	"Defines the contents of each line in the Scratch IP Routing
	 Table."
    INDEX   { pktSwchIpRoutIdS }
    ::=  { pktSwchIpRoutSTable 1  }

PktSwchIpRoutSEntry ::=  SEQUENCE {
    pktSwchIpRoutIdS
     Integer32,
    pktSwchIpRoutIpAddressS
     IpAddress,
    pktSwchIpRoutIpMaskS
     IpAddress,
    pktSwchIpRoutDestProtocolS
     INTEGER,
    pktSwchIpRoutDestinationS
     DisplayString,
    pktSwchIpRoutInactivityS
     Integer32,
    pktSwchIpRoutStatusS
     INTEGER,
    pktSwchIpRoutMetricS
     Integer32,
    pktSwchIpRoutNextHopS
     IpAddress,
    pktSwchIpRoutInterfaceIdS
     Integer32
    }

pktSwchIpRoutIdS OBJECT-TYPE
    SYNTAX Integer32 (1..200)
	MAX-ACCESS  read-only
	STATUS  current
	DESCRIPTION
	"Index of the pktSwchIpRoutSTable."
	::= { pktSwchIpRoutSEntry 1 }

pktSwchIpRoutIpAddressS OBJECT-TYPE
    SYNTAX IpAddress
    MAX-ACCESS  read-write
    STATUS  current
    DESCRIPTION
        "The IP address to which the entry applies.
         A string of the format: X.X.X.X
         where every X is a number in the range 0-255."
    ::= { pktSwchIpRoutSEntry 2 }

pktSwchIpRoutIpMaskS OBJECT-TYPE
    SYNTAX 	IpAddress
    MAX-ACCESS  read-write
    STATUS  current
    DESCRIPTION
        "The IP mask to which the entry applies.
         A string of the format: X.X.X.X
         where every X is a number in the range 0-255."
    ::= { pktSwchIpRoutSEntry 3 }

pktSwchIpRoutDestProtocolS OBJECT-TYPE
    SYNTAX  INTEGER {
             slip       (1),
             x25SVC     (2),
             x25PVC     (3),
             frameRelay (4),
             hdlc       (5),
             ethernet   (7),     --  (6) is reserved for snmp agent.
             ppp        (8),
             none      (255)
    }
    MAX-ACCESS  read-write
    STATUS  deprecated
    DESCRIPTION
	"Destination protocol for the associated address.
	 None(255) when not used"
    ::= { pktSwchIpRoutSEntry 4 }

pktSwchIpRoutDestinationS OBJECT-TYPE
    SYNTAX DisplayString
    MAX-ACCESS  read-write
    STATUS  deprecated
    DESCRIPTION
    " Destination for the associated address.
    Possible values:
    Default :     Not Used.
    X.25 PVC:     Port:LCN  or a pre defined PVC number
    X.25 SVC:     X.25 Addr or cid followed by a predefined Call ID number
    Frame Relay:  Port:DLCI
    HDLC:         'H' followed by the HDLC Port Number
    SLIP:         'S' followed by the SLIP Channel Number
    Ethernet:     'E' followed by the Ethernet Port Number
    PPP:          'P' followed by the PPP Port Number."
    ::= { pktSwchIpRoutSEntry 5 }

pktSwchIpRoutInactivityS OBJECT-TYPE
    SYNTAX Integer32
    MAX-ACCESS  read-write
    STATUS  deprecated
    DESCRIPTION
	"Inactivity time in steps of 50 mili seconds for X25 SVC
	 protocol only. Range: 0..255. Default: 2."
    ::= { pktSwchIpRoutSEntry 6 }

pktSwchIpRoutStatusS OBJECT-TYPE
    SYNTAX  INTEGER {
       valid        (1),
       createRequest(2),
       underCreation(3),
       invalid      (4)
    }
    MAX-ACCESS  read-write
    STATUS  current
    DESCRIPTION
	"The status of this routing table entry.  The choices are those
	 defined in the SNMPv2 Textual Conventions for RowStatus.
	 This will allow easy replacement of the INTEGER syntax with
	 the RowStatus textual convention SYNTAX."
  ::= { pktSwchIpRoutSEntry 7 }

pktSwchIpRoutMetricS OBJECT-TYPE
    SYNTAX   Integer32
    MAX-ACCESS  read-write
    STATUS  current
    DESCRIPTION
    "No. of hops for this route.
     The default value is 1.
     Legal values: 1 to the max no. of hops this device will support.
     The max no. is defined by pktSwchIpGlobalMaxHopCount."
    ::= { pktSwchIpRoutSEntry 8 }

pktSwchIpRoutNextHopS OBJECT-TYPE
    SYNTAX  IpAddress
    MAX-ACCESS  read-write
    STATUS  current
    DESCRIPTION
    "IP address of the next hop.
     A string of the format: X.X.X.X
     where every X is a number in the range 0-255."
    ::= { pktSwchIpRoutSEntry 9 }

pktSwchIpRoutInterfaceIdS OBJECT-TYPE
    SYNTAX   Integer32
    MAX-ACCESS  read-write
    STATUS  current
    DESCRIPTION
    "ID of the logical IP interface in the pktSwchIpInterface table.
     The IP routing module will route the IP frame according to this
     interface ID.
     Legal values: 1 to 200 and 65535.
     1-200 : ID of interface.
     65535 : No IP interface ID.
     Default value: 65535."
     ::= { pktSwchIpRoutSEntry 10 }

pktSwchIpRoutATable    OBJECT-TYPE
    SYNTAX  SEQUENCE  OF PktSwchIpRoutAEntry
    MAX-ACCESS  not-accessible
    STATUS  current
    DESCRIPTION
	"The Active Routing Table defines the active routes for incoming
	 and outgoing ip datagrams on the device."
    ::=  { pktSwchIpRouting 2 }

pktSwchIpRoutAEntry OBJECT-TYPE
    SYNTAX  PktSwchIpRoutAEntry
    MAX-ACCESS  not-accessible
    STATUS  current
    DESCRIPTION
	"Defines the contents of each line in the Active IP Routing Table."
    INDEX   { pktSwchIpRoutIdA }
    ::=  { pktSwchIpRoutATable 1  }

PktSwchIpRoutAEntry ::=  SEQUENCE {
    pktSwchIpRoutIdA
     Integer32,
    pktSwchIpRoutIpAddressA
     IpAddress,
    pktSwchIpRoutIpMaskA
     IpAddress,
    pktSwchIpRoutDestProtocolA
     INTEGER,
    pktSwchIpRoutDestinationA
     DisplayString,
    pktSwchIpRoutInactivityA
     Integer32,
    pktSwchIpRoutBuffsInA
     Counter32,
    pktSwchIpRoutBuffsOutA
     Counter32,
    pktSwchIpRoutFCA
     INTEGER,
    pktSwchIpRoutMetricA
     Integer32,
    pktSwchIpRoutNextHopA
     IpAddress,
    pktSwchIpRoutInterfaceIdA
     Integer32
    }


pktSwchIpRoutIdA OBJECT-TYPE
    SYNTAX Integer32 (1..200)
    MAX-ACCESS  read-only
	STATUS  current
	DESCRIPTION
	"Index of the IP pktSwchIpRoutATable."
	::= { pktSwchIpRoutAEntry 1 }


pktSwchIpRoutIpAddressA OBJECT-TYPE
    SYNTAX IpAddress
    MAX-ACCESS  read-only
    STATUS  current
    DESCRIPTION
        "The IP address to which the entry applies.
         A string of the format: X.X.X.X
         where every X is a number in the range 0-255."
    ::= { pktSwchIpRoutAEntry 2 }

pktSwchIpRoutIpMaskA OBJECT-TYPE
    SYNTAX 	IpAddress
    MAX-ACCESS  read-only
    STATUS  current
    DESCRIPTION
        "The IP mask to which the entry applies.
         A string of the format: X.X.X.X
         where every X is a number in the range 0-255."
    ::= { pktSwchIpRoutAEntry 3 }


pktSwchIpRoutDestProtocolA OBJECT-TYPE
    SYNTAX  INTEGER {
             slip       (1),
             x25SVC     (2),
             x25PVC     (3),
             frameRelay (4),
             hdlc       (5),
             snmpAgent  (6),
             ethernet   (7),
             ppp        (8),
             none      (255)
    }
    MAX-ACCESS  read-only
    STATUS  deprecated
    DESCRIPTION
	"Destination protocol for the associated address.
	 None(255) when not used."
    ::= { pktSwchIpRoutAEntry 4 }

pktSwchIpRoutDestinationA OBJECT-TYPE
    SYNTAX DisplayString
    MAX-ACCESS  read-only
    STATUS  deprecated
    DESCRIPTION
    " Destination for the associated address.
    Possible values:
    Default :     Not Used.
    X.25 PVC:     Port:LCN  or a pre defined PVC number
    X.25 SVC:     X.25 Addr or cid followed by a predefined Call ID number
    Frame Relay:  Port:DLCI
    HDLC:         'H' followed by the HDLC Port Number
    SLIP:         'S' followed by the SLIP Channel Number
    Ethernet:     'E' followed by the Ethernet Port Number
    PPP:          'P' followed by the PPP Port Number."
    ::= { pktSwchIpRoutAEntry 5 }


pktSwchIpRoutInactivityA OBJECT-TYPE
    SYNTAX Integer32
    MAX-ACCESS  read-only
    STATUS  deprecated
    DESCRIPTION
	"Inactivity time in steps of 50 mili seconds for X25 SVC
	 protocol only. Range: 0..255. Default: 2."
    ::= { pktSwchIpRoutAEntry 6 }

pktSwchIpRoutBuffsInA OBJECT-TYPE
    SYNTAX  Counter32
    MAX-ACCESS  read-only
    STATUS  current
    DESCRIPTION
    "The number of packets in the Input buffer link list,
     received but not routed yet."
    ::= { pktSwchIpRoutAEntry 7 }

pktSwchIpRoutBuffsOutA OBJECT-TYPE
    SYNTAX  Counter32
    MAX-ACCESS  read-only
    STATUS  current
    DESCRIPTION
    "The number of packets in the Output buffer link list,
     routed but not sent yet."
    ::= { pktSwchIpRoutAEntry 8 }

pktSwchIpRoutFCA OBJECT-TYPE
    SYNTAX  INTEGER {
             discard (1),
             flowControl (2),
             normal (3)
    }
    MAX-ACCESS  read-only
    STATUS  current
    DESCRIPTION
        "This is the flow control status of this ip routing
         entry\connection"
    ::= { pktSwchIpRoutAEntry 9 }

pktSwchIpRoutMetricA OBJECT-TYPE
    SYNTAX   Integer32
    MAX-ACCESS  read-only
    STATUS  current
    DESCRIPTION
    "No. of hops for this route.
     The default value is 1.
     Legal values: 1 to the max no. of hops this device will support.
     The max no. is defined by pktSwchIpGlobalMaxHopCount."
    ::= { pktSwchIpRoutAEntry 10 }

pktSwchIpRoutNextHopA OBJECT-TYPE
    SYNTAX  IpAddress
    MAX-ACCESS  read-only
    STATUS  current
    DESCRIPTION
    "IP address of the next hop.
     A string of the format: X.X.X.X
     where every X is a number in the range 0-255."
    ::= { pktSwchIpRoutAEntry 11 }

pktSwchIpRoutInterfaceIdA OBJECT-TYPE
    SYNTAX   Integer32
    MAX-ACCESS  read-only
    STATUS  current
    DESCRIPTION
    "ID of the logical IP interface in the pktSwchIpInterface table.
     The IP routing module will route the IP frame according to this
     interface ID.
     Legal values: 1 to 200 and 65535.
     1-200 : ID of interface.
     65535 : No IP interface ID.
     Default value: 65535."
     ::= { pktSwchIpRoutAEntry 12 }

-- System Priorities

pktSwchPriority  OBJECT IDENTIFIER ::= { pktSwchSystem 7 }

-- This is a table of Tx Priorities.
-- At present, it is used for DLCIs. There are 4 levels of priorities.
-- Each level contains 2 parameters: max delay time and max queue length.

-- This is a status which is used for saving the Tx Priority table.
pktSwchTxPriorityStatus OBJECT-TYPE
    SYNTAX  INTEGER {
       valid(1),
       underCreation(3)
     }
    MAX-ACCESS  read-write
    STATUS  current
    DESCRIPTION
    "The status of the Priorities table.
     Used for saving the Priority parameters. "
         ::= {pktSwchPriority 1}

pktSwchTxPriorityTable    OBJECT-TYPE
    SYNTAX  SEQUENCE  OF PktSwchTxPriorityEntry
    MAX-ACCESS  not-accessible
    STATUS  current
    DESCRIPTION
        "The Tx Priorities table."
         ::= {pktSwchPriority 2}

pktSwchTxPriorityEntry OBJECT-TYPE
    SYNTAX  PktSwchTxPriorityEntry
    MAX-ACCESS  not-accessible
    STATUS  current
    DESCRIPTION
        "The Tx Priority Entry defines the max delay time and max queue
         length for each Priority level."
    INDEX   {pktSwchTxPriorityLevel}
    ::=  { pktSwchTxPriorityTable 1 }

PktSwchTxPriorityEntry ::= SEQUENCE {
pktSwchTxPriorityLevel
Integer32,
pktSwchTxPriorityMaxDelayTime
Integer32,
pktSwchTxPriorityMaxQueueLen
Integer32     }

pktSwchTxPriorityLevel  OBJECT-TYPE
    SYNTAX Integer32 (1..4)
    MAX-ACCESS  read-only
    STATUS  current
    DESCRIPTION
        "Level of an entry in the Tx Priority Table.
         At present, the PS supports 4 priority levels.
         Default level: 1"
    ::= { pktSwchTxPriorityEntry 1 }

pktSwchTxPriorityMaxDelayTime  OBJECT-TYPE
    SYNTAX Integer32 (0..60000)
    MAX-ACCESS  read-write
    STATUS  current
    DESCRIPTION
        "Max delay time in Tx queue (in 100 msec intervals).
         Each frame will wait no more than the Max delay time until
         it is handled.
         0 means that the delay is Unlimited.
         Default value: 0"
    ::= { pktSwchTxPriorityEntry 2 }


pktSwchTxPriorityMaxQueueLen  OBJECT-TYPE
    SYNTAX Integer32 (0..65535)
    MAX-ACCESS  read-write
    STATUS  current
    DESCRIPTION
        "Max allowed length of the Tx queue. Frames will be discarded
         if the length is exceeded.
         0 means that the queue is of Unlimited length.
         Default value: 0"
    ::= { pktSwchTxPriorityEntry 3 }


-- The PS Async Group contains the Profile Table, the Channel Table,
-- the Call ID Table, the Alias Table, and the AsyncStat Table

pktSwchAsync    OBJECT IDENTIFIER ::= { radPS 2 }

-- pktSwchProfile defines the (Scratch and Active) profiles that the Packet Switch devices can use to configure a channel

pktSwchProfile 	OBJECT IDENTIFIER ::= { pktSwchAsync 1 }

-- pktSwchProfileSTable defines the Scratch profiles that the Packet Switch devices can use to configure a channel

pktSwchProfileSTable    OBJECT-TYPE
    SYNTAX  SEQUENCE  OF PktSwchProfileSEntry
    MAX-ACCESS  not-accessible
    STATUS  current
    DESCRIPTION
	"The Profile Table S defines the Scratch profiles that the PS can use to configure
   	a channel."
    ::=  { pktSwchProfile 1 }

pktSwchProfileSEntry OBJECT-TYPE
    SYNTAX  PktSwchProfileSEntry
    MAX-ACCESS  not-accessible
    STATUS  current
    DESCRIPTION
	"Defines the contents of each line in the Profile Table S."
    INDEX   { pktSwchProfileNumberS }
    ::=  { pktSwchProfileSTable 1  }

PktSwchProfileSEntry ::= SEQUENCE {
    pktSwchProfileNumberS
     Integer32,
    pktSwchProfileRecallCharS
     Integer32,
    pktSwchProfileEchoS
     INTEGER,
    pktSwchProfileDataForwCharS
     Integer32,
    pktSwchProfileIdleTimerS
     Integer32,
    pktSwchProfileDevFlowContS
     INTEGER,
    pktSwchProfileServSigS
     INTEGER,
    pktSwchProfileBreakS
     Integer32,
    pktSwchProfileDiscOutS
     INTEGER,
    pktSwchProfileCRPaddingS
     Integer32,
    pktSwchProfileLineFoldS
     Integer32,
    pktSwchProfileSpeedS
     INTEGER,
    pktSwchProfilePadFlowContS
     INTEGER,
    pktSwchProfileLineFeedInsertS
     INTEGER,
    pktSwchProfileLineFeedPadS
     Integer32,
    pktSwchProfileEditingS
     INTEGER,
    pktSwchProfileCharDelS
     Integer32,
	pktSwchProfileLineDelS
     Integer32,
    pktSwchProfileLineDispS
     Integer32,
    pktSwchProfileEditServSigS
     Integer32,
    pktSwchProfileEchomaskS
     Integer32,
    pktSwchProfileParTreatS
     INTEGER,
    pktSwchProfilePageWaitS
     Integer32,
    pktSwchProfileBitsPerCharS
     Integer32,
    pktSwchProfileDvParityS
     INTEGER,
    pktSwchProfileStopBitsS
     INTEGER,
    pktSwchProfileSpecFlowS
     INTEGER,
    pktSwchProfileCountFwdS
     Integer32,
    pktSwchProfileEscDelayS
     Integer32,
    pktSwchProfileCharBreakS
     Integer32,
    pktSwchProfileCharSuppressS
     Integer32,
    pktSwchProfileCharSubsS
     Integer32,
    pktSwchProfileFormFeedPadS
     Integer32,
    pktSwchProfileInactivityS
     Integer32,
    pktSwchProfileOptionsS
     Integer32,
    pktSwchProfileClrTimerS
     Integer32,
    pktSwchProfileSubAddInCUDS
     Integer32,
    pktSwchProfileStatusS
     INTEGER,
	pktSwchProfileIncomingMsgS
	 DisplayString,
	pktSwchProfileOutgoingMsgS
	 DisplayString,
	pktSwchProfileClearMsgS
	 DisplayString
    }

pktSwchProfileNumberS  OBJECT-TYPE
    SYNTAX Integer32 (1..200)
    MAX-ACCESS  read-only
    STATUS  current
    DESCRIPTION
	"The number by which a profile is identified.  This is also used as the index for the profile table.
		 The maximum profile number is 200."
    ::= { pktSwchProfileSEntry 1  }

pktSwchProfileRecallCharS  OBJECT-TYPE
    SYNTAX Integer32 (0..126)
    MAX-ACCESS  read-write
    STATUS  current
    DESCRIPTION
	"The character specified by this entry is used to escape from the data transfer
		 mode and enter the PAD command mode.  The integer values have the following meanings:
			 (0)                 PAD recall is not possible
			 (1)                 The PAD recall character is DLE
			 (2)  to (126)  The PAD recall character is specified by the user by entering its ASCII
		code."
    ::= { pktSwchProfileSEntry 2  }

pktSwchProfileEchoS OBJECT-TYPE
    SYNTAX  INTEGER {
       echEn(1),
       noEch(2)
     }
    MAX-ACCESS  read-write
    STATUS  current
    DESCRIPTION
	"This determines if an echo of the input characters is retured to the DTE.
		 The options are either  'echo enabled'  or 'no echo'."
   ::= { pktSwchProfileSEntry 3  }

pktSwchProfileDataForwCharS OBJECT-TYPE
    SYNTAX  Integer32 (0..127)
    MAX-ACCESS  read-write
    STATUS  current
    DESCRIPTION
	"The value is a sum of values (powers of two), where each value in the sum represents
		a character (or characters) that is (are) used as a data forwarding character.  The data
		forwarding characters are used to instruct the PAD to complete the assembly of and to
		forward a packet containing the data accumulated up to the reception of such a character.
		The values that may be included in the sum and their meanings are:
		0   Data forwarding characters are not used
		1   Alpha-numeric characters (A to Z, a to z, 0 to 9, inclusive)
		2   Character CR
		4   Characters ESC, BEL, ENQ, ACK
		8   Characters DEL, CAN, DC2
		16 Characters EOT, ETX
		32 Characters HT, LF, VT, FF
		64 All the other characters in colums 0 and 1 of IA5 and not listed above."
   ::= { pktSwchProfileSEntry 4 }

pktSwchProfileIdleTimerS OBJECT-TYPE
    SYNTAX  Integer32 (0..255)
    MAX-ACCESS  read-write
    STATUS  current
    DESCRIPTION
	"Packets will be forwarded when the idle timer expires.  The idle time interval is specified
		 as a multiple of 50 milliseconds.  The multiple is given by the parameter value.  For example,
		 a value of 60 sets an interval of 3 seconds.  If the parameter value is 0, no forwarding occurs
		 after the idle condition."
   ::= { pktSwchProfileSEntry 5 }

pktSwchProfileDevFlowContS OBJECT-TYPE
    SYNTAX  INTEGER  {
       trans(1),
       transAndCom(2),
       noFlow(255)
    }
    MAX-ACCESS  read-write
    STATUS  current
    DESCRIPTION
	"This parameter determines whether or not the PAD uses software flow control for the
		attached device.  The options are either (1) PAD uses flow control during data transfer
		 mode, (2) PAD uses flow control both in the data transfer mode and in the command mode,
		 or (255) PAD does not use flow control."
   ::= { pktSwchProfileSEntry 6 }

pktSwchProfileServSigS OBJECT-TYPE
    SYNTAX  INTEGER  {
       serv(1),
       prompt(4),
       servAndPrompt(5),
       noSig(255)
    }
    MAX-ACCESS  read-write
    STATUS  current
    DESCRIPTION
	"This parameter is used to instruct the PAD whether to transfer PAD service signals and
		 the PAD prompt to the local DTE in standard format.  The options are (1) PAD service
		 signals are transmitted to the DTE using the standard format, (4) The PAD prompt is
		 transmitted using the standard format, (5) PAD service signals and the PAD prompt are
		 transmitted in the standard format, or (255) No PAD service signals are transmitted to the
		 DTE."
    ::= { pktSwchProfileSEntry 7 }

pktSwchProfileBreakS OBJECT-TYPE
    SYNTAX  Integer32 (0..31)
    MAX-ACCESS  read-write
    STATUS  current
    DESCRIPTION
	"The value is a sum of values (powers of two), where each value in the sum represents
		a PAD operation on receipt of the break signal from the DTE.
		The values that may be included in the sum and their meanings are:
		0   Nothing
		1   Send interrupt packet to network
		2   Send RESET packet to network
		4   Send and 'indication of break' message
		8   Escape from data transfer mode
		16 Discard output data waiting to be sent to the DTE ."
   ::= { pktSwchProfileSEntry 8 }

pktSwchProfileDiscOutS OBJECT-TYPE
    SYNTAX  INTEGER {
       discOut(1),
       normal(2)
     }
    MAX-ACCESS  read-only
    STATUS  current
    DESCRIPTION
	"This parameter instructs the PAD whether to forward the user sequences included in
		data packets to the local DTE or discard them.  The options are (1) discard output or
		 (2) normal data delivery.  If the value of radSPSProfileBreak is 21, the value of
		 pktSwchProfileDiscOut is automatically set to (1) when a break signal is received."
   ::= { pktSwchProfileSEntry 9  }

pktSwchProfileCRPaddingS OBJECT-TYPE
    SYNTAX  Integer32 (0..127)
    MAX-ACCESS  read-write
    STATUS  current
    DESCRIPTION
	"This parameter specifies the number of padding characters to be added after a carriage
		 return character is transmitted to the local DTE."
   ::= { pktSwchProfileSEntry 10}

pktSwchProfileLineFoldS OBJECT-TYPE
    SYNTAX  Integer32 (0..255)
    MAX-ACCESS  read-write
    STATUS  current
    DESCRIPTION
	"This parameter specifies the maximum number of characters to be inserted before the
		 format effector.  If the value is zero, there is no insertion of a format effector (line folding)."
    ::= { pktSwchProfileSEntry 11}

pktSwchProfileSpeedS OBJECT-TYPE
    SYNTAX  INTEGER  {
       s110bps(1),
       s300bps(2),
       s1200bps(3),
       s600bps(4),
       s75bps(5),
       s150bps(6),
       s2400bps(12),
       s4800bps(13),
       s9600bps(14),
       s19200bps(15),
       s38400bps(19),
	   s57600bps(20),
	   s115200bps(21)
    }
    MAX-ACCESS  read-write
    STATUS  current
    DESCRIPTION
	"This parameter determines the rate of data transmission to and from the DTE."
    ::= { pktSwchProfileSEntry 12 }

pktSwchProfilePadFlowContS OBJECT-TYPE
    SYNTAX  INTEGER {
       flowCont(1),
       noFlowCont(2)
     }
    MAX-ACCESS  read-write
    STATUS  current
    DESCRIPTION
	"This determines whether or not the terminal can exercise flow control over the PAD.
		 The options are either 'device can exercise flow control' or 'device cannot exercise flow
		 control."
   ::= { pktSwchProfileSEntry 13  }

pktSwchProfileLineFeedInsertS OBJECT-TYPE
    SYNTAX  INTEGER  {
       afterCR(1),
       recCR(2),
       echoCR(4),
       onePlusFour(5),
       twoPlusFour(6),
       oneTwoFour(7),
       noFeed(255)
    }
    MAX-ACCESS  read-write
    STATUS  current
    DESCRIPTION
	"This parameter indicates when there is a line feed insertion after CR.  The options are
		  (1) Insert line feed after transmission of CR to the DTE, (2) Insert line feed after receipt
		 of CR from the DTE, (4) Insert line feed after echoing a CR character to the DTE,
		 (5) Combination of (1) and (4), (6) Insert line feed after any CR to the DTE (combination of
		 (2) and (4)), (7) Combination of (1), (2), and (4), or (255) No line feed insertion."
    ::= { pktSwchProfileSEntry 14 }

pktSwchProfileLineFeedPadS OBJECT-TYPE
    SYNTAX  Integer32 (0..127)
    MAX-ACCESS  read-write
    STATUS  current
    DESCRIPTION
	"This parameter specifies the number of padding characters to be added after a line
		 feed."
   ::= { pktSwchProfileSEntry 15 }

pktSwchProfileEditingS OBJECT-TYPE
    SYNTAX  INTEGER {
       edit(1),
       noEdit(2)
     }
    MAX-ACCESS  read-write
    STATUS  current
    DESCRIPTION
	"This parameter specifies the editing capabilities available in the data transfer mode.
		Editing is always possible when the PAD is in the command mode.  The options are
		 (1) Command editing in the data trasfer mode is enabled or (2) No command editing
		 in the data transfer mode."
   ::= { pktSwchProfileSEntry 16  }

pktSwchProfileCharDelS OBJECT-TYPE
    SYNTAX  Integer32 (0..127)
    MAX-ACCESS  read-write
    STATUS  current
    DESCRIPTION
	"This parameter specifies the character delete, which is one character from IA5.  The default
		selection is 127 (character DEL)."
   ::= { pktSwchProfileSEntry 17}


pktSwchProfileLineDelS OBJECT-TYPE
    SYNTAX  Integer32 (0..127)
    MAX-ACCESS  read-write
    STATUS  current
    DESCRIPTION
	"This parameter specifies the line delete (last line stored in the edit buffer), which is one character from IA5.  The default
		selection is 24 (character CAN)."
   ::= { pktSwchProfileSEntry 18}

pktSwchProfileLineDispS OBJECT-TYPE
    SYNTAX  Integer32 (0..127)
    MAX-ACCESS  read-write
    STATUS  current
    DESCRIPTION
	"This entry specifies the line display character, which is one character
		from IA5.  The default selection is 18 (character DC2)."
   ::= { pktSwchProfileSEntry 19}

pktSwchProfileEditServSigS  OBJECT-TYPE
    SYNTAX Integer32 (0..126)
    MAX-ACCESS  read-write
    STATUS  current
    DESCRIPTION
	"This entry specifies the editing PAD service signals.
		The integer values have the following meanings:
			 (0)                 No editing PAD service signals
			 (1)                 Editing PAD service signals for printing terminals
			 (2)                 Editing PAD service signals for display terminals
			 (3)  to (126)  Editing PAD service signals using the desired character from IA5."
    ::= { pktSwchProfileSEntry 20  }

pktSwchProfileEchomaskS OBJECT-TYPE
    SYNTAX  Integer32 (0..255)
    MAX-ACCESS  read-write
    STATUS  current
    DESCRIPTION
	"The value is a sum of values (powers of two), where each value in the sum represents
		a character (or characters) that is (are) included in the echo mask.  The characters in the
		echo mask are not echoed to the DTE when PAD echo is enabled.
		The values that may be included in the sum and their meanings are:
		0   No echo mask (all the characters are echoed)
		1   No echo of character CR
		2   No echo of character LF
		4   No echo of characters VT, HT, FF
		8   No echo of characters BEL, BS
		16 No echo of characters ESC, ENQ
		32 No echo of characters ACK, NAK, STX, SOH, EOT, ETB, ETX
		64 No echo of the editing characters selected by radSPSProfileCharDel,
														       radSPSProfileLineDel, and
														       radSPSProfileLineDisp
				128 No echo of the DEL character and of all the other characters in the range of
					ASCII 00 through 31 not mentioned above."
	::= { pktSwchProfileSEntry 21 }

pktSwchProfileParTreatS OBJECT-TYPE
    SYNTAX  INTEGER  {
       parCheck(1),
       parGen(2),
       checkAndGen(3),
       noPar(255)
    }
    MAX-ACCESS  read-write
    STATUS  current
    DESCRIPTION
	"This entry controls the generation of parity bits in the data sent to the local DTE and the
		checking of the parity bit when generated by the local DTE.  The options are (1) parity
		checking is enabled, (2) parity generation is enabled, (3) parity checking and generation are
		enabled, or (255) no parity checking nor parity generation."
    ::= { pktSwchProfileSEntry 22 }

pktSwchProfilePageWaitS OBJECT-TYPE
    SYNTAX  Integer32 (0..255)
    MAX-ACCESS  read-write
    STATUS  current
    DESCRIPTION
	"This entry specifies the number of line feed characters counted by the PAD before the
		page wait condition is entered.  If the value is zero, page wait is disabled."
   ::= { pktSwchProfileSEntry 23}

pktSwchProfileBitsPerCharS  OBJECT-TYPE
    SYNTAX Integer32 (5..8)
    MAX-ACCESS  read-write
    STATUS  current
    DESCRIPTION
	"The number of data bits per character supported by the PAD."
    ::= { pktSwchProfileSEntry 24 }

pktSwchProfileDvParityS OBJECT-TYPE
    SYNTAX  INTEGER  {
       space(1),
       mark(2),
       even(3),
       odd(4),
       none(255)
    }
    MAX-ACCESS  read-write
    STATUS  current
    DESCRIPTION
	"This entry selects the type of parity to be checked and or generated by the PAD
		 when radSPSProfileParTreat is a value other than 255.  The options are
		  (1) space parity, (2) mark parity, (3) even parity, (4) odd parity, or (255) no parity."
    ::= { pktSwchProfileSEntry 25 }

pktSwchProfileStopBitsS OBJECT-TYPE
    SYNTAX  INTEGER  {
       one(1),
       two(2),
       oneAndHalf(3)
    }
    MAX-ACCESS  read-write
    STATUS  current
    DESCRIPTION
	"This entry indicates the number of stop bits per character supported by the PAD.
		The options are either (1) one stop bit, (2) two stop bits, or (3) 1.5 stop bits."
   ::= { pktSwchProfileSEntry 26 }

pktSwchProfileSpecFlowS OBJECT-TYPE
    SYNTAX  INTEGER {
       spec(1),
       noSpec(2)
     }
    MAX-ACCESS  read-write
    STATUS  current
    DESCRIPTION
	"This entry is used to define additional flow control possiblilites.
		 The options are either  (1) Flow control by means of the terminal DTR line
		 or (2) No special flow control."
   ::= { pktSwchProfileSEntry 27  }

pktSwchProfileCountFwdS OBJECT-TYPE
    SYNTAX  Integer32 (0..255)
    MAX-ACCESS  read-write
    STATUS  current
    DESCRIPTION
	"This entry can be used to instruct the PAD to complete the assembly of a packet
		and to forward it after the specifed number of characters has been received.
		If the value is zero, count forwarding is disabled."
   ::= { pktSwchProfileSEntry 28}

pktSwchProfileEscDelayS OBJECT-TYPE
    SYNTAX  Integer32 (0..255)
    MAX-ACCESS  read-write
    STATUS  current
    DESCRIPTION
"This entry can be used to instruct the PAD whether to delay the forwarding of
a data packet when an escape character is detected in the data stream and to
determine the required delay.  The packet forwarding is delayed until the specified
number of characters is received after the escape character.  A value of zero indicates
no special handling( at the moment up to 10 chars are accepted)."
   ::= { pktSwchProfileSEntry 29}

pktSwchProfileCharBreakS OBJECT-TYPE
    SYNTAX  Integer32 (0..127)
    MAX-ACCESS  read-write
    STATUS  current
    DESCRIPTION
	"This entry specifies the decimal value of the character that will be interpreted
		as an additional break signal by the PAD.  A value of zero indicates no break character."
   ::= { pktSwchProfileSEntry 30}

pktSwchProfileCharSuppressS OBJECT-TYPE
    SYNTAX  Integer32 (0..127)
    MAX-ACCESS  read-write
    STATUS  current
    DESCRIPTION
	"This entry specifies the decimal value of the character that will toggle
		echo suppression in the PAD.  A value of zero indicates that echo suppression
		 is only controlled by radSPSProfileEcho."
   ::= { pktSwchProfileSEntry 31}

pktSwchProfileCharSubsS OBJECT-TYPE
    SYNTAX  Integer32 (0..127)
    MAX-ACCESS  read-write
    STATUS  current
    DESCRIPTION
	"This entry specifies the decimal value of the character that will be echoed
		instead of the character received from the user's DTE.  A zero value indicates that
		 no character is echoed."
   ::= { pktSwchProfileSEntry 32}

pktSwchProfileFormFeedPadS OBJECT-TYPE
    SYNTAX  Integer32 (0..127)
    MAX-ACCESS  read-write
    STATUS  current
    DESCRIPTION
	"This entry specifies the number of padding (NUL) characters that will be
		automatically sent after the form feed character."
   ::= { pktSwchProfileSEntry 33}

pktSwchProfileInactivityS OBJECT-TYPE
    SYNTAX  Integer32 (0..255)
    MAX-ACCESS  read-write
    STATUS  current
    DESCRIPTION
	"This entry specifies the number of minutes after which the PAD will forward
		the accumulated data and clear the call.  A zero value indicates no disconnection
		on inactivity."
   ::= { pktSwchProfileSEntry 34 }

pktSwchProfileOptionsS OBJECT-TYPE
    SYNTAX  Integer32 (0..255)
    MAX-ACCESS  read-write
    STATUS  current
    DESCRIPTION
	"This entry defines several options to control the profile.  The value is a sum of values
		(powers of two), where each value in the sum represents an option .
	The values that may be included in the sum and their meanings are:
		0   No options
		1   Remote set of local X.3 parameters through X.29 is disabled
		2   Add sub address to call request
		4   Don't use protocol ID in user data field.
		8   SPRINT NUI format
		16  More bit is set when the edit buffer is full
        32  Extended error message
        64  Discard  connect extended service signal
        128 enable connect by typing the address w/out a command"
   ::= { pktSwchProfileSEntry 35 }

pktSwchProfileClrTimerS OBJECT-TYPE
    SYNTAX  Integer32 (0..255)
    MAX-ACCESS  read-write
    STATUS  current
    DESCRIPTION
	"This entry specifies the number of minutes after which a call is cleared.
		  If the parameter value is 0, there is no disconnection timer."
   ::= { pktSwchProfileSEntry 36 }

pktSwchProfileSubAddInCUDS OBJECT-TYPE
    SYNTAX  Integer32 (0..5)
    MAX-ACCESS  read-write
    STATUS  current
    DESCRIPTION
	"This entry defines the number of digits for the subaddress in CUD."
    ::= { pktSwchProfileSEntry 37 }

pktSwchProfileStatusS OBJECT-TYPE
    SYNTAX  INTEGER {
       valid(1),
       createRequest(2),
       underCreation(3),
       invalid(4)
     }
    MAX-ACCESS  read-write
    STATUS  current
    DESCRIPTION
	"The status of this profile.  The choices are those defined in the SNMPv2 Textual Conventions
		 for RowStatus.  This will allow easy replacement of the INTEGER syntax with the RowStatus
		 textual convention SYNTAX."
    ::= { pktSwchProfileSEntry 38 }

pktSwchProfileIncomingMsgS OBJECT-TYPE
    SYNTAX  DisplayString (SIZE (0..20))
    MAX-ACCESS  read-write
    STATUS  current
    DESCRIPTION
	"This object enables the asynchronous user to change the 'com' message for 
	 Incoming calls to a string of up to 20 characters.
	 If user selects the value xxx for this object, the PAD will convert it to
	 the relevant X.25 address, followed by CR LF COM (Carriage-Return, Line-Feed,
	 com). 
	 Example: 'called by XXX' will be converted to 'called by <X.25 address> com'."
    ::= { pktSwchProfileSEntry 39 }

pktSwchProfileOutgoingMsgS OBJECT-TYPE
    SYNTAX  DisplayString (SIZE (0..20))
    MAX-ACCESS  read-write
    STATUS  current
    DESCRIPTION
	"This object enables the asynchronous user to change the 'com' message for 
	 Outgoing calls to a string of up to 20 characters.
	 If user selects the value xxx for this object, the PAD will convert it to
	 the relevant X.25 address, followed by CR LF COM (Carriage-Return, Line-Feed,
	 com)."
    ::= { pktSwchProfileSEntry 40 }

pktSwchProfileClearMsgS OBJECT-TYPE
    SYNTAX  DisplayString (SIZE (0..20))
    MAX-ACCESS  read-write
    STATUS  current
    DESCRIPTION
	"This object enables the user to edit a message, which will appear when
	 the channel is cleared. The message is a string of up to 20 characters.
	 Example of such a string: 'Call Cleared'."
    ::= { pktSwchProfileSEntry 41 }



-- pktSwchProfileATable defines the Active profiles that the Packet Switch devices can use to configure a channel


pktSwchProfileATable    OBJECT-TYPE
    SYNTAX  SEQUENCE  OF PktSwchProfileAEntry
    MAX-ACCESS  not-accessible
    STATUS  current
    DESCRIPTION
	"The Profile Table defines the profiles that the PS can use to configure
	a channel."
    ::=  { pktSwchProfile 2 }

pktSwchProfileAEntry OBJECT-TYPE
    SYNTAX  PktSwchProfileAEntry
    MAX-ACCESS  not-accessible
    STATUS  current
    DESCRIPTION
	"Defines the contents of each line in the Profile Table."
    INDEX   { pktSwchProfileNumberA }
    ::=  { pktSwchProfileATable 1  }

PktSwchProfileAEntry ::= SEQUENCE {
    pktSwchProfileNumberA
     Integer32,
    pktSwchProfileRecallCharA
     Integer32,
    pktSwchProfileEchoA
     INTEGER,
    pktSwchProfileDataForwCharA
     Integer32,
    pktSwchProfileIdleTimerA
     Integer32,
    pktSwchProfileDevFlowContA
     INTEGER,
    pktSwchProfileServSigA
     INTEGER,
    pktSwchProfileBreakA
     Integer32,
    pktSwchProfileDiscOutA
     INTEGER,
    pktSwchProfileCRPaddingA
     Integer32,
    pktSwchProfileLineFoldA
     Integer32,
    pktSwchProfileSpeedA
     INTEGER,
    pktSwchProfilePadFlowContA
     INTEGER,
    pktSwchProfileLineFeedInsertA
     INTEGER,
    pktSwchProfileLineFeedPadA
     Integer32,
    pktSwchProfileEditingA
     INTEGER,
    pktSwchProfileCharDelA
     Integer32,
	pktSwchProfileLineDelA
     Integer32,
    pktSwchProfileLineDispA
     Integer32,
    pktSwchProfileEditServSigA
     Integer32,
    pktSwchProfileEchomaskA
     Integer32,
    pktSwchProfileParTreatA
     INTEGER,
    pktSwchProfilePageWaitA
     Integer32,
    pktSwchProfileBitsPerCharA
     Integer32,
    pktSwchProfileDvParityA
     INTEGER,
    pktSwchProfileStopBitsA
     INTEGER,
    pktSwchProfileSpecFlowA
     INTEGER,
    pktSwchProfileCountFwdA
     Integer32,
    pktSwchProfileEscDelayA
     Integer32,
    pktSwchProfileCharBreakA
     Integer32,
    pktSwchProfileCharSuppressA
     Integer32,
    pktSwchProfileCharSubsA
     Integer32,
    pktSwchProfileFormFeedPadA
     Integer32,
    pktSwchProfileInactivityA
     Integer32,
    pktSwchProfileOptionsA
     Integer32,
    pktSwchProfileClrTimerA
     Integer32,
    pktSwchProfileSubAddInCUDA
     Integer32,
	pktSwchProfileIncomingMsgA
	 DisplayString,
	pktSwchProfileOutgoingMsgA
	 DisplayString,
	pktSwchProfileClearMsgA
	 DisplayString
    }

pktSwchProfileNumberA  OBJECT-TYPE
    SYNTAX Integer32 (1..200)
    MAX-ACCESS  read-only
    STATUS  current
    DESCRIPTION
	"The number by which a profile is identified.  This is also used as the index for the profile table.
		 The maximum profile number is 200."
    ::= { pktSwchProfileAEntry 1  }

pktSwchProfileRecallCharA  OBJECT-TYPE
    SYNTAX Integer32 (0..126)
    MAX-ACCESS  read-only
    STATUS  current
    DESCRIPTION
	"The character specified by this entry is used to escape from the data transfer
		 mode and enter the PAD command mode.  The integer values have the following meanings:
			 (0)                 PAD recall is not possible
			 (1)                 The PAD recall character is DLE
			 (2)  to (126)  The PAD recall character is specified by the user by entering its ASCII
		code."
    ::= { pktSwchProfileAEntry 2  }

pktSwchProfileEchoA OBJECT-TYPE
    SYNTAX  INTEGER {
       echEn(1),
       noEch(2)
     }
    MAX-ACCESS  read-only
    STATUS  current
    DESCRIPTION
	"This determines if an echo of the input characters is retured to the DTE.
		 The options are either  'echo enabled'  or 'no echo'."
   ::= { pktSwchProfileAEntry 3  }

pktSwchProfileDataForwCharA OBJECT-TYPE
    SYNTAX  Integer32 (0..127)
    MAX-ACCESS  read-only
    STATUS  current
    DESCRIPTION
	"The value is a sum of values (powers of two), where each value in the sum represents
		a character (or characters) that is (are) used as a data forwarding character.  The data
		forwarding characters are used to instruct the PAD to complete the assembly of and to
		forward a packet containing the data accumulated up to the reception of such a character.
		The values that may be included in the sum and their meanings are:
		0   Data forwarding characters are not used
		1   Alpha-numeric characters (A to Z, a to z, 0 to 9, inclusive)
		2   Character CR
		4   Characters ESC, BEL, ENQ, ACK
		8   Characters DEL, CAN, DC2
		16 Characters EOT, ETX
		32 Characters HT, LF, VT, FF
		64 All the other characters in colums 0 and 1 of IA5 and not listed above."
   ::= { pktSwchProfileAEntry 4 }

pktSwchProfileIdleTimerA OBJECT-TYPE
    SYNTAX  Integer32 (0..255)
    MAX-ACCESS  read-only
    STATUS  current
    DESCRIPTION
	"Packets will be forwarded when the idle timer expires.  The idle time interval is specified
		 as a multiple of 50 milliseconds.  The multiple is given by the parameter value.  For example,
		 a value of 60 sets an interval of 3 seconds.  If the parameter value is 0, no forwarding occurs
		 after the idle condition."
   ::= { pktSwchProfileAEntry 5 }

pktSwchProfileDevFlowContA OBJECT-TYPE
    SYNTAX  INTEGER  {
       trans(1),
       transAndCom(2),
       noFlow(255)
    }
    MAX-ACCESS  read-only
    STATUS  current
    DESCRIPTION
	"This parameter determines whether or not the PAD uses software flow control for the
		attached device.  The options are either (1) PAD uses flow control during data transfer
		 mode, (2) PAD uses flow control both in the data transfer mode and in the command mode,
		 or (255) PAD does not use flow control."
   ::= { pktSwchProfileAEntry 6 }

pktSwchProfileServSigA OBJECT-TYPE
    SYNTAX  INTEGER  {
       serv(1),
       prompt(4),
       servAndPrompt(5),
       noSig(255)
    }
    MAX-ACCESS  read-only
    STATUS  current
    DESCRIPTION
	"This parameter is used to instruct the PAD whether to transfer PAD service signals and
		 the PAD prompt to the local DTE in standard format.  The options are (1) PAD service
		 signals are transmitted to the DTE using the standard format, (4) The PAD prompt is
		 transmitted using the standard format, (5) PAD service signals and the PAD prompt are
		 transmitted in the standard format, or (255) No PAD service signals are transmitted to the
		 DTE."
    ::= { pktSwchProfileAEntry 7 }

pktSwchProfileBreakA OBJECT-TYPE
    SYNTAX  Integer32 (0..31)
    MAX-ACCESS  read-only
    STATUS  current
    DESCRIPTION
	"The value is a sum of values (powers of two), where each value in the sum represents
		a PAD operation on receipt of the break signal from the DTE.
		The values that may be included in the sum and their meanings are:
		0   Nothing
		1   Send interrupt packet to network
		2   Send RESET packet to network
		4   Send and 'indication of break' message
		8   Escape from data transfer mode
		16 Discard output data waiting to be sent to the DTE ."
   ::= { pktSwchProfileAEntry 8 }

pktSwchProfileDiscOutA OBJECT-TYPE
    SYNTAX  INTEGER {
       discOut(1),
       normal(2)
     }
    MAX-ACCESS  read-only
    STATUS  current
    DESCRIPTION
	"This parameter instructs the PAD whether to forward the user sequences included in
		data packets to the local DTE or discard them.  The options are (1) discard output or
		 (2) normal data delivery.  If the value of radSPSProfileBreak is 21, the value of
		 pktSwchProfileDiscOut is automatically set to (1) when a break signal is received."
   ::= { pktSwchProfileAEntry 9  }

pktSwchProfileCRPaddingA OBJECT-TYPE
    SYNTAX  Integer32 (0..127)
    MAX-ACCESS  read-only
    STATUS  current
    DESCRIPTION
	"This parameter specifies the number of padding characters to be added after a carriage
		 return character is transmitted to the local DTE."
   ::= { pktSwchProfileAEntry 10}

pktSwchProfileLineFoldA OBJECT-TYPE
    SYNTAX  Integer32 (0..255)
    MAX-ACCESS  read-only
    STATUS  current
    DESCRIPTION
	"This parameter specifies the maximum number of characters to be inserted before the
		 format effector.  If the value is zero, there is no insertion of a format effector (line folding)."
    ::= { pktSwchProfileAEntry 11}

pktSwchProfileSpeedA OBJECT-TYPE
    SYNTAX  INTEGER  {
       s110bps(1),
       s300bps(2),
       s1200bps(3),
       s600bps(4),
       s75bps(5),
       s150bps(6),
       s2400bps(12),
       s4800bps(13),
       s9600bps(14),
       s19200bps(15),
       s38400bps(19),
	   s57600bps(20),
	   s115200bps(21)
    }
    MAX-ACCESS  read-only
    STATUS  current
    DESCRIPTION
	"This parameter determines the rate of data transmission to and from the DTE."
    ::= { pktSwchProfileAEntry 12 }

pktSwchProfilePadFlowContA OBJECT-TYPE
    SYNTAX  INTEGER {
       flowCont(1),
       noFlowCont(2)
     }
    MAX-ACCESS  read-only
    STATUS  current
    DESCRIPTION
	"This determines whether or not the terminal can exercise flow control over the PAD.
		 The options are either 'device can exercise flow control' or 'device cannot exercise flow
		 control."
   ::= { pktSwchProfileAEntry 13  }

pktSwchProfileLineFeedInsertA OBJECT-TYPE
    SYNTAX  INTEGER  {
       afterCR(1),
       recCR(2),
       echoCR(4),
       onePlusFour(5),
       twoPlusFour(6),
       oneTwoFour(7),
       noFeed(255)
    }
    MAX-ACCESS  read-only
    STATUS  current
    DESCRIPTION
	"This parameter indicates when there is a line feed insertion after CR.  The options are
		  (1) Insert line feed after transmission of CR to the DTE, (2) Insert line feed after receipt
		 of CR from the DTE, (4) Insert line feed after echoing a CR character to the DTE,
		 (5) Combination of (1) and (4), (6) Insert line feed after any CR to the DTE (combination of
		 (2) and (4)), (7) Combination of (1), (2), and (4), or (255) No line feed insertion."
    ::= { pktSwchProfileAEntry 14 }

pktSwchProfileLineFeedPadA OBJECT-TYPE
    SYNTAX  Integer32 (0..255)
    MAX-ACCESS  read-only
    STATUS  current
    DESCRIPTION
	"This parameter specifies the number of padding characters to be added after a line
		 feed."
   ::= { pktSwchProfileAEntry 15 }

pktSwchProfileEditingA OBJECT-TYPE
    SYNTAX  INTEGER {
       edit(1),
       noEdit(2)
     }
    MAX-ACCESS  read-only
    STATUS  current
    DESCRIPTION
	"This parameter specifies the editing capabilities available in the data transfer mode.
		Editing is always possible when the PAD is in the command mode.  The options are
		 (1) Command editing in the data trasfer mode is enabled or (2) No command editing
		 in the data transfer mode."
   ::= { pktSwchProfileAEntry 16  }

pktSwchProfileCharDelA OBJECT-TYPE
    SYNTAX  Integer32 (0..127)
    MAX-ACCESS  read-only
    STATUS  current
    DESCRIPTION
	"This parameter specifies the character delete, which is one character from IA5.  The default
		selection is 127 (character DEL)."
   ::= { pktSwchProfileAEntry 17}


pktSwchProfileLineDelA OBJECT-TYPE
    SYNTAX  Integer32 (0..127)
    MAX-ACCESS  read-only
    STATUS  current
    DESCRIPTION
	"This parameter specifies the line delete, which is one character from IA5.  The default
		selection is 24 (character CAN)."
   ::= { pktSwchProfileAEntry 18}

pktSwchProfileLineDispA OBJECT-TYPE
    SYNTAX  Integer32 (0..127)
    MAX-ACCESS  read-only
    STATUS  current
    DESCRIPTION
	"This entry specifies the line display character, which is one character
		from IA5.  The default selection is 18 (character DC2)."
   ::= { pktSwchProfileAEntry 19}

pktSwchProfileEditServSigA  OBJECT-TYPE
    SYNTAX Integer32 (0..126)
    MAX-ACCESS  read-only
    STATUS  current
    DESCRIPTION
	"This entry specifies the editing PAD service signals.
		The integer values have the following meanings:
			 (0)                 No editing PAD service signals
			 (1)                 Editing PAD service signals for printing terminals
			 (2)                 Editing PAD service signals for display terminals
			 (3)  to (126)  Editing PAD service signals using the desired character from IA5."
    ::= { pktSwchProfileAEntry 20  }

pktSwchProfileEchomaskA OBJECT-TYPE
    SYNTAX  Integer32 (0..255)
    MAX-ACCESS  read-only
    STATUS  current
    DESCRIPTION
	"The value is a sum of values (powers of two), where each value in the sum represents
		a character (or characters) that is (are) included in the echo mask.  The characters in the
		echo mask are not echoed to the DTE when PAD echo is enabled.
		The values that may be included in the sum and their meanings are:
		0   No echo mask (all the characters are echoed)
		1   No echo of character CR
		2   No echo of character LF
		4   No echo of characters VT, HT, FF
		8   No echo of characters BEL, BS
		16 No echo of characters ESC, ENQ
		32 No echo of characters ACK, NAK, STX, SOH, EOT, ETB, ETX
		64 No echo of the editing characters selected by radSPSProfileCharDel,
														       radSPSProfileLineDel, and
														       radSPSProfileLineDisp
				128 No echo of the DEL character and of all the other characters in the range of
					ASCII 00 through 31 not mentioned above."
	::= { pktSwchProfileAEntry 21 }

pktSwchProfileParTreatA OBJECT-TYPE
    SYNTAX  INTEGER  {
       parCheck(1),
       parGen(2),
       checkAndGen(3),
       noPar(255)
    }
    MAX-ACCESS  read-only
    STATUS  current
    DESCRIPTION
	"This entry controls the generation of parity bits in the data sent to the local DTE and the
		checking of the parity bit when generated by the local DTE.  The options are (1) parity
		checking is enabled, (2) parity generation is enabled, (3) parity checking and generation are
		enabled, or (255) no parity checking nor parity generation."
    ::= { pktSwchProfileAEntry 22 }

pktSwchProfilePageWaitA OBJECT-TYPE
    SYNTAX  Integer32 (0..255)
    MAX-ACCESS  read-only
    STATUS  current
    DESCRIPTION
	"This entry specifies the number of line feed characters counted by the PAD before the
		page wait condition is entered.  If the value is zero, page wait is disabled."
   ::= { pktSwchProfileAEntry 23}

pktSwchProfileBitsPerCharA  OBJECT-TYPE
    SYNTAX Integer32 (5..8)
    MAX-ACCESS  read-only
    STATUS  current
    DESCRIPTION
	"The number of data bits per character supported by the PAD."
    ::= { pktSwchProfileAEntry 24 }

pktSwchProfileDvParityA OBJECT-TYPE
    SYNTAX  INTEGER  {
       space(1),
       mark(2),
       even(3),
       odd(4),
       none(255)
    }
    MAX-ACCESS  read-only
    STATUS  current
    DESCRIPTION
	"This entry selects the type of parity to be checked and or generated by the PAD
		 when radSPSProfileParTreat is a value other than 255.  The options are
		  (1) space parity, (2) mark parity, (3) even parity, (4) odd parity, or (255) no parity."
    ::= { pktSwchProfileAEntry 25 }

pktSwchProfileStopBitsA OBJECT-TYPE
    SYNTAX  INTEGER  {
       one(1),
       two(2),
       oneAndHalf(3)
    }
    MAX-ACCESS  read-only
    STATUS  current
    DESCRIPTION
	"This entry indicates the number of stop bits per character supported by the PAD.
		The options are either (1) one stop bit, (2) two stop bits, or (3) 1.5 stop bits."
   ::= { pktSwchProfileAEntry 26 }

pktSwchProfileSpecFlowA OBJECT-TYPE
    SYNTAX  INTEGER {
       spec(1),
       noSpec(2)
     }
    MAX-ACCESS  read-only
    STATUS  current
    DESCRIPTION
	"This entry is used to define additional flow control possiblilites.
		 The options are either  (1) Flow control by means fo the terminal DTR line
		 or (2) No special flow control."
   ::= { pktSwchProfileAEntry 27  }

pktSwchProfileCountFwdA OBJECT-TYPE
    SYNTAX  Integer32 (0..255)
    MAX-ACCESS  read-only
    STATUS  current
    DESCRIPTION
	"This entry can be used to instruct the PAD to complete the assembly of a packet
		and to forward it after the specifed number of characters has been received.
		If the value is zero, count forwarding is disabled."
   ::= { pktSwchProfileAEntry 28}

pktSwchProfileEscDelayA OBJECT-TYPE
    SYNTAX  Integer32 (1..255)
    MAX-ACCESS  read-only
    STATUS  current
    DESCRIPTION
	"This entry can be used to instruct the PAD whether to delay the forwarding of
		a data packet when an escape character is detected in the data stream and to
		determine the required delay.  The packet forwarding is delayed until the specified
		number of characters is received after the escape character.  A value of zero indicates
		no special handling."
   ::= { pktSwchProfileAEntry 29}

pktSwchProfileCharBreakA OBJECT-TYPE
    SYNTAX  Integer32 (0..127)
    MAX-ACCESS  read-only
    STATUS  current
    DESCRIPTION
	"This entry specifies the decimal value of the character that will be interpreted
		as an additional break signal by the PAD.  A value of zero indicates no break character."
   ::= { pktSwchProfileAEntry 30}

pktSwchProfileCharSuppressA OBJECT-TYPE
    SYNTAX  Integer32 (0..127)
    MAX-ACCESS  read-only
    STATUS  current
    DESCRIPTION
	"This entry specifies the decimal value of the character that will toggle
		echo suppression in the PAD.  A value of zero indicates that echo suppression
		 is only controlled by radSPSProfileEcho."
   ::= { pktSwchProfileAEntry 31}

pktSwchProfileCharSubsA OBJECT-TYPE
    SYNTAX  Integer32 (0..127)
    MAX-ACCESS  read-only
    STATUS  current
    DESCRIPTION
	"This entry specifies the decimal value of the character that will be echoed
		instead of the character received from the user's DTE.  A zero value indicates that
		 no character is echoed."
   ::= { pktSwchProfileAEntry 32}

pktSwchProfileFormFeedPadA OBJECT-TYPE
    SYNTAX  Integer32 (0..127)
    MAX-ACCESS  read-only
    STATUS  current
    DESCRIPTION
	"This entry specifies the number of padding (NUL) characters that will be
		automatically sent after the form feed character."
   ::= { pktSwchProfileAEntry 33}

pktSwchProfileInactivityA OBJECT-TYPE
    SYNTAX  Integer32 (0..255)
    MAX-ACCESS  read-only
    STATUS  current
    DESCRIPTION
	"This entry specifies the number of minutes after which the PAD will forward
		the accumulated data and clear the call.  A zero value indicates no disconnection
		on inactivity."
   ::= { pktSwchProfileAEntry 34 }

pktSwchProfileOptionsA OBJECT-TYPE
    SYNTAX  Integer32 (0..255)
    MAX-ACCESS  read-only
    STATUS  current
    DESCRIPTION
	"This entry defines several options to control the profile.  The value is a sum of values
		(powers of two), where each value in the sum represents an option .
				The values that may be included in the sum and their meanings are:
		0   No options
		1   Remote set of local X.3 parameters though X.29 is disabled
		2  Add sub address to call request
		4   Don't use protocol ID in user data field.
		8   SPRINT NUI format
		16  More bit is set when the edit buffer is full
                                 32 Extended error message
                                 64 Discard  connect extended service signal
                                128 enable connect by typing the address w/out a command"
   ::= { pktSwchProfileAEntry 35 }

pktSwchProfileClrTimerA OBJECT-TYPE
    SYNTAX  Integer32 (0..255)
    MAX-ACCESS  read-only
    STATUS  current
    DESCRIPTION
	"This entry specifies the number of minutes after which a call is cleared.
		  If the parameter value is 0, there is no disconnection timer."
   ::= { pktSwchProfileAEntry 36 }

pktSwchProfileSubAddInCUDA OBJECT-TYPE
    SYNTAX  Integer32 (0..5)
    MAX-ACCESS  read-only
    STATUS  current
    DESCRIPTION
	"This entry defines the number of digits for the subaddress in CUD."
    ::= { pktSwchProfileAEntry 37 }

pktSwchProfileIncomingMsgA OBJECT-TYPE
    SYNTAX  DisplayString (SIZE (0..20))
    MAX-ACCESS  read-only
    STATUS  current
    DESCRIPTION
	"This object is used by an asynchronous user to change the 'com' message for 
	 Incoming calls to a string of up to 20 characters.
	 If user selects the value xxx for this object, the PAD will convert it to
	 the relevant X.25 address, followed by CR LF COM (Carriage-Return, Line-Feed,
	 com). 
	 Example: 'called by XXX' will be converted to 'called by <X.25 address> com'."
    ::= { pktSwchProfileAEntry 38 }

pktSwchProfileOutgoingMsgA OBJECT-TYPE
    SYNTAX  DisplayString (SIZE (0..20))
    MAX-ACCESS  read-only
    STATUS  current
    DESCRIPTION
	"This object is used by an asynchronous user to change the 'com' message for 
	 Outgoing calls to a string of up to 20 characters.
	 If user selects the value xxx for this object, the PAD will convert it to
	 the relevant X.25 address, followed by CR LF COM (Carriage-Return, Line-Feed,
	 com)."
    ::= { pktSwchProfileAEntry 39 }

pktSwchProfileClearMsgA OBJECT-TYPE
    SYNTAX  DisplayString (SIZE (0..20))
    MAX-ACCESS  read-only
    STATUS  current
    DESCRIPTION
	"This object is the message selected by user, which will appear when
	 the channel is cleared. The message is a string of up to 20 characters.
	 Example of such a string: 'Call Cleared'."
    ::= { pktSwchProfileAEntry 40 }



-- pktSwchChannel (Scratch and Active) defines the channel configurations
-- of all the channels on the PS

pktSwchChannel 	OBJECT IDENTIFIER ::= { pktSwchAsync 2 }

-- pktSwchChannelSTable defines the Scratch channel configurations of all
-- the channels on the PS

pktSwchChannelSTable    OBJECT-TYPE
    SYNTAX  SEQUENCE  OF PktSwchChannelSEntry
    MAX-ACCESS  not-accessible
    STATUS  current
    DESCRIPTION
	"The Scratch Channel Table defines the channels configured on the PS."
     ::=  { pktSwchChannel 1 }

pktSwchChannelSEntry OBJECT-TYPE
    SYNTAX  PktSwchChannelSEntry
    MAX-ACCESS  not-accessible
    STATUS  current
    DESCRIPTION
	"Defines the contents of each line in the Scratch Channel Table."
    INDEX   { pktSwchChannelIfIndexS }
    ::=  { pktSwchChannelSTable 1 }

PktSwchChannelSEntry ::= SEQUENCE {
    pktSwchChannelIfIndexS
     Integer32,
    pktSwchChannelNumberS
     Integer32,
    pktSwchChannelProfileS
     Integer32,
    pktSwchChannelOutCallProfileS
     Integer32,
    pktSwchChannelInCallProfileS
     Integer32,
    pktSwchChannelRemoteProfileS
     Integer32,
    pktSwchChannelAutocallIdS
     Integer32,
    pktSwchChannelAlterAutocallIdS
     Integer32,
    pktSwchChannelAutocallRetriesS
     Integer32,
    pktSwchChannelAutocallIntervalS
     Integer32,
    pktSwchChannelCallAliasS
     Integer32,
    pktSwchChannelSubAddress1S
     Integer32,
    pktSwchChannelSubAddress2S
     Integer32,
    pktSwchChannelNUISEntry
     Integer32,
    pktSwchChannelClearTimerS
     Integer32,
    pktSwchChannelOptionsS
     Integer32,
	pktSwchChannelClear
	 INTEGER,
	pktSwchChannelCopyTo
	 Integer32,
	pktSwchChannelCopyToWMask
	 Integer32,
	pktSwchChannelCopyMask
	 Integer32
    }

pktSwchChannelIfIndexS  OBJECT-TYPE
    SYNTAX Integer32
    MAX-ACCESS  read-only
    STATUS  current
    DESCRIPTION
	"This is used as the index for the channel table."
    ::= { pktSwchChannelSEntry 1 }

pktSwchChannelNumberS  OBJECT-TYPE
    SYNTAX Integer32 (1..1224)
    MAX-ACCESS  read-only
    STATUS  current
    DESCRIPTION
	"The number by which a channel is identified."
    ::= { pktSwchChannelSEntry 2 }

pktSwchChannelProfileS  OBJECT-TYPE
    SYNTAX Integer32 (1..200)
    MAX-ACCESS  read-write
    STATUS  current
    DESCRIPTION
	"The profile that the channel uses for command mode operations."
    ::= { pktSwchChannelSEntry 3 }

pktSwchChannelOutCallProfileS  OBJECT-TYPE
    SYNTAX Integer32 (0..200)
    MAX-ACCESS  read-write
    STATUS  current
    DESCRIPTION
	"The number of the profile that will be used during an outgoing
	 call on the channel."
    ::= { pktSwchChannelSEntry 4 }

pktSwchChannelInCallProfileS  OBJECT-TYPE
    SYNTAX Integer32 (0..200)
    MAX-ACCESS  read-write
    STATUS  current
    DESCRIPTION
	"The number of the profile that will be used during an incoming
	 call on the channel."
    ::= { pktSwchChannelSEntry 5 }

pktSwchChannelRemoteProfileS  OBJECT-TYPE
    SYNTAX Integer32 (0..200)
    MAX-ACCESS  read-write
    STATUS  current
    DESCRIPTION
	"The number of the profile that will be downloaded to the remote
	 PAD at the beginning of a new call."
    ::= { pktSwchChannelSEntry 6 }

pktSwchChannelAutocallIdS  OBJECT-TYPE
    SYNTAX Integer32 (0..200)
    MAX-ACCESS  read-write
    STATUS  current
    DESCRIPTION
	"Selects the mnemonic (call ID) to be used as the first alternative.
	 A value of zero indicates that the autocall function is disabled."
    ::= { pktSwchChannelSEntry 7 }

pktSwchChannelAlterAutocallIdS  OBJECT-TYPE
    SYNTAX Integer32 (0..200)
    MAX-ACCESS  read-write
    STATUS  current
    DESCRIPTION
	"Selects the alternate mnemonic for the autocall function.  A value of zero indicates that the
		 alternate destination is not used."
    ::= { pktSwchChannelSEntry 8 }

pktSwchChannelAutocallRetriesS  OBJECT-TYPE
    SYNTAX Integer32 (0..255)
    MAX-ACCESS  read-write
    STATUS  current
    DESCRIPTION
	"The number of autocall retries if the autocall setup request is
	 rejected with a busy cause."
    ::= { pktSwchChannelSEntry 9 }

pktSwchChannelAutocallIntervalS OBJECT-TYPE
    SYNTAX Integer32 (0..255)
    MAX-ACCESS  read-write
    STATUS  current
    DESCRIPTION
	"The interval in seconds between consecutive autocall retries."
    ::= { pktSwchChannelSEntry 10 }

pktSwchChannelCallAliasS OBJECT-TYPE
    SYNTAX Integer32 (0..200)
    MAX-ACCESS  read-write
    STATUS  current
    DESCRIPTION
	"The alias to be sent after the call is set up.  A value of zero
	 indicates that alias sending is disabled.  The aliases are
	 configured on the Alias Table."
    ::= { pktSwchChannelSEntry 11 }

pktSwchChannelSubAddress1S OBJECT-TYPE
    SYNTAX Integer32 (0..255)
    MAX-ACCESS  read-write
    STATUS  current
    DESCRIPTION
	"The first subaddress for the channel."
    ::= { pktSwchChannelSEntry 12 }

pktSwchChannelSubAddress2S OBJECT-TYPE
    SYNTAX Integer32 (0..255)
    MAX-ACCESS  read-write
    STATUS  current
    DESCRIPTION
	"The second subaddress for the channel."
    ::= { pktSwchChannelSEntry 13}

pktSwchChannelNUISEntry OBJECT-TYPE
    SYNTAX Integer32 (1..200)
    MAX-ACCESS  read-write
    STATUS  current
    DESCRIPTION
	"The number corresponding to the NUI information to be sent.
	 This number is the same as the pktSwchNuiGroupId."
    ::= { pktSwchChannelSEntry 14 }

pktSwchChannelClearTimerS OBJECT-TYPE
    SYNTAX Integer32 (0..255)
    MAX-ACCESS  read-write
    STATUS  current
    DESCRIPTION
	"Time limitation for an open session.  A value of zero indicates that
	 the Clear timer is not used."
    ::= { pktSwchChannelSEntry 15 }

pktSwchChannelOptionsS OBJECT-TYPE
    SYNTAX Integer32 (0..255)
    MAX-ACCESS  read-write
    STATUS  current
    DESCRIPTION
	"This controls the use of gneral non-correlated channel options.
	 The value is a sum of values (powers of two), where each value in
	 the sum represents an option.
	 The values that may be included in the sum and their meanings are:
		0   No options
		1   HW signal is checked
		2   Auto call after clear
		4   Auto call after <CR>
		8   DCD is ON, only in DATA TRANSFER mode
		16  Charging Info Facility
		32  Auto call if HW signal is set
                               64  Accept calls even  if HW signal is  is OFF
                              128 A transparent channel."
::= { pktSwchChannelSEntry 16 }

pktSwchChannelClear OBJECT-TYPE
	SYNTAX INTEGER {
	                noOp(1),
	                clear(2)
	               }
	MAX-ACCESS read-write
	STATUS current
	DESCRIPTION
	"The Clearing Channel operation disconnects all sessions"
	::= { pktSwchChannelSEntry 17 }

pktSwchChannelCopyTo OBJECT-TYPE
 	SYNTAX Integer32
	MAX-ACCESS  read-write
	STATUS  current
    DESCRIPTION
	"The destination channel number, to which the Copy
	 is performed."
	::= { pktSwchChannelSEntry 18 }

pktSwchChannelCopyToWMask OBJECT-TYPE
 	SYNTAX Integer32
	MAX-ACCESS  read-write
	STATUS  current
    DESCRIPTION
	"The destination channel number, to which the Copy with Mask
	 is performed."
	::= { pktSwchChannelSEntry 19 }

pktSwchChannelCopyMask OBJECT-TYPE
 	SYNTAX Integer32 (0..16383)
	MAX-ACCESS  read-write
	STATUS  current
    DESCRIPTION
	"The selected configuration parameters to be copied from the source
	 channel to the target channels. The value is a sum of values
	 (powers of two), where each value in the sum represents a selected
	 parameter that is not copied. The values that may be included in the
	 sum and their meanings are:
	 0	  Copy all.
	 1	  Do not copy Profile.
	 2	  Do not copy OutCallProfile.
	 4	  Do not copy InCallProfile.
	 8	  Do not copy RemoteProfile.
	 16	  Do not copy AutocallId.
	 32	  Do not copy AlterCallId.
	 64	  Do not copy AutoCallRetries.
	 128  Do not copy AutoCallInterval.
	 256  Do not copy CallAlias.
	 512  Do not copy SubAddress1.
	 1024  Do not copy SubAddress2.
	 2048  Do not copy NUIEntry.
	 4096  Do not copy ClearTimer.
	 8192  Do not copy Options.
	 XXX - Any combination of the above."
	::= { pktSwchChannelSEntry 20 }


pktSwchChannelATable    OBJECT-TYPE
    SYNTAX  SEQUENCE  OF PktSwchChannelAEntry
    MAX-ACCESS  not-accessible
    STATUS  current
    DESCRIPTION
	"The Active Channel Table defines the channels configured on the PS."
     ::=  { pktSwchChannel 2 }

pktSwchChannelAEntry OBJECT-TYPE
    SYNTAX  PktSwchChannelAEntry
    MAX-ACCESS  not-accessible
    STATUS  current
    DESCRIPTION
	"Defines the contents of each line in the Active Channel
	     Table."
    INDEX   { pktSwchChannelIfIndexA }
    ::=  { pktSwchChannelATable 1 }

PktSwchChannelAEntry ::= SEQUENCE {
    pktSwchChannelIfIndexA
     Integer32,
    pktSwchChannelNumberA
     Integer32,
    pktSwchChannelProfileA
     Integer32,
    pktSwchChannelOutCallProfileA
     Integer32,
    pktSwchChannelInCallProfileA
     Integer32,
    pktSwchChannelRemoteProfileA
     Integer32,
    pktSwchChannelAutocallIdA
     Integer32,
    pktSwchChannelAlterAutocallIdA
     Integer32,
    pktSwchChannelAutocallRetriesA
     Integer32,
    pktSwchChannelAutocallIntervalA
     Integer32,
    pktSwchChannelCallAliasA
     Integer32,
    pktSwchChannelSubAddress1A
     Integer32,
    pktSwchChannelSubAddress2A
     Integer32,
    pktSwchChannelNUIAEntry
     Integer32,
    pktSwchChannelClearTimerA
     Integer32,
    pktSwchChannelOptionsA
     Integer32
    }

pktSwchChannelIfIndexA  OBJECT-TYPE
    SYNTAX Integer32
    MAX-ACCESS  read-only
    STATUS  current
    DESCRIPTION
	"This is used as the index for the channel table."
    ::= { pktSwchChannelAEntry 1 }

pktSwchChannelNumberA  OBJECT-TYPE
    SYNTAX Integer32 (1..288)
    MAX-ACCESS  read-only
    STATUS  current
    DESCRIPTION
	"The number by which a channel is identified."
    ::= { pktSwchChannelAEntry 2 }

pktSwchChannelProfileA  OBJECT-TYPE
    SYNTAX Integer32
    MAX-ACCESS  read-only
    STATUS  current
    DESCRIPTION
	"The profile that the channel uses for command mode operations."
    ::= { pktSwchChannelAEntry 3 }

pktSwchChannelOutCallProfileA  OBJECT-TYPE
    SYNTAX Integer32
    MAX-ACCESS  read-only
    STATUS  current
    DESCRIPTION
	"The number of the profile that is used during an outgoing call on the channel."
    ::= { pktSwchChannelAEntry 4 }

pktSwchChannelInCallProfileA  OBJECT-TYPE
    SYNTAX Integer32
    MAX-ACCESS  read-only
    STATUS  current
    DESCRIPTION
	"The number of the profile that is used during an incoming call on the channel."
    ::= { pktSwchChannelAEntry 5 }

pktSwchChannelRemoteProfileA  OBJECT-TYPE
    SYNTAX Integer32
    MAX-ACCESS  read-only
    STATUS  current
    DESCRIPTION
	"The number of the profile that is downloaded to the remote PAD at the beginning of
		 a new call."
    ::= { pktSwchChannelAEntry 6 }

pktSwchChannelAutocallIdA  OBJECT-TYPE
    SYNTAX Integer32
    MAX-ACCESS  read-only
    STATUS  current
    DESCRIPTION
	"Selects the mnemonic (call ID) to be used as the first alternative.  A value of zero indicates that
		 the autocall function is disabled."
    ::= { pktSwchChannelAEntry 7 }

pktSwchChannelAlterAutocallIdA  OBJECT-TYPE
    SYNTAX Integer32
    MAX-ACCESS  read-only
    STATUS  current
    DESCRIPTION
	"Selects the alternate mnemonic for the autocall function.  A value of zero indicates that the
		 alternate destination is not used."
    ::= { pktSwchChannelAEntry 8 }

pktSwchChannelAutocallRetriesA  OBJECT-TYPE
    SYNTAX Integer32
    MAX-ACCESS  read-only
    STATUS  current
    DESCRIPTION
	"The number of autocall retrues if the autocall setup request is rejected with a busy cause."
    ::= { pktSwchChannelAEntry 9 }

pktSwchChannelAutocallIntervalA OBJECT-TYPE
    SYNTAX Integer32
    MAX-ACCESS  read-only
    STATUS  current
    DESCRIPTION
	"The interval in seconds between consecutive autocall retries."
    ::= { pktSwchChannelAEntry 10 }

pktSwchChannelCallAliasA OBJECT-TYPE
    SYNTAX Integer32
    MAX-ACCESS  read-only
    STATUS  current
    DESCRIPTION
	"The alias to be sent after the call is set up.  A value of zero indicates that alias
		sending is disabled.  The aliases are configured on the Alias Table."
    ::= { pktSwchChannelAEntry 11 }

pktSwchChannelSubAddress1A OBJECT-TYPE
    SYNTAX Integer32
    MAX-ACCESS  read-only
    STATUS  current
    DESCRIPTION
	"The first subaddress for the channel."
    ::= { pktSwchChannelAEntry 12 }

pktSwchChannelSubAddress2A OBJECT-TYPE
    SYNTAX Integer32
    MAX-ACCESS  read-only
    STATUS  current
    DESCRIPTION
	"The second subaddress for the channel."
    ::= { pktSwchChannelAEntry 13}

pktSwchChannelNUIAEntry OBJECT-TYPE
    SYNTAX Integer32
    MAX-ACCESS  read-only
    STATUS  current
    DESCRIPTION
	"The number corresponding to the NUI information to be sent.  This number is the same as the
		 pktSwchNuiIndex."
    ::= { pktSwchChannelAEntry 14 }

pktSwchChannelClearTimerA OBJECT-TYPE
    SYNTAX Integer32
    MAX-ACCESS  read-only
    STATUS  current
    DESCRIPTION
	"Time limitation for an open session.  A value of zero indicates that the Clear timer is not used."
    ::= { pktSwchChannelAEntry 15 }

pktSwchChannelOptionsA OBJECT-TYPE
    SYNTAX Integer32
    MAX-ACCESS  read-only
    STATUS  current
    DESCRIPTION
	"This controls the use of general non-correlated channel options.  The value is a sum of values
		(powers of two), where each value in the sum represents an option.
		The values that may be included in the sum and their meanings are:
		0   No options
		1   RTS line checked
		2   Auto call after clear
		4   Auto call after <CR>
		8 DCD is ON, only in DATA TRANSFER mode.
		16  Charging Info Facility
		32  Auto call if HW signal is set
                               64  Accept calls even  if HW signal is  is OFF
                              128 A transparent channel."
    ::= { pktSwchChannelAEntry 16 }


-- pktSwchCallId defines the Call IDs

pktSwchCallId OBJECT IDENTIFIER ::=  { pktSwchAsync 3 }

-- pktSwchCallIdSTable defines the Scratch Call IDs

pktSwchCallIdSTable    OBJECT-TYPE
    SYNTAX  SEQUENCE  OF PktSwchCallIdSEntry
    MAX-ACCESS  not-accessible
    STATUS  current
    DESCRIPTION
	"The Call ID Table S defines the Scratch Call IDs configured on the device."
     ::=  { pktSwchCallId 1 }

pktSwchCallIdSEntry OBJECT-TYPE
    SYNTAX  PktSwchCallIdSEntry
    MAX-ACCESS  not-accessible
    STATUS  current
    DESCRIPTION
	"Defines the contents of each line in the Scratch CallId Table."
    INDEX   { pktSwchCallIdNumberS }
    ::=  { pktSwchCallIdSTable 1 }

PktSwchCallIdSEntry ::= SEQUENCE {
    pktSwchCallIdNumberS
     Integer32,
    pktSwchCallIdMnemonicS
     DisplayString,
    pktSwchCallIdAddressS
     DisplayString,
    pktSwchCallIdStatusS
     INTEGER
    }

pktSwchCallIdNumberS OBJECT-TYPE
    SYNTAX Integer32 (1..200)
    MAX-ACCESS  read-only
    STATUS  current
    DESCRIPTION
	"The index of this entry."
    ::= { pktSwchCallIdSEntry 1 }

pktSwchCallIdMnemonicS OBJECT-TYPE
    SYNTAX DisplayString
    MAX-ACCESS  read-write
    STATUS  current
    DESCRIPTION
	"The mnemonic for this call ID."
    ::= { pktSwchCallIdSEntry 2 }

pktSwchCallIdAddressS OBJECT-TYPE
    SYNTAX DisplayString
    MAX-ACCESS  read-write
    STATUS  current
    DESCRIPTION
	"The address for this call ID."
    ::= { pktSwchCallIdSEntry 3 }

pktSwchCallIdStatusS OBJECT-TYPE
    SYNTAX  INTEGER {
       valid(1),
       createRequest(2),
       underCreation(3),
       invalid(4)
     }
    MAX-ACCESS  read-write
    STATUS  current
    DESCRIPTION
	"The status of this Call ID table entry.  The choices are those defined in the SNMPv2 Textual
		 Conventions for RowStatus.  This will allow easy replacement of the INTEGER syntax with
		 the RowStatus textual convention SYNTAX."
  ::= { pktSwchCallIdSEntry 4 }

-- pktSwchCallIdATable defines the Active Call IDs

pktSwchCallIdATable    OBJECT-TYPE
    SYNTAX  SEQUENCE  OF PktSwchCallIdAEntry
    MAX-ACCESS  not-accessible
    STATUS  current
    DESCRIPTION
	"The Call ID Table A defines the Active Call IDs configured on the device."
     ::=  { pktSwchCallId 2 }

pktSwchCallIdAEntry OBJECT-TYPE
    SYNTAX  PktSwchCallIdAEntry
    MAX-ACCESS  not-accessible
    STATUS  current
    DESCRIPTION
	"Defines the contents of each line in the Active CallId Table."
    INDEX   { pktSwchCallIdNumberA }
    ::=  { pktSwchCallIdATable 1 }

PktSwchCallIdAEntry ::= SEQUENCE {
    pktSwchCallIdNumberA
     Integer32,
    pktSwchCallIdMnemonicA
     DisplayString,
    pktSwchCallIdAddressA
     DisplayString
    }

pktSwchCallIdNumberA OBJECT-TYPE
    SYNTAX Integer32 (1..200)
    MAX-ACCESS  read-only
    STATUS  current
    DESCRIPTION
	"The index of this entry."
    ::= { pktSwchCallIdAEntry 1 }

pktSwchCallIdMnemonicA OBJECT-TYPE
    SYNTAX DisplayString
    MAX-ACCESS  read-only
    STATUS  current
    DESCRIPTION
	"The mnemonic for this call ID."
    ::= { pktSwchCallIdAEntry 2 }

pktSwchCallIdAddressA OBJECT-TYPE
    SYNTAX DisplayString
    MAX-ACCESS  read-only
    STATUS  current
    DESCRIPTION
	"The address for this call ID."
    ::= { pktSwchCallIdAEntry 3 }


-- pktSwchAlias defines the Aliases

pktSwchAlias OBJECT IDENTIFIER ::=  { pktSwchAsync 4 }

-- pktSwchAliasSTable defines the Scratch Aliases

pktSwchAliasSTable    OBJECT-TYPE
    SYNTAX  SEQUENCE  OF PktSwchAliasSEntry
    MAX-ACCESS  not-accessible
    STATUS  current
    DESCRIPTION
	"The Alias Table defines the aliases configured on the device."
     ::=  { pktSwchAlias 1 }

pktSwchAliasSEntry OBJECT-TYPE
    SYNTAX  PktSwchAliasSEntry
    MAX-ACCESS  not-accessible
    STATUS  current
    DESCRIPTION
	"Defines the contents of each line in the Alias Table."
    INDEX   { pktSwchAliasNumberS }
    ::=  { pktSwchAliasSTable 1 }

PktSwchAliasSEntry ::= SEQUENCE {
    pktSwchAliasNumberS
     Integer32,
    pktSwchAliasValueS
     DisplayString,
    pktSwchAliasStatusS
     INTEGER
    }

pktSwchAliasNumberS OBJECT-TYPE
    SYNTAX Integer32 (1..200)
    MAX-ACCESS  read-only
    STATUS  current
    DESCRIPTION
	"The index of this entry."
    ::= { pktSwchAliasSEntry 1 }

pktSwchAliasValueS OBJECT-TYPE
    SYNTAX DisplayString (SIZE (0..64))
    MAX-ACCESS  read-write
    STATUS  current
    DESCRIPTION
	"The alias is defined using up to 64 characters."
    ::= { pktSwchAliasSEntry 2 }

pktSwchAliasStatusS OBJECT-TYPE
    SYNTAX  INTEGER {
       valid(1),
       createRequest(2),
       underCreation(3),
       invalid(4)
     }
    MAX-ACCESS  read-write
    STATUS  current
    DESCRIPTION
	"The status of this Alias table entry.  The choices are those defined in the SNMPv2 Textual
		 Conventions for RowStatus.  This will allow easy replacement of the INTEGER syntax with
		 the RowStatus textual convention SYNTAX."
  ::= { pktSwchAliasSEntry 3 }


-- pktSwchAliasATable defines the Active Aliases

pktSwchAliasATable    OBJECT-TYPE
    SYNTAX  SEQUENCE  OF PktSwchAliasAEntry
    MAX-ACCESS  not-accessible
    STATUS  current
    DESCRIPTION
	"The Alias Table defines the aliases configured on the device."
     ::=  { pktSwchAlias 2 }

pktSwchAliasAEntry OBJECT-TYPE
    SYNTAX  PktSwchAliasAEntry
    MAX-ACCESS  not-accessible
    STATUS  current
    DESCRIPTION
	"Defines the contents of each line in the Alias Table."
    INDEX   { pktSwchAliasNumberA }
    ::=  { pktSwchAliasATable 1 }

PktSwchAliasAEntry ::= SEQUENCE {
    pktSwchAliasNumberA
     Integer32,
    pktSwchAliasValueA
     DisplayString
    }

pktSwchAliasNumberA OBJECT-TYPE
    SYNTAX Integer32 (1..200)
    MAX-ACCESS  read-only
    STATUS  current
    DESCRIPTION
	"The index of this entry."
    ::= { pktSwchAliasAEntry 1 }

pktSwchAliasValueA OBJECT-TYPE
    SYNTAX DisplayString (SIZE (0..64))
    MAX-ACCESS  read-only
    STATUS  current
    DESCRIPTION
	"The alias is defined using up to 64 characters."
    ::= { pktSwchAliasAEntry 2 }



-- The pktSwchAsyncStatTable contains status information and statistics
-- for the Async channels

pktSwchAsyncStatTable  OBJECT-TYPE
    SYNTAX  SEQUENCE  OF PktSwchAsyncStatEntry
    MAX-ACCESS  not-accessible
    STATUS  current
    DESCRIPTION
	"The AsyncStat Table includes status information and statistics
	 provided by the PS on the async channels."
       ::=  { pktSwchAsync 5 }

pktSwchAsyncStatEntry OBJECT-TYPE
    SYNTAX  PktSwchAsyncStatEntry
    MAX-ACCESS  not-accessible
    STATUS  current
    DESCRIPTION
	"Defines the contents of each line in the Async Stat Table."
    INDEX   { pktSwchAsyncIfIndex }
    ::=  { pktSwchAsyncStatTable 1  }

PktSwchAsyncStatEntry ::= SEQUENCE {
    pktSwchAsyncIfIndex
     Integer32,
    pktSwchAsyncChannelNumber
     Integer32,
    pktSwchAsyncConnectionStatus
     INTEGER,
    pktSwchAsyncNumLogChannels
     Integer32,
    pktSwchAsyncNumActSessions
     Integer32,
    pktSwchAsyncAutocallId
     Integer32,
    pktSwchAsyncRTSStatus
     INTEGER,
    pktSwchAsyncBuffToNet
     Integer32,
    pktSwchAsyncBuffToUser
     Integer32,
    pktSwchAsyncTxXoff
     INTEGER,
    pktSwchAsyncRxXoff
     INTEGER,
    pktSwchAsyncBuffOutstand
     Integer32,
    pktSwchAsyncChannelMode
     INTEGER

   }

pktSwchAsyncIfIndex OBJECT-TYPE
    SYNTAX Integer32
    MAX-ACCESS  read-only
    STATUS  current
    DESCRIPTION
	"An index for the table."
    ::= { pktSwchAsyncStatEntry 1 }

pktSwchAsyncChannelNumber OBJECT-TYPE
    SYNTAX Integer32
    MAX-ACCESS  read-only
    STATUS  current
    DESCRIPTION
	"The channel to which this entry applies.  This value is the
	 same as the pktSwchChannelNumber."
    ::= { pktSwchAsyncStatEntry 2 }

pktSwchAsyncConnectionStatus OBJECT-TYPE
    SYNTAX INTEGER {
	  engaged(1),
	  free   (2)
	  }
    MAX-ACCESS  read-only
    STATUS  current
    DESCRIPTION
	"The connection status of the channel is either FREE or ENG (engaged)."
    ::= { pktSwchAsyncStatEntry 3}

pktSwchAsyncNumLogChannels OBJECT-TYPE
    SYNTAX Integer32
    MAX-ACCESS  read-only
    STATUS  current
    DESCRIPTION
	"The number of active logical channels used by the asynchronous channel."
    ::= { pktSwchAsyncStatEntry 4 }

pktSwchAsyncNumActSessions OBJECT-TYPE
    SYNTAX Integer32
    MAX-ACCESS  read-only
    STATUS  current
    DESCRIPTION
	"The number of active sessions opened by this asynchronous channel."
    ::= { pktSwchAsyncStatEntry 5 }

pktSwchAsyncAutocallId OBJECT-TYPE
    SYNTAX Integer32
    MAX-ACCESS  read-only
    STATUS  current
    DESCRIPTION
	"Indicates whether the channel has been configured to use the autocall function and
		 what is the call  ID.  NONE means that the channel is not configured for autocall."
    ::= { pktSwchAsyncStatEntry 6}

pktSwchAsyncRTSStatus OBJECT-TYPE
    SYNTAX INTEGER {
	  unused(1),
	  off   (2),
	  on    (3)
	  }
    MAX-ACCESS  read-only
    STATUS  current
    DESCRIPTION
	"Shows the status of the RTS line of the asynchronous channel.
	 OFF indicates that the RTS line is not active, ON indicates that
	 it is active, and UNUSED indicates that the channel PAD is
	 programmed to disregard the state of the RTS line."
    ::= { pktSwchAsyncStatEntry 7 }

pktSwchAsyncBuffToNet OBJECT-TYPE
    SYNTAX Integer32
    MAX-ACCESS  read-only
    STATUS  current
    DESCRIPTION
	"The number of data buffers currently used by the transmit direction of the channel."
    ::= { pktSwchAsyncStatEntry 8 }

pktSwchAsyncBuffToUser OBJECT-TYPE
    SYNTAX Integer32
    MAX-ACCESS  read-only
    STATUS  current
    DESCRIPTION
	"The number of data buffers currently used by the receive direction of the channel."
    ::= { pktSwchAsyncStatEntry 9}

pktSwchAsyncTxXoff OBJECT-TYPE
    SYNTAX INTEGER {
      no (1),
      yes(2)
      }
    MAX-ACCESS  read-only
    STATUS  current
    DESCRIPTION
	"The current state of software flow control in the transmit direction.
	 NO indicates that traffic flow is enabled.  YES indicates that traffic
	 flow from the user's DTE to the device channel has been interrupted
	 by sending the X-OFF character to the DTE."
    ::= { pktSwchAsyncStatEntry 10 }


pktSwchAsyncRxXoff OBJECT-TYPE
    SYNTAX  INTEGER {
      no (1),
      yes(2)
      }
    MAX-ACCESS  read-only
    STATUS  current
    DESCRIPTION
	"The current state of software flow control in the receive direction.
	 NO indicates that traffic flow is enabled.  YES indicates that traffic
	 flow to the user's DTE from the device channel has been interrupted
	 by means of the X-OFF character."
    ::= { pktSwchAsyncStatEntry 11 }

pktSwchAsyncBuffOutstand OBJECT-TYPE
    SYNTAX Integer32
    MAX-ACCESS  read-only
    STATUS  current
    DESCRIPTION
	"Indicates the number of buffers which were sent to the async user
	 but weren't yet freed."
    ::= { pktSwchAsyncStatEntry 12 }

pktSwchAsyncChannelMode OBJECT-TYPE
    SYNTAX INTEGER {
	  none        (1),
	  activeLink  (2),
	  x28command  (3),
	  dataTransfer(4)
	  }
    MAX-ACCESS  read-only
    STATUS  current
    DESCRIPTION
	"The channel mode is either X28 COMMAND or DATA TRANSFER."
    ::= { pktSwchAsyncStatEntry 13 }


-- The pktSwchAsyncRunProTable contains status information and statistics for the Async channels

pktSwchAsyncRunProTable  OBJECT-TYPE
    SYNTAX  SEQUENCE  OF PktSwchAsyncRunProEntry
    MAX-ACCESS  not-accessible
    STATUS  current
    DESCRIPTION
	"The AsyncRunPro Table includes status information and statistics provided by the PS
		on the async channels."
       ::=  { pktSwchAsync 6 }

pktSwchAsyncRunProEntry OBJECT-TYPE
    SYNTAX  PktSwchAsyncRunProEntry
    MAX-ACCESS  not-accessible
    STATUS  current
    DESCRIPTION
	"Defines the contents of each line in the Async RunPro Table."
    INDEX   { pktSwchAsyncRunProIfIndex }
    ::=  { pktSwchAsyncRunProTable 1  }


PktSwchAsyncRunProEntry ::= SEQUENCE {
     pktSwchAsyncRunProIfIndex
     Integer32,
    pktSwchAsyncRunProChannelNumber
     Integer32,
	pktSwchAsyncRunProRecallChar
	 Integer32,
	pktSwchAsyncRunProEcho
	 INTEGER,
	pktSwchAsyncRunProDataForwChar
	 Integer32,
	pktSwchAsyncRunProIdleTimer
	 Integer32,
	pktSwchAsyncRunProDevFlowCont
	 INTEGER,
	pktSwchAsyncRunProServSig
	 INTEGER,
	pktSwchAsyncRunProBreak
	 Integer32,
	pktSwchAsyncRunProDiscOut
	 INTEGER,
	pktSwchAsyncRunProCRPPadding
	 Integer32,
	pktSwchAsyncRunProLineFold
	 Integer32,
	pktSwchAsyncRunProSpeed
	 INTEGER,
	pktSwchAsyncRunProPadFlowCont
	 INTEGER,
	pktSwchAsyncRunProLineFeedInsert
	 INTEGER,
	pktSwchAsyncRunProLineFeedPad
	 Integer32,
	pktSwchAsyncRunProEditing
	 INTEGER,
	pktSwchAsyncRunProCharDel
	 Integer32,
	pktSwchAsyncRunProLineDel
	 Integer32,
	pktSwchAsyncRunProLineDisp
	 Integer32,
	pktSwchAsyncRunProEditServSig
	 Integer32,
	pktSwchAsyncRunProEchomask
	 Integer32,
	pktSwchAsyncRunProParTreat
	 INTEGER,
	pktSwchAsyncRunProPageWait
	 Integer32
    }

pktSwchAsyncRunProIfIndex OBJECT-TYPE
    SYNTAX Integer32
    MAX-ACCESS  read-only
    STATUS  current
    DESCRIPTION
	"An index for the table."
    ::= { pktSwchAsyncRunProEntry 1 }


pktSwchAsyncRunProChannelNumber OBJECT-TYPE
    SYNTAX Integer32
    MAX-ACCESS  read-only
    STATUS  current
    DESCRIPTION
	"The channel to which this entry applies.  This value is the same as the pktSwchChannelNumber."
    ::= { pktSwchAsyncRunProEntry 2 }




pktSwchAsyncRunProRecallChar  OBJECT-TYPE
    SYNTAX Integer32 (0..126)
    MAX-ACCESS  read-only
    STATUS  current
    DESCRIPTION
	"The character specified by this entry is used to escape from the data transfer
		 mode and enter the PAD command mode.  The integer values have the following meanings:
			 (0)                 PAD recall is not possible
			 (1)                 The PAD recall character is DLE
			 (2)  to (126)  The PAD recall character is specified by the user by entering its ASCII
		code."
    ::= { pktSwchAsyncRunProEntry 3  }

pktSwchAsyncRunProEcho OBJECT-TYPE
    SYNTAX  INTEGER {
       echEn(1),
       noEch(2)
     }
    MAX-ACCESS  read-only
    STATUS  current
    DESCRIPTION
	"This determines if an echo of the input characters is retured to the DTE.
		 The options are either  'echo enabled'  or 'no echo'."
   ::= { pktSwchAsyncRunProEntry 4  }

pktSwchAsyncRunProDataForwChar OBJECT-TYPE
    SYNTAX  Integer32 (0..127)
    MAX-ACCESS  read-only
    STATUS  current
    DESCRIPTION
	"The value is a sum of values (powers of two), where each value in the sum represents
		a character (or characters) that is (are) used as a data forwarding character.  The data
		forwarding characters are used to instruct the PAD to complete the assembly of and to
		forward a packet containing the data accumulated up to the reception of such a character.
		The values that may be included in the sum and their meanings are:
		0   Data forwarding characters are not used
		1   Alpha-numeric characters (A to Z, a to z, 0 to 9, inclusive)
		2   Character CR
		4   Characters ESC, BEL, ENQ, ACK
		8   Characters DEL, CAN, DC2
		16 Characters EOT, ETX
		32 Characters HT, LF, VT, FF
		64 All the other characters in colums 0 and 1 of IA5 and not listed above."
   ::= { pktSwchAsyncRunProEntry 5 }

pktSwchAsyncRunProIdleTimer OBJECT-TYPE
    SYNTAX  Integer32 (0..255)
    MAX-ACCESS  read-only
    STATUS  current
    DESCRIPTION
	"Packets will be forwarded when the idle timer expires.  The idle time interval is specified
		 as a multiple of 50 milliseconds.  The multiple is given by the parameter value.  For example,
		 a value of 60 sets an interval of 3 seconds.  If the parameter value is 0, no forwarding occurs
		 after the idle condition."
   ::= { pktSwchAsyncRunProEntry 6 }

pktSwchAsyncRunProDevFlowCont OBJECT-TYPE
    SYNTAX  INTEGER  {
       trans(1),
       transAndCom(2),
       noFlow(255)
    }
    MAX-ACCESS  read-only
    STATUS  current
    DESCRIPTION
	"This parameter determines whether or not the PAD uses software flow control for the
		attached device.  The options are either (1) PAD uses flow control during data transfer
		 mode, (2) PAD uses flow control both in the data transfer mode and in the command mode,
		 or (255) PAD does not use flow control."
   ::= { pktSwchAsyncRunProEntry 7 }

pktSwchAsyncRunProServSig OBJECT-TYPE
    SYNTAX  INTEGER  {
       serv(1),
       prompt(4),
       servAndPrompt(5),
       noSig(255)
    }
    MAX-ACCESS  read-only
    STATUS  current
    DESCRIPTION
	"This parameter is used to instruct the PAD whether to transfer PAD service signals and
		 the PAD prompt to the local DTE in standard format.  The options are (1) PAD service
		 signals are transmitted to the DTE using the standard format, (4) The PAD prompt is
		 transmitted using the standard format, (5) PAD service signals and the PAD prompt are
		 transmitted in the standard format, or (255) No PAD service signals are transmitted to the
		 DTE."
    ::= { pktSwchAsyncRunProEntry 8 }

pktSwchAsyncRunProBreak OBJECT-TYPE
    SYNTAX  Integer32 (0..31)
    MAX-ACCESS  read-only
    STATUS  current
    DESCRIPTION
	"The value is a sum of values (powers of two), where each value in the sum represents
		a PAD operation on receipt of the break signal from the DTE.
		The values that may be included in the sum and their meanings are:
		0   Nothing
		1   Send interrupt packet to network
		2   Send RESET packet to network
		4   Send and 'indication of break' message
		8   Escape from data transfer mode
		16 Discard output data waiting to be sent to the DTE ."
   ::= { pktSwchAsyncRunProEntry 9 }

pktSwchAsyncRunProDiscOut OBJECT-TYPE
    SYNTAX  INTEGER {
       discOut(1),
       normal(2)
     }
    MAX-ACCESS  read-only
    STATUS  current
    DESCRIPTION
	"This parameter instructs the PAD whether to forward the user sequences included in
		data packets to the local DTE or discard them.  The options are (1) discard output or
		 (2) normal data delivery.  If the value of radSPSProfileBreak is 21, the value of
		 pktSwchAsyncRunProDiscOut is automatically set to (1) when a break signal is received."
   ::= { pktSwchAsyncRunProEntry 10  }

pktSwchAsyncRunProCRPPadding OBJECT-TYPE
    SYNTAX  Integer32 (0..127)
    MAX-ACCESS  read-only
    STATUS  current
    DESCRIPTION
	"This parameter specifies the number of padding characters to be added after a carriage
		 return character is transmitted to the local DTE."
   ::= { pktSwchAsyncRunProEntry 11}

pktSwchAsyncRunProLineFold OBJECT-TYPE
    SYNTAX  Integer32 (0..255)
    MAX-ACCESS  read-only
    STATUS  current
    DESCRIPTION
	"This parameter specifies the maximum number of characters to be inserted before the
		 format effector.  If the value is zero, there is no insertion of a format effector (line folding)."
    ::= { pktSwchAsyncRunProEntry 12}

pktSwchAsyncRunProSpeed OBJECT-TYPE
    SYNTAX  INTEGER  {
       s110bps(1),
       s300bps(2),
       s1200bps(3),
       s600bps(4),
       s75bps(5),
       s150bps(6),
       s2400bps(12),
       s4800bps(13),
       s9600bps(14),
       s19200bps(15),
       s38400bps(19),
	   s57600bps(20),
	   s115200bps(21)
    }
    MAX-ACCESS  read-only
    STATUS  current
    DESCRIPTION
	"This parameter determines the rate of data transmission to and from the DTE."
    ::= { pktSwchAsyncRunProEntry 13 }

pktSwchAsyncRunProPadFlowCont OBJECT-TYPE
    SYNTAX  INTEGER {
       flowCont(1),
       noFlowCont(2)
     }
    MAX-ACCESS  read-only
    STATUS  current
    DESCRIPTION
	"This determines whether or not the terminal can exercise flow control over the PAD.
		 The options are either 'device can exercise flow control' or 'device cannot exercise flow
		 control."
   ::= { pktSwchAsyncRunProEntry 14  }

pktSwchAsyncRunProLineFeedInsert OBJECT-TYPE
    SYNTAX  INTEGER  {
       afterCR(1),
       recCR(2),
       echoCR(4),
       onePlusFour(5),
       twoPlusFour(6),
       oneTwoFour(7),
       noFeed(255)
    }
    MAX-ACCESS  read-only
    STATUS  current
    DESCRIPTION
	"This parameter indicates when there is a line feed insertion after CR.  The options are
		  (1) Insert line feed after transmission of CR to the DTE, (2) Insert line feed after receipt
		 of CR from the DTE, (4) Insert line feed after echoing a CR character to the DTE,
		 (5) Combination of (1) and (4), (6) Insert line feed after any CR to the DTE (combination of
		 (2) and (4)), (7) Combination of (1), (2), and (4), or (255) No line feed insertion."
    ::= { pktSwchAsyncRunProEntry 15 }

pktSwchAsyncRunProLineFeedPad OBJECT-TYPE
    SYNTAX  Integer32 (0..255)
    MAX-ACCESS  read-only
    STATUS  current
    DESCRIPTION
	"This parameter specifies the number of padding characters to be added after a line
		 feed."
   ::= { pktSwchAsyncRunProEntry 16 }

pktSwchAsyncRunProEditing OBJECT-TYPE
    SYNTAX  INTEGER {
       edit(1),
       noEdit(2)
     }
    MAX-ACCESS  read-only
    STATUS  current
    DESCRIPTION
	"This parameter specifies the editing capabilities available in the data transfer mode.
		Editing is always possible when the PAD is in the command mode.  The options are
		 (1) Command editing in the data trasfer mode is enabled or (2) No command editing
		 in the data transfer mode."
   ::= { pktSwchAsyncRunProEntry 17  }

pktSwchAsyncRunProCharDel OBJECT-TYPE
    SYNTAX  Integer32 (0..127)
    MAX-ACCESS  read-only
    STATUS  current
    DESCRIPTION
	"This parameter specifies the character delete, which is one character from IA5.  The default
		selection is 127 (character DEL)."
   ::= { pktSwchAsyncRunProEntry 18}

pktSwchAsyncRunProLineDel OBJECT-TYPE
    SYNTAX  Integer32 (0..127)
    MAX-ACCESS  read-only
    STATUS  current
    DESCRIPTION
	"This parameter specifies the line delete, which is one character from IA5.  The default
		selection is 24 (character CAN)."
   ::= { pktSwchAsyncRunProEntry 19}

pktSwchAsyncRunProLineDisp OBJECT-TYPE
    SYNTAX  Integer32 (0..127)
    MAX-ACCESS  read-only
    STATUS  current
    DESCRIPTION
	"This entry specifies the line display character, which is one character
		from IA5.  The default selection is 18 (character DC2)."
   ::= { pktSwchAsyncRunProEntry 20}

pktSwchAsyncRunProEditServSig  OBJECT-TYPE
    SYNTAX Integer32 (0..126)
    MAX-ACCESS  read-only
    STATUS  current
    DESCRIPTION
	"This entry specifies the editing PAD service signals.
		The integer values have the following meanings:
			 (0)                 No editing PAD service signals
			 (1)                 Editing PAD service signals for printing terminals
			 (2)                 Editing PAD service signals for display terminals
			 (3)  to (126)  Editing PAD service signals using the desired character from IA5."
    ::= { pktSwchAsyncRunProEntry 21  }

pktSwchAsyncRunProEchomask OBJECT-TYPE
    SYNTAX  Integer32 (0..255)
    MAX-ACCESS  read-only
    STATUS  current
    DESCRIPTION
	"The value is a sum of values (powers of two), where each value in the sum represents
		a character (or characters) that is (are) included in the echo mask.  The characters in the
		echo mask are not echoed to the DTE when PAD echo is enabled.
		The values that may be included in the sum and their meanings are:
		0   No echo mask (all the characters are echoed)
		1   No echo of character CR
		2   No echo of character LF
		4   No echo of characters VT, HT, FF
		8   No echo of characters BEL, BS
		16 No echo of characters ESC, ENQ
		32 No echo of characters ACK, NAK, STX, SOH, EOT, ETB, ETX
		64 No echo of the editing characters selected by radSPSProfileCharDel,
														       radSPSProfileLineDel, and
														       radSPSProfileLineDisp
				128 No echo of the DEL character and of all the other characters in the range of
					ASCII 00 through 31 not mentioned above."
	::= { pktSwchAsyncRunProEntry 22 }

pktSwchAsyncRunProParTreat OBJECT-TYPE
    SYNTAX  INTEGER  {
       parCheck(1),
       parGen(2),
       checkAndGen(3),
       noPar(255)
    }
    MAX-ACCESS  read-only
    STATUS  current
    DESCRIPTION
	"This entry controls the generation of parity bits in the data sent to the local DTE and the
		checking of the parity bit when generated by the local DTE.  The options are (1) parity
		checking is enabled, (2) parity generation is enabled, (3) parity checking and generation are
		enabled, or (255) no parity checking nor parity generation."
    ::= { pktSwchAsyncRunProEntry 23 }

pktSwchAsyncRunProPageWait OBJECT-TYPE
    SYNTAX  Integer32 (0..255)
    MAX-ACCESS  read-only
    STATUS  current
    DESCRIPTION
	"This entry specifies the number of line feed characters counted by the PAD before the
		page wait condition is entered.  If the value is zero, page wait is disabled."
   ::= { pktSwchAsyncRunProEntry 24}


-- pktSwch defines the scratch and active PhyInterface configurations of
-- the PS

pktSwchPhyInterfaceTable    OBJECT-TYPE
    SYNTAX  SEQUENCE  OF PktSwchPhyInterfaceEntry
    MAX-ACCESS  not-accessible
    STATUS  current
    DESCRIPTION
	"The Link Table defines the links configured on the PS."
     ::=  { radPS 3 }

pktSwchPhyInterfaceEntry OBJECT-TYPE
    SYNTAX  PktSwchPhyInterfaceEntry
    MAX-ACCESS  not-accessible
    STATUS  current
    DESCRIPTION
	"Defines the contents of each line in the Link Table."
    INDEX   { pktSwchPhyInterfaceIfIndex }
    ::=  { pktSwchPhyInterfaceTable 1 }

PktSwchPhyInterfaceEntry ::= SEQUENCE {
    pktSwchPhyInterfaceIfIndex
     Integer32,
    pktSwchPhyInterfaceProtocolS
     INTEGER,
    pktSwchPhyInterfaceProtocolA
     INTEGER,
    pktSwchPhyInterfaceCopyTo
     Integer32,
    pktSwchPhyInterfaceChanged
     INTEGER,
    pktSwchPhyInterfaceRxBuffInPool
     Integer32,
    pktSwchPhyInterfaceConnector
     INTEGER,
    pktSwchPhyInterfaceNeighborIp
     IpAddress,
    pktSwchPhyInterfaceProtocolStatus
     INTEGER,
    pktSwchPhyInterfaceTestCmd
     INTEGER,
    pktSwchPhyInterfaceTestTransmittedFrames
     Counter32,
    pktSwchPhyInterfaceTestReceivedFrames
     Counter32,
    pktSwchPhyInterfaceTestLostFrames
     Integer32
    }

pktSwchPhyInterfaceIfIndex  OBJECT-TYPE
    SYNTAX Integer32
    MAX-ACCESS  read-only
    STATUS  current
    DESCRIPTION
	"The ifIndex identified with this link."
    ::= { pktSwchPhyInterfaceEntry 1 }

pktSwchPhyInterfaceProtocolS  OBJECT-TYPE
    SYNTAX INTEGER {
       x25(1),
       frameRelay(2),
       hdlc(3),
       sdlc(4),
       async(5),
       stm4(6),
       stm8(7),
       stm16(8),
       stm24(9),
       mpe(10),
       bscHpad(11),
       bscTpad(12),
       slip(13),
       ethernet(14),
       ppp(15)
     }
    MAX-ACCESS  read-write
    STATUS  current
    DESCRIPTION
        "The protocol to be used on this link.

         Note for PPP:
         PPP protocol is allowed to be applied on Sync Links (1-3)
         as well as Async channels (1-24).
         In order to eliminate ambiguity in the IP destination where
         a destination of P1 can be used for example for async channel 1
         and Sync Link 1, it was decided NOT TO ALLOW configuring PPP on both
         Sync Link no. 1 and async channel 1. Same for Link 2 and
         Link 3."
    ::= { pktSwchPhyInterfaceEntry 2 }

pktSwchPhyInterfaceProtocolA  OBJECT-TYPE
    SYNTAX INTEGER {
       x25(1),
       frameRelay(2),
       hdlc(3),
       sdlc(4),
       async(5),
       stm4(6),
       stm8(7),
       stm16(8),
       stm24(9),
       mpe(10),
       bscHpad(11),
       bscTpad(12),
       slip(13),
       ethernet(14),
       ppp(15)
     }
    MAX-ACCESS  read-only
    STATUS  current
    DESCRIPTION
	"The protocol  currently used on this link."
    ::= { pktSwchPhyInterfaceEntry 3 }

pktSwchPhyInterfaceCopyTo OBJECT-TYPE
 	SYNTAX Integer32
	MAX-ACCESS  read-write
	STATUS  current
    DESCRIPTION
	"The destination interface number, to which the Copy
	 is performed."
	::= { pktSwchPhyInterfaceEntry 4 }

pktSwchPhyInterfaceChanged OBJECT-TYPE
 	SYNTAX INTEGER {
	no  (2),
	yes (3)
	}
	MAX-ACCESS  read-only
	STATUS  current
    DESCRIPTION
	"Indicates if the current running protocol is different than the defined
	 protocol"
	::= { pktSwchPhyInterfaceEntry 5 }

pktSwchPhyInterfaceRxBuffInPool  OBJECT-TYPE
    SYNTAX Integer32
	MAX-ACCESS read-only
	STATUS current
	DESCRIPTION
	"The free data buffers in the Rx pool per interface"
	::= { pktSwchPhyInterfaceEntry 6 }

pktSwchPhyInterfaceConnector  OBJECT-TYPE
    SYNTAX INTEGER {
                    v24(2),
                    v35(3),
                    x21(4),
                    rs530(5),
                    acd(6),
                    mobi(7),
                    u(8),
                    etherUtp(9),
                    noConnector(255)
				   }
	MAX-ACCESS read-only
	STATUS current
	DESCRIPTION
	"The connector type of the interface"
	::= { pktSwchPhyInterfaceEntry 7 }

pktSwchPhyInterfaceNeighborIp  OBJECT-TYPE
    SYNTAX IpAddress
	MAX-ACCESS read-only
	STATUS current
	DESCRIPTION
	"The Ip address of the device on the other side of the link."
	::= { pktSwchPhyInterfaceEntry 8 }

pktSwchPhyInterfaceProtocolStatus OBJECT-TYPE
 	SYNTAX INTEGER {
       valid(1),
       createRequest(2),
       underCreation(3),
       invalid(4)
     }
    MAX-ACCESS  read-write
    STATUS  current
    DESCRIPTION
    "The status of the Interface Protocol row in the Table."
	::= { pktSwchPhyInterfaceEntry 9 }

pktSwchPhyInterfaceTestCmd OBJECT-TYPE
    SYNTAX INTEGER {
        noOp     (1),
        v54Local (2),
        v54Remote(3)
        }
    MAX-ACCESS  read-write
    STATUS  current
    DESCRIPTION
    "START/STOP a test on the current interface.
     The available tests are:
     v54Local  - Local  Analog  Loopback (AL), L3 according to ITU-T standard.
     v54Remote - Remote Digital Loopback(RDL), L2 according to ITU-T standard.
     For stopping the test, SET the noOp (1) option. "
 ::= { pktSwchPhyInterfaceEntry 10 }

pktSwchPhyInterfaceTestTransmittedFrames OBJECT-TYPE
    SYNTAX  Counter32
    MAX-ACCESS  read-only
    STATUS  current
    DESCRIPTION
    "No. of frames which were transmitted from this interface
     during the TEST."
 ::= { pktSwchPhyInterfaceEntry 11 }

pktSwchPhyInterfaceTestReceivedFrames OBJECT-TYPE
    SYNTAX  Counter32
    MAX-ACCESS  read-only
    STATUS  current
    DESCRIPTION
    "No. of frames which were received on this interface
     during the TEST."
 ::= { pktSwchPhyInterfaceEntry 12 }

pktSwchPhyInterfaceTestLostFrames OBJECT-TYPE
    SYNTAX  Integer32
    MAX-ACCESS  read-only
    STATUS  current
    DESCRIPTION
    "Percentage of the frames which were lost during the TEST."
 ::= { pktSwchPhyInterfaceEntry 13 }


-- The PS X.25 Group contains the Lapb Table, the PLP Table

pktSwchx25      OBJECT IDENTIFIER ::= { radPS 4 }

pktSwchLapb     OBJECT IDENTIFIER ::= { pktSwchx25 1 }

-- The PS Lapb Scratch Table

pktSwchLapbSTable  OBJECT-TYPE
    SYNTAX  SEQUENCE  OF PktSwchLapbSEntry
    MAX-ACCESS  not-accessible
    STATUS  current
    DESCRIPTION
	"The Lapb Table includes statistics and configurable objects
	 provided by the PS that are not included in RFC 1381."
    ::=  { pktSwchLapb 1 }

pktSwchLapbSEntry OBJECT-TYPE
    SYNTAX  PktSwchLapbSEntry
    MAX-ACCESS  not-accessible
    STATUS  current
    DESCRIPTION
	"Defines the contents of each line in the RAD Lapb Table."
    INDEX   { pktSwchLapbLinkNumberS }
    ::=  { pktSwchLapbSTable 1  }

PktSwchLapbSEntry ::= SEQUENCE {
    pktSwchLapbLinkNumberS
     Integer32,
    pktSwchLapbInternalClockS
     INTEGER,
    pktSwchLapbLineOptionS
     Integer32,
    pktSwchLapbSegmentSizeS
     Integer32,
    pktSwchLapbXIDS
     Integer32,
    pktSwchLapbAckCounterS
     Integer32,
    pktSwchLapbAckTimerS
     Integer32
      }

pktSwchLapbLinkNumberS  OBJECT-TYPE
    SYNTAX Integer32
    MAX-ACCESS  read-only
    STATUS  current
    DESCRIPTION
	"The link number with which this entry is associated.  This value
	 corresponds to pktSwchPhyInterfaceNumber.  There is an entry for
	 each link for which the pktSwchPhyInterfaceProtocol is X.25  and one
	 entry for each link and DLCI if the pktSwchPhyInterfaceProtocol for
	 the link is Frame Relay and the DLCI is defined as using X.25."
    ::= { pktSwchLapbSEntry 1 }

pktSwchLapbInternalClockS  OBJECT-TYPE
    SYNTAX INTEGER {
       r2400bps (1),
       r4800bps (2),
       r9600bps (3),
       r14400bps(4),
       r19200bps(5),
       r38400bps(6),
	   r48Kbps  (7),
       r56Kbps  (8),
       r64Kbps  (9),
       r128Kbps (10),
       r256Kbps (11),
	   r384Kbps (12),
       r504Kbps (13),
	   r768Kbps (14),
	   r1008Kbps(15),
       r1466Kbps(16),
       r2016Kbps(17),
       external(255)
     }
    MAX-ACCESS  read-write
    STATUS  current
    DESCRIPTION
	"The internal clock speed to be used on this LAPB link.  If external clock is used, the value is
	 255."
    ::= { pktSwchLapbSEntry 2 }

pktSwchLapbLineOptionS  OBJECT-TYPE
    SYNTAX Integer32 (0..2048)
    MAX-ACCESS  read-write
    STATUS  current
    DESCRIPTION
	"The line option to be used on this link.  A value of zero indicates
	 no options.  A value between 0 and 255 inclusive specifes a time in
	 minutes after which the line will be disconnected if no session is open.
	 The following values have the associated meanings:
			       256     Dialed line
			       512     Return to leased line
			       1024   DTR is ON permanent
			       2048   DTR is OFF permanent.
		 any valid combination of the above options should be represented as
		 a sum of the corresponding values. Valid combinations are:
		 DTR ON or OFF (but not both). Dialed line options or not applicable.
		 If DTR control is on (256), then all combinations are possible
		 except 1024 and 2048 (which are not possible)."
    ::= { pktSwchLapbSEntry 3 }

pktSwchLapbSegmentSizeS  OBJECT-TYPE
    SYNTAX Integer32 (1..4096)
    MAX-ACCESS  read-write
    STATUS  current
    DESCRIPTION
	"This value is for the use of billing information.  The value can be no larger than the maximum
		packet size."
    ::= { pktSwchLapbSEntry 4 }


pktSwchLapbXIDS  OBJECT-TYPE
    SYNTAX  Integer32
    MAX-ACCESS read-write
    STATUS  current
    DESCRIPTION
	"When this parameter is different than zero, this lapb is configured
	 as a V25 bis dialed link. This is the XID entry Index which this dialed link is
	 associated with."
	::= { pktSwchLapbSEntry 5 }

pktSwchLapbAckCounterS  OBJECT-TYPE
    SYNTAX  Integer32 (1..128)
    MAX-ACCESS read-write
    STATUS  current
    DESCRIPTION
        "This object defines how many frames will be received on the link
         before the PS will send Acknowledge (RR frame).
         It is used for Piggy Back Acknowledge (ack within the info frames)
         and saves traffic on the line.
         Default value: 1 ."
    ::= { pktSwchLapbSEntry 6 }

pktSwchLapbAckTimerS  OBJECT-TYPE
    SYNTAX  Integer32 (0..255)
    MAX-ACCESS read-write
    STATUS  current
    DESCRIPTION
         "The Ack Timer defines the maximum time in seconds that the device
         will wait before sending RR acknowledgment on the received frames.
         It is used for Piggy Back Acknowledge (ack within the info frames)
         and saves traffic on the line.
         Default value: 0 ."
        ::= { pktSwchLapbSEntry 7 }

-- The PS Lapb Active Table

pktSwchLapbATable  OBJECT-TYPE
    SYNTAX  SEQUENCE  OF PktSwchLapbAEntry
    MAX-ACCESS  not-accessible
    STATUS  current
    DESCRIPTION
	"The Lapb Table includes statistics and configurable objects provided
	 by the PS that are not included in RFC 1381."
    ::=  { pktSwchLapb 2 }

pktSwchLapbAEntry OBJECT-TYPE
    SYNTAX  PktSwchLapbAEntry
    MAX-ACCESS  not-accessible
    STATUS  current
    DESCRIPTION
	"Defines the contents of each line in the RAD Lapb Table."
    INDEX   { pktSwchLapbLinkNumberA }
    ::=  { pktSwchLapbATable 1  }

PktSwchLapbAEntry ::= SEQUENCE {
    pktSwchLapbLinkNumberA
     Integer32,
    pktSwchLapbInternalClockA
     INTEGER,
    pktSwchLapbLineOptionA
     Integer32,
    pktSwchLapbSegmentSizeA
     Integer32,
 	pktSwchLapbLineProtocol
	 INTEGER,
	pktSwchLapbLowerId
	 Integer32,
	pktSwchLapbXIDA
	 Integer32,
	pktSwchLapbTransmittedIFrames
     Counter32,
	pktSwchLapbReceivedIFrames
     Counter32,
	pktSwchLapbNSError
     Counter32,
    pktSwchLapbTransmittedRRFrames
     Counter32,
    pktSwchLapbReceivedRRFrames
     Counter32,
    pktSwchLapbTransmittedRNRFrames
     Counter32,
    pktSwchLapbReceivedRNRFrames
     Counter32,
    pktSwchLapbTransmittedFRMRFrames
     Counter32,
    pktSwchLapbReceivedFRMRFrames
     Counter32,
    pktSwchLapbAckCounterA
     Integer32,
    pktSwchLapbAckTimerA
     Integer32
     }


pktSwchLapbLinkNumberA  OBJECT-TYPE
    SYNTAX Integer32
    MAX-ACCESS  read-only
    STATUS  current
    DESCRIPTION
	"The link number with which this entry is associated.  This value corresponds to
		 pktSwchPhyInterfaceNumber.  There is an entry for each link for which the pktSwchPhyInterfaceProtocol is
		 X.25  and one entry for each link and DLCI if the pktSwchPhyInterfaceProtocol for the link is Frame
		 Relay and theDLCI is defined as using X.25."
    ::= { pktSwchLapbAEntry 1 }


pktSwchLapbInternalClockA  OBJECT-TYPE
    SYNTAX INTEGER {
       r2400bps (1),
       r4800bps (2),
       r9600bps (3),
       r14400bps(4),
       r19200bps(5),
       r38400bps(6),
	   r48Kbps  (7),
       r56Kbps  (8),
       r64Kbps  (9),
       r128Kbps (10),
       r256Kbps (11),
	   r384Kbps (12),
       r504Kbps (13),
	   r768Kbps (14),
	   r1008Kbps(15),
       r1466Kbps(16),
       r2016Kbps(17),
       external(255)
     }
    MAX-ACCESS  read-only
    STATUS  current
    DESCRIPTION
	"The internal clock speed currently used on this LAPB link.
	 If external clock is used, the value is 255."
    ::= { pktSwchLapbAEntry 2 }

pktSwchLapbLineOptionA  OBJECT-TYPE
    SYNTAX Integer32 (0..2048)
    MAX-ACCESS  read-only
    STATUS  current
    DESCRIPTION
	"The line option currently used on this link.  A value of zero
	 indicates no options.  A value between 1 and 255 inclusive specifes
	 a time in minutes after which the line will be disconnected if no
	 session is open.  The following values have the associated meanings:
			       256     Dialed line
			       512     Return to leased line
			       1024   DTR is ON permanent
			       2048   DTR is OFF permanent.
		 any valid combination of the above options should be represented as
		 a sum of the corresponding values. Valid combinations are:
		 DTR ON or OFF (but not both). Dialed line options or not applicable.
		 If DTR control is on (256), then all combinations are possible
		 except 1024 and 2048 (which are not possible)."
       ::= { pktSwchLapbAEntry 3 }

pktSwchLapbSegmentSizeA  OBJECT-TYPE
    SYNTAX Integer32 (1..4096)
    MAX-ACCESS  read-only
    STATUS  current
    DESCRIPTION
	"The current value of the segment size."
    ::= { pktSwchLapbAEntry 4 }

pktSwchLapbLineProtocol  OBJECT-TYPE
    SYNTAX  INTEGER {
	unknown(1),
	x25  (2),
	fr   (3),
	isdn (4)
	}
	MAX-ACCESS read-only
	STATUS  current
    DESCRIPTION
	"This is the lower level protocol which runs under this lapb interface."
	::= { pktSwchLapbAEntry 5 }

pktSwchLapbLowerId  OBJECT-TYPE
    SYNTAX  Integer32
	MAX-ACCESS read-only
	STATUS  current
    DESCRIPTION
	"In case of X.25 over Frame-relay this is the lower level link
	 number."
	::= { pktSwchLapbAEntry 6 }


pktSwchLapbXIDA  OBJECT-TYPE
    SYNTAX  Integer32
    MAX-ACCESS read-only
	STATUS  current
    DESCRIPTION
	"When this parameter is different than zero, this lapb is configured
	 as a V25 bis dialed link. This is the XID entry which this dialed link is
	 associated with."
	::= { pktSwchLapbAEntry 7 }

pktSwchLapbTransmittedIFrames  OBJECT-TYPE
    SYNTAX Counter32
    MAX-ACCESS  read-only
    STATUS  current
    DESCRIPTION
	"The transmitted I frames on this link."
    ::= { pktSwchLapbAEntry 8 }

pktSwchLapbReceivedIFrames  OBJECT-TYPE
    SYNTAX Counter32
    MAX-ACCESS  read-only
    STATUS  current
    DESCRIPTION
	"The received I frames on this link."
    ::= { pktSwchLapbAEntry 9 }

pktSwchLapbNSError  OBJECT-TYPE
    SYNTAX Counter32
    MAX-ACCESS  read-only
    STATUS  current
    DESCRIPTION
	"The number of I frames transmitted out of sequence."
    ::= { pktSwchLapbAEntry 10 }

pktSwchLapbTransmittedRRFrames  OBJECT-TYPE
    SYNTAX Counter32
    MAX-ACCESS  read-only
    STATUS  current
    DESCRIPTION
	"The transmitted RR frames on this link."
    ::= { pktSwchLapbAEntry 11 }

pktSwchLapbReceivedRRFrames  OBJECT-TYPE
    SYNTAX Counter32
    MAX-ACCESS  read-only
    STATUS  current
    DESCRIPTION
	"The received RR frames on this link."
    ::= { pktSwchLapbAEntry 12 }

pktSwchLapbTransmittedRNRFrames  OBJECT-TYPE
    SYNTAX Counter32
    MAX-ACCESS  read-only
    STATUS  current
    DESCRIPTION
	"The transmitted RNR frames on this link."
    ::= { pktSwchLapbAEntry 13 }

pktSwchLapbReceivedRNRFrames  OBJECT-TYPE
    SYNTAX Counter32
    MAX-ACCESS  read-only
    STATUS  current
    DESCRIPTION
	"The received RNR frames on this link."
    ::= { pktSwchLapbAEntry 14 }

pktSwchLapbTransmittedFRMRFrames  OBJECT-TYPE
    SYNTAX Counter32
    MAX-ACCESS  read-only
    STATUS  current
    DESCRIPTION
	"The transmitted FRMR frames on this link."
    ::= { pktSwchLapbAEntry 15 }

pktSwchLapbReceivedFRMRFrames  OBJECT-TYPE
    SYNTAX Counter32
    MAX-ACCESS  read-only
    STATUS  current
    DESCRIPTION
	"The received FRMR frames on this link."
    ::= { pktSwchLapbAEntry 16 }

pktSwchLapbAckCounterA  OBJECT-TYPE
    SYNTAX  Integer32 (1..128)
    MAX-ACCESS read-only
    STATUS  current
    DESCRIPTION
        "This object defines how many frames will be received on the link
         before the PS will send Acknowledge (RR frame).
         It is used for Piggy Back Acknowledge (ack within the info frames)
         and saves traffic on the line.
         Default value: 1 ."
        ::= { pktSwchLapbAEntry 17 }

pktSwchLapbAckTimerA  OBJECT-TYPE
    SYNTAX  Integer32 (0..255)
    MAX-ACCESS read-only
    STATUS  current
    DESCRIPTION
         "The Ack Timer defines the maximum time in seconds that the device
         will wait before sending RR acknowledgment on the received frames.
         It is used for Piggy Back Acknowledge (ack within the info frames)
         and saves traffic on the line.
         Default value: 0 ."
        ::= { pktSwchLapbAEntry 18 }



-- PLP (Packet Layer Protocol: Scratch + Active}

pktSwchPlp  OBJECT IDENTIFIER  ::=  { pktSwchx25 2 }

-- PLP Scratch table

pktSwchPlpSTable  OBJECT-TYPE
    SYNTAX  SEQUENCE  OF PktSwchPlpSEntry
    MAX-ACCESS  not-accessible
    STATUS  current
    DESCRIPTION
	"The Scratch Plp Table includes configurable objects provided by the PS
		that are not included in RFC 1382."
    ::=  { pktSwchPlp 1 }

pktSwchPlpSEntry OBJECT-TYPE
    SYNTAX  PktSwchPlpSEntry
    MAX-ACCESS  not-accessible
    STATUS  current
    DESCRIPTION
	"Defines the contents of each line in the RAD Scratch Plp Table."
    INDEX   { pktSwchPlpLinkNumberS }
    ::=  { pktSwchPlpSTable 1  }

PktSwchPlpSEntry ::= SEQUENCE {
    pktSwchPlpLinkNumberS
     Integer32,
    pktSwchPlpInCallOptionS
     Integer32,
    pktSwchPlpOutCallOptionS
     Integer32,
    pktSwchPlpCugSubscriptionS
     INTEGER,
	pktSwchPlpNUIS
	 Integer32,
	pktSwchPlpCpyPktSize
	 Integer32,
	pktSwchPlpCpyWinSize
	 Integer32
    }

pktSwchPlpLinkNumberS  OBJECT-TYPE
    SYNTAX Integer32
    MAX-ACCESS  read-only
    STATUS  current
    DESCRIPTION
	"The ifIndex of the X.25 interface."
    ::= { pktSwchPlpSEntry 1 }

pktSwchPlpInCallOptionS  OBJECT-TYPE
    SYNTAX Integer32 
    MAX-ACCESS  read-write
    STATUS  current
    DESCRIPTION
	"The in call options for the link.  The value is a sum of values (powers of two), where each
		 value in the sum represents an option.  The values that may be included in the sum and
		 their meanings are:
		0 No options
		1 Fast select acceptance - included in RFC 1382
		2 Reverse charge acceptance - included in RFC 1382
		4 Subaddress in Call User Data field (CUD)
	  	8 Protocol ID (PID) is not used.
	   16 Assume PVC down when link is synchronized
	   32 Delay Reset Response by 2 seconds."
    ::= { pktSwchPlpSEntry 2 }

pktSwchPlpOutCallOptionS  OBJECT-TYPE
    SYNTAX Integer32 (0..15)
    MAX-ACCESS  read-write
    STATUS  current
    DESCRIPTION
	"The out call options for the link. The value is a sum of values
	 (powers of two), where each value in the sum represents an
	 option. The values that may be included in the sum and their
	 meanings are:
		0 No options
		1 Don't add calling and call addressin call accept packet
		2 Network link, call request spread enabled
		4 Add source link number to called address
	  	8 Don't change calling address
	  	XX - Any combination of the values specified above."
      ::= { pktSwchPlpSEntry 3 }

pktSwchPlpCugSubscriptionS  OBJECT-TYPE
    SYNTAX INTEGER {
       cug(1),    --  CUG with preferential
       cugOa(2),   --  CUG/OA with preferential
       cugIa(3),   --  CUG/IA with preferential
       cugOaIa(4),   --  CUG/OA/IA with preferential
       noPref(5),    -- CUG/OA/IA without preferential (transparent)
       noCug(255)  -- no CUG
     }
    MAX-ACCESS  read-write
    STATUS  current
    DESCRIPTION
	"The CUG subscription for the link."
    ::= { pktSwchPlpSEntry 4 }

pktSwchPlpNUIS OBJECT-TYPE
 	SYNTAX Integer32
    MAX-ACCESS  read-write
    STATUS  current
    DESCRIPTION
    "This is the NUI group which this Plp is part of."
	::= { pktSwchPlpSEntry 5 }

pktSwchPlpCpyPktSize OBJECT-TYPE
 	SYNTAX Integer32
    MAX-ACCESS  read-write
    STATUS  current
    DESCRIPTION
    "x25 packet size."
	::= { pktSwchPlpSEntry 6 }

pktSwchPlpCpyWinSize OBJECT-TYPE
 	SYNTAX Integer32
    MAX-ACCESS  read-write
    STATUS  current
    DESCRIPTION
    "x25 window size."
	::= { pktSwchPlpSEntry 7 }


-- PLP Active table

pktSwchPlpATable  OBJECT-TYPE
    SYNTAX  SEQUENCE  OF PktSwchPlpAEntry
    MAX-ACCESS  not-accessible
    STATUS  current
    DESCRIPTION
	"The Active Plp Table includes objects provided by the PS
		that are not included in RFC 1382.  It also includes some packet
		layer statistics, some of which are defined in RFC 1382, but are
	    not supported there, as the x25StatTable in RFC 1382 is not supported."
    ::=  { pktSwchPlp 2 }

pktSwchPlpAEntry OBJECT-TYPE
    SYNTAX  PktSwchPlpAEntry
    MAX-ACCESS  not-accessible
    STATUS  current
    DESCRIPTION
	"Defines the contents of each line in the RAD Active Plp Table."
    INDEX   { pktSwchPlpLinkNumberA }
    ::=  { pktSwchPlpATable 1 }

PktSwchPlpAEntry ::= SEQUENCE {
    pktSwchPlpLinkNumberA
     Integer32,
    pktSwchPlpInCallOptionA
     Integer32,
    pktSwchPlpOutCallOptionA
     Integer32,
    pktSwchPlpCugSubscriptionA
     INTEGER,
	pktSwchPlpNUIA
	 Integer32,
	pktSwchStatOutRestarts
	 Counter32
    }

pktSwchPlpLinkNumberA  OBJECT-TYPE
    SYNTAX Integer32
    MAX-ACCESS  read-only
    STATUS  current
    DESCRIPTION
	"The link number with which this entry is associated.  This value corresponds to
		 pktSwchPhyInterfaceNumber.  There is an entry for each link for which the pktSwchPhyInterfaceProtocol is
		 X.25  and one entry for each link and DLCI if the pktSwchPhyInterfaceProtocol for the link is Frame
		 Relay and theDLCI is defined as using X.25."
    ::= { pktSwchPlpAEntry 1 }

pktSwchPlpInCallOptionA  OBJECT-TYPE
    SYNTAX Integer32 
    MAX-ACCESS  read-only
    STATUS  current
    DESCRIPTION
	"The current in call options for the link.  The value is a sum of values (powers of two),
		 where each value in the sum represents an option.  The values that can be included in
		 the sum and their meanings are:
		0 No options
		1 Fast select acceptance - included in RFC 1382
		2 Reverse charge acceptance - included in RFC 1382
		4 Subaddress in Call User Data field (CUD)
		8 Protocol ID (PID) is not used.
	   16 Assume PVC down when link is synchronized
	   32 Delay Reset Response by 2 seconds."
    ::= { pktSwchPlpAEntry 2 }

pktSwchPlpOutCallOptionA  OBJECT-TYPE
    SYNTAX Integer32 (0..15)
    MAX-ACCESS  read-only
    STATUS  current
    DESCRIPTION
	"The out call options for the link. The value is a sum of values
	 (powers of two), where each value in the sum represents an
	 option. The values that may be included in the sum and their
	 meanings are:
		0 No options
		1 Don't add calling and call addressin call accept packet
		2 Network link, call request spread enabled
		4 Add source link number to called address
	  	8 Don't change calling address
	  	XX - Any combination of the values specified above."
    ::= { pktSwchPlpAEntry 3 }

pktSwchPlpCugSubscriptionA  OBJECT-TYPE
    SYNTAX INTEGER {
       cug(1),    --  CUG with preferential
       cugOa(2),   --  CUG/OA with preferential
       cugIa(3),   --  CUG/IA with preferential
       cugOaIa(4),   --  CUG/OA/IA with preferential
       noPref(5),    -- CUG/OA/IA without preferential (transparent)
       noCug(255)  -- no CUG
     }
    MAX-ACCESS  read-only
    STATUS  current
    DESCRIPTION
	"The current CUG subscription for the link."
    ::= { pktSwchPlpAEntry 4 }

pktSwchPlpNUIA OBJECT-TYPE
 	SYNTAX  Integer32
    MAX-ACCESS  read-only
    STATUS  current
    DESCRIPTION
    "This is the NUI group which this Plp is part of."
	::= { pktSwchPlpAEntry 5 }

pktSwchStatOutRestarts OBJECT-TYPE
    SYNTAX  Counter32
    MAX-ACCESS  read-only
    STATUS  current
    DESCRIPTION
        "The number of remotely initiated (including
         provider initiated) restarts experienced by
         the PLE excluding the restart associated
         with bringing up the PLE interface.  This
         only counts restarts received when the PLE
         already has an established connection with
         the remove PLE."
   ::= { pktSwchPlpAEntry 6 }



pktSwchPlaceHolderForFutureUse  OBJECT IDENTIFIER  ::=  { pktSwchx25 3 }


-- CUG (Scratch + Active}

pktSwchCug  OBJECT IDENTIFIER  ::=  { pktSwchx25 4 }

-- CUG Scratch table


pktSwchCugSTable  OBJECT-TYPE
    SYNTAX  SEQUENCE  OF PktSwchCugSEntry
    MAX-ACCESS  not-accessible
    STATUS  current
    DESCRIPTION
	"The Scratch Cug Table lists the Closed User Groups defined to each
	 X.25 link."
    ::=  { pktSwchCug 1 }

pktSwchCugSEntry OBJECT-TYPE
    SYNTAX  PktSwchCugSEntry
    MAX-ACCESS  not-accessible
    STATUS  current
    DESCRIPTION
	"Defines the contents of each line in the Scratch RAD Cug Table."
    INDEX   { pktSwchCugLinkNumberS,  pktSwchCugIndexS }
    ::=  { pktSwchCugSTable 1  }

PktSwchCugSEntry ::= SEQUENCE {
    pktSwchCugLinkNumberS
     Integer32,
    pktSwchCugIndexS
     Integer32,
    pktSwchCugNumberS
     Integer32,
    pktSwchCugStatus
     INTEGER
    }

pktSwchCugLinkNumberS  OBJECT-TYPE
    SYNTAX Integer32
    MAX-ACCESS  read-only
    STATUS  current
    DESCRIPTION
	"The link number with which this entry is associated.  This value
	 corresponds to pktSwchPhyInterfaceNumber.  There is an entry for
	 each link for which the pktSwchPhyInterfaceProtocol is X.25  if the
	 link has CUG options and one entry for each link and DLCI if the
	 pktSwchPhyInterfaceProtocol for the link is Frame Relay and the DLCI
	 is defined as using X.25 if the link has CUG options."
    ::= { pktSwchCugSEntry 1 }

pktSwchCugIndexS  OBJECT-TYPE
    SYNTAX Integer32                       -- how many CUGs??
    MAX-ACCESS  read-only
    STATUS  current
    DESCRIPTION
	"The index of the CUG for a specific link.  The lowest indexed CUG
	 is the preferential CUG."
    ::= { pktSwchCugSEntry 2 }

pktSwchCugNumberS  OBJECT-TYPE
    SYNTAX Integer32
    MAX-ACCESS  read-write
    STATUS  current
    DESCRIPTION
	"The CUG number for this entry."
    ::= { pktSwchCugSEntry 3 }

pktSwchCugStatus OBJECT-TYPE
    SYNTAX  INTEGER {
       valid(1),
       createRequest(2),
       underCreation(3),
       invalid(4)
     }
    MAX-ACCESS  read-write
    STATUS  current
    DESCRIPTION
	"The status of this CUG table entry.  The choices are those defined in the SNMPv2 Textual
		 Conventions for RowStatus.  This will allow easy replacement of the INTEGER syntax with
		 the RowStatus textual convention SYNTAX."
  ::= { pktSwchCugSEntry 4 }

-- CUG Active table

pktSwchCugATable  OBJECT-TYPE
    SYNTAX  SEQUENCE  OF PktSwchCugAEntry
    MAX-ACCESS  not-accessible
    STATUS  current
    DESCRIPTION
	"The Active Cug Table lists the active Closed User Groups defined
	 to each X.25 link."
    ::=  { pktSwchCug 2 }

pktSwchCugAEntry OBJECT-TYPE
    SYNTAX  PktSwchCugAEntry
    MAX-ACCESS  not-accessible
    STATUS  current
    DESCRIPTION
	"Defines the contents of each line in the Active RAD Cug Table."
    INDEX   { pktSwchCugLinkNumberA,  pktSwchCugIndexA }
    ::=  { pktSwchCugATable 1  }

PktSwchCugAEntry ::= SEQUENCE {
    pktSwchCugLinkNumberA
     Integer32,
    pktSwchCugIndexA
     Integer32,
    pktSwchCugNumberA
     Integer32
    }

pktSwchCugLinkNumberA  OBJECT-TYPE
    SYNTAX Integer32
    MAX-ACCESS  read-only
    STATUS  current
    DESCRIPTION
	"The link number with which this entry is associated.  This value corresponds to
		 pktSwchPhyInterfaceNumber.  There is an entry for each link for which the pktSwchPhyInterfaceProtocol is
		 X.25  if the link has CUG options and one entry for each link and DLCI if the
		 pktSwchPhyInterfaceProtocol for the link is Frame Relay and theDLCI is defined as using X.25
		 if the link has CUG options."
    ::= { pktSwchCugAEntry 1 }

pktSwchCugIndexA  OBJECT-TYPE
    SYNTAX Integer32
    MAX-ACCESS  read-only
    STATUS  current
    DESCRIPTION
	"The index of the CUG for a specific link.  The lowest indexed CUG is the preferential CUG."
    ::= { pktSwchCugAEntry 2 }

pktSwchCugNumberA  OBJECT-TYPE
    SYNTAX Integer32
    MAX-ACCESS  read-only
    STATUS  current
    DESCRIPTION
	"The CUG number for this entry."
    ::= { pktSwchCugAEntry 3 }


--  X.25 Channel LCN Table

pktSwchLogCh  OBJECT IDENTIFIER  ::=  { pktSwchx25 5 }

pktSwchLogChAssTable OBJECT-TYPE
SYNTAX  SEQUENCE OF PktSwchLogChAssEntry
MAX-ACCESS  not-accessible
STATUS  current
DESCRIPTION
        "These objects contain information about the
        channel number configuration in an X.25 PLE.
        These values are the configured values.
        changes in these values after the interface
        has started may not be reflected in the
        operating PLE."
REFERENCE "See ISO 8208, Section 3.7"
::= {pktSwchLogCh 1 }

pktSwchLogChAssEntry OBJECT-TYPE
        SYNTAX  PktSwchLogChAssEntry
        MAX-ACCESS  not-accessible
        STATUS  current
        DESCRIPTION
                "Entries of pktSwchLogChAssTable."
        REFERENCE "This provides the information available
                in 10733 logicalChannelAssignments."
        INDEX { pktSwchLogChAssIndex }
        ::= { pktSwchLogChAssTable 1    }

PktSwchLogChAssEntry ::= SEQUENCE {
        pktSwchLogChAssIndex
                IfIndexType,
        pktSwchLogChAssLIC
                Integer32,
        pktSwchLogChAssHIC
                Integer32,
        pktSwchLogChAssLTC
                Integer32,
        pktSwchLogChAssHTC
                Integer32,
        pktSwchLogChAssLOC
                Integer32,
        pktSwchLogChAssHOC
                Integer32
        }

pktSwchLogChAssIndex OBJECT-TYPE
        SYNTAX  IfIndexType
        MAX-ACCESS  read-only
        STATUS  current
        DESCRIPTION
                "The ifIndex value for the X.25 Interface."
        ::= { pktSwchLogChAssEntry 1 }


pktSwchLogChAssLIC OBJECT-TYPE
        SYNTAX  Integer32 (0..4095)
        MAX-ACCESS  read-only
        STATUS  current
        DESCRIPTION
                "Lowest Incoming channel."
        ::= { pktSwchLogChAssEntry 2 }

pktSwchLogChAssHIC OBJECT-TYPE
        SYNTAX  Integer32 (0..4095)
        MAX-ACCESS  read-only
        STATUS  current
        DESCRIPTION
                "Highest Incoming channel.  A value of zero
                indicates no channels in this range."
        ::= { pktSwchLogChAssEntry 3 }

pktSwchLogChAssLTC OBJECT-TYPE
        SYNTAX  Integer32 (0..4095)
        MAX-ACCESS  read-only
        STATUS  current
        DESCRIPTION
                "Lowest Two-way channel."
        ::= { pktSwchLogChAssEntry 4 }

pktSwchLogChAssHTC OBJECT-TYPE
        SYNTAX  Integer32 (0..4095)
        MAX-ACCESS  read-only
        STATUS  current
        DESCRIPTION
                "Highest Two-way channel.  A value of zero
                indicates no channels in this range."
        ::= { pktSwchLogChAssEntry 5 }

pktSwchLogChAssLOC OBJECT-TYPE
        SYNTAX  Integer32 (0..4095)
        MAX-ACCESS  read-only
        STATUS  current
        DESCRIPTION
                "Lowest outgoing channel."
        ::= { pktSwchLogChAssEntry 6 }

pktSwchLogChAssHOC OBJECT-TYPE
        SYNTAX  Integer32 (0..4095)
        MAX-ACCESS  read-only
        STATUS  current
        DESCRIPTION
                "Highest outgoing channel.  A value of zero
                indicates no channels in this range."
        ::= { pktSwchLogChAssEntry 7 }

pktSwchLogChPartnerTable OBJECT-TYPE
SYNTAX  SEQUENCE OF PktSwchLogChPartnerEntry
MAX-ACCESS  not-accessible
STATUS  current
DESCRIPTION
        "These objects contain information about the
        partner channel number configuration in an X.25 PLE.
        These values are the configured values.
        changes in these values after the interfaces
        has started may not be reflected in the
        operating PLE."
REFERENCE "See ISO 8208, Section 3.7"
::= {pktSwchLogCh 2 }

pktSwchLogChPartnerEntry  OBJECT-TYPE
        SYNTAX  PktSwchLogChPartnerEntry
        MAX-ACCESS  not-accessible
        STATUS  current
        DESCRIPTION
                "Entries of pktSwchLogChPartnerTable."
        REFERENCE "This provides the information available
                in 10733 logicalChannelPartners."
        INDEX { pktSwchLogChPartnerIfIndex, pktSwchLogChPartnerLcIndex }
        ::= { pktSwchLogChPartnerTable 1 }

PktSwchLogChPartnerEntry  ::= SEQUENCE {
        pktSwchLogChPartnerIfIndex
		IfIndexType,
		pktSwchLogChPartnerLcIndex
		Integer32,
		pktSwchLogChPartnerProtocol
		INTEGER,
		pktSwchLogChPartnerOpIfIndex
		IfIndexType,
		pktSwchLogChPartnerOpLcIndex
		Integer32
		}

pktSwchLogChPartnerIfIndex  OBJECT-TYPE
        SYNTAX  IfIndexType
        MAX-ACCESS  read-only
        STATUS  current
        DESCRIPTION
                "The ifIndex value for the Lapb Interface."
        ::= { pktSwchLogChPartnerEntry 1 }

pktSwchLogChPartnerLcIndex OBJECT-TYPE
		SYNTAX  Integer32
        MAX-ACCESS  read-only
        STATUS  current
        DESCRIPTION
                "The Index value for the LCN."
        ::= { pktSwchLogChPartnerEntry 2 }

pktSwchLogChPartnerProtocol OBJECT-TYPE
		SYNTAX  INTEGER {
		                  other(1),
                          x25(2),
                          hdlc(3),
                          sdlc(4),
                          async(5),
	                      mpe(6),
						  ip(7)
	                 	}
        MAX-ACCESS  read-only
        STATUS  current
        DESCRIPTION
                " The protocol of the partner."
        ::= { pktSwchLogChPartnerEntry 3 }

pktSwchLogChPartnerOpIfIndex  OBJECT-TYPE
        SYNTAX  IfIndexType
        MAX-ACCESS  read-only
        STATUS  current
        DESCRIPTION
                "The ifIndex value for the partner Lapb Interface."
        ::= { pktSwchLogChPartnerEntry 4 }


pktSwchLogChPartnerOpLcIndex OBJECT-TYPE
		SYNTAX  Integer32
        MAX-ACCESS  read-only
        STATUS  current
        DESCRIPTION
                "The Index value for the partner LCN."
        ::= { pktSwchLogChPartnerEntry 5 }



-- The PS HDLC Group contains  HDLC Scratch and Active Tables, which contain configuration for
-- HDLC links

pktSwchHdlc   OBJECT IDENTIFIER ::= { radPS 5 }

pktSwchHdlcSTable  OBJECT-TYPE
    SYNTAX  SEQUENCE  OF PktSwchHdlcSEntry
    MAX-ACCESS  not-accessible
    STATUS  current
    DESCRIPTION
	"The Scratch Hdlc Table contains configuration information for HDLC links"
    ::=  { pktSwchHdlc 1 }

pktSwchHdlcSEntry OBJECT-TYPE
    SYNTAX  PktSwchHdlcSEntry
    MAX-ACCESS  not-accessible
    STATUS  current
    DESCRIPTION
	"Defines the contents of each line in the RAD Hdlc Table."
    INDEX   { pktSwchHdlcLinkNumberS }
    ::=  { pktSwchHdlcSTable 1  }

PktSwchHdlcSEntry ::= SEQUENCE {
    pktSwchHdlcLinkNumberS
     Integer32,
    pktSwchHdlcDestAddrS
     DisplayString,
    pktSwchHdlcDestSubAddrS
     Integer32,
    pktSwchHdlcRedialTimeoutS
     Integer32,
    pktSwchHdlcRedialRetriesS
     Integer32,
    pktSwchHdlcInactivityS
     Integer32,
    pktSwchHdlcX25FacilitiesS
     Integer32,
    pktSwchHdlcLocalSubaddr1S
     Integer32,
    pktSwchHdlcLocalSubaddr2S
     Integer32,
    pktSwchHdlcDestDlciS
     Integer32,
    pktSwchHdlcDestPortS
     Integer32,
    pktSwchHdlcProtocolS
     INTEGER,
    pktSwchHdlcFlowContOptionsS
     Integer32,
    pktSwchHdlcBufferFlowControlS
     Integer32,
    pktSwchHdlcInternalClockS
     INTEGER,
    pktSwchHdlcNrzModeS
     Integer32
    }

pktSwchHdlcLinkNumberS  OBJECT-TYPE
    SYNTAX Integer32
    MAX-ACCESS  read-only
    STATUS  current
    DESCRIPTION
	"The link number with which this entry is associated.  This value
	 corresponds to pktSwchPhyInterfaceNumber.  There is an entry for
	 each link for which the pktSwchPhyInterfaceProtocol is HDLC."
    ::= { pktSwchHdlcSEntry 1 }

pktSwchHdlcDestAddrS  OBJECT-TYPE
    SYNTAX DisplayString
    MAX-ACCESS  read-write
    STATUS  current
    DESCRIPTION
	"The destination address.  It defines the X.25 address on the remote
	 device."
    ::= { pktSwchHdlcSEntry 2 }

pktSwchHdlcDestSubAddrS  OBJECT-TYPE
    SYNTAX Integer32 (0..99)
    MAX-ACCESS  read-write
    STATUS  current
    DESCRIPTION
	"The destination subaddress.  It defines the synchronous link subaddress
	 on the remote device."
    ::= { pktSwchHdlcSEntry 3 }

pktSwchHdlcRedialTimeoutS  OBJECT-TYPE
    SYNTAX Integer32 (0..255)   -- seconds??
    MAX-ACCESS  read-write
    STATUS  current
    DESCRIPTION
	"The time interval in seconds between two consecutive connect
	 operations retries."
    ::= { pktSwchHdlcSEntry 4 }

pktSwchHdlcRedialRetriesS  OBJECT-TYPE
    SYNTAX Integer32 (0..255)
    MAX-ACCESS  read-write
    STATUS  current
    DESCRIPTION
	"This defines how many times the call operation is repeated if the
	 call request has failed."
    ::= { pktSwchHdlcSEntry 5 }

pktSwchHdlcInactivityS  OBJECT-TYPE
    SYNTAX Integer32 (0..255)
    MAX-ACCESS  read-write
    STATUS  current
    DESCRIPTION
	"The amount of time in minutes of inactivity that will cause the
	 session to disconnect."
    ::= { pktSwchHdlcSEntry 6 }

pktSwchHdlcX25FacilitiesS  OBJECT-TYPE
    SYNTAX Integer32 (0..7)
    MAX-ACCESS  read-write
    STATUS  current
    DESCRIPTION
	"This specifies the X.25 facilities.  The value is a sum of values
	 (powers of two), where each value in the sum represents an option.
	 The values that may be included in the sum and their meanings are:
		0 No options
		1 Packet size negotiation
		2 Window size negotiation
		4 Reverse  charge."
    ::= { pktSwchHdlcSEntry 7 }

pktSwchHdlcLocalSubaddr1S  OBJECT-TYPE
    SYNTAX Integer32 (0..99)
    MAX-ACCESS  read-write
    STATUS  current
    DESCRIPTION
	"The first local subaddress."
    ::= { pktSwchHdlcSEntry 8 }

pktSwchHdlcLocalSubaddr2S  OBJECT-TYPE
    SYNTAX Integer32 (0..99)
    MAX-ACCESS  read-write
    STATUS  current
    DESCRIPTION
	"The secondary local subaddress."
    ::= { pktSwchHdlcSEntry 9 }

pktSwchHdlcDestDlciS  OBJECT-TYPE
    SYNTAX Integer32
    MAX-ACCESS  read-write
    STATUS  current
    DESCRIPTION
	"The local DLCI which is used for HDLC encapsulation over Frame Relay.
	 Range: 16...991"
    ::= { pktSwchHdlcSEntry 10 }

pktSwchHdlcDestPortS  OBJECT-TYPE
    SYNTAX Integer32
    MAX-ACCESS  read-write
    STATUS  current
    DESCRIPTION
	"The local port that is used for HDLC encapsulation over Frame Relay.
	 Range: 1...12"
    ::= { pktSwchHdlcSEntry 11 }

pktSwchHdlcProtocolS  OBJECT-TYPE
    SYNTAX INTEGER {
       hdlcOverX25(1),   -- HDLC encapsulated over X.25
       hdlcOverFrRel(2),  -- HDLC encapsulated over Frame Relay
	   hdlcOverMpe(3),   -- HDLC encapsulated over MPE
       hdlcReg(4),  -- HDLC regular protocol for inner routing
	   hdlcOverIp(5)     -- HDLC encapsulated over IP
     }
    MAX-ACCESS  read-write
    STATUS  current
    DESCRIPTION
	"The HDLC protocol type."
    ::= { pktSwchHdlcSEntry 12 }

pktSwchHdlcFlowContOptionsS  OBJECT-TYPE
    SYNTAX Integer32 (0..3)
    MAX-ACCESS  read-write
    STATUS  current
    DESCRIPTION
	"This specifies the type of flow control of the HDLC link.  The value
	 is a sum of values (powers of two), where each value in the sum
	 represents an option.  The values that may be included in the sum and
	 their meanings are:
		0 No flow control
		1 CTS flow control
		2 Clock flow control."
    ::= { pktSwchHdlcSEntry 13 }

pktSwchHdlcBufferFlowControlS  OBJECT-TYPE
    SYNTAX Integer32 (1..200)
    MAX-ACCESS  read-write
    STATUS  current
    DESCRIPTION
	"The number of buffers that will be allocated for the HDLC link. Default value is 10"
    ::= { pktSwchHdlcSEntry 14 }

pktSwchHdlcInternalClockS  OBJECT-TYPE
    SYNTAX INTEGER {
       r2400bps (1),
       r4800bps (2),
       r9600bps (3),
       r14400bps(4),
       r19200bps(5),
       r38400bps(6),
	   r48Kbps  (7),
       r56Kbps  (8),
       r64Kbps  (9),
       r128Kbps (10),
       r256Kbps (11),
	   r384Kbps (12),
       r504Kbps (13),
	   r768Kbps (14),
	   r1008Kbps(15),
       r1466Kbps(16),
       r2016Kbps(17),
       external(255)
     }
    MAX-ACCESS  read-write
    STATUS  current
    DESCRIPTION
	"The baud rate of the internal clock."
    ::= { pktSwchHdlcSEntry 15 }

pktSwchHdlcNrzModeS  OBJECT-TYPE
    SYNTAX Integer32 (0..7)
    MAX-ACCESS  read-write
    STATUS  current
    DESCRIPTION
	"The data encoding format.
     The value is a sum of values (powers of two), where each
     value in the sum represents an option.
     The values that may be included in the sum and their
     meanings are:
		0   NRZ
		1   NRZI
		2   Transmit Idles between frames and control the RTS pin
		4   Normal Operation (DCD, CTS lines under automatic control)
		XX  Any combination of the values specified above."
    ::= { pktSwchHdlcSEntry 16 }


pktSwchHdlcATable  OBJECT-TYPE
    SYNTAX  SEQUENCE  OF PktSwchHdlcAEntry
    MAX-ACCESS  not-accessible
    STATUS  current
    DESCRIPTION
	"The Active Hdlc Table contains active configuration information for HDLC links"
    ::=  { pktSwchHdlc 2 }

pktSwchHdlcAEntry OBJECT-TYPE
    SYNTAX  PktSwchHdlcAEntry
    MAX-ACCESS  not-accessible
    STATUS  current
    DESCRIPTION
	"Defines the contents of each line in the RAD Hdlc Table."
    INDEX   { pktSwchHdlcLinkNumberA }
    ::=  { pktSwchHdlcATable 1  }

PktSwchHdlcAEntry ::= SEQUENCE {
    pktSwchHdlcLinkNumberA
     Integer32,
    pktSwchHdlcDestAddrA
     DisplayString,
    pktSwchHdlcDestSubAddrA
     Integer32,
    pktSwchHdlcRedialTimeoutA
     Integer32,
    pktSwchHdlcRedialRetriesA
     Integer32,
    pktSwchHdlcInactivityA
     Integer32,
    pktSwchHdlcX25FacilitiesA
     Integer32,
    pktSwchHdlcLocalSubaddr1A
     Integer32,
    pktSwchHdlcLocalSubaddr2A
     Integer32,
    pktSwchHdlcDestDlciA
     Integer32,
    pktSwchHdlcDestPortA
     Integer32,
    pktSwchHdlcProtocolA
     INTEGER,
    pktSwchHdlcFlowContOptionsA
     Integer32,
    pktSwchHdlcBufferFlowControlA
     Integer32,
    pktSwchHdlcInternalClockA
     INTEGER,
    pktSwchHdlcNrzModeA
     Integer32,
	pktSwchHdlcConnStatus
	 INTEGER,
	pktSwchHdlcSpecialStatus
	 INTEGER,
    pktSwchHdlcCtsStatus
	 INTEGER,
	pktSwchHdlcRunningX25Lcn
	 DisplayString,
	pktSwchHdlcRunningDlci
	 DisplayString,
	pktSwchHdlcMaxBuffToNet
	 Integer32,
	pktSwchHdlcBuffToNet
	 Integer32
    }

pktSwchHdlcLinkNumberA  OBJECT-TYPE
    SYNTAX Integer32
    MAX-ACCESS  read-only
    STATUS  current
    DESCRIPTION
	"The link number with which this entry is associated.  This value corresponds to
		 pktSwchPhyInterfaceNumber.  There is an entry for each link for which the pktSwchPhyInterfaceProtocol is
		 HDLC."
    ::= { pktSwchHdlcAEntry 1 }

pktSwchHdlcDestAddrA  OBJECT-TYPE
    SYNTAX DisplayString
    MAX-ACCESS  read-only
    STATUS  current
    DESCRIPTION
	"The destination address.  It defines the X.25 address on the remote device."
    ::= { pktSwchHdlcAEntry 2 }

pktSwchHdlcDestSubAddrA  OBJECT-TYPE
    SYNTAX Integer32 (0..99)
    MAX-ACCESS  read-only
    STATUS  current
    DESCRIPTION
	"The destination subaddress.  It defines the synchronous link subaddress on the remote
		 device."
    ::= { pktSwchHdlcAEntry 3 }

pktSwchHdlcRedialTimeoutA  OBJECT-TYPE
    SYNTAX Integer32 (0..255)   -- seconds??
    MAX-ACCESS  read-only
    STATUS  current
    DESCRIPTION
	"The time interval in seconds between two consecutive connect operations retries."
    ::= { pktSwchHdlcAEntry 4 }

pktSwchHdlcRedialRetriesA  OBJECT-TYPE
    SYNTAX Integer32 (0..255)
    MAX-ACCESS  read-only
    STATUS  current
    DESCRIPTION
	"This defines how many times the call operation is repeated if the call request has failed."
    ::= { pktSwchHdlcAEntry 5 }

pktSwchHdlcInactivityA  OBJECT-TYPE
    SYNTAX Integer32 (0..255)
    MAX-ACCESS  read-only
    STATUS  current
    DESCRIPTION
	"The amount of time in minutes of inactivity that will cause the
	 session to disconnect."
    ::= { pktSwchHdlcAEntry 6 }

pktSwchHdlcX25FacilitiesA  OBJECT-TYPE
    SYNTAX Integer32 (0..7)
    MAX-ACCESS  read-only
    STATUS  current
    DESCRIPTION
	"This specifies the X.25 facilities.  The value is a sum of values (powers of two), where each
		 value in the sum represents an option.  The values that may be included in the sum and
		 their meanings are:
		0 No options
		1 Packet size negotiation
		2 Window size negotiation
		4 Reverse  charge."
    ::= { pktSwchHdlcAEntry 7 }

pktSwchHdlcLocalSubaddr1A  OBJECT-TYPE
    SYNTAX Integer32 (0..99)
    MAX-ACCESS  read-only
    STATUS  current
    DESCRIPTION
	"The first local subaddress."
    ::= { pktSwchHdlcAEntry 8 }

pktSwchHdlcLocalSubaddr2A  OBJECT-TYPE
    SYNTAX Integer32 (0..99)
    MAX-ACCESS  read-only
    STATUS  current
    DESCRIPTION
	"The secondary local subaddress."
    ::= { pktSwchHdlcAEntry 9 }

pktSwchHdlcDestDlciA  OBJECT-TYPE
    SYNTAX Integer32
    MAX-ACCESS  read-only
    STATUS  current
    DESCRIPTION
	"The local DLCI which is used for HDLC encapsulation over Frame Relay."
    ::= { pktSwchHdlcAEntry 10 }

pktSwchHdlcDestPortA  OBJECT-TYPE
    SYNTAX Integer32
    MAX-ACCESS  read-only
    STATUS  current
    DESCRIPTION
	"The local port that is used for HDCL encapsulation over Frame Relay."
    ::= { pktSwchHdlcAEntry 11 }

pktSwchHdlcProtocolA  OBJECT-TYPE
    SYNTAX INTEGER {
       hdlcOverX25(1),   -- HDLC encapsulated over X.25
       hdlcOverFrRel(2),  -- HDLC encapsulated over Frame Relay
	   hdlcOverMpe(3),   -- HDLC encapsulated over MPE
       hdlcReg(4),  -- HDLC regular protocol for inner routing
           hdlcOverIp(5)     -- It is actually IP over HDLC
     }
    MAX-ACCESS  read-only
    STATUS  current
    DESCRIPTION
	"The HDLC protocol type."
    ::= { pktSwchHdlcAEntry 12 }

pktSwchHdlcFlowContOptionsA  OBJECT-TYPE
    SYNTAX Integer32 (0..3)
    MAX-ACCESS  read-only
    STATUS  current
    DESCRIPTION
	"This specifies the type of flow control of the HDLC link.  The value is a sum of values
		 (powers of two), where each value in the sum represents an option.  The values that may
		 be included in the sum and their meanings are:
		0 No flow control
		1 CTS flow control
		2 Clock flow control."
    ::= { pktSwchHdlcAEntry 13 }

pktSwchHdlcBufferFlowControlA  OBJECT-TYPE
    SYNTAX Integer32 (1..200)
    MAX-ACCESS  read-only
    STATUS  current
    DESCRIPTION
	"The number of buffers that will be allocated for the HDLC link."
    ::= { pktSwchHdlcAEntry 14 }

pktSwchHdlcInternalClockA  OBJECT-TYPE
    SYNTAX INTEGER {
       r2400bps (1),
       r4800bps (2),
       r9600bps (3),
       r14400bps(4),
       r19200bps(5),
       r38400bps(6),
	   r48Kbps  (7),
       r56Kbps  (8),
       r64Kbps  (9),
       r128Kbps (10),
       r256Kbps (11),
	   r384Kbps (12),
       r504Kbps (13),
	   r768Kbps (14),
	   r1008Kbps(15),
       r1466Kbps(16),
       r2016Kbps(17),
       external(255)
      }
    MAX-ACCESS  read-only
    STATUS  current
    DESCRIPTION
	"The baud rate of the internal clock."
    ::= { pktSwchHdlcAEntry 15 }

pktSwchHdlcNrzModeA  OBJECT-TYPE
    SYNTAX Integer32 (0..7)
    MAX-ACCESS  read-only
    STATUS  current
    DESCRIPTION
	"The data encoding format.
     The value is a sum of values (powers of two), where each
     value in the sum represents an option.
     The values that may be included in the sum and their
     meanings are:
		0   NRZ
		1   NRZI
		2   Transmit Idles between frames and control the RTS pin
		4   Normal Operation (DCD, CTS lines under automatic control)
		XX  Any combination of the values specified above."
    ::= { pktSwchHdlcAEntry 16 }

pktSwchHdlcConnStatus  OBJECT-TYPE
    SYNTAX INTEGER {
	                disconnect(1),
					connect(2),
					pvc(3)
				   }
    MAX-ACCESS  read-only
    STATUS  current
    DESCRIPTION
	"The status of the Hdlc session."
    ::= { pktSwchHdlcAEntry 17 }

pktSwchHdlcSpecialStatus  OBJECT-TYPE
    SYNTAX INTEGER {
	                busy(1),
					overflow(2),
					noStatus(255)
				   }
    MAX-ACCESS  read-only
    STATUS  current
    DESCRIPTION
	"The status of the Hdlc link."
    ::= { pktSwchHdlcAEntry 18 }

pktSwchHdlcCtsStatus  OBJECT-TYPE
    SYNTAX INTEGER {
                    off(2),
                    on(3)
                   }
    MAX-ACCESS  read-only
    STATUS  current
    DESCRIPTION
	"The CTS status."
    ::= { pktSwchHdlcAEntry 19 }

pktSwchHdlcRunningX25Lcn  OBJECT-TYPE
    SYNTAX DisplayString
    MAX-ACCESS  read-only
    STATUS  current
    DESCRIPTION
	"The format of the string is ifIndex:LCN "
    ::= { pktSwchHdlcAEntry 20 }

pktSwchHdlcRunningDlci  OBJECT-TYPE
    SYNTAX DisplayString
    MAX-ACCESS  read-only
    STATUS  current
    DESCRIPTION
	"The format of the string is ifIndex:DLCI"
    ::= { pktSwchHdlcAEntry 21 }

pktSwchHdlcMaxBuffToNet  OBJECT-TYPE
    SYNTAX Integer32
    MAX-ACCESS  read-only
    STATUS  current
    DESCRIPTION
	"The maximum number of buffers above which Flow Control is enabled"
    ::= { pktSwchHdlcAEntry 22 }

pktSwchHdlcBuffToNet  OBJECT-TYPE
    SYNTAX Integer32
    MAX-ACCESS  read-only
    STATUS  current
    DESCRIPTION
	"The number of buffers waiting for transmission."
    ::= { pktSwchHdlcAEntry 23 }

pktSwchStmTable  OBJECT-TYPE
    SYNTAX  SEQUENCE  OF PktSwchStmEntry
    MAX-ACCESS  not-accessible
    STATUS  current
    DESCRIPTION
	"The STM table contains information for STM links"
    ::=  { radPS 7 }

pktSwchStmEntry OBJECT-TYPE
    SYNTAX  PktSwchStmEntry
    MAX-ACCESS  not-accessible
    STATUS  current
    DESCRIPTION
	"Defines the contents of each line in the RAD STM Table."
    INDEX   { pktSwchStmLinkNumber }
    ::=  { pktSwchStmTable 1  }

PktSwchStmEntry ::= SEQUENCE {
    pktSwchStmLinkNumber
     Integer32,
    pktSwchStmInternalClockS
     INTEGER,
    pktSwchStmInternalClockA
     INTEGER,
	pktSwchStmConn
	 INTEGER,
	pktSwchStmSyncLoss
	 Counter32
    }

pktSwchStmLinkNumber  OBJECT-TYPE
    SYNTAX Integer32
    MAX-ACCESS  read-only
    STATUS  current
    DESCRIPTION
	"The link number with which this entry is associated.  This value
	 corresponds to pktSwchPhyInterfaceNumber.  There is an entry for
	 each link whose pktSwchPhyInterfaceProtocol is STM 4, 8, 16, or 24."
    ::= { pktSwchStmEntry 1 }

pktSwchStmInternalClockS  OBJECT-TYPE
    SYNTAX INTEGER {
       r2400bps (1),
       r4800bps (2),
       r9600bps (3),
       r14400bps(4),
       r19200bps(5),
       r38400bps(6),
	   r48Kbps  (7),
       r56Kbps  (8),
       r64Kbps  (9),
       r128Kbps (10),
       r256Kbps (11),
	   r384Kbps (12),
       r504Kbps (13),
	   r768Kbps (14),
	   r1008Kbps(15),
       r1466Kbps(16),
       r2016Kbps(17),
       external(255)
       }
    MAX-ACCESS  read-write
    STATUS  current
    DESCRIPTION
	"The baud rate of the internal clock."
    ::= { pktSwchStmEntry 2 }

pktSwchStmInternalClockA  OBJECT-TYPE
    SYNTAX INTEGER {
       r2400bps (1),
       r4800bps (2),
       r9600bps (3),
       r14400bps(4),
       r19200bps(5),
       r38400bps(6),
	   r48Kbps  (7),
       r56Kbps  (8),
       r64Kbps  (9),
       r128Kbps (10),
       r256Kbps (11),
	   r384Kbps (12),
       r504Kbps (13),
	   r768Kbps (14),
	   r1008Kbps(15),
       r1466Kbps(16),
       r2016Kbps(17),
       external(255)
      }
    MAX-ACCESS  read-only
    STATUS  current
    DESCRIPTION
	"The current baud rate of the internal clock."
    ::= { pktSwchStmEntry 3 }

pktSwchStmConn OBJECT-TYPE
    SYNTAX   INTEGER {
                    disconnect(1),
					connect(2)
					}
    MAX-ACCESS   read-only
    STATUS   current
    DESCRIPTION
       "The connectivity status of the STM interface."
   ::= { pktSwchStmEntry 4 }

pktSwchStmSyncLoss OBJECT-TYPE
    SYNTAX   Counter32
    MAX-ACCESS   read-only
    STATUS   current
    DESCRIPTION
       "The counter for sync loss."
   ::= { pktSwchStmEntry 5 }

-- The PS Frame Relay Group

pktSwchFr  OBJECT IDENTIFIER ::= { radPS 8 }

pktSwchFrTotFunnels OBJECT-TYPE
    SYNTAX Integer32
    MAX-ACCESS  read-only
    STATUS  current
    DESCRIPTION
	"The total number of Funnels on the PS."
    ::= { pktSwchFr 1 }

pktSwchFrSTable  OBJECT-TYPE
   SYNTAX  SEQUENCE  OF PktSwchFrSEntry
   MAX-ACCESS  not-accessible
   STATUS  current
   DESCRIPTION
      "The Frame Relay Scratch Table includes the scratch values of
       configurable objects provided by the PS that are not included
       in RFC 1315."
   ::=  { pktSwchFr 2 }

 pktSwchFrSEntry OBJECT-TYPE
    SYNTAX  PktSwchFrSEntry
    MAX-ACCESS  not-accessible
    STATUS  current
    DESCRIPTION
	"Defines the contents of each line in the RAD PS Frame Relay
	 Scratch Table."
    INDEX   { pktSwchFrIfIndexS }
    ::=  { pktSwchFrSTable 1  }

 PktSwchFrSEntry ::= SEQUENCE {
    pktSwchFrIfIndexS
     Integer32,
    pktSwchFrMaintProtS
     Integer32,
    pktSwchFrMaintModeS
     INTEGER,
    pktSwchFrRxPoolRedLineS
     Integer32,
    pktSwchFrRxPoolOkS
     Integer32,
    pktSwchFrTxPoolRedLineS
     Integer32,
    pktSwchFrTxPoolOkS
     Integer32,
    pktSwchFrTxCeilingS
     Integer32,
    pktSwchFrInternalClockS
     INTEGER,
    pktSwchFrNrzModeS
     INTEGER,
    pktSwchFrDlciHeaderModeS
     INTEGER,
    pktSwchFrDcdLinkFailureS
     INTEGER,
    pktSwchFrTxIdlesS
     INTEGER,
    pktSwchFrOperationModeS
     INTEGER,
    pktSwchFrPhysInterfOptionsS
     INTEGER
       }


pktSwchFrIfIndexS OBJECT-TYPE
    SYNTAX   Integer32
    MAX-ACCESS   read-only
    STATUS   current
    DESCRIPTION
       "This is the ifIndex of the frame relay port."
   ::= { pktSwchFrSEntry 1 }

pktSwchFrMaintProtS OBJECT-TYPE
    SYNTAX   Integer32 (0..12)
    MAX-ACCESS   read-write
    STATUS   current
    DESCRIPTION
       "This defines what maintenance protocol is running over this port.
        0 - No maintenance protocol.
        1 - ANSI PVC maintenance protocol running on DLCI number 0.
        2 - LMI maintenance protocol running on DLCI number 1023.
        4 - ITU Q.933 ANNEX A maintenance protocol running on DLCI number 0.
        8 - Consolidate Link Layer Management CLLM running on DLCI number 1023.
		    8 cannot be a choice by itself, it can only be as part of the
			combination 9, 10, 12.
        XXX - The combination of 9, 10, 12."
   ::= { pktSwchFrSEntry 2 }

pktSwchFrMaintModeS OBJECT-TYPE
    SYNTAX   INTEGER {
	user(1),
	network(2),
	both(3)}
    MAX-ACCESS   read-write
    STATUS   current
    DESCRIPTION
       "This defines the mode of maintenance protocol running over this port."
   ::= { pktSwchFrSEntry 3 }

pktSwchFrRxPoolRedLineS OBJECT-TYPE
    SYNTAX   Integer32 (0..39)
    MAX-ACCESS   read-write
    STATUS   current
    DESCRIPTION
       "When the number of empty receive buffers at the port reaches this
        figure (of frames),the port receiver is congested.  This field
        value should be less than the Rx pool OK field."
   ::= { pktSwchFrSEntry 4 }

pktSwchFrRxPoolOkS OBJECT-TYPE
    SYNTAX   Integer32 (1..40)
    MAX-ACCESS   read-write
    STATUS   current
    DESCRIPTION
       "Clear the receive congestion condition when the number of empty
        receive buffers at the port reaches this figure.  This value
        (of frames) should be greater than the Rx pool red line."
   ::= { pktSwchFrSEntry 5 }

pktSwchFrTxPoolRedLineS OBJECT-TYPE
    SYNTAX   Integer32 (1..500)
    MAX-ACCESS   read-write
    STATUS   current
    DESCRIPTION
       "When the number of frames awaiting transmission reaches this figure,
        the port transmitter is congested.  This field value should be
        greater than the Tx pool OK field."
   ::= { pktSwchFrSEntry 6 }

pktSwchFrTxPoolOkS OBJECT-TYPE
    SYNTAX   Integer32 (0..499)
    MAX-ACCESS   read-write
    STATUS   current
    DESCRIPTION
       "Clear the transmit congestion condition when the number of frames
        awaiting transmission at the port reaches this figure.  This value
        (of frames) should be less than the Tx pool red line."
   ::= { pktSwchFrSEntry 7 }

pktSwchFrTxCeilingS OBJECT-TYPE
    SYNTAX   Integer32 (1..500)
    MAX-ACCESS   read-write
    STATUS   current
    DESCRIPTION
       "The maximum allowable transmit pool for this port."
   ::= { pktSwchFrSEntry 8 }

pktSwchFrInternalClockS  OBJECT-TYPE
    SYNTAX INTEGER {
       r2400bps (1),
       r4800bps (2),
       r9600bps (3),
       r14400bps(4),
       r19200bps(5),
       r38400bps(6),
	   r48Kbps  (7),
       r56Kbps  (8),
       r64Kbps  (9),
       r128Kbps (10),
       r256Kbps (11),
	   r384Kbps (12),
       r504Kbps (13),
	   r768Kbps (14),
	   r1008Kbps(15),
       r1466Kbps(16),
       r2016Kbps(17),
       external (255)
     }
    MAX-ACCESS  read-write
    STATUS  current
    DESCRIPTION
	"The baud rate of the internal clock."
    ::= { pktSwchFrSEntry 9 }

pktSwchFrNrzModeS  OBJECT-TYPE
    SYNTAX INTEGER {
       nrz(1),
       nrzi(2)
     }
    MAX-ACCESS  read-write
    STATUS  current
    DESCRIPTION
	"The data encoding format."
    ::= { pktSwchFrSEntry 10 }

pktSwchFrDlciHeaderModeS  OBJECT-TYPE
    SYNTAX INTEGER {
       two-octets(1),
       three-octets(2),
       four-octets(3),
       four-octets-nomanag(4)
     }
    MAX-ACCESS  read-write
    STATUS  current
    DESCRIPTION
        "Dlci Header length for this FR port. Option 4 means that there
         will be no management Dlci in the range of 1024 to 8388607.
         The management Dlci will be in the range of 0-15 or 991-1023.
         Default value: 1."
         ::= { pktSwchFrSEntry 11 }

pktSwchFrDcdLinkFailureS  OBJECT-TYPE
    SYNTAX INTEGER {
       no-Detect(2),
       linkFailure-Detect(3)
     }
    MAX-ACCESS  read-write
    STATUS  current
    DESCRIPTION
        "Link Failure Detection by DCD.
         If Link Failure detection by DCD is on - (3), when the DCD is
         down, the FR SW will detect it and change the FR link status
         from UP to DOWN. A trap of LINK DOWN will be sent to the NMS.
         Default: (2)."
         ::= { pktSwchFrSEntry 12 }


pktSwchFrTxIdlesS  OBJECT-TYPE
    SYNTAX INTEGER {
       no(2),
       yes(3)
     }
    MAX-ACCESS  read-write
    STATUS  current
    DESCRIPTION
        "This parameter shows whether the PS will Transmit Idles between
         frames and control the RTS pin.
         Default: no(2)."
        ::= { pktSwchFrSEntry 13 }

pktSwchFrOperationModeS  OBJECT-TYPE
    SYNTAX INTEGER {
       swControl(2),
       hwControl(3)
     }
    MAX-ACCESS  read-write
    STATUS  current
    DESCRIPTION
        "When H/W Control is configured, the SCC H/W will detect the change in the
		 DCD or CTS signals and Start or Stop transmission automatically.
		 When S/W Control is configured the S/W will decide when to start or stop
		 the transmission.
         Default: swControl(2)."
         ::= { pktSwchFrSEntry 14 }

pktSwchFrPhysInterfOptionsS  OBJECT-TYPE
    SYNTAX INTEGER {
       noOption(2),
       dds4800bps(3),
	   dds9600bps(4),
	   dds19200bps(5),
	   dds56000bos(6)
     }
    MAX-ACCESS  read-write
    STATUS  current
    DESCRIPTION
        "This is the physical interface.
		 Note that the DDS physical interface H/W does not exist in the FPS-8.
		 It is relevant for other PS devices only.
		 For FPS-8 only the default (noOption) should be used.
		 Default: (2)."
         ::= { pktSwchFrSEntry 15 }


 pktSwchFrATable  OBJECT-TYPE
    SYNTAX  SEQUENCE  OF PktSwchFrAEntry
    MAX-ACCESS  not-accessible
    STATUS  current
    DESCRIPTION
	"The Frame Relay Active Table includes statistics and the active values of configurable
                objects provided by the PS that are not included in RFC 1315."
    ::=  { pktSwchFr 3 }

 pktSwchFrAEntry OBJECT-TYPE
    SYNTAX  PktSwchFrAEntry
    MAX-ACCESS  not-accessible
    STATUS  current
    DESCRIPTION
	"Defines the contents of each line in the RAD PS Frame Relay Active Table."
    INDEX   { pktSwchFrIfIndexA }
    ::=  { pktSwchFrATable 1  }

PktSwchFrAEntry ::= SEQUENCE {
    pktSwchFrIfIndexA
     Integer32,
    pktSwchFrMaintProtA
     Integer32,
    pktSwchFrMaintModeA
     INTEGER,
    pktSwchFrRxPoolRedLineA
     Integer32,
    pktSwchFrRxPoolOkA
     Integer32,
    pktSwchFrTxPoolRedLineA
     Integer32,
    pktSwchFrTxPoolOkA
     Integer32,
    pktSwchFrTxCeilingA
     Integer32,
    pktSwchFrInternalClockA
     INTEGER,
    pktSwchFrNrzModeA
     INTEGER,
    pktSwchFrDlcmiPollingInterval
     Integer32,
    pktSwchFrDlcmiFullEnquiryInterval
     Integer32,
    pktSwchFrDlcmiErrorThreshold
     Integer32,
    pktSwchFrDlcmiMonitoredEvents
     Integer32,
    pktSwchFrDlciHeaderModeA
     INTEGER,
    pktSwchFrDcdLinkFailureA
     INTEGER,
    pktSwchFrTxIdlesA
     INTEGER,
    pktSwchFrOperationModeA
     INTEGER,
    pktSwchFrPhysInterfOptionsA
     INTEGER
    }


pktSwchFrIfIndexA OBJECT-TYPE
    SYNTAX   Integer32
    MAX-ACCESS   read-only
    STATUS   current
    DESCRIPTION
       "This is the ifIndex of the frame relay port."
   ::= { pktSwchFrAEntry 1 }

pktSwchFrMaintProtA OBJECT-TYPE
    SYNTAX   Integer32 (0..12)
    MAX-ACCESS   read-only
    STATUS   current
    DESCRIPTION
       "This defines what maintenance protocol is running over this port.
        0 - No maintenance protocol.
        1 - ANSI PVC maintenance protocol running on DLCI number 0.
        2 - LMI maintenance protocol running on DLCI number 1023.
        4 - ITU Q.933 ANNEX A maintenance protocol running on DLCI number 0.
        8 - Consolidate Link Layer Management CLLM running on DLCI number 1023.
		    8 cannot be a choice by itself, it can only be as part of the
			combination 9, 10, 12.
        XXX - The combination of 9, 10, 12."
   ::= { pktSwchFrAEntry 2 }

pktSwchFrMaintModeA OBJECT-TYPE
    SYNTAX   INTEGER {
	user(1),
	network(2),
	both(3)}
    MAX-ACCESS   read-only
    STATUS   current
    DESCRIPTION
       "This defines the mode of maintenance protocol running over this port."
   ::= { pktSwchFrAEntry 3 }

pktSwchFrRxPoolRedLineA OBJECT-TYPE
    SYNTAX   Integer32 (0..39)
    MAX-ACCESS   read-only
    STATUS   current
    DESCRIPTION
       "When the number of empty receive buffers at the port reaches this figure (of frames),
        the port receiver is congested.  This field value should be less than the Rx pool OK field."
   ::= { pktSwchFrAEntry 4 }

pktSwchFrRxPoolOkA OBJECT-TYPE
    SYNTAX   Integer32 (1..40)
    MAX-ACCESS   read-only
    STATUS   current
    DESCRIPTION
       "Clear the receive congestion condition when the number of empty receive buffers at the port
        reaches this figure.  This value (of frames) should be greater than the Rx pool red line."
   ::= { pktSwchFrAEntry 5 }

pktSwchFrTxPoolRedLineA OBJECT-TYPE
    SYNTAX   Integer32 (1..500)
    MAX-ACCESS   read-only
    STATUS   current
    DESCRIPTION
       "When the number of frames awaiting transmission reaches this figure,
        the port transmitter is congested.  This field value should be greater than the Tx pool OK field."
   ::= { pktSwchFrAEntry 6 }

pktSwchFrTxPoolOkA OBJECT-TYPE
    SYNTAX   Integer32 (0..499)
    MAX-ACCESS   read-only
    STATUS   current
    DESCRIPTION
       "Clear the transmit congestion condition when the number of frames awaiting transmission
        at the port reaches this figure.  This value (of frames) should be less than the Tx pool red line."
   ::= { pktSwchFrAEntry 7 }

pktSwchFrTxCeilingA OBJECT-TYPE
    SYNTAX   Integer32 (0..500)
    MAX-ACCESS   read-only
    STATUS   current
    DESCRIPTION
       "The maximum allowable transmit pool for this port."
   ::= { pktSwchFrAEntry 8 }

pktSwchFrInternalClockA  OBJECT-TYPE
    SYNTAX INTEGER {
       r2400bps (1),
       r4800bps (2),
       r9600bps (3),
       r14400bps(4),
       r19200bps(5),
       r38400bps(6),
	   r48Kbps  (7),
       r56Kbps  (8),
       r64Kbps  (9),
       r128Kbps (10),
       r256Kbps (11),
	   r384Kbps (12),
       r504Kbps (13),
	   r768Kbps (14),
	   r1008Kbps(15),
       r1466Kbps(16),
       r2016Kbps(17),
       external (255)
     }
    MAX-ACCESS  read-only
    STATUS  current
    DESCRIPTION
	"The baud rate of the internal clock."
    ::= { pktSwchFrAEntry 9 }

pktSwchFrNrzModeA  OBJECT-TYPE
    SYNTAX INTEGER {
       nrz(1),
       nrzi(2)
     }
    MAX-ACCESS  read-only
    STATUS  current
    DESCRIPTION
	"The data encoding format."
    ::= { pktSwchFrAEntry 10 }

pktSwchFrDlcmiPollingInterval OBJECT-TYPE
             SYNTAX   Integer32 (5..30)
             MAX-ACCESS   read-only
             STATUS   current
             DESCRIPTION
                "This is the number of seconds between succes-
                sive status enquiry messages."
            REFERENCE
               "Draft American National  Standard  T1.617-1991,
               Section D.7 Timer T391."
           DEFVAL { 10 }
    ::= { pktSwchFrAEntry 11 }

pktSwchFrDlcmiFullEnquiryInterval OBJECT-TYPE
             SYNTAX   Integer32 (1..255)
             MAX-ACCESS   read-only
             STATUS   current
             DESCRIPTION
                "Number of status enquiry intervals  that  pass
                before  issuance  of a full status enquiry mes-
                sage."
            REFERENCE
               "Draft American National  Standard  T1.617-1991,
               Section D.7 Counter32 N391."
           DEFVAL { 6 }
    ::= { pktSwchFrAEntry 12 }

pktSwchFrDlcmiErrorThreshold OBJECT-TYPE
             SYNTAX   Integer32 (1..10)
             MAX-ACCESS   read-only
             STATUS   current
             DESCRIPTION
                "This  is  the  maximum  number  of  unanswered
                Status Enquiries the equipment shall accept be-
                fore declaring the interface down."
            REFERENCE
               "Draft American National  Standard  T1.617-1991,
               Section D.5.1 Counter32 N392."
           DEFVAL { 3 }
    ::= { pktSwchFrAEntry 13 }

pktSwchFrDlcmiMonitoredEvents OBJECT-TYPE
             SYNTAX   Integer32 (1..10)
             MAX-ACCESS   read-only
             STATUS   current
             DESCRIPTION
                "This is the number of status polling intervals
                over which the error threshold is counted.  For
                example, if within 'MonitoredEvents' number  of
                events  the  station  receives 'ErrorThreshold'
                number of errors, the interface  is  marked  as
                down."
            REFERENCE
               "Draft American National  Standard  T1.617-1991,
               Section D.5.2 Counter32 N393."
           DEFVAL { 4 }
    ::= { pktSwchFrAEntry 14 }

pktSwchFrDlciHeaderModeA  OBJECT-TYPE
    SYNTAX INTEGER {
       two-octets(1),
       three-octets(2),
       four-octets(3),
       four-octets-nomanag(4)
     }
    MAX-ACCESS  read-only
    STATUS  current
    DESCRIPTION
        "Dlci Header length for this FR port. Option 4 means that there
         will be no management Dlci in the range of 1024 to 8388607.
         The management Dlci will be in the range of 0-15 or 991-1023.
         Default value: 1."
    ::= { pktSwchFrAEntry 15 }

pktSwchFrDcdLinkFailureA  OBJECT-TYPE
    SYNTAX INTEGER {
       no-Detect(2),
       linkFailure-Detect(3)
     }
    MAX-ACCESS  read-only
    STATUS  current
    DESCRIPTION
        "Link Failure Detection by DCD.
         If Link Failure detection by DCD is on - (3), when the DCD is
         down, the FR SW will detect it and change the FR link status
         from UP to DOWN. A trap of LINK DOWN will be sent to the NMS.
         Default: (2)."
         ::= { pktSwchFrAEntry 16 }

pktSwchFrTxIdlesA  OBJECT-TYPE
    SYNTAX INTEGER {
       no(2),
       yes(3)
     }
    MAX-ACCESS  read-only
    STATUS  current
    DESCRIPTION
        "This parameter shows whether the PS will Transmit Idles between
         frames and control the RTS pin.
         Default: no(2)."
        ::= { pktSwchFrAEntry 17 }

pktSwchFrOperationModeA  OBJECT-TYPE
    SYNTAX INTEGER {
       swControl(2),
       hwControl(3)
     }
    MAX-ACCESS  read-only
    STATUS  current
    DESCRIPTION
        "When H/W Control is configured, the SCC H/W will detect the change in the
		 DCD or CTS signals and Start or Stop transmission automatically.
		 When S/W Control is configured the S/W will decide when to start or stop
		 the transmission.
         Default: swControl(2)."
         ::= { pktSwchFrAEntry 18 }

pktSwchFrPhysInterfOptionsA  OBJECT-TYPE
    SYNTAX INTEGER {
       noOption(2),
       dds4800bps(3),
	   dds9600bps(4),
	   dds19200bps(5),
	   dds56000bos(6)
     }
    MAX-ACCESS  read-only
    STATUS  current
    DESCRIPTION
        "This is the physical interface.
		 Note that the DDS physical interface H/W does not exist in the FPS-8.
		 It is relevant for other PS devices only.
		 For FPS-8 only the default (noOption) should be used.
		 Default: (2)."
         ::= { pktSwchFrAEntry 19 }


pktSwchFrIfTable  OBJECT-TYPE
    SYNTAX  SEQUENCE  OF PktSwchFrIfEntry
    MAX-ACCESS  not-accessible
    STATUS  current
    DESCRIPTION
	"The Frame Relay Active Port Table includes statistics and configurable objects
                 provided by the PS  that are not included in RFC 1315."
    ::=  { pktSwchFr 4 }

pktSwchFrIfEntry OBJECT-TYPE
    SYNTAX  PktSwchFrIfEntry
    MAX-ACCESS  not-accessible
    STATUS  current
    DESCRIPTION
	"Defines the contents of each line in the RAD PS Frame Relay Port Active Table."
    INDEX   { ifIndex }
    ::=  { pktSwchFrIfTable 1  }

PktSwchFrIfEntry ::= SEQUENCE {
	pktSwchFrIfTxBytes
     Counter32,
    pktSwchFrIfRxBytes
     Counter32,
    pktSwchFrIfTxCongDiscards
     Counter32,
    pktSwchFrIfDeTxFrames
     Counter32,
    pktSwchFrIfDeRxFrames
     Counter32,
    pktSwchFrIfFecnTxFrames
     Counter32,
	pktSwchFrIfFecnRxFrames
     Counter32,
    pktSwchFrIfBecnTxFrames
     Counter32,
	pktSwchFrIfBecnRxFrames
     Counter32,
    pktSwchFrIfCommRateViolTxFrames
     Counter32,
    pktSwchFrIfCommRateViolRxFrames
     Counter32,
    pktSwchFrIfExcessRateViolTxFrames
     Counter32,
    pktSwchFrIfExcessRateViolRxFrames
     Counter32,
    pktSwchFrIfBuffersInTxPool
     Integer32,
    pktSwchFrIfFreeBuffersInRxPool
     Integer32,
    pktSwchFrIfLmiTxFrames
     Counter32,
    pktSwchFrIfLmiRxFrames
     Counter32,
    pktSwchFrIfAnsiTxFrames
     Counter32,
    pktSwchFrIfAnsiRxFrames
     Counter32,
    pktSwchFrIfCllmTxFrames
     Counter32,
    pktSwchFrIfCllmRxFrames
     Counter32,
    pktSwchFrIfTxCongestions
     Counter32,
    pktSwchFrIfRxCongestions
     Counter32,
    pktSwchFrIfTotDlciNumber
	 Integer32
     }

pktSwchFrIfTxBytes  OBJECT-TYPE
    SYNTAX Counter32
    MAX-ACCESS  read-only
    STATUS  current
    DESCRIPTION
	"The number of Tx bytes."
    ::= { pktSwchFrIfEntry 1 }

pktSwchFrIfRxBytes  OBJECT-TYPE
    SYNTAX Counter32
    MAX-ACCESS  read-only
    STATUS  current
    DESCRIPTION
	"The number of Rx bytes."
    ::= { pktSwchFrIfEntry 2 }

pktSwchFrIfTxCongDiscards  OBJECT-TYPE
    SYNTAX Counter32
    MAX-ACCESS  read-only
    STATUS  current
    DESCRIPTION
	"The number of frames discarded because of Tx congestion."
    ::= { pktSwchFrIfEntry 3 }

pktSwchFrIfDeTxFrames  OBJECT-TYPE
    SYNTAX Counter32
    MAX-ACCESS  read-only
    STATUS  current
    DESCRIPTION
	"The number of DE Tx frames."
    ::= { pktSwchFrIfEntry 4 }

pktSwchFrIfDeRxFrames  OBJECT-TYPE
    SYNTAX Counter32
    MAX-ACCESS  read-only
    STATUS  current
    DESCRIPTION
	"The number of DE Rx frames."
    ::= { pktSwchFrIfEntry 5 }

pktSwchFrIfFecnTxFrames  OBJECT-TYPE
    SYNTAX Counter32
    MAX-ACCESS  read-only
    STATUS  current
    DESCRIPTION
	"The number of FECN Tx frames."
    ::= { pktSwchFrIfEntry 6 }

pktSwchFrIfFecnRxFrames  OBJECT-TYPE
    SYNTAX Counter32
    MAX-ACCESS  read-only
    STATUS  current
    DESCRIPTION
	"The number of FECN Tx frames."
    ::= { pktSwchFrIfEntry 7 }

pktSwchFrIfBecnTxFrames  OBJECT-TYPE
    SYNTAX Counter32
    MAX-ACCESS  read-only
    STATUS  current
    DESCRIPTION
	"The number of BECN Tx frames."
    ::= { pktSwchFrIfEntry 8 }

pktSwchFrIfBecnRxFrames  OBJECT-TYPE
    SYNTAX Counter32
    MAX-ACCESS  read-only
    STATUS  current
    DESCRIPTION
	"The number of BECN Tx frames."
    ::= { pktSwchFrIfEntry 9 }

pktSwchFrIfCommRateViolTxFrames  OBJECT-TYPE
    SYNTAX Counter32
    MAX-ACCESS  read-only
    STATUS  current
    DESCRIPTION
	"The number of  Tx committed rate violations in number of frames."
    ::= { pktSwchFrIfEntry 10 }

pktSwchFrIfCommRateViolRxFrames  OBJECT-TYPE
    SYNTAX Counter32
    MAX-ACCESS  read-only
    STATUS  current
    DESCRIPTION
	"The number of  Rx committed rate violations in number of frames."
    ::= { pktSwchFrIfEntry 11 }

pktSwchFrIfExcessRateViolTxFrames  OBJECT-TYPE
    SYNTAX Counter32
    MAX-ACCESS  read-only
    STATUS  current
    DESCRIPTION
	"The number of  Tx excess rate violations in number of frames."
    ::= { pktSwchFrIfEntry 12 }

pktSwchFrIfExcessRateViolRxFrames  OBJECT-TYPE
    SYNTAX Counter32
    MAX-ACCESS  read-only
    STATUS  current
    DESCRIPTION
	"The number of  Rx excess rate violations in number of frames."
    ::= { pktSwchFrIfEntry 13 }

pktSwchFrIfBuffersInTxPool OBJECT-TYPE
    SYNTAX   Integer32
    MAX-ACCESS   read-only
    STATUS   current
    DESCRIPTION
       "The number of buffers waiting for transmission."
   ::= { pktSwchFrIfEntry 14 }

pktSwchFrIfFreeBuffersInRxPool OBJECT-TYPE
    SYNTAX   Integer32
    MAX-ACCESS   read-only
    STATUS   current
    DESCRIPTION
       "The number of free buffers in the Rx pool."
   ::= { pktSwchFrIfEntry 15 }

pktSwchFrIfLmiTxFrames OBJECT-TYPE
    SYNTAX   Counter32
    MAX-ACCESS   read-only
    STATUS   current
    DESCRIPTION
       "The number of LMI Tx Frames."
   ::= { pktSwchFrIfEntry 16 }

pktSwchFrIfLmiRxFrames OBJECT-TYPE
    SYNTAX   Counter32
    MAX-ACCESS   read-only
    STATUS   current
    DESCRIPTION
       "The number of  LMI Rx Frames."
   ::= { pktSwchFrIfEntry 17 }

pktSwchFrIfAnsiTxFrames OBJECT-TYPE
    SYNTAX   Counter32
    MAX-ACCESS   read-only
    STATUS   current
    DESCRIPTION
       "The number of  ANSI Tx Frames."
   ::= { pktSwchFrIfEntry 18 }

pktSwchFrIfAnsiRxFrames OBJECT-TYPE
    SYNTAX   Counter32
    MAX-ACCESS   read-only
    STATUS   current
    DESCRIPTION
       "The number of  ANSI Rx Frames."
   ::= { pktSwchFrIfEntry 19 }

pktSwchFrIfCllmTxFrames OBJECT-TYPE
    SYNTAX   Counter32
    MAX-ACCESS   read-only
    STATUS   current
    DESCRIPTION
       "The number of  CLLM Tx Frames."
   ::= { pktSwchFrIfEntry 20 }

pktSwchFrIfCllmRxFrames OBJECT-TYPE
    SYNTAX   Counter32
    MAX-ACCESS   read-only
    STATUS   current
    DESCRIPTION
       "The number of  CLLM Rx Frames."
   ::= { pktSwchFrIfEntry 21 }

pktSwchFrIfTxCongestions OBJECT-TYPE
    SYNTAX   Counter32
    MAX-ACCESS   read-only
    STATUS   current
    DESCRIPTION
       "The number of  Tx congestions."
   ::= { pktSwchFrIfEntry 22 }

pktSwchFrIfRxCongestions OBJECT-TYPE
    SYNTAX   Counter32
    MAX-ACCESS   read-only
    STATUS   current
    DESCRIPTION
       "The number of  Rx congestions."
   ::= { pktSwchFrIfEntry 23 }

pktSwchFrIfTotDlciNumber  OBJECT-TYPE
    SYNTAX Integer32
    MAX-ACCESS  read-only
    STATUS  current
    DESCRIPTION
	"The total number of DLCIs defined."
    ::= { pktSwchFrIfEntry 24 }


pktSwchFrCircuitSTable  OBJECT-TYPE
    SYNTAX  SEQUENCE  OF PktSwchFrCircuitSEntry
    MAX-ACCESS  not-accessible
    STATUS  current
    DESCRIPTION
	"The Frame Relay Scratch Circuit Table includes configurable objects
                 provided by the PS  that are not included in RFC 1315."
    ::=  { pktSwchFr 5 }

pktSwchFrCircuitSEntry OBJECT-TYPE
    SYNTAX  PktSwchFrCircuitSEntry
    MAX-ACCESS  not-accessible
    STATUS  current
    DESCRIPTION
	"Defines the contents of each line in the RAD PS Frame Relay
	 Circuit Scratch Table."
    INDEX   { pktSwchFrCircuitIfIndexS,pktSwchFrCircuitIndexS }
    ::=  { pktSwchFrCircuitSTable 1  }

PktSwchFrCircuitSEntry ::= SEQUENCE {
    pktSwchFrCircuitIfIndexS
     Integer32,
    pktSwchFrCircuitIndexS
     Integer32,
    pktSwchFrCircuitDestProtS
     INTEGER,
    pktSwchFrCircuitDestIdS
     DisplayString,
    pktSwchFrCircuitBackIdS
     DisplayString,
    pktSwchFrCircuitTxCirIntervalS
     Integer32,
    pktSwchFrCircuitTxCommittedS
     Integer32,
    pktSwchFrCircuitTxExcessS
     Integer32,
    pktSwchFrCircuitRxCirIntervalS
     Integer32,
    pktSwchFrCircuitRxCommittedS
     Integer32,
    pktSwchFrCircuitRxExcessS
     Integer32,
    pktSwchFrCircuitFunnelIdS
     Integer32,
    pktSwchFrCircuitStatusS
     INTEGER,
    pktSwchFrCircuitExtendedDlciS
     Integer32,
    pktSwchFrCircuitTxPriorityS
     Integer32,
    pktSwchFrCircuitIsdnRoutIdS
     Integer32
     }

pktSwchFrCircuitIfIndexS OBJECT-TYPE
    SYNTAX   Integer32
    MAX-ACCESS   read-only
    STATUS   current
    DESCRIPTION
       "This is the ifIndex of the circuit, according to RFC 1573."
   ::= { pktSwchFrCircuitSEntry 1 }

pktSwchFrCircuitIndexS OBJECT-TYPE
    SYNTAX   Integer32
    MAX-ACCESS   read-only
    STATUS   current
    DESCRIPTION
       "This Index is the DLCI of the circuit."
   ::= { pktSwchFrCircuitSEntry 2 }

pktSwchFrCircuitDestProtS OBJECT-TYPE
    SYNTAX   INTEGER {
	x25(1),
	none(2),
	hdlc(3),
	async(4),
	multiPoint(5),
	rfc1490(6)}
    MAX-ACCESS   read-write
    STATUS   current
    DESCRIPTION
       "The protocol encapsulation, if any, on this DLCI.
        The MPE protocol is a proprietary RAD protocol that enables
        a generic HDLC device to have multiple connections over X.25
        or Frame Relay."
   ::= { pktSwchFrCircuitSEntry 3 }

pktSwchFrCircuitDestIdS OBJECT-TYPE
    SYNTAX  DisplayString
    MAX-ACCESS   read-write
    STATUS   current
    DESCRIPTION
       "If the DLCI destination protocol is none or async, this field
        has a value of an existing DLCI or async channel, respectively.
        Otherwise, a value of zero is used."
   ::= { pktSwchFrCircuitSEntry 4 }

  pktSwchFrCircuitBackIdS OBJECT-TYPE
    SYNTAX  DisplayString
    MAX-ACCESS   read-write
    STATUS   current
    DESCRIPTION
       "The backup DLCI which is used when the current DLCI goes inactive.
        The destination protocol and destination id are the same as in the
        current DLCI"
   ::= { pktSwchFrCircuitSEntry 5 }

pktSwchFrCircuitTxCirIntervalS OBJECT-TYPE
    SYNTAX   Integer32 (0..10)
    MAX-ACCESS   read-write
    STATUS   current
    DESCRIPTION
       "The Tx  CIR interval in 1/10 seconds."
   ::= { pktSwchFrCircuitSEntry 6 }

pktSwchFrCircuitTxCommittedS OBJECT-TYPE
    SYNTAX   Integer32 (0..65000)
    MAX-ACCESS   read-write
    STATUS   current
    DESCRIPTION
       "The Tx committed rate in bytes per interval."
   ::= { pktSwchFrCircuitSEntry 7 }

pktSwchFrCircuitTxExcessS OBJECT-TYPE
    SYNTAX   Integer32 (0..65000)
    MAX-ACCESS   read-write
    STATUS   current
    DESCRIPTION
       "The Tx excess in bytes per interval."
   ::= { pktSwchFrCircuitSEntry 8 }

pktSwchFrCircuitRxCirIntervalS OBJECT-TYPE
    SYNTAX   Integer32 (0..10)
    MAX-ACCESS   read-write
    STATUS   current
    DESCRIPTION
       "The Rx  CIR interval in 1/10 seconds."
   ::= { pktSwchFrCircuitSEntry 9 }

pktSwchFrCircuitRxCommittedS OBJECT-TYPE
    SYNTAX   Integer32 (0..65000)
    MAX-ACCESS   read-write
    STATUS   current
    DESCRIPTION
       "The Rx committed rate in bytes per interval."
   ::= { pktSwchFrCircuitSEntry 10 }

pktSwchFrCircuitRxExcessS OBJECT-TYPE
    SYNTAX   Integer32 (0..65000)
    MAX-ACCESS   read-write
    STATUS   current
    DESCRIPTION
       "The Rx excess in bytes per interval."
   ::= { pktSwchFrCircuitSEntry 11 }

pktSwchFrCircuitFunnelIdS OBJECT-TYPE
    SYNTAX   Integer32 (1..200)
    MAX-ACCESS   read-write
    STATUS   current
    DESCRIPTION
       "The funnel ID."
   ::= { pktSwchFrCircuitSEntry 12 }

pktSwchFrCircuitStatusS OBJECT-TYPE
 	SYNTAX INTEGER {
       valid(1),
       createRequest(2),
       underCreation(3),
       invalid(4)
     }
    MAX-ACCESS  read-write
    STATUS  current
    DESCRIPTION
    "The status of the circuit row in the Table."
	::= { pktSwchFrCircuitSEntry 13 }

pktSwchFrCircuitExtendedDlciS OBJECT-TYPE
    SYNTAX   Integer32 (0..8388607)
    MAX-ACCESS   read-only
    STATUS   current
    DESCRIPTION
       "The no. of the DLCI represented in 23 bits."
   ::= { pktSwchFrCircuitSEntry 14 }

pktSwchFrCircuitTxPriorityS OBJECT-TYPE
    SYNTAX   Integer32 (1..4)
    MAX-ACCESS   read-write
    STATUS   current
    DESCRIPTION
       "DLCI TX Priority level. The levels are defined in the
        pktSwchTxPriorityTable"
    ::= { pktSwchFrCircuitSEntry 15 }

pktSwchFrCircuitIsdnRoutIdS OBJECT-TYPE
    SYNTAX   Integer32 (0..200)
    MAX-ACCESS   read-write
    STATUS   current
    DESCRIPTION
       "ISDN destination. ID in the ISDN routing table containing
        the outgoing ISDN address for this DLCI.

        Default value: 0 for no ISDN routing ID. "
    ::= { pktSwchFrCircuitSEntry 16 }


pktSwchFrCircuitATable  OBJECT-TYPE
    SYNTAX  SEQUENCE  OF PktSwchFrCircuitAEntry
    MAX-ACCESS  not-accessible
    STATUS  current
    DESCRIPTION
	"The Frame Relay Active Circuit Table includes statistics and configurable objects
                 provided by the PS  that are not included in RFC 1315."
    ::=  { pktSwchFr 6 }

pktSwchFrCircuitAEntry OBJECT-TYPE
    SYNTAX  PktSwchFrCircuitAEntry
    MAX-ACCESS  not-accessible
    STATUS  current
    DESCRIPTION
	"Defines the contents of each line in the RAD PS Frame Relay Circuit Active Table."
    INDEX   { pktSwchFrCircuitIfIndexA,pktSwchFrCircuitIndexA }
    ::=  { pktSwchFrCircuitATable 1  }

PktSwchFrCircuitAEntry ::= SEQUENCE {
    pktSwchFrCircuitIfIndexA
     Integer32,
	pktSwchFrCircuitIndexA
     Integer32,
    pktSwchFrCircuitDestProtA
     INTEGER,
    pktSwchFrCircuitDestIdA
     DisplayString,
	pktSwchFrCircuitBackIdA
     DisplayString,
    pktSwchFrCircuitTxCirIntervalA
     Integer32,
    pktSwchFrCircuitTxCommittedA
     Integer32,
    pktSwchFrCircuitTxExcessA
     Integer32,
    pktSwchFrCircuitRxCirIntervalA
     Integer32,
    pktSwchFrCircuitRxCommittedA
     Integer32,
    pktSwchFrCircuitRxExcessA
     Integer32,
    pktSwchFrCircuitFunnelIdA
     Integer32,
    pktSwchFrCircuitFunnelStat
     DisplayString,
    pktSwchFrCircuitTxCongDiscards
     Counter32,
    pktSwchFrCircuitDeTxFrames
     Counter32,
    pktSwchFrCircuitDeRxFrames
     Counter32,
    pktSwchFrCircuitFecnTxFrames
     Counter32,
    pktSwchFrCircuitBecnTxFrames
     Counter32,
    pktSwchFrCircuitCommRateViolTxFrames
     Counter32,
    pktSwchFrCircuitCommRateViolRxFrames
     Counter32,
    pktSwchFrCircuitExcessRateViolTxFrames
     Counter32,
    pktSwchFrCircuitExcessRateViolRxFrames
     Counter32,
    pktSwchFrCircuitState
     INTEGER,
    pktSwchFrCircuitExtendedDlciA
     Integer32,
    pktSwchFrCircuitTxPriorityA
     Integer32,
    pktSwchFrCircuitIsdnRoutIdA
     Integer32
     }

pktSwchFrCircuitIfIndexA OBJECT-TYPE
    SYNTAX   Integer32
    MAX-ACCESS   read-only
    STATUS   current
    DESCRIPTION
       "This is the ifIndex of the circuit, according to RFC 1573."
   ::= { pktSwchFrCircuitAEntry 1 }

pktSwchFrCircuitIndexA OBJECT-TYPE
    SYNTAX   Integer32
    MAX-ACCESS   read-only
    STATUS   current
    DESCRIPTION
       "This Index is the DLCI of the circuit."
   ::= { pktSwchFrCircuitAEntry 2 }

pktSwchFrCircuitDestProtA OBJECT-TYPE
    SYNTAX   INTEGER {
	x25(1),
	none(2),
	hdlc(3),
	async(4),
	multiPoint(5),
	rfc1490(6)}
    MAX-ACCESS   read-only
    STATUS   current
    DESCRIPTION
       "The protocol encapsulation, if any, on this DLCI.
        The MPE protocol is a proprietary RAD protocol that enables
        a generic HDLC device to have multiple connections over X.25
        or Frame Relay."
   ::= { pktSwchFrCircuitAEntry 3 }

pktSwchFrCircuitDestIdA OBJECT-TYPE
    SYNTAX  DisplayString
    MAX-ACCESS   read-only
    STATUS   current
    DESCRIPTION
       "If the DLCI destination protocol is none or async, this field
        has a value of an existing DLCI or async channel, respectively.
        Otherwise, a value of zero is used."
   ::= { pktSwchFrCircuitAEntry 4 }

pktSwchFrCircuitBackIdA OBJECT-TYPE
    SYNTAX  DisplayString
    MAX-ACCESS   read-only
    STATUS   current
    DESCRIPTION
	"The backup DLCI which is used when the current DLCI goes inactive.
        The destination protocol and destination id are the same as in the
        current DLCI"
    ::= { pktSwchFrCircuitAEntry 5 }

pktSwchFrCircuitTxCirIntervalA OBJECT-TYPE
    SYNTAX   Integer32 (0..10)
    MAX-ACCESS   read-only
    STATUS   current
    DESCRIPTION
       "The Tx  CIR interval in 1/10 seconds."
   ::= { pktSwchFrCircuitAEntry 6 }

pktSwchFrCircuitTxCommittedA OBJECT-TYPE
    SYNTAX   Integer32 (0..65000)
    MAX-ACCESS   read-only
    STATUS   current
    DESCRIPTION
       "The Tx committed rate in bytes per interval."
   ::= { pktSwchFrCircuitAEntry 7 }

pktSwchFrCircuitTxExcessA OBJECT-TYPE
    SYNTAX   Integer32 (0..65000)
    MAX-ACCESS   read-only
    STATUS   current
    DESCRIPTION
       "The Tx excess in bytes per interval."
   ::= { pktSwchFrCircuitAEntry 8 }

pktSwchFrCircuitRxCirIntervalA OBJECT-TYPE
    SYNTAX   Integer32 (0..10)
    MAX-ACCESS   read-only
    STATUS   current
    DESCRIPTION
       "The Rx  CIR interval in 1/10 seconds."
   ::= { pktSwchFrCircuitAEntry 9 }

pktSwchFrCircuitRxCommittedA OBJECT-TYPE
    SYNTAX   Integer32 (0..65000)
    MAX-ACCESS   read-only
    STATUS   current
    DESCRIPTION
       "The Rx committed rate in bytes per interval."
   ::= { pktSwchFrCircuitAEntry 10 }

pktSwchFrCircuitRxExcessA OBJECT-TYPE
    SYNTAX   Integer32 (0..65000)
    MAX-ACCESS   read-only
    STATUS   current
    DESCRIPTION
       "The Rx excess in bytes per interval."
   ::= { pktSwchFrCircuitAEntry 11 }

pktSwchFrCircuitFunnelIdA OBJECT-TYPE
    SYNTAX   Integer32 (1..200)
    MAX-ACCESS   read-only
    STATUS   current
    DESCRIPTION
       "The funnel ID."
   ::= { pktSwchFrCircuitAEntry 12 }

pktSwchFrCircuitFunnelStat OBJECT-TYPE
    SYNTAX  DisplayString
    MAX-ACCESS   read-only
    STATUS   current
    DESCRIPTION
       "The funnel status."
   ::= { pktSwchFrCircuitAEntry 13 }

pktSwchFrCircuitTxCongDiscards  OBJECT-TYPE
    SYNTAX Counter32
    MAX-ACCESS  read-only
    STATUS  current
    DESCRIPTION
	"The number of frames discarded because of Tx congestion."
    ::= { pktSwchFrCircuitAEntry 14 }

pktSwchFrCircuitDeTxFrames  OBJECT-TYPE
    SYNTAX Counter32
    MAX-ACCESS  read-only
    STATUS  current
    DESCRIPTION
	"The number of DE Tx frames."
    ::= { pktSwchFrCircuitAEntry 15 }

pktSwchFrCircuitDeRxFrames  OBJECT-TYPE
    SYNTAX Counter32
    MAX-ACCESS  read-only
    STATUS  current
    DESCRIPTION
	"The number of DE Rx frames."
    ::= { pktSwchFrCircuitAEntry 16 }

pktSwchFrCircuitFecnTxFrames  OBJECT-TYPE
    SYNTAX Counter32
    MAX-ACCESS  read-only
    STATUS  current
    DESCRIPTION
	"The number of FECN Tx frames."
    ::= { pktSwchFrCircuitAEntry 17 }

pktSwchFrCircuitBecnTxFrames  OBJECT-TYPE
    SYNTAX Counter32
    MAX-ACCESS  read-only
    STATUS  current
    DESCRIPTION
	"The number of BECN Tx frames."
    ::= { pktSwchFrCircuitAEntry 18 }

pktSwchFrCircuitCommRateViolTxFrames  OBJECT-TYPE
    SYNTAX Counter32
    MAX-ACCESS  read-only
    STATUS  current
    DESCRIPTION
	"The number of  Tx committed rate violations in number of frames."
    ::= { pktSwchFrCircuitAEntry 19 }

pktSwchFrCircuitCommRateViolRxFrames  OBJECT-TYPE
    SYNTAX Counter32
    MAX-ACCESS  read-only
    STATUS  current
    DESCRIPTION
	"The number of  Rx committed rate violations in number of frames."
    ::= { pktSwchFrCircuitAEntry 20 }

pktSwchFrCircuitExcessRateViolTxFrames  OBJECT-TYPE
    SYNTAX Counter32
    MAX-ACCESS  read-only
    STATUS  current
    DESCRIPTION
	"The number of  Tx excess rate violations in number of frames."
    ::= { pktSwchFrCircuitAEntry 21 }

pktSwchFrCircuitExcessRateViolRxFrames  OBJECT-TYPE
    SYNTAX Counter32
    MAX-ACCESS  read-only
    STATUS  current
    DESCRIPTION
	"The number of  Rx excess rate violations in number of frames."
    ::= { pktSwchFrCircuitAEntry 22 }

pktSwchFrCircuitState OBJECT-TYPE
             SYNTAX   INTEGER {
                         new (1),
                         noState (2)
                      }
             MAX-ACCESS   read-only
             STATUS   current
             DESCRIPTION
                "Indicates whether the particular virtual  cir-
                cuit  is new or not."
            ::= { pktSwchFrCircuitAEntry 23 }

pktSwchFrCircuitExtendedDlciA OBJECT-TYPE
    SYNTAX   Integer32 (0..8388607)
    MAX-ACCESS   read-only
    STATUS   current
    DESCRIPTION
       "The no. of the DLCI represented in 23 bits."
   ::= { pktSwchFrCircuitAEntry 24 }

pktSwchFrCircuitTxPriorityA OBJECT-TYPE
    SYNTAX   Integer32 (1..4)
    MAX-ACCESS   read-only
    STATUS   current
    DESCRIPTION
       "DLCI TX Priority level. The levels are defined in the
        pktSwchTxPriorityTable"
    ::= { pktSwchFrCircuitAEntry 25 }

pktSwchFrCircuitIsdnRoutIdA OBJECT-TYPE
    SYNTAX   Integer32 (0..200)
    MAX-ACCESS   read-only
    STATUS   current
    DESCRIPTION
       "ISDN destination. ID in the ISDN routing table containing
        the outgoing ISDN address for this DLCI.

        Default value: 0 for no ISDN routing ID. "
    ::= { pktSwchFrCircuitAEntry 26 }


pktSwchFrFunnelSTable  OBJECT-TYPE
    SYNTAX  SEQUENCE  OF PktSwchFrFunnelSEntry
    MAX-ACCESS  not-accessible
    STATUS  current
    DESCRIPTION
	"The Frame Relay Funnel Table defines the funnels that DLCIs may use."
    ::=  { pktSwchFr 7 }

pktSwchFrFunnelSEntry OBJECT-TYPE
    SYNTAX  PktSwchFrFunnelSEntry
    MAX-ACCESS  not-accessible
    STATUS  current
    DESCRIPTION
	"Defines the contents of each line in the RAD PS Frame Relay Funnel Table."
    INDEX   { pktSwchFrFunnelIndexS }
    ::=  { pktSwchFrFunnelSTable 1  }

PktSwchFrFunnelSEntry ::= SEQUENCE {
    pktSwchFrFunnelIndexS
     Integer32,
    pktSwchFrFunnelSizeS
     Integer32,
    pktSwchFrFunnelHighWaterFramesS
     Integer32,
    pktSwchFrFunnelHighWaterBytesS
     Integer32,
    pktSwchFrFunnelGaugeTxRateS
     Integer32,
    pktSwchFrFunnelTransWindowS
     Integer32,
    pktSwchFrFunnelStatusS
     INTEGER
    }

pktSwchFrFunnelIndexS OBJECT-TYPE
    SYNTAX   Integer32
    MAX-ACCESS   read-only
    STATUS   current
    DESCRIPTION
       "This is the index of the funnel table."
   ::= { pktSwchFrFunnelSEntry 1 }

pktSwchFrFunnelSizeS OBJECT-TYPE
    SYNTAX   Integer32 (0..256)
    MAX-ACCESS   read-write
    STATUS   current
    DESCRIPTION
       "The number of frames the funnel can store internally, where each
        frame is 512 bytes."
   ::= { pktSwchFrFunnelSEntry 2 }

pktSwchFrFunnelHighWaterFramesS OBJECT-TYPE
    SYNTAX  Integer32 (0..256)
    MAX-ACCESS   read-write
    STATUS   current
    DESCRIPTION
       "The maximum number of frames the funnel can hold before it
        expands and transmits all the data."
   ::= { pktSwchFrFunnelSEntry 3 }

pktSwchFrFunnelHighWaterBytesS OBJECT-TYPE
    SYNTAX   Integer32 (0..65000)
    MAX-ACCESS   read-write
    STATUS   current
    DESCRIPTION
       "The maximum number of bytes the funnel can hold before it expands
        and transmits all the data."
   ::= { pktSwchFrFunnelSEntry 4 }

pktSwchFrFunnelGaugeTxRateS OBJECT-TYPE
    SYNTAX   Integer32 (0..65000)
    MAX-ACCESS   read-write
    STATUS   current
    DESCRIPTION
       "The outgoing data rate in bytes per window of the funnel."
   ::= { pktSwchFrFunnelSEntry 5 }

pktSwchFrFunnelTransWindowS OBJECT-TYPE
    SYNTAX   Integer32 (0..10)
    MAX-ACCESS   read-write
    STATUS   current
    DESCRIPTION
       "The transmission rate is measured during a sliding time window.
        This parameter defines the window in 1/10 seconds."
   ::= { pktSwchFrFunnelSEntry 6 }

pktSwchFrFunnelStatusS OBJECT-TYPE
    SYNTAX  INTEGER {
      valid(1),
      createRequest(2),
      underCreation(3),
      invalid(4)
    }
    MAX-ACCESS  read-write
    STATUS  current
    DESCRIPTION
	"The status of this funnel table entry.  The choices are those defined in the SNMPv2 Textual
                 Conventions for RowStatus.  This will allow easy replacement of the INTEGER syntax with
                 the RowStatus textual convention SYNTAX."
  ::= { pktSwchFrFunnelSEntry 7 }



pktSwchFrFunnelATable  OBJECT-TYPE
    SYNTAX  SEQUENCE  OF PktSwchFrFunnelAEntry
    MAX-ACCESS  not-accessible
    STATUS  current
    DESCRIPTION
	"The Frame Relay Funnel Table defines the funnels that DLCIs may use."
    ::=  { pktSwchFr 8 }

pktSwchFrFunnelAEntry OBJECT-TYPE
    SYNTAX  PktSwchFrFunnelAEntry
    MAX-ACCESS  not-accessible
    STATUS  current
    DESCRIPTION
	"Defines the contents of each line in the RAD PS Frame Relay Funnel Table."
    INDEX   { pktSwchFrFunnelIndexA }
    ::=  { pktSwchFrFunnelATable 1  }

PktSwchFrFunnelAEntry ::= SEQUENCE {
    pktSwchFrFunnelIndexA
     Integer32,
    pktSwchFrFunnelSizeA
     Integer32,
    pktSwchFrFunnelHighWaterFramesA
     Integer32,
    pktSwchFrFunnelHighWaterBytesA
     Integer32,
    pktSwchFrFunnelGaugeTxRateA
     Integer32,
    pktSwchFrFunnelTransWindowA
     Integer32
    }

pktSwchFrFunnelIndexA OBJECT-TYPE
    SYNTAX   Integer32
    MAX-ACCESS   read-only
    STATUS   current
    DESCRIPTION
       "This is the index of the funnel table."
   ::= { pktSwchFrFunnelAEntry 1 }

pktSwchFrFunnelSizeA OBJECT-TYPE
    SYNTAX   Integer32 (0..256)
    MAX-ACCESS   read-only
    STATUS   current
    DESCRIPTION
       "The number of frames the funnel can store internally, where each frame is 512 bytes."
   ::= { pktSwchFrFunnelAEntry 2 }

pktSwchFrFunnelHighWaterFramesA OBJECT-TYPE
    SYNTAX  Integer32 (0..256)
    MAX-ACCESS   read-only
    STATUS   current
    DESCRIPTION
       "The maximum number of frames the funnel can hold before it expands and transmits all the data."
   ::= { pktSwchFrFunnelAEntry 3 }

pktSwchFrFunnelHighWaterBytesA OBJECT-TYPE
    SYNTAX   Integer32 (0..65000)
    MAX-ACCESS   read-only
    STATUS   current
    DESCRIPTION
       "The maximum number of bytes the funnel can hold before it expands and transmits all the data."
   ::= { pktSwchFrFunnelAEntry 4 }

pktSwchFrFunnelGaugeTxRateA OBJECT-TYPE
    SYNTAX   Integer32 (0..65000)
    MAX-ACCESS   read-only
    STATUS   current
    DESCRIPTION
       "The outgoing data rate in bytes per window of the funnel."
   ::= { pktSwchFrFunnelAEntry 5 }

pktSwchFrFunnelTransWindowA OBJECT-TYPE
    SYNTAX   Integer32 (0..10)
    MAX-ACCESS   read-only
    STATUS   current
    DESCRIPTION
       "The transmission rate is measured during a sliding time window.  This parameter defines the
         window in 1/10 seconds."
   ::= { pktSwchFrFunnelAEntry 6 }

pktSwchFrDlciMapTable  OBJECT-TYPE
    SYNTAX  SEQUENCE  OF PktSwchFrDlciMapEntry
    MAX-ACCESS  not-accessible
    STATUS  current
    DESCRIPTION
        "The Frame Relay Dlci mapping Table maps the Dlci numbers.
         For each long Dlci a short one is mapped.
         A long Dlci is a Dlci which contains a Dlci header of 3 or
         4 bytes instead of the regular 2 bytes.
         The long Dlci number has values from 1024 to 8,388,607."
    ::=  { pktSwchFr 9 }

pktSwchFrDlciMapEntry OBJECT-TYPE
    SYNTAX  PktSwchFrDlciMapEntry
    MAX-ACCESS  not-accessible
    STATUS  current
    DESCRIPTION
        "Defines the contents of each Dlci Map Table entry."
    INDEX   { pktSwchFrDlciMapPort, pktSwchFrDlciMapLongDlci }
    ::=  { pktSwchFrDlciMapTable 1  }

PktSwchFrDlciMapEntry ::= SEQUENCE {
    pktSwchFrDlciMapPort
     Integer32,
    pktSwchFrDlciMapLongDlci
     Integer32,
    pktSwchFrDlciMapShortDlci
     Integer32,
    pktSwchFrDlciMapStatus
     INTEGER
    }

pktSwchFrDlciMapPort OBJECT-TYPE
    SYNTAX   Integer32
    MAX-ACCESS   read-only
    STATUS   current
    DESCRIPTION
       "Frame Relay port no. : 1-8 for FPS-8, 1-4 for FPS-4,
        1-3 for APS, 1-6 for SPS-6, 1-12 for SPS-12."
   ::= { pktSwchFrDlciMapEntry 1 }


pktSwchFrDlciMapLongDlci OBJECT-TYPE
    SYNTAX   Integer32 (0..8388607)
    MAX-ACCESS   read-only
    STATUS   current
    DESCRIPTION
       "The Long Dlci number.
        For Dlci's of 4 octets, the long Dlci number has values
        from 1024 to 8,388,607.
        For Dlci's of 2 octets, the long Dlci number has values
        of 16-991."
   ::= { pktSwchFrDlciMapEntry 2 }


pktSwchFrDlciMapShortDlci OBJECT-TYPE
    SYNTAX   Integer32 (0..1023)
    MAX-ACCESS   read-only
    STATUS   current
    DESCRIPTION
       "The Short Dlci number. Legal values: 0 - 1023."
   ::= { pktSwchFrDlciMapEntry 3 }

pktSwchFrDlciMapStatus OBJECT-TYPE
 	SYNTAX INTEGER {
       valid(1),
       createRequest(2),
       underCreation(3),
       invalid(4)
     }
    MAX-ACCESS  read-write
    STATUS  current
    DESCRIPTION
    "The status of the map row in the Table.
     The only value which can be set is: createRequest.
     This value is set when a new long dlci is created."
   ::= { pktSwchFrDlciMapEntry 4 }


pktSwchMpe  OBJECT IDENTIFIER ::= { radPS 9 }

pktSwchMpeSTable  OBJECT-TYPE
    SYNTAX  SEQUENCE  OF PktSwchMpeSEntry
    MAX-ACCESS  not-accessible
    STATUS  current
    DESCRIPTION
	"The MPE Table defines Scratch configuration parameters for the MPE protocol."
    ::=  { pktSwchMpe 1 }

pktSwchMpeSEntry OBJECT-TYPE
    SYNTAX  PktSwchMpeSEntry
    MAX-ACCESS  not-accessible
    STATUS  current
    DESCRIPTION
	"Defines the contents of each line in the MPE Table."
    INDEX   { pktSwchMpeLinkNumberS }
    ::=  { pktSwchMpeSTable 1  }

PktSwchMpeSEntry ::= SEQUENCE {
    pktSwchMpeLinkNumberS
     Integer32,
    pktSwchMpeInactivityS
     Integer32,
    pktSwchMpeX25FacilitiesS
     Integer32,
    pktSwchMpeLocSubAddr1S
     Integer32,
    pktSwchMpeLocSubAddr2S
     Integer32,
    pktSwchMpeFlwCtrlDurS
     Integer32,
	pktSwchMpeFlwCtrlOptS
     Integer32,
	pktSwchMpeFlwCtrlBufS
     Integer32,
	pktSwchMpeInternalClkS
	 INTEGER
    }

pktSwchMpeLinkNumberS OBJECT-TYPE
    SYNTAX   Integer32
    MAX-ACCESS   read-only
    STATUS   current
    DESCRIPTION
       "The link number with which this entry is associated.  This value
        corresponds to pktSwchPhyInterfaceNumber.  There is an entry for
        each link for which the pktSwchPhyInterfaceProtocol is MPE."
   ::= { pktSwchMpeSEntry 1 }

pktSwchMpeInactivityS OBJECT-TYPE
    SYNTAX   Integer32 (0..255)
    MAX-ACCESS   read-write
    STATUS   current
    DESCRIPTION
       "The amount of time in minutes of inactivity that will cause the
	    session to disconnect."
   ::= { pktSwchMpeSEntry 2 }

pktSwchMpeX25FacilitiesS OBJECT-TYPE
    SYNTAX   Integer32 (0..7)
    MAX-ACCESS   read-write
    STATUS   current
    DESCRIPTION
       "This specifies the X.25 facilities.  The value is a sum of values
        (powers of two), where each value in the sum represents an option.
         The values that may be included in the sum and their meanings are:
		0 No options
		1 Packet size negotiation
		2 Window size negotiation
		4 Reverse  charge."
   ::= { pktSwchMpeSEntry 3 }

pktSwchMpeLocSubAddr1S OBJECT-TYPE
    SYNTAX   Integer32 (1..99)
    MAX-ACCESS   read-write
    STATUS   current
    DESCRIPTION
       "The first local subaddress."
   ::= { pktSwchMpeSEntry 4 }

pktSwchMpeLocSubAddr2S OBJECT-TYPE
    SYNTAX   Integer32 (1..99)
    MAX-ACCESS   read-write
    STATUS   current
    DESCRIPTION
       "The second local subaddress."
   ::= { pktSwchMpeSEntry 5 }

pktSwchMpeFlwCtrlDurS OBJECT-TYPE
    SYNTAX   Integer32 (0..200)
    MAX-ACCESS   read-write
    STATUS   current
    DESCRIPTION
       "The duration in 50 milliseconds of a hardware flow control signal. Default is 0"
   ::= { pktSwchMpeSEntry 6 }

pktSwchMpeFlwCtrlOptS OBJECT-TYPE
    SYNTAX   Integer32 (0..3)
    MAX-ACCESS   read-write
    STATUS   current
    DESCRIPTION
       "This specifies the type of flow control of the MPE link.  The value
        is a sum of values (powers of two), where each value in the sum
        represents an option.  The values that may be included in the sum
        and their meanings are:
		0 No flow control
		1 CTS flow control
		2 Clock flow control."
   ::= { pktSwchMpeSEntry 7 }

pktSwchMpeFlwCtrlBufS OBJECT-TYPE
    SYNTAX   Integer32 (0..200)
    MAX-ACCESS   read-write
    STATUS   current
    DESCRIPTION
       "The number of buffers that will be allocated for the MPE link."
   ::= { pktSwchMpeSEntry 8 }

pktSwchMpeInternalClkS  OBJECT-TYPE
    SYNTAX INTEGER {
       r2400bps (1),
       r4800bps (2),
       r9600bps (3),
       r14400bps(4),
       r19200bps(5),
       r38400bps(6),
	   r48Kbps  (7),
       r56Kbps  (8),
       r64Kbps  (9),
       r128Kbps (10),
       r256Kbps (11),
	   r384Kbps (12),
       r504Kbps (13),
	   r768Kbps (14),
	   r1008Kbps(15),
       r1466Kbps(16),
       r2016Kbps(17),
       external(255)
      }
    MAX-ACCESS  read-write
    STATUS  current
    DESCRIPTION
	"The baud rate of the internal clock."
    ::= { pktSwchMpeSEntry 9 }


pktSwchMpeATable  OBJECT-TYPE
    SYNTAX  SEQUENCE  OF PktSwchMpeAEntry
    MAX-ACCESS  not-accessible
    STATUS  current
    DESCRIPTION
	"The MPE Table defines Active configuration parameters for the MPE protocol."
    ::=  { pktSwchMpe 2 }

pktSwchMpeAEntry OBJECT-TYPE
    SYNTAX  PktSwchMpeAEntry
    MAX-ACCESS  not-accessible
    STATUS  current
    DESCRIPTION
	"Defines the contents of each line in the MPE Table."
    INDEX   { pktSwchMpeLinkNumberA }
    ::=  { pktSwchMpeATable 1  }

PktSwchMpeAEntry ::= SEQUENCE {
    pktSwchMpeLinkNumberA
     Integer32,
    pktSwchMpeInactivityA
     Integer32,
    pktSwchMpeX25FacilitiesA
     Integer32,
    pktSwchMpeLocSubAddr1A
     Integer32,
    pktSwchMpeLocSubAddr2A
     Integer32,
    pktSwchMpeFlwCtrlDurA
     Integer32,
	pktSwchMpeFlwCtrlOptA
     Integer32,
	pktSwchMpeFlwCtrlBufA
     Integer32,
	pktSwchMpeInternalClkA
	 INTEGER,
	pktSwchMpeCtsStatus
	 INTEGER
    }

pktSwchMpeLinkNumberA OBJECT-TYPE
    SYNTAX   Integer32
    MAX-ACCESS   read-only
    STATUS   current
    DESCRIPTION
       "The link number with which this entry is associated.  This value
        corresponds to pktSwchPhyInterfaceNumber.  There is an entry for
        each link for which the pktSwchPhyInterfaceProtocol is MPE."
   ::= { pktSwchMpeAEntry 1 }

pktSwchMpeInactivityA OBJECT-TYPE
    SYNTAX   Integer32 (0..255)
    MAX-ACCESS   read-only
    STATUS   current
    DESCRIPTION
       "The amount of time in minutes of inactivity that will cause the
	    session to disconnect."
   ::= { pktSwchMpeAEntry 2 }

pktSwchMpeX25FacilitiesA OBJECT-TYPE
    SYNTAX   Integer32 (0..7)
    MAX-ACCESS   read-only
    STATUS   current
    DESCRIPTION
       "This specifies the X.25 facilities.  The value is a sum of values
        (powers of two), where each value in the sum represents an option.
         The values that may be included in the sum and their meanings are:
		0 No options
		1 Packet size negotiation
		2 Window size negotiation
		4 Reverse  charge."
   ::= { pktSwchMpeAEntry 3 }

pktSwchMpeLocSubAddr1A OBJECT-TYPE
    SYNTAX   Integer32 (1..99)
    MAX-ACCESS   read-only
    STATUS   current
    DESCRIPTION
       "The first local subaddress."
   ::= { pktSwchMpeAEntry 4 }

pktSwchMpeLocSubAddr2A OBJECT-TYPE
    SYNTAX   Integer32 (1..99)
    MAX-ACCESS   read-only
    STATUS   current
    DESCRIPTION
       "The second local subaddress."
   ::= { pktSwchMpeAEntry 5 }

pktSwchMpeFlwCtrlDurA OBJECT-TYPE
    SYNTAX   Integer32 (0..200)
    MAX-ACCESS   read-only
    STATUS   current
    DESCRIPTION
       "The duration in 50 milliseconds of a hardware flow control signal."
   ::= { pktSwchMpeAEntry 6 }

pktSwchMpeFlwCtrlOptA OBJECT-TYPE
    SYNTAX   Integer32 (0..3)
    MAX-ACCESS   read-only
    STATUS   current
    DESCRIPTION
       "This specifies the type of flow control of the MPE link.  The value
        is a sum of values (powers of two), where each value in the sum
        represents an option.  The values that may be included in the sum
        and their meanings are:
		0 No flow control
		1 CTS flow control
		2 Clock flow control."
   ::= { pktSwchMpeAEntry 7 }

pktSwchMpeFlwCtrlBufA OBJECT-TYPE
    SYNTAX   Integer32 (0..200)
    MAX-ACCESS   read-only
    STATUS   current
    DESCRIPTION
       "The number of buffers that will be allocated for the MPE link."
   ::= { pktSwchMpeAEntry 8 }

pktSwchMpeInternalClkA  OBJECT-TYPE
    SYNTAX INTEGER {
       r2400bps (1),
       r4800bps (2),
       r9600bps (3),
       r14400bps(4),
       r19200bps(5),
       r38400bps(6),
	   r48Kbps  (7),
       r56Kbps  (8),
       r64Kbps  (9),
       r128Kbps (10),
       r256Kbps (11),
	   r384Kbps (12),
       r504Kbps (13),
	   r768Kbps (14),
	   r1008Kbps(15),
       r1466Kbps(16),
       r2016Kbps(17),
       external(255)
      }
    MAX-ACCESS  read-only
    STATUS  current
    DESCRIPTION
	"The baud rate of the internal clock."
    ::= { pktSwchMpeAEntry 9 }

pktSwchMpeCtsStatus  OBJECT-TYPE
    SYNTAX INTEGER {
                    off(2),
                    on(3)
                   }
    MAX-ACCESS  read-only
    STATUS  current
    DESCRIPTION
	"The CTS status."
    ::= { pktSwchMpeAEntry 10 }


pktSwchMpeAidSTable  OBJECT-TYPE
    SYNTAX  SEQUENCE  OF PktSwchMpeAidSEntry
    MAX-ACCESS  not-accessible
    STATUS  current
    DESCRIPTION
	"The AID Table defines Scratch configuration parameters for the
	 logical connections (Address Id)."
    ::=  { pktSwchMpe 3 }

pktSwchMpeAidSEntry OBJECT-TYPE
    SYNTAX  PktSwchMpeAidSEntry
    MAX-ACCESS  not-accessible
    STATUS  current
    DESCRIPTION
	"Defines the contents of each line in the MPE Table."
    INDEX   { ifIndex, pktSwchMpeAddressIdS }
    ::=  { pktSwchMpeAidSTable 1  }

PktSwchMpeAidSEntry ::= SEQUENCE {
    pktSwchMpeAddressIdS
     Integer32,
    pktSwchMpeAidMainTypeS
     INTEGER,
    pktSwchMpeAidMainIdS
     Integer32,
    pktSwchMpeAidMainSubIdS
     Integer32,
    pktSwchMpeAidBackupTypeS
     INTEGER,
    pktSwchMpeAidBackupIdS
     Integer32,
	pktSwchMpeAidBackupSubIdS
     Integer32,
	pktSwchMpeAidStatusS
	 INTEGER
    }

pktSwchMpeAddressIdS OBJECT-TYPE
    SYNTAX   Integer32
    MAX-ACCESS   read-only
    STATUS   current
    DESCRIPTION
       "The Address Id (AID) with which this entry is associated."
   ::= { pktSwchMpeAidSEntry 1 }

pktSwchMpeAidMainTypeS OBJECT-TYPE
    SYNTAX   INTEGER {
	                  x25Svc(1),
					  x25Pvc(2),
					  fr(3),
					  innerCom(4),
					  notActive(255)
					 }
    MAX-ACCESS   read-write
    STATUS   current
    DESCRIPTION
       "The protocol with which the AID is communicating."
   ::= { pktSwchMpeAidSEntry 2 }

pktSwchMpeAidMainIdS OBJECT-TYPE
    SYNTAX   Integer32 (0..200)
    MAX-ACCESS   read-write
    STATUS   current
    DESCRIPTION
       "The link number of the protocol with which the AID is communicating.
    The link number of the protocol with which the AID is communicating.

    For X.25 SVC this number is Any Autocall ID (Pre-defined) ,
    values: 1..200

    For X.25 PVC this number is a local PVC that its source link has
    already been set to the current link with a prefix of N.
    values: 1..200

    For FR this number is any Frame Relay link number (Pre-defined),
    values: 1..12

    For Inner communication this number is an HDLC or MPE link number
    (Pre-defined), values: 1..12

    For notActive this number is 0."
   ::= { pktSwchMpeAidSEntry 3 }

pktSwchMpeAidMainSubIdS OBJECT-TYPE
    SYNTAX   Integer32 (0..991)
    MAX-ACCESS   read-write
    STATUS   current
    DESCRIPTION
       "The DLCI with which the AID is communicating.
    Sub ID is used only when Type is Frame Relay or Inner Comm.
    The DLCI or destination AID with which the current AID is communicating.

    If type is: Frame Relay PVC:
    Sub ID must be an existing DLCI, 16-991.
    (The DLCI's destination protocol has to be predefined to MPE).

    If type is: Inner Communication:
    In case of an HDLC link, Sub ID must be 0.
    In case of an MPE link, Sub ID must be in AID permitted range.

    For notActive this number is 0."
   ::= { pktSwchMpeAidSEntry 4 }

pktSwchMpeAidBackupTypeS OBJECT-TYPE
    SYNTAX   INTEGER {
	                  x25Svc(1),
					  x25Pvc(2),
					  fr(3),
					  innerCom(4),
	                  notActive(255)
					 }
    MAX-ACCESS   read-write
    STATUS   current
    DESCRIPTION
       "The protocol with which the AID is communicating on the backup."
   ::= { pktSwchMpeAidSEntry 5 }

pktSwchMpeAidBackupIdS OBJECT-TYPE
    SYNTAX   Integer32 (0..200)
    MAX-ACCESS   read-write
    STATUS   current
    DESCRIPTION
       "The link number of the protocol with which the AID is communicating
        on the backup.
    The link number of the protocol with which the AID is communicating.

    For X.25 SVC this number is Any Autocall ID (Pre-defined) ,
    values: 1..200

    For X.25 PVC this number is a local PVC that its source link has
    already been set to the current link with a prefix of N.
    values: 1..200

    For FR this number is any Frame Relay link number (Pre-defined),
    values: 1..12

    For Inner communication this number is an HDLC or MPE link number
    (Pre-defined), values: 1..12

    For notActive this number is 0."
   ::= { pktSwchMpeAidSEntry 6 }

pktSwchMpeAidBackupSubIdS OBJECT-TYPE
    SYNTAX   Integer32 (0..991)
    MAX-ACCESS   read-write
    STATUS   current
    DESCRIPTION
       "The DLCI with which the AID is communicating.
    Sub ID is used only when Type is Frame Relay or Inner Comm.
    The DLCI or destination AID with which the current AID is communicating.

    If type is: Frame Relay PVC:
    Sub ID must be an existing DLCI, 16-991.
    (The DLCI's destination protocol has to be predefined to MPE).

    If type is: Inner Communication:
    In case of an HDLC link, Sub ID must be 0.
    In case of an MPE link, Sub ID must be in AID permitted range.

    For notActive this number is 0."
   ::= { pktSwchMpeAidSEntry 7 }

pktSwchMpeAidStatusS OBJECT-TYPE
    SYNTAX  INTEGER {
       valid(1),
       createRequest(2),
       underCreation(3),
       invalid(4)
     }
    MAX-ACCESS  read-write
    STATUS  current
    DESCRIPTION
	"The status of this Address Id table entry."
  ::= { pktSwchMpeAidSEntry 8 }


pktSwchMpeAidATable  OBJECT-TYPE
    SYNTAX  SEQUENCE  OF PktSwchMpeAidAEntry
    MAX-ACCESS  not-accessible
    STATUS  current
    DESCRIPTION
	"The AID Table defines Active configuration parameters for the
	 logical connections (Address Id)."
    ::=  { pktSwchMpe 4 }

pktSwchMpeAidAEntry OBJECT-TYPE
    SYNTAX  PktSwchMpeAidAEntry
    MAX-ACCESS  not-accessible
    STATUS  current
    DESCRIPTION
	"Defines the contents of each line in the MPE Table."
    INDEX   { ifIndex, pktSwchMpeAddressIdA }
    ::=  { pktSwchMpeAidATable 1  }

PktSwchMpeAidAEntry ::= SEQUENCE {
    pktSwchMpeAddressIdA
     Integer32,
    pktSwchMpeAidMainTypeA
     INTEGER,
    pktSwchMpeAidMainIdA
     Integer32,
    pktSwchMpeAidMainSubIdA
     Integer32,
    pktSwchMpeAidBackupTypeA
     INTEGER,
    pktSwchMpeAidBackupIdA
     Integer32,
	pktSwchMpeAidBackupSubIdA
     Integer32,
	pktSwchMpeAidConn
	 INTEGER,
	pktSwchMpeAidFlwCtrl
	 INTEGER
    }

pktSwchMpeAddressIdA OBJECT-TYPE
    SYNTAX   Integer32
    MAX-ACCESS   read-only
    STATUS   current
    DESCRIPTION
       "The Address Id (AID) with which this entry is associated."
   ::= { pktSwchMpeAidAEntry 1 }

pktSwchMpeAidMainTypeA OBJECT-TYPE
    SYNTAX   INTEGER {
	                  x25Svc(1),
					  x25Pvc(2),
					  fr(3),
					  innerCom(4),
	                  notActive(255)
					 }
    MAX-ACCESS   read-only
    STATUS   current
    DESCRIPTION
       "The protocol with which the AID is communicating."
   ::= { pktSwchMpeAidAEntry 2 }

pktSwchMpeAidMainIdA OBJECT-TYPE
    SYNTAX   Integer32 (0..200)
    MAX-ACCESS   read-only
    STATUS   current
    DESCRIPTION
       "The link number of the protocol with which the AID is communicating.
    The link number of the protocol with which the AID is communicating.

    For X.25 SVC this number is Any Autocall ID (Pre-defined) ,
    values: 1..200

    For X.25 PVC this number is a local PVC that its source link has
    already been set to the current link with a prefix of N.
    values: 1..200

    For FR this number is any Frame Relay link number (Pre-defined),
    values: 1..12

    For Inner communication this number is an HDLC or MPE link number
    (Pre-defined), values: 1..12

    For notActive this number is 0."
   ::= { pktSwchMpeAidAEntry 3 }

pktSwchMpeAidMainSubIdA OBJECT-TYPE
    SYNTAX   Integer32 (0..991)
    MAX-ACCESS   read-only
    STATUS   current
    DESCRIPTION
       "The DLCI with which the AID is communicating.
    Sub ID is used only when Type is Frame Relay or Inner Comm.
    The DLCI or destination AID with which the current AID is communicating.

    If type is: Frame Relay PVC:
    Sub ID must be an existing DLCI, 16-991.
    (The DLCI's destination protocol has to be predefined to MPE).

    If type is: Inner Communication:
    In case of an HDLC link, Sub ID must be 0.
    In case of an MPE link, Sub ID must be in AID permitted range.

    For notActive this number is 0."
   ::= { pktSwchMpeAidAEntry 4 }

pktSwchMpeAidBackupTypeA OBJECT-TYPE
    SYNTAX   INTEGER {
	                  x25Svc(1),
					  x25Pvc(2),
					  fr(3),
					  innerCom(4),
	                  notActive(255)
					 }
    MAX-ACCESS   read-only
    STATUS   current
    DESCRIPTION
       "The protocol with which the AID is communicating on the backup."
   ::= { pktSwchMpeAidAEntry 5 }

pktSwchMpeAidBackupIdA OBJECT-TYPE
    SYNTAX   Integer32 (0..200)
    MAX-ACCESS   read-only
    STATUS   current
    DESCRIPTION
       "The link number of the protocol with which the AID is communicating
        on the backup.
    The link number of the protocol with which the AID is communicating.

    For X.25 SVC this number is Any Autocall ID (Pre-defined) ,
    values: 1..200

    For X.25 PVC this number is a local PVC that its source link has
    already been set to the current link with a prefix of N.
    values: 1..200

    For FR this number is any Frame Relay link number (Pre-defined),
    values: 1..12

    For Inner communication this number is an HDLC or MPE link number
    (Pre-defined), values: 1..12

    For notActive this number is 0."
   ::= { pktSwchMpeAidAEntry 6 }

pktSwchMpeAidBackupSubIdA OBJECT-TYPE
    SYNTAX   Integer32 (0..991)
    MAX-ACCESS   read-only
    STATUS   current
    DESCRIPTION
       "The DLCI with which the AID is communicating.
    Sub ID is used only when Type is Frame Relay or Inner Comm.
    The DLCI or destination AID with which the current AID is communicating.

    If type is: Frame Relay PVC:
    Sub ID must be an existing DLCI, 16-991.
    (The DLCI's destination protocol has to be predefined to MPE).

    If type is: Inner Communication:
    In case of an HDLC link, Sub ID must be 0.
    In case of an MPE link, Sub ID must be in AID permitted range.

    For notActive this number is 0."
   ::= { pktSwchMpeAidAEntry 7 }

pktSwchMpeAidConn OBJECT-TYPE
    SYNTAX   INTEGER {
                    disconnect(1),
					connect(2),
					pvc(3)
					}
    MAX-ACCESS   read-only
    STATUS   current
    DESCRIPTION
       "The connectivity status of the AID."
   ::= { pktSwchMpeAidAEntry 8 }

pktSwchMpeAidFlwCtrl OBJECT-TYPE
    SYNTAX   INTEGER {
	                  inactive(1),
	                  active(2)
					 }
    MAX-ACCESS   read-only
    STATUS   current
    DESCRIPTION
       "The Flow Control status of the AID."
   ::= { pktSwchMpeAidAEntry 9 }


-- The PS Slip Group contains  Slip Scratch and Active Tables,
-- which contain configuration for Slip links

pktSwchSlip  OBJECT IDENTIFIER ::= { radPS 10 }

pktSwchSlipSTable  OBJECT-TYPE
    SYNTAX  SEQUENCE  OF PktSwchSlipSEntry
    MAX-ACCESS  not-accessible
    STATUS  current
    DESCRIPTION
    "The Scratch Slip Table contains configuration information for
     Slip links"
    ::=  { pktSwchSlip 1 }

pktSwchSlipSEntry OBJECT-TYPE
    SYNTAX  PktSwchSlipSEntry
    MAX-ACCESS  not-accessible
    STATUS  current
    DESCRIPTION
    "Defines the contents of each line in the RAD Slip Table."
    INDEX   { pktSwchSlipLinkNumberS }
    ::=  { pktSwchSlipSTable 1  }

PktSwchSlipSEntry ::= SEQUENCE {
    pktSwchSlipLinkNumberS
     Integer32,
    pktSwchSlipSpeedS
     INTEGER,
    pktSwchSlipFCOptionS
     Integer32,
    pktSwchSlipStopBitsS
     INTEGER,
    pktSwchSlipBitPerCharS
     Integer32,
    pktSwchSlipParityS
     INTEGER,
    pktSwchSlipIpAddressS
     IpAddress,
    pktSwchSlipIpMaskS
     IpAddress,
    pktSwchSlipDefEncapsTypeS
     INTEGER,
    pktSwchSlipDefDestinationS
     DisplayString
    }

pktSwchSlipLinkNumberS  OBJECT-TYPE
    SYNTAX Integer32
    MAX-ACCESS  read-only
    STATUS  current
    DESCRIPTION
    "The link number with which this entry is associated.  This value
     corresponds to pktSwchPhyInterfaceIfIndex.  There is an entry for
     each link for which the pktSwchPhyInterfaceProtocol is Slip."
    ::= { pktSwchSlipSEntry 1 }

pktSwchSlipSpeedS OBJECT-TYPE
    SYNTAX  INTEGER  {
       s110bps    (1),
       s300bps    (2),
       s1200bps   (3),
       s600bps    (4),
       s75bps     (5),
       s150bps    (6),

       s2400bps  (12),
       s4800bps  (13),
       s9600bps  (14),
       s19200bps (15),

       s38400bps (19),
       s57600bps (20),
       s115200bps(21)
    }
    MAX-ACCESS  read-write
    STATUS  current
    DESCRIPTION
    "This parameter determines the rate of data transmission to
     and from the DTE."
    ::= { pktSwchSlipSEntry 2 }

pktSwchSlipFCOptionS OBJECT-TYPE
    SYNTAX Integer32 (0..255)
    MAX-ACCESS  read-write
    STATUS  current
    DESCRIPTION  " The flow control options
              0 - No HARDWARE flow control
         1..254 - Timer value (in 50ms intervals),
                  when timer expires, flow control stops
            255 - The timer is not used"
    ::= { pktSwchSlipSEntry 3 }

pktSwchSlipStopBitsS OBJECT-TYPE
    SYNTAX  INTEGER  {
       one       (1),
       two       (2),
       oneAndHalf(3)
    }
    MAX-ACCESS  read-write
    STATUS  current
    DESCRIPTION
    "This entry indicates the number of stop bits per character
     supported by the PAD.
     The options are either (1) one stop bit, (2) two stop bits,
     or (3) 1.5 stop bits."
    ::= { pktSwchSlipSEntry 4 }

pktSwchSlipBitPerCharS  OBJECT-TYPE
    SYNTAX Integer32 (5..8)
    MAX-ACCESS  read-write
    STATUS  current
    DESCRIPTION
    "The number of data bits per character supported by the Slip
     link."
    ::= { pktSwchSlipSEntry 5 }

pktSwchSlipParityS  OBJECT-TYPE
    SYNTAX  INTEGER  {
       space(1),
       mark(2),
       even(3),
       odd(4),
       none(255)
    }
    MAX-ACCESS  read-write
    STATUS  current
    DESCRIPTION
    "This entry selects the type of parity to be checked and or
     generated by the PAD when radSPSProfileParTreat is a value
     other than 255.
     The options are (1) space parity, (2) mark parity,
     (3) even parity, (4) odd parity, or (255) no parity."
    ::= { pktSwchSlipSEntry 6 }

pktSwchSlipIpAddressS  OBJECT-TYPE
    SYNTAX IpAddress
    MAX-ACCESS  read-write
    STATUS  deprecated
    DESCRIPTION
        "The IP address connected to this Slip port. This variable is
         used when an automatic connection is done by the IP Routing."
    ::= { pktSwchSlipSEntry 7 }

pktSwchSlipIpMaskS  OBJECT-TYPE
    SYNTAX 	IpAddress
    MAX-ACCESS  read-write
    STATUS  deprecated
    DESCRIPTION
        "The IP mask. This variable is
         used when an automatic connection by the IP Routing is done."
    ::= { pktSwchSlipSEntry 8 }

pktSwchSlipDefEncapsTypeS  OBJECT-TYPE
    SYNTAX  INTEGER {
             slip       (1),
             x25SVC     (2),
             x25PVC     (3),
             frameRelay (4),
             hdlc       (5),
             none      (255)
    }
    MAX-ACCESS  read-write
    STATUS  deprecated
    DESCRIPTION
        "Destination protocol of this Slip port. This variable is used
         when a direct connection without IP Routing is done."
    ::= { pktSwchSlipSEntry 9 }

pktSwchSlipDefDestinationS  OBJECT-TYPE
    SYNTAX DisplayString
    MAX-ACCESS  read-write
    STATUS  deprecated
    DESCRIPTION
    "Default destination for this Slip port.
    This variable is used when a direct connection without
    IP Routing is done.
    Possible values:
    Default :     Not Used.
    X.25 PVC:     Port:LCN  or a pre defined PVC number
    X.25 SVC:     X.25 Addr or cid followed by a predefined Call ID number
    Frame Relay:  Port:DLCI
    HDLC:         HDLC Port Number
    SLIP:         SLIP Channel Number"
    ::= { pktSwchSlipSEntry 10 }


--  The active slip table
--

pktSwchSlipATable  OBJECT-TYPE
    SYNTAX  SEQUENCE  OF PktSwchSlipAEntry
    MAX-ACCESS  not-accessible
    STATUS  current
    DESCRIPTION
    "The Active Slip Table contains configuration information for
     Slip links"
    ::=  { pktSwchSlip 2 }


pktSwchSlipAEntry OBJECT-TYPE
    SYNTAX  PktSwchSlipAEntry
    MAX-ACCESS  not-accessible
    STATUS  current
    DESCRIPTION
    "Defines the contents of each line in the RAD Slip Table."
    INDEX   { pktSwchSlipLinkNumberA }
    ::=  { pktSwchSlipATable 1  }

PktSwchSlipAEntry ::= SEQUENCE {
    pktSwchSlipLinkNumberA
     Integer32,
    pktSwchSlipSpeedA
     INTEGER,
    pktSwchSlipFCOptionA
     Integer32,
    pktSwchSlipStopBitsA
     INTEGER,
    pktSwchSlipBitPerCharA
     Integer32,
    pktSwchSlipParityA
     INTEGER,
    pktSwchSlipIpAddressA
     IpAddress,
    pktSwchSlipIpMaskA
     IpAddress,
    pktSwchSlipDefEncapsTypeA
     INTEGER,
    pktSwchSlipDefDestinationA
     DisplayString
    }

pktSwchSlipLinkNumberA  OBJECT-TYPE
    SYNTAX Integer32
    MAX-ACCESS  read-only
    STATUS  current
    DESCRIPTION
    "The link number with which this entry is associated.  This value
     corresponds to pktSwchPhyInterfaceIfIndex.  There is an entry for
     each link for which the pktSwchPhyInterfaceProtocol is Slip."
    ::= { pktSwchSlipAEntry 1 }


pktSwchSlipSpeedA OBJECT-TYPE
    SYNTAX  INTEGER  {
       s110bps    (1),
       s300bps    (2),
       s1200bps   (3),
       s600bps    (4),
       s75bps     (5),
       s150bps    (6),

       s2400bps  (12),
       s4800bps  (13),
       s9600bps  (14),
       s19200bps (15),

       s38400bps (19),
       s57600bps (20),
       s115200bps(21)
    }
    MAX-ACCESS  read-only
    STATUS  current
    DESCRIPTION
    "This parameter determines the rate of data transmission to
     and from the DTE."
    ::= { pktSwchSlipAEntry 2 }

pktSwchSlipFCOptionA OBJECT-TYPE
    SYNTAX Integer32 (0..255)
    MAX-ACCESS  read-only
    STATUS  current
    DESCRIPTION
    " The flow control options
              0 - No HARDWARE flow control
         1..254 - Timer value (in 50ms intervals),
                  when timer expires, flow control stops
            255 - The timer is not used"
    ::= { pktSwchSlipAEntry 3 }

 pktSwchSlipStopBitsA OBJECT-TYPE
    SYNTAX  INTEGER  {
       one       (1),
       two       (2),
       oneAndHalf(3)
    }
    MAX-ACCESS  read-only
    STATUS  current
    DESCRIPTION
    "This entry indicates the number of stop bits per character
     supported by the PAD.
     The options are either (1) one stop bit, (2) two stop bits,
     or (3) 1.5 stop bits."
    ::= { pktSwchSlipAEntry 4 }

pktSwchSlipBitPerCharA  OBJECT-TYPE
    SYNTAX Integer32 (5..8)
    MAX-ACCESS  read-only
    STATUS  current
    DESCRIPTION
    "The number of data bits per character supported by the Slip
     link."
    ::= { pktSwchSlipAEntry 5 }

pktSwchSlipParityA  OBJECT-TYPE
    SYNTAX  INTEGER  {
       space(1),
       mark(2),
       even(3),
       odd(4),
       none(255)
    }
    MAX-ACCESS  read-only
    STATUS  current
    DESCRIPTION
    "This entry selects the type of parity to be checked and or
     generated by the PAD when radSPSProfileParTreat is a value
     other than 255.
     The options are (1) space parity, (2) mark parity,
     (3) even parity, (4) odd parity, or (255) no parity."
    ::= { pktSwchSlipAEntry 6 }

pktSwchSlipIpAddressA  OBJECT-TYPE
    SYNTAX IpAddress
    MAX-ACCESS  read-only
    STATUS  deprecated
    DESCRIPTION
        "The IP address connected to this Slip port."
    ::= { pktSwchSlipAEntry 7 }

pktSwchSlipIpMaskA  OBJECT-TYPE
    SYNTAX  IpAddress
    MAX-ACCESS  read-only
    STATUS  deprecated
    DESCRIPTION
        "The IP mask."
    ::= { pktSwchSlipAEntry 8 }

pktSwchSlipDefEncapsTypeA  OBJECT-TYPE
    SYNTAX  INTEGER {
             slip       (1),
             x25SVC     (2),
             x25PVC     (3),
             frameRelay (4),
             hdlc       (5),
             none      (255)
    }
    MAX-ACCESS  read-only
    STATUS  deprecated
    DESCRIPTION
        "Destination protocol of this Slip port."
    ::= { pktSwchSlipAEntry 9 }

pktSwchSlipDefDestinationA  OBJECT-TYPE
    SYNTAX DisplayString
    MAX-ACCESS  read-only
    STATUS  deprecated
    DESCRIPTION
    "Default destination for this Slip port.
    This variable is used when a direct connection without
    IP Routing is done.
    Possible values:
    Default :     Not Used.
    X.25 PVC:     Port:LCN  or a pre defined PVC number
    X.25 SVC:     X.25 Addr or cid followed by a predefined Call ID number
    Frame Relay:  Port:DLCI
    HDLC:         HDLC Port Number
    SLIP:         SLIP Channel Number"
    ::= { pktSwchSlipAEntry 10 }



pktSwchSna    OBJECT IDENTIFIER ::= { radPS 11}

pktSwchSnaSDLCLinkTableS    OBJECT-TYPE
    SYNTAX  SEQUENCE  OF PktSwchSnaSDLCLinkEntryS
    MAX-ACCESS  not-accessible
    STATUS  current
    DESCRIPTION
	"The SDLC Link Table defines the SDLC links configured on the PS."
     ::=  { pktSwchSna 1 }

pktSwchSnaSDLCLinkEntryS OBJECT-TYPE
    SYNTAX  PktSwchSnaSDLCLinkEntryS
    MAX-ACCESS  not-accessible
    STATUS  current
    DESCRIPTION
	"SDLC Link Entry defines the contents of each link in the SDLC Link Table."
    INDEX   {ifIndex }
    ::=  { pktSwchSnaSDLCLinkTableS 1 }

PktSwchSnaSDLCLinkEntryS ::= SEQUENCE {
pktSwchSnaSDLCLinkTypeS
INTEGER,
pktSwchSnaSDLCLinkPUSharedS
INTEGER,
pktSwchSnaSDLCLinkDuplexPhyS
INTEGER,
pktSwchSnaSDLCLinkflagsS
Integer32,
pktSwchSnaSDLCLinkDuplexS
INTEGER,
pktSwchSnaSDLCLinkClockS
INTEGER,
pktSwchSnaSDLCLinkNRZS
INTEGER
     }

pktSwchSnaSDLCLinkTypeS  OBJECT-TYPE
    SYNTAX INTEGER{
	primary(1),
	secondary(2)
	       }
    MAX-ACCESS  read-write
    STATUS  current
    DESCRIPTION
	"This parameter identifies whether this link operates as
         TPAD(Primary) or HPAD(Secondary) SDLC device."
    ::= { pktSwchSnaSDLCLinkEntryS 1 }

pktSwchSnaSDLCLinkPUSharedS  OBJECT-TYPE
    SYNTAX INTEGER {
       yes(1),
       no (2)
	       }
    MAX-ACCESS  read-write
    STATUS  current
    DESCRIPTION
	"This parameter defines whether the link participates with more than
	 one PU or not."
    ::= { pktSwchSnaSDLCLinkEntryS 2 }

pktSwchSnaSDLCLinkDuplexPhyS OBJECT-TYPE
    SYNTAX INTEGER {
        half (1),
        full (2)
	 }
    MAX-ACCESS  read-write
    STATUS  current
    DESCRIPTION
        "This parameter describes whether the physical level of the
        SDLC line is half or full duplex."
    ::= { pktSwchSnaSDLCLinkEntryS 3 }

pktSwchSnaSDLCLinkflagsS OBJECT-TYPE
        SYNTAX Integer32 (1..15)
	MAX-ACCESS  read-write
	STATUS  current
    DESCRIPTION
        "Number of flags between frames."
  ::= { pktSwchSnaSDLCLinkEntryS 4 }

pktSwchSnaSDLCLinkDuplexS OBJECT-TYPE
	SYNTAX INTEGER {
        twoWayAlter (1),
        twoWaySimul (2)
	}
	MAX-ACCESS  read-write
	STATUS  current
    DESCRIPTION
        " This parameter shows wether the link level is Two Way Alternate
          or Two Way Simultaneous."
	::= { pktSwchSnaSDLCLinkEntryS 5 }

pktSwchSnaSDLCLinkClockS OBJECT-TYPE
    SYNTAX INTEGER {
	r2400bps(1),
	r4800bps(2),
	r9600Bps(3),
	r14400bps(4),
	r19200bps(5),
	r38400bps(6),
	r48000bps(7),
	r56000bps(8),
	r64000bps(9),
	r128000bps(10),
	r256000bps(11),
	r384000bps(12),
	r504000bps(13),
	r768000bps(14),
	r1008000bps(15),
	r1466000bps(16),
	r2016000bps(17),
	external(255)
	}
	MAX-ACCESS read-write
	STATUS current
	DESCRIPTION
	" This parameter defines the link clock rate "
	::= { pktSwchSnaSDLCLinkEntryS 6 }

pktSwchSnaSDLCLinkNRZS OBJECT-TYPE
SYNTAX INTEGER {
        nrzFlags(1),
        nrziFlags(2),
        nrzIdle(3),
        nrziIdle(4)
		}
MAX-ACCESS read-write
STATUS current
DESCRIPTION
        " This parameter describes the following combinations of NRZ,
          NRZI with FLAGS or IDLE between frames:
          Legal values:
           1 - NRZ  with FLAGs between frames. RTS is Constant
           2 - NRZI with FLAGs between frames. RTS is Constant.
           3 - NRZ  with IDLE between frames.  RTS is Controlled.
           4 - NRZI with IDLE between frames.  RTS is Controlled."
	::={ pktSwchSnaSDLCLinkEntryS 7}


pktSwchSnaSDLCLinkTableA    OBJECT-TYPE
    SYNTAX  SEQUENCE  OF PktSwchSnaSDLCLinkEntryA
    MAX-ACCESS  not-accessible
    STATUS  current
    DESCRIPTION
	"The SDLC Link Table defines the SDLC links configured on the SPS."
     ::=  { pktSwchSna 2 }

pktSwchSnaSDLCLinkEntryA OBJECT-TYPE
    SYNTAX  PktSwchSnaSDLCLinkEntryA
    MAX-ACCESS  not-accessible
    STATUS  current
    DESCRIPTION
	"SDLC Link Entry defines the contents of each link in the SDLC Link Table."
    INDEX   {ifIndex }
    ::=  { pktSwchSnaSDLCLinkTableA 1 }

PktSwchSnaSDLCLinkEntryA ::= SEQUENCE {
pktSwchSnaSDLCLinkTypeA
INTEGER,
pktSwchSnaSDLCLinkPUSharedA
INTEGER,
pktSwchSnaSDLCLinkDuplexPhyA
INTEGER,
pktSwchSnaSDLCLinkflagsA
Integer32,
pktSwchSnaSDLCLinkDuplexA
INTEGER,
pktSwchSnaSDLCLinkClockA
INTEGER,
pktSwchSnaSDLCLinkNRZA
INTEGER,
pktSwchSnaSDLCLinkStatFrames
Counter32,
pktSwchSnaSDLCLinkStatErrors
Counter32,
pktSwchSnaSDLCLinkStatInvalidAddresses
Counter32,
pktSwchSnaSDLCLinkStatShortFrames
Counter32
     }

pktSwchSnaSDLCLinkTypeA  OBJECT-TYPE
    SYNTAX INTEGER{
	primary(1),
	secondary(2)
	     }
    MAX-ACCESS  read-only
    STATUS  current
    DESCRIPTION
	"This parameter identifies whether this link operates as
         TPAD(Primary) or HPAD(Secondary) SDLC device."
    ::= { pktSwchSnaSDLCLinkEntryA 1 }

pktSwchSnaSDLCLinkPUSharedA  OBJECT-TYPE
    SYNTAX INTEGER {
       yes(1),
       no (2)
		 }
    MAX-ACCESS  read-only
    STATUS  current
    DESCRIPTION
	"This parameter defines whether the link participates with more
	 than one PU or not."
    ::= { pktSwchSnaSDLCLinkEntryA 2 }

pktSwchSnaSDLCLinkDuplexPhyA OBJECT-TYPE
    SYNTAX INTEGER {
        half (1),
        full (2)
	 }
    MAX-ACCESS  read-only
    STATUS  current
    DESCRIPTION
        "This parameter describes whether the physical level of the
        SDLC line is half or full duplex."
    ::= { pktSwchSnaSDLCLinkEntryA 3 }

pktSwchSnaSDLCLinkflagsA OBJECT-TYPE
        SYNTAX Integer32 (1..15)
	MAX-ACCESS  read-only
	STATUS  current
    DESCRIPTION
        "Number of flags between frames."
  ::= { pktSwchSnaSDLCLinkEntryA 4 }

pktSwchSnaSDLCLinkDuplexA OBJECT-TYPE
	SYNTAX INTEGER {
        twoWayAlter (1),
        twoWaySimul (2)
	}
	MAX-ACCESS  read-only
	STATUS  current
    DESCRIPTION
        " This parameter shows wether the link level is Two Way Alternate
          or Two Way Simultaneous."
	::= { pktSwchSnaSDLCLinkEntryA 5 }

pktSwchSnaSDLCLinkClockA OBJECT-TYPE
    SYNTAX INTEGER {
	r2400bps(1),
	r4800bps(2),
	r9600Bps(3),
	r14400bps(4),
	r19200bps(5),
	r38400bps(6),
	r48000bps(7),
	r56000bps(8),
	r64000bps(9),
	r128000bps(10),
	r256000bps(11),
	r384000bps(12),
	r504000bps(13),
	r768000bps(14),
	r1008000bps(15),
	r1466000bps(16),
	r2016000bps(17),
	external(255)
	}
	MAX-ACCESS read-only
	STATUS current
	DESCRIPTION
	" This parameter defines the link clock rate."
	::= { pktSwchSnaSDLCLinkEntryA 6 }

pktSwchSnaSDLCLinkNRZA OBJECT-TYPE
SYNTAX INTEGER {
        nrzFlags(1),
        nrziFlags(2),
        nrzIdle(3),
        nrziIdle(4)
		}
MAX-ACCESS read-only
STATUS current
DESCRIPTION
        " This parameter describes the following combinations of NRZ,
          NRZI with FLAGS or IDLE between frames:
          Legal values:
           1 - NRZ  with FLAGs between frames. RTS is Constant
           2 - NRZI with FLAGs between frames. RTS is Constant.
           3 - NRZ  with IDLE between frames.  RTS is Controlled.
           4 - NRZI with IDLE between frames.  RTS is Controlled."
	::={ pktSwchSnaSDLCLinkEntryA 7}

pktSwchSnaSDLCLinkStatFrames OBJECT-TYPE
    SYNTAX  Counter32
    MAX-ACCESS  read-only
    STATUS  current
    DESCRIPTION
    "The number of frames received or transmitted via this link "
	::= { pktSwchSnaSDLCLinkEntryA 8 }

pktSwchSnaSDLCLinkStatErrors OBJECT-TYPE
    SYNTAX  Counter32
    MAX-ACCESS  read-only
    STATUS  current
    DESCRIPTION
    "The number of error frames received. "
	::= { pktSwchSnaSDLCLinkEntryA 9}

pktSwchSnaSDLCLinkStatInvalidAddresses OBJECT-TYPE
    SYNTAX  Counter32
    MAX-ACCESS  read-only
    STATUS  current
    DESCRIPTION
    "The number of frames with wrong address received by this link. "
	::= { pktSwchSnaSDLCLinkEntryA 10}

pktSwchSnaSDLCLinkStatShortFrames OBJECT-TYPE
    SYNTAX  Counter32
    MAX-ACCESS  read-only
    STATUS  current
    DESCRIPTION
    "The number of short  frames received by this link. "
	::= { pktSwchSnaSDLCLinkEntryA 11}


pktSwchSnaPUTableS    OBJECT-TYPE
    SYNTAX  SEQUENCE  OF PktSwchSnaPUEntryS
    MAX-ACCESS  not-accessible
    STATUS  current
    DESCRIPTION
	"The SDLC PU table defines the PUs configured on the PS."
     ::=  { pktSwchSna 3 }

pktSwchSnaPUEntryS OBJECT-TYPE
    SYNTAX  PktSwchSnaPUEntryS
    MAX-ACCESS  not-accessible
    STATUS  current
    DESCRIPTION
	"SDLC PU Entry defines the contents of each PU in the
	 SDLC PU Table."
    INDEX   {pktSwchSnaPUNumberS}
    ::=  { pktSwchSnaPUTableS 1 }

PktSwchSnaPUEntryS ::= SEQUENCE {
pktSwchSnaPUNumberS
Integer32,
pktSwchSnaPUXIDProcessingS
INTEGER,
pktSwchSnaPUEnableS
INTEGER,
pktSwchSnaPULinkATypeS
INTEGER,
pktSwchSnaPULinkARoleS
INTEGER,
pktSwchSnaPULinkBTypeS
INTEGER,
pktSwchSnaPULinkBRoleS
INTEGER,
pktSwchSnaPUEntryStatusS
INTEGER
}
pktSwchSnaPUNumberS OBJECT-TYPE
    SYNTAX  Integer32
    MAX-ACCESS  read-only
    STATUS  current
    DESCRIPTION
    "This parameter defines an identifier associated with the PU Entry
     which is unique within the SPS"
	::= { pktSwchSnaPUEntryS 1}

pktSwchSnaPUXIDProcessingS OBJECT-TYPE
    SYNTAX  INTEGER {
	localXid(1),
	end2EndSupNoAct(2),
	end2EndNoSupNoAct(3)
		}
    MAX-ACCESS  read-write
    STATUS  current
    DESCRIPTION
   "Exchange Identification (XID) processing. The following values are legal:
    1 - Local XID handling
    2 - End-to-End XID handling, Support for NON-Activation XID
    3 - End-to-End XID handling, NO Support for NON-Activation XID"
	::= { pktSwchSnaPUEntryS 2}

pktSwchSnaPUEnableS OBJECT-TYPE
    SYNTAX INTEGER {
	 enable(1),
	 disable(2)
		   }
    MAX-ACCESS  read-write
    STATUS  current
    DESCRIPTION
    "The PU runs or not at this specific time"
	::= { pktSwchSnaPUEntryS 3}


pktSwchSnaPULinkATypeS OBJECT-TYPE
    SYNTAX  INTEGER {
	sdlc(1),
	x25Qllc(2),
	frameRelayLLC2(3)
			}
    MAX-ACCESS  read-write
    STATUS  current
    DESCRIPTION
    "The PU link A type."
	::= { pktSwchSnaPUEntryS 4}

pktSwchSnaPULinkARoleS OBJECT-TYPE
    SYNTAX  INTEGER {
	primary(1),
	secondary(2)
	}
    MAX-ACCESS  read-write
    STATUS  current
    DESCRIPTION
    "The PU role for link A. Note that the role of an SDLC PU may
     not be changed. It is defined by the SDLC Link Type."
	::= { pktSwchSnaPUEntryS 5}

pktSwchSnaPULinkBTypeS OBJECT-TYPE
    SYNTAX  INTEGER {
	sdlc(1),
	x25Qllc(2),
	frameRelayLLC2(3)
			}
    MAX-ACCESS  read-write
    STATUS  current
    DESCRIPTION
    "The PU partner link B type"
	::= { pktSwchSnaPUEntryS 6}

pktSwchSnaPULinkBRoleS OBJECT-TYPE
    SYNTAX  INTEGER {
	primary(1),
	secondary(2)
	}
    MAX-ACCESS  read-write
    STATUS  current
    DESCRIPTION
    "The PU role for link B. Note that the role of an SDLC PU may
     not be changed. It is defined by the SDLC Link Type."
	::= { pktSwchSnaPUEntryS 7}

pktSwchSnaPUEntryStatusS OBJECT-TYPE
    SYNTAX  INTEGER {
       valid(1),
       createRequest(2),
       underCreation(3),
       invalid(4)
     }
    MAX-ACCESS  read-write
    STATUS  current
    DESCRIPTION
    "The status of this PU table entry.
     This Set request will fail if there are any conflicts between any of
     of the parameter values in any of the tables comprising this PU
     definition "
         ::= {pktSwchSnaPUEntryS 8}

pktSwchSnaPUTableA    OBJECT-TYPE
    SYNTAX  SEQUENCE  OF PktSwchSnaPUEntryA
    MAX-ACCESS  not-accessible
    STATUS  current
    DESCRIPTION
	"The SDLC PU table defines the PUs configured on the PS."
     ::=  { pktSwchSna 4 }

pktSwchSnaPUEntryA OBJECT-TYPE
    SYNTAX  PktSwchSnaPUEntryA
    MAX-ACCESS  not-accessible
    STATUS  current
    DESCRIPTION
	"SDLC PU Entry defines the contents of each PU in the
	 SDLC PU Table."
    INDEX   {pktSwchSnaPUNumberA}
    ::=  { pktSwchSnaPUTableA 1 }

PktSwchSnaPUEntryA ::= SEQUENCE {
pktSwchSnaPUNumberA
Integer32,
pktSwchSnaPUXIDProcessingA
INTEGER,
pktSwchSnaPUEnableA
INTEGER,
pktSwchSnaPULinkATypeA
INTEGER,
pktSwchSnaPULinkARoleA
INTEGER,
pktSwchSnaPULinkBTypeA
INTEGER,
pktSwchSnaPULinkBRoleA
INTEGER
}
pktSwchSnaPUNumberA OBJECT-TYPE
    SYNTAX  Integer32
    MAX-ACCESS  read-only
    STATUS  current
    DESCRIPTION
    "This parameter defines an identifier associated with the PU Entry
     which is unique within the SPS"
	::= { pktSwchSnaPUEntryA 1}

pktSwchSnaPUXIDProcessingA OBJECT-TYPE
    SYNTAX  INTEGER {
	localXid(1),
	end2EndSupNoAct(2),
	end2EndNoSupNoAct(3)
		}
    MAX-ACCESS  read-only
    STATUS  current
    DESCRIPTION
    "The PU XID Processing"
	::= { pktSwchSnaPUEntryA 2}

pktSwchSnaPUEnableA OBJECT-TYPE
    SYNTAX INTEGER {
	 enable(1),
	 disable(2)
		   }
    MAX-ACCESS  read-only
    STATUS  current
    DESCRIPTION
    "The PU runs or not at this specific time"
	::= { pktSwchSnaPUEntryA 3}


pktSwchSnaPULinkATypeA OBJECT-TYPE
    SYNTAX  INTEGER {
	sdlc(1),
	x25Qllc(2),
	frameRelayLLC2(3)
	}
    MAX-ACCESS  read-only
    STATUS  current
    DESCRIPTION
    "The PU link type"
	::= { pktSwchSnaPUEntryA 4}

pktSwchSnaPULinkARoleA OBJECT-TYPE
    SYNTAX  INTEGER {
	primary(1),
	secondary(2)
	}
    MAX-ACCESS  read-only
    STATUS  current
    DESCRIPTION
    "The PU role for link A"
	::= { pktSwchSnaPUEntryA 5}

pktSwchSnaPULinkBTypeA OBJECT-TYPE
    SYNTAX  INTEGER {
	sdlc(1),
	x25Qllc(2),
	frameRelayLLC2(3)
			}
    MAX-ACCESS  read-only
    STATUS  current
    DESCRIPTION
    "The PU partner link type"
	::= { pktSwchSnaPUEntryA 6}

pktSwchSnaPULinkBRoleA OBJECT-TYPE
    SYNTAX  INTEGER {
	primary(1),
	secondary(2)
	}
    MAX-ACCESS  read-only
    STATUS  current
    DESCRIPTION
    "The PU role for link B"
	::= { pktSwchSnaPUEntryA 7}

pktSwchSnaPUSdlcTableS    OBJECT-TYPE
    SYNTAX  SEQUENCE  OF PktSwchSnaPUSdlcEntryS
    MAX-ACCESS  not-accessible
    STATUS  current
    DESCRIPTION
	"Defines links for PUs running on SDLC link "
     ::=  { pktSwchSna 5 }

pktSwchSnaPUSdlcEntryS OBJECT-TYPE
    SYNTAX  PktSwchSnaPUSdlcEntryS
    MAX-ACCESS  not-accessible
    STATUS  current
    DESCRIPTION
	"Defines parameters of a link for a PU running on an SDLC link "
    INDEX   {pktSwchSnaPUSdlcNumberS , pktSwchSnaPUSdlcSideS }
    ::=  { pktSwchSnaPUSdlcTableS 1 }

PktSwchSnaPUSdlcEntryS ::= SEQUENCE {
pktSwchSnaPUSdlcNumberS
Integer32,
pktSwchSnaPUSdlcSideS
INTEGER,
pktSwchSnaPUSdlcAddressS
OCTET STRING,
pktSwchSnaPUSdlcIfIndexS
Integer32,
pktSwchSnaPUSdlcIdBlkS
OCTET STRING,
pktSwchSnaPUSdlcIdNumS
OCTET STRING,
pktSwchSnaPUSdlcMaxPiuSizeS
Integer32,
pktSwchSnaPUSdlcTxWindowS
Integer32,
pktSwchSnaPUSdlcGrpAddressS
OCTET STRING,
pktSwchSnaPUSdlcPollTimerS
Integer32,
pktSwchSnaPUSdlcXIDInitiationS
INTEGER,
pktSwchSnaPUSdlcEntryStatusS
INTEGER
}

pktSwchSnaPUSdlcNumberS OBJECT-TYPE
    SYNTAX  Integer32
    MAX-ACCESS  read-only
    STATUS  current
    DESCRIPTION
    "This parameter defines an identifier associated with the PU Entry
     SDLC side, which is unique within the SPS"
	::= { pktSwchSnaPUSdlcEntryS 1}

pktSwchSnaPUSdlcSideS OBJECT-TYPE
    SYNTAX  INTEGER {
	    sideA(1),
	    sideB(2)
	    }
    MAX-ACCESS  read-only
    STATUS  current
    DESCRIPTION
    "Is this side A or side B of the PU definition "
	::= { pktSwchSnaPUSdlcEntryS 2}

pktSwchSnaPUSdlcAddressS OBJECT-TYPE
    SYNTAX  OCTET STRING (SIZE(1))
    MAX-ACCESS  read-write
    STATUS  current
    DESCRIPTION
    "SNA SDLC PU address. Range: 0x00-0xFE "
	::= { pktSwchSnaPUSdlcEntryS 3}

pktSwchSnaPUSdlcIfIndexS OBJECT-TYPE
    SYNTAX  Integer32
    MAX-ACCESS  read-write
    STATUS  current
    DESCRIPTION
    "ifIndex of the SDLC link"
	::= { pktSwchSnaPUSdlcEntryS 4}

pktSwchSnaPUSdlcIdBlkS OBJECT-TYPE
    SYNTAX  OCTET STRING (SIZE(1..2))
    MAX-ACCESS  read-write
    STATUS  current
    DESCRIPTION
"Part of the IBM device ID (the full ID is defined by the IDBLK and
 the IDNUM). The Idblk is required for secondary PU with Local XID
 handling.  Up to 3 Hexadecimal digits, format: 0X XX."
       ::= {pktSwchSnaPUSdlcEntryS 5}

pktSwchSnaPUSdlcIdNumS OBJECT-TYPE
    SYNTAX  OCTET STRING (SIZE(1..3))
    MAX-ACCESS  read-write
    STATUS  current
    DESCRIPTION
"Second part of the IBM device ID (the full ID is defined by the IDBLK and
 the IDNUM). The Idnum is required for secondary PU with Local XID
 handling.  Up to 5 Hexadecimal digits, format: 0X XX XX."
       ::= {pktSwchSnaPUSdlcEntryS 6}


pktSwchSnaPUSdlcMaxPiuSizeS OBJECT-TYPE
    SYNTAX Integer32 (137..7642)
    MAX-ACCESS  read-write
    STATUS  current
    DESCRIPTION
    "Maximum Path Information Size"
	::= { pktSwchSnaPUSdlcEntryS 7}


pktSwchSnaPUSdlcTxWindowS OBJECT-TYPE
    SYNTAX  Integer32
    MAX-ACCESS  read-write
    STATUS  current
    DESCRIPTION
    "Window Size(in frames) used when sending from the SPS. Range: 1-7."
	::= { pktSwchSnaPUSdlcEntryS 8}

pktSwchSnaPUSdlcGrpAddressS OBJECT-TYPE
    SYNTAX  OCTET STRING (SIZE(1))
    MAX-ACCESS  read-write
    STATUS  current
    DESCRIPTION
    "SNA Group address used by the SPS when sending polls (TPAD ONLY).
     Range: 0x00-0xFE"
	::= { pktSwchSnaPUSdlcEntryS 9}

pktSwchSnaPUSdlcPollTimerS OBJECT-TYPE
    SYNTAX  Integer32
    MAX-ACCESS  read-write
    STATUS  current
    DESCRIPTION
    "Time in between polls in 50 millisecond increments (TPAD ONLY).
     Range: 1-65535."
	::= { pktSwchSnaPUSdlcEntryS 10}

pktSwchSnaPUSdlcXIDInitiationS OBJECT-TYPE
    SYNTAX  INTEGER{
	notInitiate(1),
	initiate(2)
	}
    MAX-ACCESS  read-write
    STATUS  current
    DESCRIPTION
 "This parameter is not applicable for PU with Local XID handling.
 Legal values:
 1 - Do not initiate an XID message.
 2 - Initiate an XID message to SDLC."
	::= { pktSwchSnaPUSdlcEntryS 11}

pktSwchSnaPUSdlcEntryStatusS OBJECT-TYPE
    SYNTAX  INTEGER {
       valid(1),
       underCreation(3)
     }
    MAX-ACCESS  read-write
    STATUS  current
    DESCRIPTION
    "The status of this PU Sdlc table entry.
     In order to save this entry, set status to valid.
     An underCreation value is set by the Agent when this entry is updated."
         ::= {pktSwchSnaPUSdlcEntryS 12}


pktSwchSnaPUSdlcTableA    OBJECT-TYPE
    SYNTAX  SEQUENCE  OF PktSwchSnaPUSdlcEntryA
    MAX-ACCESS  not-accessible
    STATUS  current
    DESCRIPTION
	"Defines links for PUs running on an SDLC link "
     ::=  { pktSwchSna 6 }

pktSwchSnaPUSdlcEntryA OBJECT-TYPE
    SYNTAX  PktSwchSnaPUSdlcEntryA
    MAX-ACCESS  not-accessible
    STATUS  current
    DESCRIPTION
	"Defines parameters of link for PU running on an SDLC link "
    INDEX   {pktSwchSnaPUSdlcNumberA , pktSwchSnaPUSdlcSideA }
    ::=  { pktSwchSnaPUSdlcTableA 1 }

PktSwchSnaPUSdlcEntryA ::= SEQUENCE {
pktSwchSnaPUSdlcNumberA
Integer32,
pktSwchSnaPUSdlcSideA
INTEGER,
pktSwchSnaPUSdlcAddressA
OCTET STRING,
pktSwchSnaPUSdlcIfIndexA
Integer32,
pktSwchSnaPUSdlcIdBlkA
OCTET STRING,
pktSwchSnaPUSdlcIdNumA
OCTET STRING,
pktSwchSnaPUSdlcMaxPiuSizeA
Integer32,
pktSwchSnaPUSdlcTxWindowA
Integer32,
pktSwchSnaPUSdlcGrpAddressA
OCTET STRING,
pktSwchSnaPUSdlcPollTimerA
Integer32,
pktSwchSnaPUSdlcXIDInitiationA
INTEGER
}
pktSwchSnaPUSdlcNumberA OBJECT-TYPE
    SYNTAX  Integer32
    MAX-ACCESS  read-only
    STATUS  current
    DESCRIPTION
    "This parameter defines an identifier associated with the PU Entry
     SDLC side, which is unique within the SPS"
	::= { pktSwchSnaPUSdlcEntryA 1}

pktSwchSnaPUSdlcSideA OBJECT-TYPE
    SYNTAX  INTEGER {
	    sideA(1),
	    sideB(2)
	    }
    MAX-ACCESS  read-only
    STATUS  current
    DESCRIPTION
    "Is this side A or side B of the PU definition "
	::= { pktSwchSnaPUSdlcEntryA 2}

pktSwchSnaPUSdlcAddressA OBJECT-TYPE
    SYNTAX  OCTET STRING (SIZE(1))
    MAX-ACCESS  read-only
    STATUS  current
    DESCRIPTION
    "SNA SDLC PU address. Range: 0x00-0xFE."
	::= { pktSwchSnaPUSdlcEntryA 3}


pktSwchSnaPUSdlcIfIndexA OBJECT-TYPE
    SYNTAX  Integer32
    MAX-ACCESS  read-only
    STATUS  current
    DESCRIPTION
    "ifIndex of the SDLC link"
	::= { pktSwchSnaPUSdlcEntryA 4}

pktSwchSnaPUSdlcIdBlkA OBJECT-TYPE
    SYNTAX  OCTET STRING (SIZE(1..2))
    MAX-ACCESS  read-only
    STATUS  current
    DESCRIPTION
"Part of the IBM device ID (the full ID is defined by the IDBLK and
 the IDNUM). The Idblk is required for secondary PU with Local XID
 handling.  Up to 3 Hexadecimal digits, format: 0X XX."
       ::= {pktSwchSnaPUSdlcEntryA 5}

pktSwchSnaPUSdlcIdNumA OBJECT-TYPE
    SYNTAX  OCTET STRING (SIZE(1..3))
    MAX-ACCESS  read-only
    STATUS  current
    DESCRIPTION
"Second part of the IBM device ID (the full ID is defined by the IDBLK and
 the IDNUM). The Idnum is required for secondary PU with Local XID
 handling.  Up to 5 Hexadecimal digits, format: 0X XX XX."
       ::= {pktSwchSnaPUSdlcEntryA 6}


pktSwchSnaPUSdlcMaxPiuSizeA OBJECT-TYPE
    SYNTAX Integer32 (137..7642)
    MAX-ACCESS  read-only
    STATUS  current
    DESCRIPTION
    "Maximum Path Information Size"
	::= {pktSwchSnaPUSdlcEntryA 7}

pktSwchSnaPUSdlcTxWindowA OBJECT-TYPE
    SYNTAX  Integer32
    MAX-ACCESS  read-only
    STATUS  current
    DESCRIPTION
    "Window Size(in frames) used when sending from the SPS.
     Range: 1-7."
	::= { pktSwchSnaPUSdlcEntryA 8}

pktSwchSnaPUSdlcGrpAddressA OBJECT-TYPE
    SYNTAX  OCTET STRING (SIZE(1))
    MAX-ACCESS  read-only
    STATUS  current
    DESCRIPTION
    "SNA Group address used by the SPS when sending polls (TPAD ONLY).
     Range: 0x00-0xFE."
	::= { pktSwchSnaPUSdlcEntryA 9}

pktSwchSnaPUSdlcPollTimerA OBJECT-TYPE
    SYNTAX  Integer32
    MAX-ACCESS  read-only
    STATUS  current
    DESCRIPTION
    "Time in between polls in 50 millisecond increments (TPAD ONLY).
     Range: 1-65535."
	::= { pktSwchSnaPUSdlcEntryA 10}

pktSwchSnaPUSdlcXIDInitiationA OBJECT-TYPE
    SYNTAX  INTEGER{
	notInitiate(1),
	initiate(2)
	}
    MAX-ACCESS  read-only
    STATUS  current
    DESCRIPTION
 "This parameter is not applicable for PU with Local XID handling.
 Legal values:
 1 - Do not initiate an XID message.
 2 - Initiate an XID message to SDLC."
	::= { pktSwchSnaPUSdlcEntryA 11}


pktSwchSnaPUSdlcStatTable    OBJECT-TYPE
    SYNTAX  SEQUENCE  OF PktSwchSnaPUSdlcStatEntry
    MAX-ACCESS  not-accessible
    STATUS  current
    DESCRIPTION
	"Shows Link Statistics for PUs running on an SDLC link "
        ::=  { pktSwchSna 7 }

pktSwchSnaPUSdlcStatEntry OBJECT-TYPE
    SYNTAX  PktSwchSnaPUSdlcStatEntry
    MAX-ACCESS  not-accessible
    STATUS  current
    DESCRIPTION
	"Shows Link Statistics for PUs running on an SDLC link "
    INDEX   {pktSwchSnaPUSdlcStatNumber , pktSwchSnaPUSdlcStatSide }
    ::=  { pktSwchSnaPUSdlcStatTable 1 }

PktSwchSnaPUSdlcStatEntry ::= SEQUENCE {
pktSwchSnaPUSdlcStatNumber
Integer32,
pktSwchSnaPUSdlcStatSide
INTEGER,
pktSwchSnaPUSdlcStatOctetsIn
Counter32,
pktSwchSnaPUSdlcStatOctetsOut
Counter32,
pktSwchSnaPUSdlcStatIFramesIn
Counter32,
pktSwchSnaPUSdlcStatIFramesOut
Counter32,
pktSwchSnaPUSdlcStatRRFramesIn
Counter32,
pktSwchSnaPUSdlcStatRRFramesOut
Counter32,
pktSwchSnaPUSdlcStatRNRFramesIn
Counter32,
pktSwchSnaPUSdlcStatRNRFramesOut
Counter32,
pktSwchSnaPUSdlcStatXIDsIn
Counter32,
pktSwchSnaPUSdlcStatXIDsOut
Counter32,
pktSwchSnaPUSdlcStatTESTsIn
Counter32,
pktSwchSnaPUSdlcStatTESTsOut
Counter32,
pktSwchSnaPUSdlcStatREJsIn
Counter32,
pktSwchSnaPUSdlcStatREJsOut
Counter32,
pktSwchSnaPUSdlcStatFRMRsIn
Counter32,
pktSwchSnaPUSdlcStatFRMRsOut
Counter32,
pktSwchSnaPUSdlcStatDISCsIn
Counter32,
pktSwchSnaPUSdlcStatDISCsOut
Counter32,
pktSwchSnaPUSdlcStatUAsIn
Counter32,
pktSwchSnaPUSdlcStatUAsOut
Counter32,
pktSwchSnaPUSdlcStatDMsIn
Counter32,
pktSwchSnaPUSdlcStatDMsOut
Counter32,
pktSwchSnaPUSdlcStatSNRMsIn
Counter32,
pktSwchSnaPUSdlcStatSNRMsOut
Counter32,
pktSwchSnaPUSdlcStatRetransmitsIn
Counter32,
pktSwchSnaPUSdlcStatRetransmitsOut
Counter32,
pktSwchSnaPUSdlcUpperState
INTEGER,
pktSwchSnaPUSdlcLowerState
INTEGER,
pktSwchSnaPUSdlcStatNRMStatus
INTEGER,
pktSwchSnaPUSdlcStatFlowCtlStatus
INTEGER
}
pktSwchSnaPUSdlcStatNumber OBJECT-TYPE
    SYNTAX  Integer32
    MAX-ACCESS  read-only
    STATUS  current
    DESCRIPTION
    "This parameter defines an identifier associated with the PU Entry
     SDLC side statistics, which is unique within the SPS"
	::= { pktSwchSnaPUSdlcStatEntry 1}

pktSwchSnaPUSdlcStatSide OBJECT-TYPE
    SYNTAX  INTEGER {
	    sideA(1),
	    sideB(2)
	    }
    MAX-ACCESS  read-only
    STATUS  current
    DESCRIPTION
    "Is this side A or side B of the PU definition "
	::= { pktSwchSnaPUSdlcStatEntry 2}

pktSwchSnaPUSdlcStatOctetsIn OBJECT-TYPE
 SYNTAX Counter32
 MAX-ACCESS  read-only
 STATUS  current
 DESCRIPTION
    ""
	::= { pktSwchSnaPUSdlcStatEntry 3}

pktSwchSnaPUSdlcStatOctetsOut OBJECT-TYPE
 SYNTAX Counter32
 MAX-ACCESS  read-only
 STATUS  current
 DESCRIPTION
    ""
	::= { pktSwchSnaPUSdlcStatEntry 4}

pktSwchSnaPUSdlcStatIFramesIn OBJECT-TYPE
 SYNTAX Counter32
 MAX-ACCESS  read-only
 STATUS  current
 DESCRIPTION
    ""
	::= { pktSwchSnaPUSdlcStatEntry 5}

pktSwchSnaPUSdlcStatIFramesOut OBJECT-TYPE
 SYNTAX Counter32
 MAX-ACCESS  read-only
 STATUS  current
 DESCRIPTION
    ""
	::= { pktSwchSnaPUSdlcStatEntry 6}

pktSwchSnaPUSdlcStatRRFramesIn OBJECT-TYPE
 SYNTAX Counter32
 MAX-ACCESS  read-only
 STATUS  current
 DESCRIPTION
    ""
	::= { pktSwchSnaPUSdlcStatEntry 7}

pktSwchSnaPUSdlcStatRRFramesOut OBJECT-TYPE
 SYNTAX Counter32
 MAX-ACCESS  read-only
 STATUS  current
 DESCRIPTION
    ""
	::= { pktSwchSnaPUSdlcStatEntry 8}

pktSwchSnaPUSdlcStatRNRFramesIn OBJECT-TYPE
 SYNTAX Counter32
 MAX-ACCESS  read-only
 STATUS  current
 DESCRIPTION
    ""
	::= { pktSwchSnaPUSdlcStatEntry 9}

pktSwchSnaPUSdlcStatRNRFramesOut OBJECT-TYPE
 SYNTAX Counter32
 MAX-ACCESS  read-only
 STATUS  current
 DESCRIPTION
    ""
	::= { pktSwchSnaPUSdlcStatEntry 10}

pktSwchSnaPUSdlcStatXIDsIn OBJECT-TYPE
 SYNTAX Counter32
 MAX-ACCESS  read-only
 STATUS  current
 DESCRIPTION
    ""
	::= { pktSwchSnaPUSdlcStatEntry 11}

pktSwchSnaPUSdlcStatXIDsOut OBJECT-TYPE
 SYNTAX Counter32
 MAX-ACCESS  read-only
 STATUS  current
 DESCRIPTION
    ""
	::= { pktSwchSnaPUSdlcStatEntry 12}

pktSwchSnaPUSdlcStatTESTsIn OBJECT-TYPE
 SYNTAX Counter32
 MAX-ACCESS  read-only
 STATUS  current
 DESCRIPTION
    ""
	::= { pktSwchSnaPUSdlcStatEntry 13}

pktSwchSnaPUSdlcStatTESTsOut OBJECT-TYPE
 SYNTAX Counter32
 MAX-ACCESS  read-only
 STATUS  current
 DESCRIPTION
    ""
	::= { pktSwchSnaPUSdlcStatEntry 14}

pktSwchSnaPUSdlcStatREJsIn OBJECT-TYPE
 SYNTAX Counter32
 MAX-ACCESS  read-only
 STATUS  current
 DESCRIPTION
    ""
	::= { pktSwchSnaPUSdlcStatEntry 15}

pktSwchSnaPUSdlcStatREJsOut OBJECT-TYPE
 SYNTAX Counter32
 MAX-ACCESS  read-only
 STATUS  current
 DESCRIPTION
    ""
	::= { pktSwchSnaPUSdlcStatEntry 16}

pktSwchSnaPUSdlcStatFRMRsIn OBJECT-TYPE
 SYNTAX Counter32
 MAX-ACCESS  read-only
 STATUS  current
 DESCRIPTION
    ""
	::= { pktSwchSnaPUSdlcStatEntry 17}

pktSwchSnaPUSdlcStatFRMRsOut OBJECT-TYPE
 SYNTAX Counter32
 MAX-ACCESS  read-only
 STATUS  current
 DESCRIPTION
    ""
	::= { pktSwchSnaPUSdlcStatEntry 18}

pktSwchSnaPUSdlcStatDISCsIn OBJECT-TYPE
 SYNTAX Counter32
 MAX-ACCESS  read-only
 STATUS  current
 DESCRIPTION
    ""
	::= { pktSwchSnaPUSdlcStatEntry 19}

pktSwchSnaPUSdlcStatDISCsOut OBJECT-TYPE
 SYNTAX Counter32
 MAX-ACCESS  read-only
 STATUS  current
 DESCRIPTION
    ""
	::= { pktSwchSnaPUSdlcStatEntry 20}

pktSwchSnaPUSdlcStatUAsIn OBJECT-TYPE
 SYNTAX Counter32
 MAX-ACCESS  read-only
 STATUS  current
 DESCRIPTION
    ""
	::= { pktSwchSnaPUSdlcStatEntry 21}

pktSwchSnaPUSdlcStatUAsOut OBJECT-TYPE
 SYNTAX Counter32
 MAX-ACCESS  read-only
 STATUS  current
 DESCRIPTION
    ""
	::= { pktSwchSnaPUSdlcStatEntry 22}

pktSwchSnaPUSdlcStatDMsIn OBJECT-TYPE
 SYNTAX Counter32
 MAX-ACCESS  read-only
 STATUS  current
 DESCRIPTION
    ""
	::= { pktSwchSnaPUSdlcStatEntry 23}

pktSwchSnaPUSdlcStatDMsOut OBJECT-TYPE
 SYNTAX Counter32
 MAX-ACCESS  read-only
 STATUS  current
 DESCRIPTION
    ""
	::= { pktSwchSnaPUSdlcStatEntry 24}

pktSwchSnaPUSdlcStatSNRMsIn OBJECT-TYPE
 SYNTAX Counter32
 MAX-ACCESS  read-only
 STATUS  current
 DESCRIPTION
    ""
	::= { pktSwchSnaPUSdlcStatEntry 25}

pktSwchSnaPUSdlcStatSNRMsOut OBJECT-TYPE
 SYNTAX Counter32
 MAX-ACCESS  read-only
 STATUS  current
 DESCRIPTION
    ""
	::= { pktSwchSnaPUSdlcStatEntry 26}

pktSwchSnaPUSdlcStatRetransmitsIn OBJECT-TYPE
 SYNTAX Counter32
 MAX-ACCESS  read-only
 STATUS  current
 DESCRIPTION
    ""
	::= { pktSwchSnaPUSdlcStatEntry 27}

pktSwchSnaPUSdlcStatRetransmitsOut OBJECT-TYPE
 SYNTAX Counter32
 MAX-ACCESS  read-only
 STATUS  current
 DESCRIPTION
    ""
	::= { pktSwchSnaPUSdlcStatEntry 28}

pktSwchSnaPUSdlcUpperState  OBJECT-TYPE
 SYNTAX INTEGER {
    unbound(1),
    bindPending(2),
    unbindPend(3),
    idle(4),
    unattached(5),
    attachPend(6),
    detachPend(7),
    udqosPending(8),
    outconPend(9),
    inconPending(10),
    connResPend(11),
    dataxfer(12),
    userResetPend(13),
    provRstPend(14),
    rstResPend(15),
    discon8Pend(16),
    discon9Pend(17),
    discon11Pend(18),
    discon12Pend(19),
    discon13Pend(20),
    subsBindPnd(21),
    noChange(22)
	}
 MAX-ACCESS read-only
 STATUS current
 DESCRIPTION
    "The internal DLPI state of the connection."
	::= { pktSwchSnaPUSdlcStatEntry 29}

pktSwchSnaPUSdlcLowerState  OBJECT-TYPE
 SYNTAX INTEGER  {
    linkClosed(1),
    disconnected(2),
    linkOpening(3),
    disconnecting(4),
    frmrSent(5),
    linkOpened(6),
    localBusy(7),
    rejection(8),
    checkpointing(9),
    cpLocalBusy(10),
    cpRejection(11),
    resetting(12),
    remoteBusy(13),
    lBusyRBusy(14),
    rejLBusy(15),
    rejRBusy(16),
    cpRejLBusy(17),
    cpClearing(18),
    cpRejClr(19),
    rejLbusyRbusy(20),
    frmrReceived(21),
    programError(22),
    noChange(23)
	}
 MAX-ACCESS read-only
 STATUS current
 DESCRIPTION
    "The internal SDLC state of the connection."
	::= { pktSwchSnaPUSdlcStatEntry 30}

pktSwchSnaPUSdlcStatNRMStatus OBJECT-TYPE
 SYNTAX INTEGER	 {sync(1),notSync(2)}
 MAX-ACCESS  read-only
 STATUS  current
 DESCRIPTION
    "This variable indicates if the link is in Normal Response Mode or not."
	::= { pktSwchSnaPUSdlcStatEntry 31}

pktSwchSnaPUSdlcStatFlowCtlStatus OBJECT-TYPE
 SYNTAX INTEGER	 {noRNR(1),txFlow(2), rxFlow(3), rxAndTx(4)}
 MAX-ACCESS  read-only
 STATUS  current
 DESCRIPTION
    "This variable indicates the flow control status of the PU interface."
	::= { pktSwchSnaPUSdlcStatEntry 32}


pktSwchSnaPUSX25QllcTableS    OBJECT-TYPE
    SYNTAX  SEQUENCE  OF PktSwchSnaPUX25QllcEntryS
    MAX-ACCESS  not-accessible
    STATUS  current
    DESCRIPTION
	"Defines links for PUs running on a QLLC link "
     ::=  {pktSwchSna 8 }

pktSwchSnaPUX25QllcEntryS OBJECT-TYPE
    SYNTAX  PktSwchSnaPUX25QllcEntryS
    MAX-ACCESS  not-accessible
    STATUS  current
    DESCRIPTION
	"Defines parameters for PU side running on SDLC link "
    INDEX   {pktSwchSnaPUX25QllcNumberS , pktSwchSnaPUX25QllcSideS }
    ::=  { pktSwchSnaPUSX25QllcTableS 1 }

PktSwchSnaPUX25QllcEntryS ::= SEQUENCE {
pktSwchSnaPUX25QllcNumberS
Integer32,
pktSwchSnaPUX25QllcSideS
INTEGER,
pktSwchSnaPUX25QllcIdBlkS
OCTET STRING,
pktSwchSnaPUX25QllcIdNumS
OCTET STRING,
pktSwchSnaPUX25QllcXIDInitS
INTEGER,
pktSwchSnaPUX25QllcMaxPiuSizeS
Integer32,
pktSwchSnaPUX25QllcStationAddressS
OCTET STRING,
pktSwchSnaPUX25QllcInPasswordS
DisplayString,
pktSwchSnaPUX25QllcSubAddressS
Integer32,
pktSwchSnaPUX25QllcAutoCallS
INTEGER,
pktSwchSnaPUX25QllcCalledAddressS
OCTET STRING,
pktSwchSnaPUX25QllcCallUserDataFacilitiesS
DisplayString,
pktSwchSnaPUX25QllcEntryStatusS
INTEGER
}

pktSwchSnaPUX25QllcNumberS OBJECT-TYPE
    SYNTAX  Integer32
    MAX-ACCESS  read-only
    STATUS  current
    DESCRIPTION
    "This parameter defines an identifier associated with the PU Entry
     X25\QLLC side, which is unique within the SPS"
	::= {pktSwchSnaPUX25QllcEntryS 1}

pktSwchSnaPUX25QllcSideS  OBJECT-TYPE
    SYNTAX  INTEGER {
	    sideA(1),
	    sideB(2)
	    }
    MAX-ACCESS  read-only
    STATUS  current
    DESCRIPTION
    "Is there side A or B of the PU connection "
	::= {pktSwchSnaPUX25QllcEntryS 2}

pktSwchSnaPUX25QllcIdBlkS OBJECT-TYPE
    SYNTAX  OCTET STRING (SIZE(1..2))
    MAX-ACCESS  read-write
    STATUS  current
    DESCRIPTION
"Part of the IBM device ID (the full ID is defined by the IDBLK and
 the IDNUM). The Idblk is required for secondary PU with Local XID
 handling.  Up to 3 Hexadecimal digits, format: 0X XX."
       ::= {pktSwchSnaPUX25QllcEntryS 3}

pktSwchSnaPUX25QllcIdNumS OBJECT-TYPE
    SYNTAX  OCTET STRING (SIZE(1..3))
    MAX-ACCESS  read-write
    STATUS  current
    DESCRIPTION
"Second part of the IBM device ID (the full ID is defined by the IDBLK and
 the IDNUM). The Idnum is required for secondary PU with Local XID
 handling.  Up to 5 Hexadecimal digits, format: 0X XX XX."
       ::= {pktSwchSnaPUX25QllcEntryS 4}

pktSwchSnaPUX25QllcXIDInitS OBJECT-TYPE
    SYNTAX  INTEGER {
	notInitiate(1),
	initiate(2)
	}
    MAX-ACCESS  read-write
    STATUS  current
    DESCRIPTION
 "This parameter is not applicable for PU with Local XID handling.
 Legal values:
 1 - Do not initiate an XID message.
 2 - Initiate an XID message to QLLC."
       ::= {pktSwchSnaPUX25QllcEntryS 5}

pktSwchSnaPUX25QllcMaxPiuSizeS OBJECT-TYPE
    SYNTAX Integer32 (137..7642)
    MAX-ACCESS  read-write
    STATUS  current
    DESCRIPTION
    "Maximum Path Information Size"
	::= { pktSwchSnaPUX25QllcEntryS 6}


pktSwchSnaPUX25QllcStationAddressS OBJECT-TYPE
    SYNTAX  OCTET STRING (SIZE(1))
    MAX-ACCESS  read-write
    STATUS  current
    DESCRIPTION
"QLLC PU Link Station Address. Range: 0x01-0xFE.
 This parameter is applicable only for PU with End-to-End XID handling,
 Support for NON-Activation XID."
       ::= {pktSwchSnaPUX25QllcEntryS 7}

pktSwchSnaPUX25QllcInPasswordS OBJECT-TYPE
    SYNTAX  DisplayString (SIZE(1..8))
    MAX-ACCESS  read-write
    STATUS  current
    DESCRIPTION
    "A field matched with the call user data in call request packets for
     purposes of security and correlation."
       ::= {pktSwchSnaPUX25QllcEntryS 8}

pktSwchSnaPUX25QllcSubAddressS OBJECT-TYPE
    SYNTAX  Integer32
    MAX-ACCESS  read-write
    STATUS  current
    DESCRIPTION
    "The X.25 Sub-address associated with the PU Entry for routing
     incoming call indications. Range: 0-99."
       ::= {pktSwchSnaPUX25QllcEntryS 9}

pktSwchSnaPUX25QllcAutoCallS OBJECT-TYPE
    SYNTAX  INTEGER {
	yes(1),
	no(2)
	}
    MAX-ACCESS  read-write
    STATUS  current
    DESCRIPTION
    "This parameter indicates whether the SPS automatically initiates
     an X.25 call request or not."
       ::= {pktSwchSnaPUX25QllcEntryS 10}

pktSwchSnaPUX25QllcCalledAddressS OBJECT-TYPE
    SYNTAX  OCTET STRING (SIZE (1..15))
    MAX-ACCESS  read-write
    STATUS  current
    DESCRIPTION
    "The destination x.25 DTE address to which the SPS calls. Used with
     AutoCall only."
       ::= {pktSwchSnaPUX25QllcEntryS 11}

pktSwchSnaPUX25QllcCallUserDataFacilitiesS OBJECT-TYPE
    SYNTAX  DisplayString (SIZE(1..60))
    MAX-ACCESS  read-write
    STATUS  current
    DESCRIPTION
    "The X.25 facilities and Call User Data which the SPS uses on
     outgoing calls. AutoCall only.
  Up to 60 Hexa-Decimal digits.
  Each pair of digits represents a BYTE.
  BYTE-0 BYTE-1 BYTE-2 ... BYTE-29 (30 Bytes maximum)

  BYTE-0 for X.25 Facilities. BYTE-1 to BYTE-29 for Call User Data.
  Facilities (BYTE-0) format: PW (Hexa-Decimal), where:
      X.25 L3 Packet Size Negotiation    : [P=1 YES] [P=0 NO].
      X.25 L3 Packet Window Negotiation  : [W=1 YES] [W=0 NO].
      Legal Values for Facilities BYTE-0 : 10, 01, 11, 00  (Hex).

    ATTENTION: a. Total number of digits in this field must be EVEN.
               b. To clear this field, enter blanks or 00."
       ::= {pktSwchSnaPUX25QllcEntryS 12}

pktSwchSnaPUX25QllcEntryStatusS OBJECT-TYPE
    SYNTAX  INTEGER {
       valid(1),
       underCreation(3)
     }
    MAX-ACCESS  read-write
    STATUS  current
    DESCRIPTION
    "The status of this PU Qllc table entry.
     In order to save this entry, set status to valid.
     An underCreation value is set by the Agent when this entry is updated."
         ::= {pktSwchSnaPUX25QllcEntryS 13}

pktSwchSnaPUX25QllcTableA    OBJECT-TYPE
    SYNTAX  SEQUENCE  OF PktSwchSnaPUX25QllcEntryA
    MAX-ACCESS  not-accessible
    STATUS  current
    DESCRIPTION
	"Defines links for PUs running on a QLLC link "
     ::=  { pktSwchSna 9 }

pktSwchSnaPUX25QllcEntryA OBJECT-TYPE
    SYNTAX  PktSwchSnaPUX25QllcEntryA
    MAX-ACCESS  not-accessible
    STATUS  current
    DESCRIPTION
	"Defines parameters for PU side running on an SDLC link "
    INDEX   {pktSwchSnaPUX25QllcNumberA , pktSwchSnaPUX25QllcSideA}
    ::=  { pktSwchSnaPUX25QllcTableA 1 }

PktSwchSnaPUX25QllcEntryA ::= SEQUENCE {
pktSwchSnaPUX25QllcNumberA
Integer32,
pktSwchSnaPUX25QllcSideA
INTEGER,
pktSwchSnaPUX25QllcIdBlkA
OCTET STRING,
pktSwchSnaPUX25QllcIdNumA
OCTET STRING,
pktSwchSnaPUX25QllcXIDInitA
INTEGER,
pktSwchSnaPUX25QllcMaxPiuSizeA
Integer32,
pktSwchSnaPUX25QllcStationAddressA
OCTET STRING,
pktSwchSnaPUX25QllcInPasswordA
DisplayString,
pktSwchSnaPUX25QllcSubAddressA
Integer32,
pktSwchSnaPUX25QllcAutoCallA
INTEGER,
pktSwchSnaPUX25QllcCalledAddressA
OCTET STRING,
pktSwchSnaPUX25QllcCallUserDataFacilitiesA
DisplayString
}

pktSwchSnaPUX25QllcNumberA OBJECT-TYPE
    SYNTAX  Integer32
    MAX-ACCESS  read-only
    STATUS  current
    DESCRIPTION
    "This parameter defines an identifier associated with the PU Entry
     X25\QLLC side, which is unique within the SPS"
	::= {pktSwchSnaPUX25QllcEntryA 1}

pktSwchSnaPUX25QllcSideA  OBJECT-TYPE
    SYNTAX  INTEGER {
	    sideA(1),
	    sideB(2)
	    }
    MAX-ACCESS  read-only
    STATUS  current
    DESCRIPTION
    "Is there side A or B of the PU connection "
	::= {pktSwchSnaPUX25QllcEntryA 2}

pktSwchSnaPUX25QllcIdBlkA OBJECT-TYPE
    SYNTAX  OCTET STRING (SIZE(1..2))
    MAX-ACCESS  read-only
    STATUS  current
    DESCRIPTION
"Part of the IBM device ID (the full ID is defined by the IDBLK and
 the IDNUM). The Idblk is required for secondary PU with Local XID
 handling.  Up to 3 Hexadecimal digits, format: 0X XX."
       ::= {pktSwchSnaPUX25QllcEntryA 3}

pktSwchSnaPUX25QllcIdNumA OBJECT-TYPE
    SYNTAX  OCTET STRING (SIZE(1..3))
    MAX-ACCESS  read-only
    STATUS  current
    DESCRIPTION
"Second part of the IBM device ID (the full ID is defined by the IDBLK and
 the IDNUM). The Idnum is required for secondary PU with Local XID
 handling.  Up to 5 Hexadecimal digits, format: 0X XX XX."
       ::= {pktSwchSnaPUX25QllcEntryA 4}

pktSwchSnaPUX25QllcXIDInitA OBJECT-TYPE
    SYNTAX  INTEGER {
	notInitiate(1),
	initiate(2)
	}
    MAX-ACCESS  read-only
    STATUS  current
    DESCRIPTION
 "This parameter is not applicable for PU with Local XID handling.
 Legal values:
 1 - Do not initiate an XID message.
 2 - Initiate an XID message to QLLC."
       ::= {pktSwchSnaPUX25QllcEntryA 5}

pktSwchSnaPUX25QllcMaxPiuSizeA OBJECT-TYPE
    SYNTAX Integer32 (137..7642)
    MAX-ACCESS  read-only
    STATUS  current
    DESCRIPTION
    "Maximum Path Information Size"
	::= { pktSwchSnaPUX25QllcEntryA 6}

pktSwchSnaPUX25QllcStationAddressA OBJECT-TYPE
    SYNTAX  OCTET STRING (SIZE(1))
    MAX-ACCESS  read-only
    STATUS  current
    DESCRIPTION
"QLLC PU Link Station Address. Range: 0x01-0xFE.
 This parameter is applicable only for PU with End-to-End XID handling,
 Support for NON-Activation XID."
       ::= {pktSwchSnaPUX25QllcEntryA 7}

pktSwchSnaPUX25QllcInPasswordA OBJECT-TYPE
    SYNTAX  DisplayString (SIZE(1..8))
    MAX-ACCESS  read-only
    STATUS  current
    DESCRIPTION
    "A field matched with the call user data in call request packets for
     purposes of security and correlation."
       ::= {pktSwchSnaPUX25QllcEntryA 8}

pktSwchSnaPUX25QllcSubAddressA OBJECT-TYPE
    SYNTAX  Integer32
    MAX-ACCESS  read-only
    STATUS  current
    DESCRIPTION
    "The X.25 Sub-address associated with the PU Entry for routing
     incoming call indications. Range: 0-99."
       ::= {pktSwchSnaPUX25QllcEntryA 9}

pktSwchSnaPUX25QllcAutoCallA OBJECT-TYPE
    SYNTAX  INTEGER{
	yes(1),
	no(2)
	}
    MAX-ACCESS  read-only
    STATUS  current
    DESCRIPTION
    "This parameter indicates whether the SPS automatically initiates
     an X.25 call request or not."
       ::= {pktSwchSnaPUX25QllcEntryA 10}

pktSwchSnaPUX25QllcCalledAddressA OBJECT-TYPE
    SYNTAX  OCTET STRING (SIZE (1..15))
    MAX-ACCESS  read-only
    STATUS  current
    DESCRIPTION
    "The destination x.25 DTE address to which the SPS calls. Used
     with AutoCall only."
       ::= {pktSwchSnaPUX25QllcEntryA 11}

pktSwchSnaPUX25QllcCallUserDataFacilitiesA OBJECT-TYPE
    SYNTAX  DisplayString (SIZE(1..60))
    MAX-ACCESS  read-only
    STATUS  current
    DESCRIPTION
    "The X.25 facilities and Call User Data which the SPS uses on
     outgoing calls. AutoCall only.
  Up to 60 Hexa-Decimal digits.
  Each pair of digits represents a BYTE.
  BYTE-0 BYTE-1 BYTE-2 ... BYTE-29 (30 Bytes maximum)

  BYTE-0 for X.25 Facilities. BYTE-1 to BYTE-29 for Call User Data.
  Facilities (BYTE-0) format: PW (Hexa-Decimal), where:
      X.25 L3 Packet Size Negotiation    : [P=1 YES] [P=0 NO].
      X.25 L3 Packet Window Negotiation  : [W=1 YES] [W=0 NO].
      Legal Values for Facilities BYTE-0 : 10, 01, 11, 00  (Hex).

    ATTENTION: a. Total number of digits in this field must be EVEN.
               b. To clear this field, enter blanks or 00."
       ::= {pktSwchSnaPUX25QllcEntryA 12}



pktSwchSnaPUX25QllcStatTable    OBJECT-TYPE
    SYNTAX  SEQUENCE  OF PktSwchSnaPUX25QllcStatEntry
    MAX-ACCESS  not-accessible
    STATUS  current
    DESCRIPTION
	"Shows link statistics for PUs running on a QLLC link "
     ::=  { pktSwchSna 10 }

pktSwchSnaPUX25QllcStatEntry OBJECT-TYPE
    SYNTAX  PktSwchSnaPUX25QllcStatEntry
    MAX-ACCESS  not-accessible
    STATUS  current
    DESCRIPTION
	"Shows link statistics for PUs running on a QLLC link "
    INDEX   {pktSwchSnaPUX25QllcStatNumber , pktSwchSnaPUX25QllcStatSide}
    ::=  { pktSwchSnaPUX25QllcStatTable 1 }

PktSwchSnaPUX25QllcStatEntry ::= SEQUENCE {
pktSwchSnaPUX25QllcStatNumber
Integer32,
pktSwchSnaPUX25QllcStatSide
INTEGER,
pktSwchSnaPUX25QllcStatlink
Integer32,
pktSwchSnaPUX25QllcStatDataPacketsIn
Counter32,
pktSwchSnaPUX25QllcStatDataPacketsOut
Counter32,
pktSwchSnaPUX25QllcStatQSMPacketsIn
Counter32,
pktSwchSnaPUX25QllcStatQSMPacketsOut
Counter32,
pktSwchSnaPUX25QllcStatQDMPacketsIn
Counter32,
pktSwchSnaPUX25QllcStatQDMPacketsOut
Counter32,
pktSwchSnaPUX25QllcStatXIDPacketsIn
Counter32,
pktSwchSnaPUX25QllcStatXIDPacketsOut
Counter32,
pktSwchSnaPUX25QllcStatQDISCPacketsIn
Counter32,
pktSwchSnaPUX25QllcStatQDISCPacketsOut
Counter32,
pktSwchSnaPUX25QllcStatCallPacketsIn
Counter32,
pktSwchSnaPUX25QllcStatCallPacketsOut
Counter32,
pktSwchSnaPUX25QllcStatClearPacketsIn
Counter32,
pktSwchSnaPUX25QllcStatClearPacketsOut
Counter32,
pktSwchSnaPUX25QllcStatCallAcceptsIn
Counter32,
pktSwchSnaPUX25QllcStatCallAcceptsOut
Counter32,
pktSwchSnaPUX25QllcStatUpperState
INTEGER,
pktSwchSnaPUX25QllcStatLowerState
INTEGER,
pktSwchSnaPUX25QllcStatNRMStatus
INTEGER,
pktSwchSnaPUX25QllcStatFlowCtlStatus
INTEGER
}

pktSwchSnaPUX25QllcStatNumber OBJECT-TYPE
    SYNTAX  Integer32
    MAX-ACCESS  read-only
    STATUS  current
    DESCRIPTION
    "This parameter defines an identifier associated with the PU Entry
     X25\QLLC side, which is unique within the SPS"
	::= {pktSwchSnaPUX25QllcStatEntry 1}

pktSwchSnaPUX25QllcStatSide  OBJECT-TYPE
    SYNTAX  INTEGER {
	    sideA(1),
	    sideB(2)
	    }
    MAX-ACCESS  read-only
    STATUS  current
    DESCRIPTION
    "Is there side A or B of the PU connection "
	::= {pktSwchSnaPUX25QllcStatEntry 2}

pktSwchSnaPUX25QllcStatlink OBJECT-TYPE
    SYNTAX  Integer32
    MAX-ACCESS  read-only
    STATUS  current
    DESCRIPTION
    "The Link on which the Qllc conversation is conducted. If there is
     no conversation the variable will be 0."
       ::= {pktSwchSnaPUX25QllcStatEntry 3}

pktSwchSnaPUX25QllcStatDataPacketsIn OBJECT-TYPE
 SYNTAX Counter32
 MAX-ACCESS  read-only
 STATUS  current
 DESCRIPTION
    ""
	::= { pktSwchSnaPUX25QllcStatEntry 4 }

pktSwchSnaPUX25QllcStatDataPacketsOut OBJECT-TYPE
 SYNTAX Counter32
 MAX-ACCESS  read-only
 STATUS  current
 DESCRIPTION
    ""
	::= { pktSwchSnaPUX25QllcStatEntry 5 }

pktSwchSnaPUX25QllcStatQSMPacketsIn OBJECT-TYPE
 SYNTAX Counter32
 MAX-ACCESS  read-only
 STATUS  current
 DESCRIPTION
    ""
	::= { pktSwchSnaPUX25QllcStatEntry 6 }

pktSwchSnaPUX25QllcStatQSMPacketsOut OBJECT-TYPE
 SYNTAX Counter32
 MAX-ACCESS  read-only
 STATUS  current
 DESCRIPTION
    ""
	::= { pktSwchSnaPUX25QllcStatEntry 7 }

pktSwchSnaPUX25QllcStatQDMPacketsIn OBJECT-TYPE
 SYNTAX Counter32
 MAX-ACCESS  read-only
 STATUS  current
 DESCRIPTION
    ""
	::= { pktSwchSnaPUX25QllcStatEntry 8 }

pktSwchSnaPUX25QllcStatQDMPacketsOut OBJECT-TYPE
 SYNTAX Counter32
 MAX-ACCESS  read-only
 STATUS  current
 DESCRIPTION
    ""
	::= { pktSwchSnaPUX25QllcStatEntry 9 }

pktSwchSnaPUX25QllcStatXIDPacketsIn OBJECT-TYPE
 SYNTAX Counter32
 MAX-ACCESS  read-only
 STATUS  current
 DESCRIPTION
    ""
	::= { pktSwchSnaPUX25QllcStatEntry 10 }

pktSwchSnaPUX25QllcStatXIDPacketsOut OBJECT-TYPE
 SYNTAX Counter32
 MAX-ACCESS  read-only
 STATUS  current
 DESCRIPTION
    ""
	::= { pktSwchSnaPUX25QllcStatEntry 11 }

pktSwchSnaPUX25QllcStatQDISCPacketsIn OBJECT-TYPE
 SYNTAX Counter32
 MAX-ACCESS  read-only
 STATUS  current
 DESCRIPTION
    ""
	::= { pktSwchSnaPUX25QllcStatEntry 12 }

pktSwchSnaPUX25QllcStatQDISCPacketsOut OBJECT-TYPE
 SYNTAX Counter32
 MAX-ACCESS  read-only
 STATUS  current
 DESCRIPTION
    ""
	::= { pktSwchSnaPUX25QllcStatEntry 13 }

pktSwchSnaPUX25QllcStatCallPacketsIn OBJECT-TYPE
 SYNTAX Counter32
 MAX-ACCESS  read-only
 STATUS  current
 DESCRIPTION
    ""
	::= { pktSwchSnaPUX25QllcStatEntry 14 }

pktSwchSnaPUX25QllcStatCallPacketsOut OBJECT-TYPE
 SYNTAX Counter32
 MAX-ACCESS  read-only
 STATUS  current
 DESCRIPTION
    ""
	::= { pktSwchSnaPUX25QllcStatEntry 15 }

pktSwchSnaPUX25QllcStatClearPacketsIn OBJECT-TYPE
 SYNTAX Counter32
 MAX-ACCESS  read-only
 STATUS  current
 DESCRIPTION
    ""
	::= { pktSwchSnaPUX25QllcStatEntry 16 }

pktSwchSnaPUX25QllcStatClearPacketsOut OBJECT-TYPE
 SYNTAX Counter32
 MAX-ACCESS  read-only
 STATUS  current
 DESCRIPTION
    ""
	::= { pktSwchSnaPUX25QllcStatEntry 17 }

pktSwchSnaPUX25QllcStatCallAcceptsIn OBJECT-TYPE
 SYNTAX Counter32
 MAX-ACCESS  read-only
 STATUS  current
 DESCRIPTION
    ""
	::= { pktSwchSnaPUX25QllcStatEntry 18 }

pktSwchSnaPUX25QllcStatCallAcceptsOut OBJECT-TYPE
 SYNTAX Counter32
 MAX-ACCESS  read-only
 STATUS  current
 DESCRIPTION
    ""
	::= { pktSwchSnaPUX25QllcStatEntry 19 }

pktSwchSnaPUX25QllcStatUpperState OBJECT-TYPE
 SYNTAX INTEGER {
    unbound(1),
    bindPending(2),
    unbindPend(3),
    idle(4),
    unattached(5),
    attachPend(6),
    detachPend(7),
    udqosPending(8),
    outconPend(9),
    inconPending(10),
    connResPend(11),
    dataxfer(12),
    userResetPend(13),
    provRstPend(14),
    rstResPend(15),
    discon8Pend(16),
    discon9Pend(17),
    discon11Pend(18),
    discon12Pend(19),
    discon13Pend(20),
    subsBindPnd(21),
    noChange(22)
   }
 MAX-ACCESS read-only
 STATUS current
 DESCRIPTION
    "The internal DLPI state of the connection."
	::= { pktSwchSnaPUX25QllcStatEntry 20 }

pktSwchSnaPUX25QllcStatLowerState OBJECT-TYPE
 SYNTAX INTEGER {
    linkClosed(1),
    disconnected(2),
    linkOpening(3),
    disconnecting(4),
    frmrSent(5),
    linkOpened(6),
    localBusy(7),
    rejection(8),
    checkpointing(9),
    cpLocalBusy(10),
    cpRejection(11),
    resetting(12),
    remoteBusy(13),
    lBusyRBusy(14),
    rejLBusy(15),
    rejRBusy(16),
    cpRejLBusy(17),
    cpClearing(18),
    cpRejClr(19),
    rejLbusyRbusy(20),
    frmrReceived(21),
    programError(22),
    noChange(23)
	}
 MAX-ACCESS read-only
 STATUS current
 DESCRIPTION
    "The internal QLLC state of the connection."
	::= { pktSwchSnaPUX25QllcStatEntry 21 }

pktSwchSnaPUX25QllcStatNRMStatus OBJECT-TYPE
 SYNTAX INTEGER	 {sync(1),notSync(2)}
 MAX-ACCESS  read-only
 STATUS  current
 DESCRIPTION
    "This variable indicates if the link is in Normal Response Mode or not."
	::= { pktSwchSnaPUX25QllcStatEntry 22 }

pktSwchSnaPUX25QllcStatFlowCtlStatus OBJECT-TYPE
 SYNTAX INTEGER	 {noRNR(1),txFlow(2), rxFlow(3), rxAndTx(4)}
 MAX-ACCESS  read-only
 STATUS  current
 DESCRIPTION
    "This variable indicates the flow control status of the PU interface."
	::= { pktSwchSnaPUX25QllcStatEntry 23 }


pktSwchSnaPULlc2FrTableS    OBJECT-TYPE
    SYNTAX  SEQUENCE  OF PktSwchSnaPULlc2FrEntryS
    MAX-ACCESS  not-accessible
    STATUS  current
    DESCRIPTION
	"Defines LLC2/Frame Relay/RFC1490 Protocol Interface of SPS SNA PU entity. "
     ::=  { pktSwchSna 11 }

pktSwchSnaPULlc2FrEntryS OBJECT-TYPE
    SYNTAX  PktSwchSnaPULlc2FrEntryS
    MAX-ACCESS  not-accessible
    STATUS  current
    DESCRIPTION
	"Defines parameters for PU LLC2 Protocol Interface over Frame Relay Protocol using RFC 1490."
    INDEX   {pktSwchSnaPULlc2FrNumberS , pktSwchSnaPULlc2FrSideS}
    ::=  { pktSwchSnaPULlc2FrTableS 1 }

PktSwchSnaPULlc2FrEntryS ::= SEQUENCE {
pktSwchSnaPULlc2FrNumberS
Integer32,
pktSwchSnaPULlc2FrSideS
INTEGER,
pktSwchSnaPULlc2FrEncapsTypeS
INTEGER,
pktSwchSnaPULlc2FrDestMACS
OCTET STRING,
pktSwchSnaPULlc2FrSrcSAPS
OCTET STRING,
pktSwchSnaPULlc2FrDestSAPS
OCTET STRING,
pktSwchSnaPULlc2FrXIDIdBlkS
OCTET STRING,
pktSwchSnaPULlc2FrXIDIdNumS
OCTET STRING,
pktSwchSnaPULlc2FrMaxPiuSizeS
Integer32,
pktSwchSnaPULlc2FrTxWindowS
Integer32,
pktSwchSnaPULlc2FrLinkS
Integer32,
pktSwchSnaPULlc2FrDLCIS
Integer32,
pktSwchSnaPULlc2FrXIDInitiationS
INTEGER,
pktSwchSnaPULlc2FrN2CountS
Integer32,
pktSwchSnaPULlc2FrT1TimerS
Integer32,
pktSwchSnaPULlc2FrTiTimerS
Integer32,
pktSwchSnaPULlc2FrEntryStatusS
INTEGER
}

pktSwchSnaPULlc2FrNumberS OBJECT-TYPE
    SYNTAX Integer32
    MAX-ACCESS  read-only
    STATUS  current
    DESCRIPTION
    "Unique Identifier for this PU. The value in this field is used as a common Key in both this table and the Main PU table. "
    ::= {pktSwchSnaPULlc2FrEntryS 1 }

pktSwchSnaPULlc2FrSideS OBJECT-TYPE
    SYNTAX INTEGER {
	    sideA(1),
	    sideB(2)
	    }
    MAX-ACCESS  read-only
    STATUS  current
    DESCRIPTION
    "Indicates for each side (SIDE-A and SIDE-B) if the Protocol Interface for that side has been defined or not. "
    ::= {pktSwchSnaPULlc2FrEntryS 2}

pktSwchSnaPULlc2FrEncapsTypeS OBJECT-TYPE
    SYNTAX INTEGER	 {ban(1),bnn(2),tren(3)}
    MAX-ACCESS  read-write
    STATUS  current
    DESCRIPTION
"Indicates if the LLC2/RFC1490 Protocol Interface uses the BNN, BAN
 or TREN method of Frame Encapsulation."
    ::= {pktSwchSnaPULlc2FrEntryS 3}

pktSwchSnaPULlc2FrDestMACS OBJECT-TYPE
    SYNTAX OCTET STRING (SIZE(6))
    MAX-ACCESS  read-write
    STATUS  current
    DESCRIPTION
"The LLC2 Destination MAC Address."
    ::= {pktSwchSnaPULlc2FrEntryS 4}

pktSwchSnaPULlc2FrSrcSAPS OBJECT-TYPE
    SYNTAX OCTET STRING (SIZE(1))
    MAX-ACCESS  read-write
    STATUS  current
    DESCRIPTION
"The LLC2 Source SAP Address. 2 Hex digits"
::= {pktSwchSnaPULlc2FrEntryS 5}

pktSwchSnaPULlc2FrDestSAPS OBJECT-TYPE
    SYNTAX OCTET STRING (SIZE(1))
    MAX-ACCESS  read-write
    STATUS  current
    DESCRIPTION
"The LLC2 Destination SAP."
    ::= {pktSwchSnaPULlc2FrEntryS 6}

pktSwchSnaPULlc2FrXIDIdBlkS OBJECT-TYPE
    SYNTAX OCTET STRING (SIZE(1..2))
    MAX-ACCESS  read-write
    STATUS  current
    DESCRIPTION
"Part of the IBM device ID (the full ID is defined by the IDBLK and
 the IDNUM). The IDBLK is required for PU with Local XID handling
 or PU with End-to-End XID handling, NO Support for NON-Activation XID.
 Up to 3 Hexadecimal digits, format: 0X XX."
    ::= {pktSwchSnaPULlc2FrEntryS 7}

pktSwchSnaPULlc2FrXIDIdNumS OBJECT-TYPE
    SYNTAX OCTET STRING (SIZE(1..3))
    MAX-ACCESS  read-write
    STATUS  current
    DESCRIPTION
"Second part of the IBM device ID (the full ID is defined by the IDBLK and
 the IDNUM). The IDNUM is required for PU with Local XID handling
 or PU with End-to-End XID handling, NO Support for NON-Activation XID.
 Up to 5 Hexadecimal digits, format: 0X XX XX."
::= {pktSwchSnaPULlc2FrEntryS 8}

pktSwchSnaPULlc2FrMaxPiuSizeS OBJECT-TYPE
    SYNTAX Integer32 (137..7642)
    MAX-ACCESS  read-write
    STATUS  current
    DESCRIPTION
    "Maximum Path Information Size"
	::= { pktSwchSnaPULlc2FrEntryS 9}

pktSwchSnaPULlc2FrTxWindowS OBJECT-TYPE
    SYNTAX Integer32
    MAX-ACCESS  read-write
    STATUS  current
    DESCRIPTION
"The LLC2 Link Window Size."
    ::= {pktSwchSnaPULlc2FrEntryS 10}

pktSwchSnaPULlc2FrLinkS OBJECT-TYPE
    SYNTAX Integer32
    MAX-ACCESS  read-write
    STATUS  current
    DESCRIPTION
"The SPS Frame Relay Link Number which this LLC2 Protocol Interface is associated with."
    ::= {pktSwchSnaPULlc2FrEntryS 11}

pktSwchSnaPULlc2FrDLCIS OBJECT-TYPE
    SYNTAX Integer32
    MAX-ACCESS  read-write
    STATUS  current
    DESCRIPTION
"The SPS Frame Relay DLCI Number which this LLC2 Protocol Interface is associated with."
    ::= {pktSwchSnaPULlc2FrEntryS 12}

pktSwchSnaPULlc2FrXIDInitiationS OBJECT-TYPE
    SYNTAX  INTEGER{
	notInitiate(1),
	initiate(2)
	}
    MAX-ACCESS  read-write
    STATUS  current
    DESCRIPTION
 "This parameter is not applicable for PU with Local XID handling.
 Legal values:
 1 - Do not initiate an XID message.
 2 - Initiate an XID message to LLC2."
	::= { pktSwchSnaPULlc2FrEntryS 13}

pktSwchSnaPULlc2FrN2CountS OBJECT-TYPE
    SYNTAX  Integer32 (1..99999)
    MAX-ACCESS  read-write
    STATUS  current
    DESCRIPTION
    "N2 Count"
	::= { pktSwchSnaPULlc2FrEntryS 14}

pktSwchSnaPULlc2FrT1TimerS OBJECT-TYPE
    SYNTAX  Integer32  (1..99999)
    MAX-ACCESS  read-write
    STATUS  current
    DESCRIPTION
    "T1 Timer in 1/10 of a second."
	::= { pktSwchSnaPULlc2FrEntryS 15}

pktSwchSnaPULlc2FrTiTimerS OBJECT-TYPE
    SYNTAX  Integer32  (1..99999)
    MAX-ACCESS  read-write
    STATUS  current
    DESCRIPTION
    "TI Timer in seconds"
	::= { pktSwchSnaPULlc2FrEntryS 16}

pktSwchSnaPULlc2FrEntryStatusS OBJECT-TYPE
    SYNTAX  INTEGER {
       valid(1),
       underCreation(3)
     }
    MAX-ACCESS  read-write
    STATUS  current
    DESCRIPTION
    "The status of this PU Llc2 table entry.
     In order to save this entry, set status to valid.
     An underCreation value is set by the Agent when this entry is updated."
         ::= {pktSwchSnaPULlc2FrEntryS 17}


pktSwchSnaPULlc2FrTableA    OBJECT-TYPE
    SYNTAX  SEQUENCE  OF PktSwchSnaPULlc2FrEntryA
    MAX-ACCESS  not-accessible
    STATUS  current
    DESCRIPTION
	"Defines links for PUs running on an LLC2 link "
     ::=  { pktSwchSna 12 }

pktSwchSnaPULlc2FrEntryA OBJECT-TYPE
    SYNTAX  PktSwchSnaPULlc2FrEntryA
    MAX-ACCESS  not-accessible
    STATUS  current
    DESCRIPTION
	"Defines parameters for PU LLC2 Protocol Interface over Frame Relay Protocol using RFC 1490."
    INDEX   {pktSwchSnaPULlc2FrNumberA , pktSwchSnaPULlc2FrSideA}
    ::=  { pktSwchSnaPULlc2FrTableA 1 }

PktSwchSnaPULlc2FrEntryA ::= SEQUENCE {
pktSwchSnaPULlc2FrNumberA
Integer32,
pktSwchSnaPULlc2FrSideA
INTEGER,
pktSwchSnaPULlc2FrEncapsTypeA
INTEGER,
pktSwchSnaPULlc2FrDestMACA
OCTET STRING,
pktSwchSnaPULlc2FrSrcSAPA
OCTET STRING,
pktSwchSnaPULlc2FrDestSAPA
OCTET STRING,
pktSwchSnaPULlc2FrXIDIdBlkA
OCTET STRING,
pktSwchSnaPULlc2FrXIDIdNumA
OCTET STRING,
pktSwchSnaPULlc2FrMaxPiuSizeA
Integer32,
pktSwchSnaPULlc2FrTxWindowA
Integer32,
pktSwchSnaPULlc2FrLinkA
Integer32,
pktSwchSnaPULlc2FrDLCIA
Integer32,
pktSwchSnaPULlc2FrXIDInitiationA
INTEGER,
pktSwchSnaPULlc2FrN2CountA
Integer32,
pktSwchSnaPULlc2FrT1TimerA
Integer32,
pktSwchSnaPULlc2FrTiTimerA
Integer32
}
pktSwchSnaPULlc2FrNumberA OBJECT-TYPE
    SYNTAX Integer32
    MAX-ACCESS  read-only
    STATUS  current
    DESCRIPTION
"Unique Identifier for this PU. The value in this field is used as a common Key in both this table and the Main PU table. "
    ::= {pktSwchSnaPULlc2FrEntryA 1 }

pktSwchSnaPULlc2FrSideA OBJECT-TYPE
    SYNTAX INTEGER {
	    sideA(1),
	    sideB(2)
	    }
    MAX-ACCESS  read-only
    STATUS  current
    DESCRIPTION
"Indicates for each side (SIDE-A and SIDE-B) if the Protocol Interface for that side has been defined or not. "
    ::= {pktSwchSnaPULlc2FrEntryA 2}

pktSwchSnaPULlc2FrEncapsTypeA OBJECT-TYPE
    SYNTAX INTEGER	 {ban(1),bnn(2),tren(3)}
    MAX-ACCESS  read-only
    STATUS  current
    DESCRIPTION
"Indicates if the LLC2/RFC1490 Protocol Interface uses the BNN, BAN
 or TREN method of Frame Encapsulation."
    ::= {pktSwchSnaPULlc2FrEntryA 3}

pktSwchSnaPULlc2FrDestMACA OBJECT-TYPE
    SYNTAX OCTET STRING (SIZE(6))
    MAX-ACCESS  read-only
    STATUS  current
    DESCRIPTION
"The LLC2 Destination MAC Address."
    ::= {pktSwchSnaPULlc2FrEntryA 4}

pktSwchSnaPULlc2FrSrcSAPA OBJECT-TYPE
    SYNTAX OCTET STRING (SIZE(1))
    MAX-ACCESS  read-only
    STATUS  current
    DESCRIPTION
"The LLC2 Source SAP Address."
    ::= {pktSwchSnaPULlc2FrEntryA 5}

pktSwchSnaPULlc2FrDestSAPA OBJECT-TYPE
    SYNTAX OCTET STRING (SIZE(1))
    MAX-ACCESS  read-only
    STATUS  current
    DESCRIPTION
"The LLC2 Destination SAP."
    ::= {pktSwchSnaPULlc2FrEntryA 6}

pktSwchSnaPULlc2FrXIDIdBlkA OBJECT-TYPE
    SYNTAX OCTET STRING (SIZE(1..2))
    MAX-ACCESS  read-only
    STATUS  current
    DESCRIPTION
"Part of the IBM device ID (the full ID is defined by the IDBLK and
 the IDNUM). The IDBLK is required for PU with Local XID handling
 or PU with End-to-End XID handling, NO Support for NON-Activation XID.
 Up to 3 Hexadecimal digits, format: 0X XX."
    ::= {pktSwchSnaPULlc2FrEntryA 7}

pktSwchSnaPULlc2FrXIDIdNumA OBJECT-TYPE
    SYNTAX OCTET STRING (SIZE(1..3))
    MAX-ACCESS  read-only
    STATUS  current
    DESCRIPTION
"Second part of the IBM device ID (the full ID is defined by the IDBLK and
 the IDNUM). The IDNUM is required for PU with Local XID handling
 or PU with End-to-End XID handling, NO Support for NON-Activation XID.
 Up to 5 Hexadecimal digits, format: 0X XX XX."
    ::= {pktSwchSnaPULlc2FrEntryA 8}

pktSwchSnaPULlc2FrMaxPiuSizeA OBJECT-TYPE
    SYNTAX Integer32 (137..7642)
    MAX-ACCESS  read-only
    STATUS  current
    DESCRIPTION
    "Maximum Path Information Size"
	::= {pktSwchSnaPULlc2FrEntryA 9}

pktSwchSnaPULlc2FrTxWindowA OBJECT-TYPE
    SYNTAX Integer32
    MAX-ACCESS  read-only
    STATUS  current
    DESCRIPTION
"The LLC2 Link Window Size."
    ::= {pktSwchSnaPULlc2FrEntryA 10}

pktSwchSnaPULlc2FrLinkA OBJECT-TYPE
    SYNTAX Integer32
    MAX-ACCESS  read-only
    STATUS  current
    DESCRIPTION
"The SPS Frame Relay Link Number which this LLC2 Protocol Interface is associated with."
    ::= {pktSwchSnaPULlc2FrEntryA 11}

pktSwchSnaPULlc2FrDLCIA OBJECT-TYPE
    SYNTAX Integer32
    MAX-ACCESS  read-only
    STATUS  current
    DESCRIPTION
"The SPS Frame Relay DLCI Number which this LLC2 Protocol Interface is associated with."
    ::= {pktSwchSnaPULlc2FrEntryA 12}

pktSwchSnaPULlc2FrXIDInitiationA OBJECT-TYPE
    SYNTAX  INTEGER{
	notInitiate(1),
	initiate(2)
	}
    MAX-ACCESS  read-only
    STATUS  current
    DESCRIPTION
 "This parameter is not applicable for PU with Local XID handling.
 Legal values:
 1 - Do not initiate an XID message.
 2 - Initiate an XID message to LLC2."
	::= { pktSwchSnaPULlc2FrEntryA 13}

pktSwchSnaPULlc2FrN2CountA OBJECT-TYPE
    SYNTAX  Integer32 (1..99999)
    MAX-ACCESS  read-only
    STATUS  current
    DESCRIPTION
    "N2 Count"
	::= { pktSwchSnaPULlc2FrEntryA 14}

pktSwchSnaPULlc2FrT1TimerA OBJECT-TYPE
    SYNTAX  Integer32  (1..99999)
    MAX-ACCESS  read-only
    STATUS  current
    DESCRIPTION
    "T1 Timer in 1/10 of a second."
	::= { pktSwchSnaPULlc2FrEntryA 15}

pktSwchSnaPULlc2FrTiTimerA OBJECT-TYPE
    SYNTAX  Integer32  (1..99999)
    MAX-ACCESS  read-only
    STATUS  current
    DESCRIPTION
    "TI Timer in seconds"
	::= { pktSwchSnaPULlc2FrEntryA 16}


pktSwchSnaPULlc2FrStatTable   OBJECT-TYPE
    SYNTAX  SEQUENCE  OF PktSwchSnaPULlc2FrStatEntry
    MAX-ACCESS  not-accessible
    STATUS  current
    DESCRIPTION
	"Shows link statistics for PUs running on an LLC2 link "
     ::=  { pktSwchSna 13 }

pktSwchSnaPULlc2FrStatEntry OBJECT-TYPE
    SYNTAX  PktSwchSnaPULlc2FrStatEntry
    MAX-ACCESS  not-accessible
    STATUS  current
    DESCRIPTION
	"Shows statistics for PU LLC2 Protocol Interface over Frame Relay Protocol using RFC 1490."
    INDEX   {pktSwchSnaPULlc2FrStatNumber ,
             pktSwchSnaPULlc2FrStatSide} ::= { pktSwchSnaPULlc2FrStatTable 1 }

PktSwchSnaPULlc2FrStatEntry ::= SEQUENCE {
pktSwchSnaPULlc2FrStatNumber
Integer32,
pktSwchSnaPULlc2FrStatSide
INTEGER,
pktSwchSnaPULlc2FrStatOctetsIn
Counter32,
pktSwchSnaPULlc2FrStatOctetsOut
Counter32,
pktSwchSnaPULlc2FrStatIFramesIn
Counter32,
pktSwchSnaPULlc2FrStatIFramesOut
Counter32,
pktSwchSnaPULlc2FrStatRRFramesIn
Counter32,
pktSwchSnaPULlc2FrStatRRFramesOut
Counter32,
pktSwchSnaPULlc2FrStatRNRFramesIn
Counter32,
pktSwchSnaPULlc2FrStatRNRFramesOut
Counter32,
pktSwchSnaPULlc2FrStatXIDsIn
Counter32,
pktSwchSnaPULlc2FrStatXIDsOut
Counter32,
pktSwchSnaPULlc2FrStatTESTsIn
Counter32,
pktSwchSnaPULlc2FrStatTESTsOut
Counter32,
pktSwchSnaPULlc2FrStatREJsIn
Counter32,
pktSwchSnaPULlc2FrStatREJsOut
Counter32,
pktSwchSnaPULlc2FrStatFRMRsIn
Counter32,
pktSwchSnaPULlc2FrStatFRMRsOut
Counter32,
pktSwchSnaPULlc2FrStatDISCsIn
Counter32,
pktSwchSnaPULlc2FrStatDISCsOut
Counter32,
pktSwchSnaPULlc2FrStatUAsIn
Counter32,
pktSwchSnaPULlc2FrStatUAsOut
Counter32,
pktSwchSnaPULlc2FrStatDMsIn
Counter32,
pktSwchSnaPULlc2FrStatDMsOut
Counter32,
pktSwchSnaPULlc2FrStatSABMEsIn
Counter32,
pktSwchSnaPULlc2FrStatSABMEsOut
Counter32,
pktSwchSnaPULlc2FrStatRetransmitsIn
Counter32,
pktSwchSnaPULlc2FrStatRetransmitsOut
Counter32,
pktSwchSnaPULlc2FrStatUpperState
INTEGER,
pktSwchSnaPULlc2FrStatLowerState
INTEGER,
pktSwchSnaPULlc2FrStatNRMStatus
INTEGER,
pktSwchSnaPULlc2FrStatFlowCtlStatus
INTEGER
}
pktSwchSnaPULlc2FrStatNumber OBJECT-TYPE
    SYNTAX Integer32
    MAX-ACCESS  read-only
    STATUS  current
    DESCRIPTION
"Unique Identifier for this PU. The value in this field is used as a common Key in both this table and the Main PU table. "
    ::= {pktSwchSnaPULlc2FrStatEntry 1 }

pktSwchSnaPULlc2FrStatSide OBJECT-TYPE
    SYNTAX INTEGER {
	    sideA(1),
	    sideB(2)
	    }
    MAX-ACCESS  read-only
    STATUS  current
    DESCRIPTION
"Indicates for each side (SIDE-A and SIDE-B) if the Protocol Interface for that side has been defined or not. "
    ::= {pktSwchSnaPULlc2FrStatEntry 2}

pktSwchSnaPULlc2FrStatOctetsIn OBJECT-TYPE
 SYNTAX Counter32
 MAX-ACCESS  read-only
 STATUS  current
 DESCRIPTION
    ""
	::= { pktSwchSnaPULlc2FrStatEntry 3}

pktSwchSnaPULlc2FrStatOctetsOut OBJECT-TYPE
 SYNTAX Counter32
 MAX-ACCESS  read-only
 STATUS  current
 DESCRIPTION
    ""
	::= { pktSwchSnaPULlc2FrStatEntry 4}

pktSwchSnaPULlc2FrStatIFramesIn OBJECT-TYPE
 SYNTAX Counter32
 MAX-ACCESS  read-only
 STATUS  current
 DESCRIPTION
    ""
	::= { pktSwchSnaPULlc2FrStatEntry 5}

pktSwchSnaPULlc2FrStatIFramesOut OBJECT-TYPE
 SYNTAX Counter32
 MAX-ACCESS  read-only
 STATUS  current
 DESCRIPTION
    ""
	::= { pktSwchSnaPULlc2FrStatEntry 6}

pktSwchSnaPULlc2FrStatRRFramesIn OBJECT-TYPE
 SYNTAX Counter32
 MAX-ACCESS  read-only
 STATUS  current
 DESCRIPTION
    ""
	::= { pktSwchSnaPULlc2FrStatEntry 7}

pktSwchSnaPULlc2FrStatRRFramesOut OBJECT-TYPE
 SYNTAX Counter32
 MAX-ACCESS  read-only
 STATUS  current
 DESCRIPTION
    ""
	::= { pktSwchSnaPULlc2FrStatEntry 8}

pktSwchSnaPULlc2FrStatRNRFramesIn OBJECT-TYPE
 SYNTAX Counter32
 MAX-ACCESS  read-only
 STATUS  current
 DESCRIPTION
    ""
	::= { pktSwchSnaPULlc2FrStatEntry 9}

pktSwchSnaPULlc2FrStatRNRFramesOut OBJECT-TYPE
 SYNTAX Counter32
 MAX-ACCESS  read-only
 STATUS  current
 DESCRIPTION
    ""
	::= { pktSwchSnaPULlc2FrStatEntry 10}

pktSwchSnaPULlc2FrStatXIDsIn OBJECT-TYPE
 SYNTAX Counter32
 MAX-ACCESS  read-only
 STATUS  current
 DESCRIPTION
    ""
	::= { pktSwchSnaPULlc2FrStatEntry 11}

pktSwchSnaPULlc2FrStatXIDsOut OBJECT-TYPE
 SYNTAX Counter32
 MAX-ACCESS  read-only
 STATUS  current
 DESCRIPTION
    ""
	::= { pktSwchSnaPULlc2FrStatEntry 12}

pktSwchSnaPULlc2FrStatTESTsIn OBJECT-TYPE
 SYNTAX Counter32
 MAX-ACCESS  read-only
 STATUS  current
 DESCRIPTION
    ""
	::= { pktSwchSnaPULlc2FrStatEntry 13}

pktSwchSnaPULlc2FrStatTESTsOut OBJECT-TYPE
 SYNTAX Counter32
 MAX-ACCESS  read-only
 STATUS  current
 DESCRIPTION
    ""
	::= { pktSwchSnaPULlc2FrStatEntry 14}

pktSwchSnaPULlc2FrStatREJsIn OBJECT-TYPE
 SYNTAX Counter32
 MAX-ACCESS  read-only
 STATUS  current
 DESCRIPTION
    ""
	::= { pktSwchSnaPULlc2FrStatEntry 15}

pktSwchSnaPULlc2FrStatREJsOut OBJECT-TYPE
 SYNTAX Counter32
 MAX-ACCESS  read-only
 STATUS  current
 DESCRIPTION
    ""
	::= { pktSwchSnaPULlc2FrStatEntry 16}

pktSwchSnaPULlc2FrStatFRMRsIn OBJECT-TYPE
 SYNTAX Counter32
 MAX-ACCESS  read-only
 STATUS  current
 DESCRIPTION
    ""
	::= { pktSwchSnaPULlc2FrStatEntry 17}

pktSwchSnaPULlc2FrStatFRMRsOut OBJECT-TYPE
 SYNTAX Counter32
 MAX-ACCESS  read-only
 STATUS  current
 DESCRIPTION
    ""
	::= { pktSwchSnaPULlc2FrStatEntry 18}

pktSwchSnaPULlc2FrStatDISCsIn OBJECT-TYPE
 SYNTAX Counter32
 MAX-ACCESS  read-only
 STATUS  current
 DESCRIPTION
    ""
	::= { pktSwchSnaPULlc2FrStatEntry 19}

pktSwchSnaPULlc2FrStatDISCsOut OBJECT-TYPE
 SYNTAX Counter32
 MAX-ACCESS  read-only
 STATUS  current
 DESCRIPTION
    ""
	::= { pktSwchSnaPULlc2FrStatEntry 20}

pktSwchSnaPULlc2FrStatUAsIn OBJECT-TYPE
 SYNTAX Counter32
 MAX-ACCESS  read-only
 STATUS  current
 DESCRIPTION
    ""
	::= { pktSwchSnaPULlc2FrStatEntry 21}

pktSwchSnaPULlc2FrStatUAsOut OBJECT-TYPE
 SYNTAX Counter32
 MAX-ACCESS  read-only
 STATUS  current
 DESCRIPTION
    ""
	::= { pktSwchSnaPULlc2FrStatEntry 22}

pktSwchSnaPULlc2FrStatDMsIn OBJECT-TYPE
 SYNTAX Counter32
 MAX-ACCESS  read-only
 STATUS  current
 DESCRIPTION
    ""
	::= { pktSwchSnaPULlc2FrStatEntry 23}

pktSwchSnaPULlc2FrStatDMsOut OBJECT-TYPE
 SYNTAX Counter32
 MAX-ACCESS  read-only
 STATUS  current
 DESCRIPTION
    ""
	::= { pktSwchSnaPULlc2FrStatEntry 24}

pktSwchSnaPULlc2FrStatSABMEsIn OBJECT-TYPE
 SYNTAX Counter32
 MAX-ACCESS  read-only
 STATUS  current
 DESCRIPTION
    ""
	::= { pktSwchSnaPULlc2FrStatEntry 25}

pktSwchSnaPULlc2FrStatSABMEsOut OBJECT-TYPE
 SYNTAX Counter32
 MAX-ACCESS  read-only
 STATUS  current
 DESCRIPTION
    ""
	::= { pktSwchSnaPULlc2FrStatEntry 26}

pktSwchSnaPULlc2FrStatRetransmitsIn OBJECT-TYPE
 SYNTAX Counter32
 MAX-ACCESS  read-only
 STATUS  current
 DESCRIPTION
    ""
	::= { pktSwchSnaPULlc2FrStatEntry 27}

pktSwchSnaPULlc2FrStatRetransmitsOut OBJECT-TYPE
 SYNTAX Counter32
 MAX-ACCESS  read-only
 STATUS  current
 DESCRIPTION
    ""
	::= { pktSwchSnaPULlc2FrStatEntry 28}

pktSwchSnaPULlc2FrStatUpperState  OBJECT-TYPE
 SYNTAX INTEGER {
    unbound(1),
    bindPending(2),
    unbindPend(3),
    idle(4),
    unattached(5),
    attachPend(6),
    detachPend(7),
    udqosPending(8),
    outconPend(9),
    inconPending(10),
    connResPend(11),
    dataxfer(12),
    userResetPend(13),
    provRstPend(14),
    rstResPend(15),
    discon8Pend(16),
    discon9Pend(17),
    discon11Pend(18),
    discon12Pend(19),
    discon13Pend(20),
    subsBindPend(21),
    noChange(22)
	}
 MAX-ACCESS read-only
 STATUS current
 DESCRIPTION
    "The internal DLPI state of the connection."
	::= { pktSwchSnaPULlc2FrStatEntry 29}

pktSwchSnaPULlc2FrStatLowerState  OBJECT-TYPE
 SYNTAX INTEGER  {
    linkClosed(1),
    disconnected(2),
    linkOpening(3),
    disconnecting(4),
    frmrSent(5),
    linkOpened(6),
    localBusy(7),
    rejection(8),
    checkpointing(9),
    cpLocalBusy(10),
    cpRejection(11),
    resetting(12),
    remoteBusy(13),
    lBusyRBusy(14),
    rejLBusy(15),
    rejRBusy(16),
    cpRejLBusy(17),
    cpClearing(18),
    cpRejClr(19),
    rejLbusyRbusy(20),
    frmrReceived(21),
    programError(22),
    noChange(23)
	}
 MAX-ACCESS read-only
 STATUS current
 DESCRIPTION
    "The internal Llc2Fr state of the connection."
	::= { pktSwchSnaPULlc2FrStatEntry 30}

pktSwchSnaPULlc2FrStatNRMStatus OBJECT-TYPE
 SYNTAX INTEGER	 {sync(1),notSync(2)}
 MAX-ACCESS  read-only
 STATUS  current
 DESCRIPTION
    "This variable indicates if the link is in Normal Response Mode or not."
	::= { pktSwchSnaPULlc2FrStatEntry 31}

pktSwchSnaPULlc2FrStatFlowCtlStatus OBJECT-TYPE
 SYNTAX INTEGER	 {noRNR(1),txFlow(2), rxFlow(3), rxAndTx(4)}
 MAX-ACCESS  read-only
 STATUS  current
 DESCRIPTION
    "This variable indicates the flow control status of the PU interface."
	::= { pktSwchSnaPULlc2FrStatEntry 32}


pktSwchSnaGlobal  OBJECT IDENTIFIER ::= { pktSwchSna 14 }

pktSwchSnaGlobalSrcMacAddrS OBJECT-TYPE
  SYNTAX OCTET STRING (SIZE(6))
  MAX-ACCESS read-write
  STATUS current
  DESCRIPTION
  "LLC2 source MAC address used for all LLC2\RFC1490 protocol interfaces,
   Scratch variable. Format: XX XX XX XX XX XX"
 ::= {pktSwchSnaGlobal 1}

pktSwchSnaGlobalSrcMacAddrA OBJECT-TYPE
  SYNTAX OCTET STRING (SIZE(6))
  MAX-ACCESS read-only
  STATUS current
  DESCRIPTION
  "LLC2 source MAC address used for all LLC2\RFC1490 protocol interfaces,
   Active variable. Format: XX XX XX XX XX XX"
 ::= {pktSwchSnaGlobal 2}


pktSwchSnaGlobalDefFrLlc2LinkS OBJECT-TYPE
    SYNTAX  Integer32
    MAX-ACCESS  read-write
    STATUS  current
    DESCRIPTION
    "The FR Link to where a mac frame will be routed when the destination
     MAC address of the frame does not match the SPS source mac address."
         ::= {pktSwchSnaGlobal 3}

pktSwchSnaGlobalDefFrLlc2LinkA OBJECT-TYPE
    SYNTAX  Integer32
    MAX-ACCESS  read-only
    STATUS  current
    DESCRIPTION
    "The FR Link to where a mac frame will be routed when the destination
     MAC address of the frame does not match the SPS source mac address."
         ::= {pktSwchSnaGlobal 4}

pktSwchSnaGlobalDefFrLlc2DlciS OBJECT-TYPE
    SYNTAX  Integer32
    MAX-ACCESS  read-write
    STATUS  current
    DESCRIPTION
    "The FR DLCI to where a mac frame will be routed when the destination
     MAC address of the frame does not match the SPS source mac address.
     DLCI range is 16..991."
         ::= {pktSwchSnaGlobal 5}

pktSwchSnaGlobalDefFrLlc2DlciA OBJECT-TYPE
    SYNTAX  Integer32
    MAX-ACCESS  read-only
    STATUS  current
    DESCRIPTION
    "The FR DLCI to where a mac frame will be routed when the destination
     MAC address of the frame does not match the SPS source mac address.
     DLCI range is 16..991."
         ::= {pktSwchSnaGlobal 6}

pktSwchSnaGlobalMaxPus OBJECT-TYPE
    SYNTAX  Integer32
    MAX-ACCESS  read-only
    STATUS  current
    DESCRIPTION
    "The maximum number of PUs that can be defined on this device. "
         ::= {pktSwchSnaGlobal 7}

pktSwchSnaGlobalStatus OBJECT-TYPE
    SYNTAX  INTEGER {
       valid(1),
       underCreation(3)
     }
    MAX-ACCESS  read-write
    STATUS  current
    DESCRIPTION
    "The status of this SNA Global entry.
     Used for saving the mac address, llc2 port, and dlci. "
         ::= {pktSwchSnaGlobal 8}

pktSwchEthernet    OBJECT IDENTIFIER ::= { radPS 12}

pktSwchEthernetLinkTable    OBJECT-TYPE
    SYNTAX  SEQUENCE  OF PktSwchEthernetLinkEntry
    MAX-ACCESS  not-accessible
    STATUS  current
    DESCRIPTION
        "The Ethernet link table defines the parameters in the PS
         Ethernet links."
     ::=  { pktSwchEthernet 1 }

pktSwchEthernetLinkEntry OBJECT-TYPE
    SYNTAX  PktSwchEthernetLinkEntry
    MAX-ACCESS  not-accessible
    STATUS  current
    DESCRIPTION
        "The Ethernet Link Entry defines the contents of each link in the
         Ethernet Link Table."
    INDEX   {ifIndex }
    ::=  { pktSwchEthernetLinkTable 1 }

PktSwchEthernetLinkEntry ::= SEQUENCE {
pktSwchEthernetLinkOperationMode
INTEGER,
pktSwchEthernetLinkUserDefMacAddr
OCTET STRING,
pktSwchEthernetLinkPointToPointDest
DisplayString,
pktSwchEthernetLinkTotalFramesIn
Counter32,
pktSwchEthernetLinkTotalFramesOut
Counter32,
pktSwchEthernetLinkIpFramesIn
Counter32,
pktSwchEthernetLinkIpFramesOut
Counter32,
pktSwchEthernetLinkLlc2FramesIn
Counter32,
pktSwchEthernetLinkLlc2FramesOut
Counter32,
pktSwchEthernetLinkBridgFramesIn
Counter32,
pktSwchEthernetLinkBridgFramesOut
Counter32,
pktSwchEthernetLinkDiscardedByFilter
Counter32
     }

pktSwchEthernetLinkOperationMode  OBJECT-TYPE
    SYNTAX INTEGER{
        bridging         (3),
        ip               (4),
        ip-and-bridging  (7),
        llc              (8),
        llc-and-bridging (11),
        ip-and-llc       (12),
        all              (15),
        none             (255) -- disabled
	       }
    MAX-ACCESS  read-write
    STATUS  current
    DESCRIPTION
        "This parameter shows the frame handling mode on this link.

         When IP mode is defined, the IP frames received on this link
         are handled and routed by the IP module in the PS.
         If IP mode is disabled, the IP frames will not be handled by the
         IP module and will be handled as bridged data.

         When Bridging mode is enabled, the PS will perform bridging from
         this link according to the bridging configuration. If disabled,
         bridge data will be ignored.

         When LLC is enabled, frames received on this link are handled by
         the LLC module in the PS. If disabled, the LLC frames will be
         treated as bridged data.

         Any combination of bridging, ip and LLC is allowed. If both IP
         and LLC are enabled, LLC frames will be handled by the LLC module,
         IP frames will be handled by the IP module, and all the other frames
         will treated as bridged data. If the bridge mode is disabled, the
         other frames will be discarded."

    ::= { pktSwchEthernetLinkEntry 1 }


pktSwchEthernetLinkUserDefMacAddr  OBJECT-TYPE
    SYNTAX OCTET STRING (SIZE(6))
    MAX-ACCESS read-write
    STATUS current
    DESCRIPTION
        "This parameter allows the user to define a different MAC address
         for this link other than the device MAC address.
         Possible values:
         6 sets of 2 Hexadecimal digits with
         spaces between them (XX XX XX XX XX XX) "
        ::= { pktSwchEthernetLinkEntry 2 }

pktSwchEthernetLinkPointToPointDest  OBJECT-TYPE
    SYNTAX DisplayString
    MAX-ACCESS read-write
    STATUS current
    DESCRIPTION
    "Destination of the frames which are received on this link.
     Possible values:
     X.25 PVC:       Port:LCN
     X.25 SVC:       X.25 Addr or 'cid' followed by a predefined Call ID
                     number.
     Frame Relay:    Port:DLCI
     No Destination: None

     If no destination, frames will be forwarded according to the
     filter table in 1st priority. If no filter match, the frames will be
     forwarded according to dynamic learning.

     Default value: None"
     ::={ pktSwchEthernetLinkEntry 3 }

pktSwchEthernetLinkTotalFramesIn     OBJECT-TYPE
    SYNTAX Counter32
    MAX-ACCESS read-only
    STATUS current
    DESCRIPTION
    "Total number of frames which were received on this link."
     ::={ pktSwchEthernetLinkEntry 4 }

pktSwchEthernetLinkTotalFramesOut     OBJECT-TYPE
    SYNTAX Counter32
    MAX-ACCESS read-only
    STATUS current
    DESCRIPTION
    "Total number of frames which were transmitted from this link."
     ::={ pktSwchEthernetLinkEntry 5 }

pktSwchEthernetLinkIpFramesIn     OBJECT-TYPE
    SYNTAX Counter32
    MAX-ACCESS read-only
    STATUS current
    DESCRIPTION
    "Number of IP frames which were received on this link."
     ::={ pktSwchEthernetLinkEntry 6 }

pktSwchEthernetLinkIpFramesOut     OBJECT-TYPE
    SYNTAX Counter32
    MAX-ACCESS read-only
    STATUS current
    DESCRIPTION
    "Number of IP frames which were transmitted from this link."
     ::={ pktSwchEthernetLinkEntry 7 }


pktSwchEthernetLinkLlc2FramesIn     OBJECT-TYPE
    SYNTAX Counter32
    MAX-ACCESS read-only
    STATUS current
    DESCRIPTION
    "Number of LLC2 frames which were received on this link."
     ::={ pktSwchEthernetLinkEntry 8 }

pktSwchEthernetLinkLlc2FramesOut     OBJECT-TYPE
    SYNTAX Counter32
    MAX-ACCESS read-only
    STATUS current
    DESCRIPTION
    "Number of LLC2 frames which were transmitted from this link."
     ::={ pktSwchEthernetLinkEntry 9 }

pktSwchEthernetLinkBridgFramesIn     OBJECT-TYPE
    SYNTAX Counter32
    MAX-ACCESS read-only
    STATUS current
    DESCRIPTION
    "Number of Bridged frames which were received on this link."
     ::={ pktSwchEthernetLinkEntry 10 }

pktSwchEthernetLinkBridgFramesOut     OBJECT-TYPE
    SYNTAX Counter32
    MAX-ACCESS read-only
    STATUS current
    DESCRIPTION
    "Number of Bridged frames which were transmitted from this link."
     ::={ pktSwchEthernetLinkEntry 11 }

pktSwchEthernetLinkDiscardedByFilter     OBJECT-TYPE
    SYNTAX Counter32
    MAX-ACCESS read-only
    STATUS current
    DESCRIPTION
    "Number of Bridged frames which were received on this link."
     ::={ pktSwchEthernetLinkEntry 12 }


pktSwchEthernetFilterTable    OBJECT-TYPE
    SYNTAX  SEQUENCE  OF PktSwchEthernetFilterEntry
    MAX-ACCESS  not-accessible
    STATUS  current
    DESCRIPTION
        "The Ethernet filter table defines the frame filtering and
         routing through the PS Ethernet links."
     ::=  { pktSwchEthernet 2 }

pktSwchEthernetFilterEntry OBJECT-TYPE
    SYNTAX  PktSwchEthernetFilterEntry
    MAX-ACCESS  not-accessible
    STATUS  current
    DESCRIPTION
        "The Ethernet Filter Entry defines the filtering on each Ethernet
         link. The filter entry is operational only if Bridging Handling
         is enabled and there is no point to point destination configured
         for this link. If there is a point to point destination configured,
         the frames will be directed to this destination."
    INDEX   {ifIndex, pktSwchEthernetFilterId}
    ::=  { pktSwchEthernetFilterTable 1 }

PktSwchEthernetFilterEntry ::= SEQUENCE {
pktSwchEthernetFilterId
Integer32,
pktSwchEthernetFilterMacAddr
OCTET STRING,
pktSwchEthernetFilterProtType
INTEGER,
pktSwchEthernetFilterDest
DisplayString,
pktSwchEthernetFilterStatus
INTEGER
     }

pktSwchEthernetFilterId  OBJECT-TYPE
    SYNTAX   Integer32 (1..10)
    MAX-ACCESS  read-only
    STATUS  current
    DESCRIPTION
        "Identification Number of an entry in the filter table.
         The ID together with the ifindex define an entry."
    ::= { pktSwchEthernetFilterEntry 1 }

pktSwchEthernetFilterMacAddr  OBJECT-TYPE
    SYNTAX OCTET STRING (SIZE(6))
    MAX-ACCESS read-write
    STATUS current
    DESCRIPTION
        "This parameter defines the MAC address in the current entry
         of the filter table.
         The MAC address in the filter table is compared with the MAC
         address in the received frame. If the MAC address and protocol
         type of the frame are equal to the values in the filter table,
         the frame will be directed to the destination address specified
         in the filter table.

         Possible values:
         MAC Address : 6 sets of 2 Hexadecimal digits with
                       spaces between them (XX XX XX XX XX XX)
         Broadcasting: FF FF FF FF FF FF
         Don't Care  : 00 00 00 00 00 00

         For Broadcasting:
         If a broadcasting entry contains a destination, the frame will
         not be broadcasted. It will be directed to the destination in this
         entry.

         For Don't care:
         The MAC address in the frame and in the filter table are not compared.
         The frames will be directed to the destination specified in the
         filter table if there is a match between the protocol types in the
         frame and in the filter table.

         Default value: 00 00 00 00 00 00 "
    ::= { pktSwchEthernetFilterEntry 2 }

pktSwchEthernetFilterProtType OBJECT-TYPE
    SYNTAX INTEGER{
        llc       (256),
        ip        (2048),
        arp       (2054),
        appleTalk (32923),
        dontCare  (65535)
	       }
    MAX-ACCESS  read-write
    STATUS  current
    DESCRIPTION
        "The protocol type which is compared with the protocol type
         in the received frame. Each protocol in the IP frame is assigned
         16 bits (see RFC1700.txt on the assignment of protocol parameters
         for the Internet protocol suite.).

         If 65535 is entered for the protocol, it means Don't Care.

         If there is a match between this protocol and the protocol in
         the received frame and a match in the MAC addresses, the frame
         will be directed to the destination specified in this table.

         Default value: dontCare (65535)."
    ::= { pktSwchEthernetFilterEntry 3}

pktSwchEthernetFilterDest OBJECT-TYPE
    SYNTAX DisplayString
    MAX-ACCESS read-write
    STATUS current
    DESCRIPTION
        "Destination of the frames which match this current entry.
         The match is in the MAC address and protocol.

         Possible values:
         X.25 PVC:     Port:LCN
         X.25 SVC:     X.25 Addr or 'cid' followed by a predefined Call ID number
         Frame Relay:  Port:DLCI
         No Destination: None

         If No Destination, the frames will be discarded.

         Default value: None ."

        ::={ pktSwchEthernetFilterEntry 4}

pktSwchEthernetFilterStatus OBJECT-TYPE
    SYNTAX  INTEGER {
       valid(1),
       createRequest(2),
       underCreation(3),
       invalid(4)
     }
    MAX-ACCESS  read-write
    STATUS  current
    DESCRIPTION
    "The status of this filter table entry.
     valid         - This entry was saved.
     createRequest - Request to create a new entry.
     underCreation - For a new/updated entry.
     invalid       - Entry is deleted."
         ::= {pktSwchEthernetFilterEntry 5}


pktSwchEthernetBridging    OBJECT IDENTIFIER ::=  { pktSwchEthernet 3 }

pktSwchEthernetBridgingWanToWan OBJECT-TYPE
    SYNTAX INTEGER{
        disable (2),
        enable  (3)
	       }
    MAX-ACCESS  read-write
    STATUS  current
    DESCRIPTION
    "Enable/Disable Ethernet Bridging, WAN to WAN."
         ::= {pktSwchEthernetBridging 1}

pktSwchEthernetBridgingTimer OBJECT-TYPE
    SYNTAX   Integer32 (0..255)
    MAX-ACCESS  read-write
    STATUS  current
    DESCRIPTION
    "Timer used for WAN to WAN communication in order to prevent broadcast
     frames looping forever between devices. When the timer expires,
     the frames are discarded.

     Possible values:
          0 - No timer is used.
     1..255 - Timer value in units of 100 mili sec."
         ::= {pktSwchEthernetBridging 2}

pktSwchEthernetBridgingStatus OBJECT-TYPE
    SYNTAX  INTEGER {
       valid(1),
       underCreation(3)
     }
    MAX-ACCESS  read-write
    STATUS  current
    DESCRIPTION
    "The status of the Ethernet Bridging Parameters.
     valid         - This table was saved.
     underCreation - The table was updated and not yet saved."
         ::= {pktSwchEthernetBridging 3}


pktSwchEthernetBroadcastDestTable    OBJECT-TYPE
    SYNTAX  SEQUENCE  OF PktSwchEthernetBroadcastDestEntry
    MAX-ACCESS  not-accessible
    STATUS  current
    DESCRIPTION
    "The Ethernet Broadcast Destination table defines all the Bridging
     destinations of the PS. Each Broadcasted frame will be
     broadcasted to all these destinations."
     ::=  { pktSwchEthernet 4 }


pktSwchEthernetBroadcastDestEntry OBJECT-TYPE
    SYNTAX  PktSwchEthernetBroadcastDestEntry
    MAX-ACCESS  not-accessible
    STATUS  current
    DESCRIPTION
        "The Ethernet Broadcast Entry defines destinations for Ethernet
         bridge data."
    INDEX   {pktSwchEthernetBroadcastDestProtocol,
             pktSwchEthernetBroadcastDestId}
    ::=  { pktSwchEthernetBroadcastDestTable 1 }

PktSwchEthernetBroadcastDestEntry ::= SEQUENCE {
pktSwchEthernetBroadcastDestProtocol
INTEGER,
pktSwchEthernetBroadcastDestId
Integer32,
pktSwchEthernetBroadcastDestDestination
DisplayString,
pktSwchEthernetBroadcastDestStatus
INTEGER
     }

pktSwchEthernetBroadcastDestProtocol  OBJECT-TYPE
    SYNTAX INTEGER{
        x25        (2),
        frameRelay (3)
	       }
    MAX-ACCESS  read-only
    STATUS  current
    DESCRIPTION
        "The protocol of the Broadcasted frames."
    ::= { pktSwchEthernetBroadcastDestEntry 1 }

pktSwchEthernetBroadcastDestId  OBJECT-TYPE
    SYNTAX   Integer32 (1..10)
    MAX-ACCESS  read-only
    STATUS  current
    DESCRIPTION
        "Identification Number of an entry in the Ethernet Broadcast
         Destination table."
    ::= { pktSwchEthernetBroadcastDestEntry 2 }

pktSwchEthernetBroadcastDestDestination OBJECT-TYPE
    SYNTAX DisplayString
    MAX-ACCESS read-write
    STATUS current
    DESCRIPTION
        "Destination for the Ethernet frames.

         Possible values for X25:
         X.25 PVC:     Port:LCN
         X.25 SVC:     X.25 Addr or 'cid' followed by a predefined Call ID number

         Possible values for fr:
         Frame Relay:  Port:DLCI

         No Destination: None"
        ::={ pktSwchEthernetBroadcastDestEntry 3}

pktSwchEthernetBroadcastDestStatus OBJECT-TYPE
    SYNTAX  INTEGER {
       valid(1),
       createRequest(2),
       underCreation(3),
       invalid(4)
     }
    MAX-ACCESS  read-write
    STATUS  current
    DESCRIPTION
    "The status of this Ethernet Destination table entry.
     valid         - This entry was saved.
     createRequest - Request to create a new entry.
     underCreation - For a new/updated entry.
     invalid       - Entry is deleted."
         ::= {pktSwchEthernetBroadcastDestEntry 4}


pktSwchIp       OBJECT IDENTIFIER ::= { radPS 13}

pktSwchIpGlobal OBJECT IDENTIFIER ::=  { pktSwchIp 1 }

pktSwchIpGlobalMaxHopCount OBJECT-TYPE
    SYNTAX   Integer32 (5..65000)
    MAX-ACCESS  read-write
    STATUS  current
    DESCRIPTION
    "Maximum no. of hops the device will support.
     The default value is 15. Legal values: 5 to 65000."
         ::= {pktSwchIpGlobal 1}

pktSwchIpIntervalBetweenUpdates OBJECT-TYPE
    SYNTAX   Integer32 (30..2550)
    MAX-ACCESS  read-write
    STATUS  current
    DESCRIPTION
    "The time in seconds from one update of the device's dynamic routing
     table to the next update. The time is in steps of 10 seconds.
     Default value: 30
     Legal values: 30,40,50 ... 2550"
         ::= {pktSwchIpGlobal 2}

pktSwchIpGlobalStatus OBJECT-TYPE
    SYNTAX  INTEGER {
       valid(1),
       underCreation(3)
     }
    MAX-ACCESS  read-write
    STATUS  current
    DESCRIPTION
    "The status of this IP Global entry.
     Used for saving the IP Global parameters. "
         ::= {pktSwchIpGlobal 3}

pktSwchIpInterfaceTable    OBJECT-TYPE
    SYNTAX  SEQUENCE  OF PktSwchIpInterfaceEntry
    MAX-ACCESS  not-accessible
    STATUS  current
    DESCRIPTION
        "The Ip interface table defines the Ip interfaces and their
         parameters in the PS device."
     ::=  { pktSwchIp 2 }

pktSwchIpInterfaceEntry OBJECT-TYPE
    SYNTAX  PktSwchIpInterfaceEntry
    MAX-ACCESS  not-accessible
    STATUS  current
    DESCRIPTION
        "The IP interface Entry defines the IP configuration parameters
         for each IP interface."
    INDEX   {pktSwchIpInterfaceId}
    ::=  { pktSwchIpInterfaceTable 1 }

PktSwchIpInterfaceEntry ::= SEQUENCE {
pktSwchIpInterfaceId
Integer32,
pktSwchIpInterfaceAddress
IpAddress,
pktSwchIpInterfaceAddressMask
IpAddress,
pktSwchIpInterfaceSendDefRoutMsgOnly
INTEGER,
pktSwchIpInterfaceDest
DisplayString,
pktSwchIpInterfaceInactivity
Integer32,
pktSwchIpInterfaceLinkCost
Integer32,
pktSwchIpInterfaceOptions
INTEGER,
pktSwchIpInterfaceStatus
INTEGER,
pktSwchIpInterfaceRxFrames
Counter32,
pktSwchIpInterfaceRxExpiredTtl
Counter32,
pktSwchIpInterfaceRxUnknownDest
Counter32,
pktSwchIpInterfaceTxFrames
Counter32,
pktSwchIpInterfaceTxQueueBufs
Counter32,
pktSwchIpInterfaceTxDiscarded
Counter32,
pktSwchIpInterfaceRipRxFrames
Counter32,
pktSwchIpInterfaceRipTxFrames
Counter32,
pktSwchIpInterfaceRipWaitingMsgs
Counter32
     }

pktSwchIpInterfaceId  OBJECT-TYPE
    SYNTAX   Integer32 (1..200)
    MAX-ACCESS  read-only
    STATUS  current
    DESCRIPTION
        "Identification Number of an entry in the IP interface table."
    ::= { pktSwchIpInterfaceEntry 1 }

pktSwchIpInterfaceAddress  OBJECT-TYPE
    SYNTAX  IpAddress
    MAX-ACCESS read-write
    STATUS current
    DESCRIPTION
        "The IP address of the interface. Legal input: any legal IP address.
         Default value: 0.0.0.0 "
    ::= { pktSwchIpInterfaceEntry 2 }

pktSwchIpInterfaceAddressMask OBJECT-TYPE
    SYNTAX  IpAddress
    MAX-ACCESS  read-write
    STATUS  current
    DESCRIPTION
        "The IP mask of the interface. Legal input: any legal IP mask:
         A string of the format X.X.X.X where every X is a number in
         the range 0-255.
         Default value: 255.255.255.255 "
    ::= { pktSwchIpInterfaceEntry 3 }

pktSwchIpInterfaceSendDefRoutMsgOnly OBJECT-TYPE
    SYNTAX  INTEGER {
       disable (2),
       enable(3)
     }
    MAX-ACCESS  read-write
    STATUS  current
    DESCRIPTION
        "Some of the RIP messages are default router messages.
         These messages inform who the default router is.

         This MIB object allows the user to configure the device so
         that it will send default router messages only.

         If sendDefaultRoutMsgOnly is set to enable, the
         device will not send any RIP messages except for default router
         messages.

         Default value: disable ."

    ::= { pktSwchIpInterfaceEntry 4 }

pktSwchIpInterfaceDest OBJECT-TYPE
    SYNTAX DisplayString
    MAX-ACCESS read-write
    STATUS current
    DESCRIPTION
        "Destination of the packets received on this interface.

         Possible values:
         X.25 PVC:       Port:LCN
         X.25 SVC:       X.25 Addr or 'cid' followed by a predefined Call ID
                         number.
         Frame Relay:    Port:DLCI
         HDLC:           'H' followed by the HDLC Port Number
         SLIP:           'S' followed by the SLIP Channel Number
         Ethernet:       'E' followed by the Ethernet Port Number
         PPP:            'P' followed by the PPP Port Number.
         Bundles(for PPP)'B' followed by the PPP Bundle Number.
         No destination:  None

         Default :       None

         Examples:
         1. For SLIP destination which is Link no. 1, the destination
            will be S100 (100 instead of 1 is for Async).
         2. For SLIP destination of APS-8, channel no. 8:
            S8
         3. For PPP destination of APS-8, Sync Link no. 1: P1
         4. For PPP destination of APS-8, Async channel on link 1: P100

         Note for PPP:
         PPP protocol is allowed to be applied on Sync Links (1-3)
         as well as Async channels (1-24).
         In the ascii terminal: If the user writes P1 for example the device
         has to check which P1 it is. Is it the async channel 1 or
         Link no. 1. The device does NOT ALLOW configuring PPP on both
         Sync Link no. 1 and async RJ45 channel 1.
         When P1 is entered by the user, the protocols on async channel 1 and sync
         link 1 are checked. As only one of them is PPP, it will apply to the
         only PPP chan/link."
         ::= { pktSwchIpInterfaceEntry 5 }

pktSwchIpInterfaceInactivity OBJECT-TYPE
    SYNTAX   Integer32 (0..255)
    MAX-ACCESS  read-write
    STATUS  current
    DESCRIPTION
        "Inactivity time in minutes before disconnecting the X25 SVC call.
         Range: 0..255. Default: 2."
        ::= { pktSwchIpInterfaceEntry 6 }

pktSwchIpInterfaceLinkCost OBJECT-TYPE
    SYNTAX   Integer32
    MAX-ACCESS  read-write
    STATUS  current
    DESCRIPTION
        "This value will be added to the value written in the
         metric field of the received frame.
         Range: 1..pktSwchIpGlobalMaxHopCount
         Default: 1."
         ::= { pktSwchIpInterfaceEntry 7 }

pktSwchIpInterfaceOptions OBJECT-TYPE
    SYNTAX  INTEGER {
             netIpAddress (2),
             none         (255)
    }
    MAX-ACCESS  read-write
    STATUS  current
    DESCRIPTION
        "When netIpAddress is selected the interface IP address
         will not be the IP address of the interface. It will be the IP
         address of the NetWork which is connected to this interface.
         This option is for an interface which does not require a
         unique IP address.
         Default is none."
        ::= { pktSwchIpInterfaceEntry 8 }

pktSwchIpInterfaceStatus OBJECT-TYPE
    SYNTAX  INTEGER {
       valid(1),
       createRequest(2),
       underCreation(3),
       invalid(4)
     }
    MAX-ACCESS  read-write
    STATUS  current
    DESCRIPTION
    "The status of this filter table entry.
     valid         - This entry was saved.
     createRequest - Request to create a new entry.
     underCreation - For a new/updated entry.
     invalid       - Entry is deleted."
        ::= { pktSwchIpInterfaceEntry 9 }

pktSwchIpInterfaceRxFrames OBJECT-TYPE
    SYNTAX  Counter32
    MAX-ACCESS  read-only
    STATUS  current
    DESCRIPTION
    "No. of frames which were received on this IP interface."
        ::= { pktSwchIpInterfaceEntry 10 }

pktSwchIpInterfaceRxExpiredTtl OBJECT-TYPE
    SYNTAX  Counter32
    MAX-ACCESS  read-only
    STATUS  current
    DESCRIPTION
    "No. of frames which were received on this IP interface
     with an Expired Time to Live value."
    ::= { pktSwchIpInterfaceEntry 11 }

pktSwchIpInterfaceRxUnknownDest OBJECT-TYPE
    SYNTAX  Counter32
    MAX-ACCESS  read-only
    STATUS  current
    DESCRIPTION
    "No. of frames which were received on this IP interface
     with an unknown IP destination. No default router is configured.
     These frames will be discarded."
    ::= { pktSwchIpInterfaceEntry 12 }

pktSwchIpInterfaceTxFrames OBJECT-TYPE
    SYNTAX  Counter32
    MAX-ACCESS  read-only
    STATUS  current
    DESCRIPTION
    "No. of frames which were Transmitted from this IP interface."
    ::= { pktSwchIpInterfaceEntry 13 }

pktSwchIpInterfaceTxQueueBufs OBJECT-TYPE
    SYNTAX  Counter32
    MAX-ACCESS  read-only
    STATUS  current
    DESCRIPTION
    "No. of buffers which are waiting in the Trasnsmit Queue. "
     ::= { pktSwchIpInterfaceEntry 14 }

pktSwchIpInterfaceTxDiscarded OBJECT-TYPE
    SYNTAX  Counter32
    MAX-ACCESS  read-only
    STATUS  current
    DESCRIPTION
    "No. of frames which were ready to be transmitted but were
     Discarded. The PS will discard frames if the transmit queue
     is too long."
     ::= { pktSwchIpInterfaceEntry 15 }

pktSwchIpInterfaceRipRxFrames OBJECT-TYPE
    SYNTAX  Counter32
    MAX-ACCESS  read-only
    STATUS  current
    DESCRIPTION
    "No. of RIP frames which were received on this IP interface."
    ::= { pktSwchIpInterfaceEntry 16 }

pktSwchIpInterfaceRipTxFrames OBJECT-TYPE
    SYNTAX  Counter32
    MAX-ACCESS  read-only
    STATUS  current
    DESCRIPTION
    "No. of RIP Frames which were transmitted from this IP interface."
    ::= { pktSwchIpInterfaceEntry 17 }

pktSwchIpInterfaceRipWaitingMsgs OBJECT-TYPE
    SYNTAX  Counter32
    MAX-ACCESS  read-only
    STATUS  current
    DESCRIPTION
    "No. of RIP messages which are waiting to be transmitted to the
     Network."
     ::= { pktSwchIpInterfaceEntry 18 }


pktSwchIsdn       OBJECT IDENTIFIER ::= { radPS 14}

--  Packet Switching devices with Integrated Services Digital Network.

pktSwchIsdnGlobal  OBJECT IDENTIFIER ::= { pktSwchIsdn 1 }

--  ISDN Global Parameters

pktSwchIsdnGlobalCallRetries OBJECT-TYPE
    SYNTAX Integer32 (0..255)
    MAX-ACCESS  read-write
    STATUS  current
    DESCRIPTION
    "Number of times the call request is repeated after failure.
     Possible values:
     0     - Disable retry mechanism
     1-255 - Number of retries
     default value: 0"
     ::= {pktSwchIsdnGlobal 1}

pktSwchIsdnGlobalCallRetryDelay OBJECT-TYPE
    SYNTAX Integer32 (5..250)
    MAX-ACCESS  read-write
    STATUS  current
    DESCRIPTION
    "Time interval between retries (in seconds).
     Possible values:
     5 - 250
     Default value: 15"
     ::= {pktSwchIsdnGlobal 2}

pktSwchIsdnGlobalCallinactivity OBJECT-TYPE
    SYNTAX Integer32 (0..65000)
    MAX-ACCESS  read-write
    STATUS  current
    DESCRIPTION
    "Time of inactivity in seconds, after which the call will be
     disconnected. An x.25 link is considered inactive when there are
     no open calls on the link. A frame relay link is considered inactive
     when there is no traffic on the link.
     Possible values:
     0 - No disconnection on inactivity.
     1 - 65000 - Time period (in seconds).
     Default value: 180"
     ::= {pktSwchIsdnGlobal 3}

pktSwchIsdnGlobalStatus OBJECT-TYPE
    SYNTAX  INTEGER {
       valid(1),
       underCreation(3)
     }
    MAX-ACCESS  read-write
    STATUS  current
    DESCRIPTION
    "The status of the Isdn Global parameters.
     Used for saving the Isdn global parameters."
         ::= {pktSwchIsdnGlobal 4}


pktSwchIsdnRoutTable    OBJECT-TYPE
    SYNTAX  SEQUENCE  OF PktSwchIsdnRoutEntry
    MAX-ACCESS  not-accessible
    STATUS  current
    DESCRIPTION
	"The Isdn Routing Table entries in the Packet Switch."
     ::=  { pktSwchIsdn 2 }

pktSwchIsdnRoutEntry OBJECT-TYPE
    SYNTAX  PktSwchIsdnRoutEntry
    MAX-ACCESS  not-accessible
    STATUS  current
    DESCRIPTION
        "Isdn Routing Entry defines the contents of each entry in the table.
         The outgoing addresses are in a different table -
         pktSwchIsdnRoutAddrTable. The row status in this
         table will be used for both tables."
         INDEX   { pktSwchIsdnRoutId }
         ::=  { pktSwchIsdnRoutTable 1 }

PktSwchIsdnRoutEntry ::=  SEQUENCE {
    pktSwchIsdnRoutId
    Integer32,
    pktSwchIsdnRoutDataBandWidth
     INTEGER,
    pktSwchIsdnRoutOptions
     INTEGER,
    pktSwchIsdnRoutStatus
     INTEGER
    }

pktSwchIsdnRoutId OBJECT-TYPE
    SYNTAX Integer32 (1..200)
        MAX-ACCESS  read-only
	STATUS  current
	DESCRIPTION
        "Number of this routing entry."
        ::= { pktSwchIsdnRoutEntry 1 }

pktSwchIsdnRoutDataBandWidth OBJECT-TYPE
    SYNTAX  INTEGER {
        bw56Kbps(2),
        bw64Kbps(3)
	}
    MAX-ACCESS  read-write
    STATUS  current
    DESCRIPTION
    "Isdn Bandwidth which will be used for the data routed via this
     entry. The ISDN interface will be configured with the speed
     which is selected.
     Possible values:
     2 - 56 Kbps.
     3 - 64 Kbps.
     Default value: 3 "
    ::= { pktSwchIsdnRoutEntry 2 }

pktSwchIsdnRoutOptions OBJECT-TYPE
    SYNTAX  INTEGER {
        noOptions(1),
        returnToMainLink(2)
	}
    MAX-ACCESS  read-write
    STATUS  current
    DESCRIPTION
    "Special Options for this routing entry.
     Possible values:
     1 - No special options.
     2 - Return to main link. This option is used when the current link
         is defined as a backup link and the main link becomes active.
     Default value: 1 "
    ::= { pktSwchIsdnRoutEntry 3 }

pktSwchIsdnRoutStatus OBJECT-TYPE
    SYNTAX  INTEGER {
       valid(1),
       createRequest(2),
       underCreation(3),
       invalid(4)
     }
    MAX-ACCESS  read-write
    STATUS  current
    DESCRIPTION
    "The status of this routing table entry + address table
     (pktSwchIsdnOutAddrTable).
     For creating a new entry select createRequest. A new route entry
     will be created together with an out address entry. There may be
     more than 1 addresses. For example, if there is 1 outgoing address
     and 2 alternatives, the new address entry will have 3 indices.
     For deleting an entry select invalid. The relevant address entry
     should be deleted too.
     For saving an entry select valid. Save should include the addresses
     of the current entry in the pktSwchIsdnOutAddrTable"
     ::= { pktSwchIsdnRoutEntry 4 }


pktSwchIsdnOutAddrTable    OBJECT-TYPE
    SYNTAX  SEQUENCE  OF PktSwchIsdnOutAddrEntry
    MAX-ACCESS  not-accessible
    STATUS  current
    DESCRIPTION
    "Outgoing ISDN addresses used by the ISDN routing table.
     The address table contains outgoing
     addresses and alternative addresses in case the connection
     to the first addresses does not succeed."
    ::=  { pktSwchIsdn 3 }

pktSwchIsdnOutAddrEntry OBJECT-TYPE
    SYNTAX  PktSwchIsdnOutAddrEntry
    MAX-ACCESS  not-accessible
    STATUS  current
    DESCRIPTION
        "Isdn Outgoing Address  Entry defines the contents of each entry in
         the outgoing address table.
         Each entry has 2 indices:
         1. RoutId is the ID in the routing table.
         2. AddrId is the ID containing the Outgoing address and
            sub address. "
    INDEX   { pktSwchIsdnOutAddrRoutId, pktSwchIsdnOutAddrId }
    ::=  { pktSwchIsdnOutAddrTable 1 }


PktSwchIsdnOutAddrEntry ::=  SEQUENCE {
    pktSwchIsdnOutAddrRoutId
    Integer32,
    pktSwchIsdnOutAddrId
    Integer32,
    pktSwchIsdnOutAddr
     DisplayString,
    pktSwchIsdnOutSubAddr
     DisplayString
    }

 pktSwchIsdnOutAddrRoutId OBJECT-TYPE
    SYNTAX Integer32 (1..200)
        MAX-ACCESS  read-only
	STATUS  current
	DESCRIPTION
        "ID in the ISDN routing table."
        ::= { pktSwchIsdnOutAddrEntry 1 }


pktSwchIsdnOutAddrId OBJECT-TYPE
    SYNTAX Integer32 (1..3)
        MAX-ACCESS  read-only
	STATUS  current
	DESCRIPTION
        "Number of the address + subaddress pair for each routing ID."
        ::= { pktSwchIsdnOutAddrEntry 2 }

pktSwchIsdnOutAddr      OBJECT-TYPE
    SYNTAX DisplayString (SIZE (0..17))
    MAX-ACCESS  read-write
    STATUS  current
    DESCRIPTION
        "Destination ISDN Outgoing (Remote) address.
	 The data will be routed out to this address.
         Possible values:
         Up to 17 decimal digits.
         Default value: string of length 0."
    ::= { pktSwchIsdnOutAddrEntry 3 }

pktSwchIsdnOutSubAddr      OBJECT-TYPE
    SYNTAX DisplayString (SIZE (0..6))
    MAX-ACCESS  read-write
    STATUS  current
    DESCRIPTION
        "Destination ISDN Outgoing (Remote) sub address.
         The data will be routed out to the out addrress with
         this sub address.
         Possible values:
         Up to 6 decimal digits.
         Default value: string of length 0."
    ::= { pktSwchIsdnOutAddrEntry 4 }


pktSwchIsdnAcceptTable    OBJECT-TYPE
    SYNTAX  SEQUENCE  OF PktSwchIsdnAcceptEntry
    MAX-ACCESS  not-accessible
    STATUS  current
    DESCRIPTION
        "Table of Isdn addresses which will be accepted by the agent.
         If there is a dial back (answer) address, the incoming call
         will be disconnected and dial back will initiate. Most of
         the accept list parameters are in RFC2128 in the
         dialCtlPeerCfgTable. The parameters which are not in the
         the standard RFC2128 and are required, are defined here
         in the private PS MIB."
     ::=  { pktSwchIsdn 4 }

pktSwchIsdnAcceptEntry OBJECT-TYPE
    SYNTAX  PktSwchIsdnAcceptEntry
    MAX-ACCESS  not-accessible
    STATUS  current
    DESCRIPTION
	"Isdn Accept Entry defines the contents of each entry in the table."
    INDEX   { pktSwchIsdnAcceptId }
    ::=  { pktSwchIsdnAcceptTable 1 }

PktSwchIsdnAcceptEntry ::=  SEQUENCE {
    pktSwchIsdnAcceptId
    Integer32,
    pktSwchIsdnAcceptSecondaryLink
    Integer32,
    pktSwchIsdnAcceptDialbkSubAddress
     DisplayString,
    pktSwchIsdnAcceptStatus
     INTEGER
    }

pktSwchIsdnAcceptId OBJECT-TYPE
    SYNTAX Integer32 (1..200)
    MAX-ACCESS  read-only
    STATUS  current
    DESCRIPTION
        "Identifier of Accept table entry."
        ::= { pktSwchIsdnAcceptEntry 1 }

pktSwchIsdnAcceptSecondaryLink OBJECT-TYPE
    SYNTAX Integer32 (1..255)
    MAX-ACCESS  read-write
    STATUS  current
    DESCRIPTION
    "A valid Isdn link number on which the call will be accepted
     when the Primary link (RFC2128.dialCtlPeerCfgLowerIf)is unavailable.

     Possible values:
     255 - No Secondary link.
     or
     The complementary to the primary ISDN link number.
     Complementary links are: [1;2] and [7;8].
     If Primary Link Number is set to first available <0>,
     the Secondary link must be set to No Secondary link <255>.

     Default value is complementary to the primary link no. defined in
     rfc2128.dialCtlPeerCfgLowerIf."
     ::= { pktSwchIsdnAcceptEntry 2 }

pktSwchIsdnAcceptDialbkSubAddress OBJECT-TYPE
    SYNTAX DisplayString (SIZE (0..6))
    MAX-ACCESS  read-write
    STATUS  current
    DESCRIPTION
    "Isdn sub address which will be used by the agent for dialing
     back.
     Possible values:
     Up to 6 decimal digits.

     Default value: string of length 0."
     ::= { pktSwchIsdnAcceptEntry 3 }

pktSwchIsdnAcceptStatus OBJECT-TYPE
    SYNTAX  INTEGER {
       valid(1),
       createRequest(2),
       underCreation(3),
       invalid(4)
     }
    MAX-ACCESS  read-write
    STATUS  current
    DESCRIPTION
    "The status of this accept table entry.
     For creating a new entry select createRequest,
     For deleting an entry select invalid.
     For saving an entry select valid."
     ::= { pktSwchIsdnAcceptEntry 4 }

pktSwchIsdnLinkTable    OBJECT-TYPE
    SYNTAX  SEQUENCE  OF PktSwchIsdnLinkEntry
    MAX-ACCESS  not-accessible
    STATUS  current
    DESCRIPTION
        "Table of Isdn Link parameters. Most of the link parameters
         are in in RFC2127. Isdn Call statistics are RFC2128.
         The parameters which are not in the the standard RFCs ,
         and are required, are defined here in the private PS MIB."
    ::=  { pktSwchIsdn 5 }

pktSwchIsdnLinkEntry OBJECT-TYPE
    SYNTAX  PktSwchIsdnLinkEntry
    MAX-ACCESS  not-accessible
    STATUS  current
    DESCRIPTION
        "Isdn Link Entry defines the contents of each entry in the table."
    INDEX   {ifIndex }
    ::=  { pktSwchIsdnLinkTable 1 }

PktSwchIsdnLinkEntry ::=  SEQUENCE {
    pktSwchIsdnLinkBchannel
    INTEGER,
    pktSwchIsdnCallsClrs
    Counter32,
    pktSwchIsdnTestCmd
    INTEGER,
    pktSwchIsdnTestAddr
    DisplayString,
    pktSwchIsdnTestSubAddr
    DisplayString
    }

pktSwchIsdnLinkBchannel OBJECT-TYPE
    SYNTAX  INTEGER {
       noBchannel(1),
       b1(2),
       b2(3),
       b1Andb2(4)
     }
    MAX-ACCESS  read-write
    STATUS  current
    DESCRIPTION
    "Defines which B channels are used for Leased Lines Only.
     Default value: noBchannel(1)."
     ::= { pktSwchIsdnLinkEntry 1 }

pktSwchIsdnCallsClrs OBJECT-TYPE
    SYNTAX  Counter32
    MAX-ACCESS  read-only
    STATUS  current
    DESCRIPTION
    "Number of calls on this link which were cleared since the link was
         activated."
    ::= { pktSwchIsdnLinkEntry 2 }

pktSwchIsdnTestCmd OBJECT-TYPE
    SYNTAX INTEGER {
        noOp     (2),
        activate (3)
        }
    MAX-ACCESS  read-write
    STATUS  current
    DESCRIPTION
    "Activate/Stop an ISDN test on the current ISDN link.
     In order to Activate the test, set the TestCmd to 3 (activate).
     For stopping the test, set the TestCmd to 2 (noOp).

     Important: In order for the test to succeed, the user must set
     the pktSwchIsdnTestAddr and Subaddr to their required values before
     activating the test. "
    ::= { pktSwchIsdnLinkEntry 3 }

pktSwchIsdnTestAddr      OBJECT-TYPE
    SYNTAX DisplayString (SIZE (0..17))
    MAX-ACCESS  read-write
    STATUS  current
    DESCRIPTION
        "Destination ISDN Outgoing (Remote) address which will be
         called in order to test the ISDN.
         Possible values:
         Up to 17 decimal digits.
         Default value: string of length 0.

        Important: In order for the test to succeed, the user must also set
        the pktSwchIsdnTestSubAddr to the required values before
        activating the test. "
    ::= { pktSwchIsdnLinkEntry 4 }

pktSwchIsdnTestSubAddr      OBJECT-TYPE
    SYNTAX DisplayString (SIZE (0..6))
    MAX-ACCESS  read-write
    STATUS  current
    DESCRIPTION
        "Destination ISDN Outgoing (Remote) address which will be
         called in order to test the ISDN.
         Possible values:
         Up to 6 decimal digits.
         Default value: string of length 0.

        Important: In order for the test to succeed, the user must also set
        the pktSwchIsdnTestAddr to the required values before
        activating the test. "
    ::= { pktSwchIsdnLinkEntry 5 }


pktSwchPpp       OBJECT IDENTIFIER ::= { radPS 15}

--  Point to Point Protocol in the Packet Switching devices.

--  PPP Global Parameters:
--  All the parameters are in: RFC1472, PPP  Security Secrets Table.
--  The Security Secrets table contains pairs of Identity and secrets
--  (Port User Name and Port Password).
--  The link no. which is used for the Secrets table is: 0.
--  Link no. 0 in RFC1472 means that the ID/Secret pair applies to all links.
--
--  The ROW status of rfc1472 could not be used because it has only 2 values:
--  valid and invalid. There is no option for create request as is used
--  in the Packet Switches.
--  The only parameter which was added here is the ROW status for the table.

pktSwchPppSecretsTable    OBJECT-TYPE
    SYNTAX  SEQUENCE  OF PktSwchPppSecretsEntry
    MAX-ACCESS  not-accessible
    STATUS  current
    DESCRIPTION
        "Table of PPP Secret parameters.
         The parameters are defined in rfc1472 except for the ROW status
         which is defined here.
         In the standard, there is no create request option, so in order
         to be consistent with other ROW statuses in the Packet Switches
         it is defined here."
    ::=  { pktSwchPpp 1 }

pktSwchPppSecretsEntry OBJECT-TYPE
    SYNTAX  PktSwchPppSecretsEntry
    MAX-ACCESS  not-accessible
    STATUS  current
    DESCRIPTION
    "PPP Secrets Entry defines the contents of each entry in the table."
    INDEX   {pktSwchPppSecretsPairId}
    ::=  { pktSwchPppSecretsTable 1 }

PktSwchPppSecretsEntry ::=  SEQUENCE {
    pktSwchPppSecretsPairId
    Integer32,
    pktSwchPppSecretsStatus
    INTEGER
    }

pktSwchPppSecretsPairId OBJECT-TYPE
    SYNTAX Integer32 (1..200)
	MAX-ACCESS  read-only
	STATUS  current
	DESCRIPTION
        "Index of the Secrets Pair."
        ::= { pktSwchPppSecretsEntry 1 }

pktSwchPppSecretsStatus OBJECT-TYPE
    SYNTAX  INTEGER {
       valid(1),
       createRequest(2),
       underCreation(3),
       invalid(4)
     }
    MAX-ACCESS  read-write
    STATUS  current
    DESCRIPTION
    "The status of the PPP Secrets table.
     For creating a new entry select createRequest,
     For deleting an entry select invalid.
     For saving an entry select valid."
        ::= { pktSwchPppSecretsEntry 2 }


pktSwchPppChanTable    OBJECT-TYPE
    SYNTAX  SEQUENCE  OF PktSwchPppChanEntry
    MAX-ACCESS  not-accessible
    STATUS  current
    DESCRIPTION
        "Table of PPP Channel parameters.
         The table can be used for Async as well as Sync parameters.
         In case a parameter is irrelevant for Async or Sync a <not
         applicable> value may be returned.
         Statistics Parameters are already defined in rfc1213:
         ifInUcastPkts, ifOutUcastPkts, ifInErrors, ifOutErrors"
    ::=  { pktSwchPpp 2 }

pktSwchPppChanEntry OBJECT-TYPE
    SYNTAX  PktSwchPppChanEntry
    MAX-ACCESS  not-accessible
    STATUS  current
    DESCRIPTION
        "PPP Channel Entry defines the contents of each entry in the table."
    INDEX   {ifIndex }
    ::=  { pktSwchPppChanTable 1 }

PktSwchPppChanEntry ::=  SEQUENCE {
    pktSwchPppChanSpeed
    INTEGER,
    pktSwchPppChanFlowCtlDuration
    Integer32,
    pktSwchPppChanStopBits
     INTEGER,
    pktSwchPppChanBitPerChar
     Integer32,
    pktSwchPppChanParity
     INTEGER,
    pktSwchPppChanNegotiationTrigger
    INTEGER,
    pktSwchPppChanMRU
    Integer32,
    pktSwchPppChanACCM
    OCTET STRING,
    pktSwchPppChanAuthentication
    INTEGER,
    pktSwchPppChanInternalClock
    INTEGER,
    pktSwchPppChanBundle
    Integer32,
    pktSwchpPppChanIsdnRoutId
    Integer32,
    pktSwchpPppChanLastEvent
    DisplayString,
    pktSwchpPppChanModemInitString
    DisplayString,
    pktSwchpPppChanModemDialString
    DisplayString
    }

pktSwchPppChanSpeed OBJECT-TYPE
    SYNTAX  INTEGER {
       s110bps    (1),
       s300bps    (2),
       s1200bps   (3),
       s600bps    (4),
       s75bps     (5),
       s150bps    (6),

       s2400bps  (12),
       s4800bps  (13),
       s9600bps  (14),
       s19200bps (15),

       s38400bps (19),
       s57600bps (20),
       s115200bps(21),
       notApplicable(255)
           }
    MAX-ACCESS  read-write
    STATUS  current
    DESCRIPTION
    "The port's speed in bits per second.
     For Async channels: Default value: 14 .
     For Sync  Links: Use not_applicable(255)
     The Sync Links have an internal clock with
     different values."
     ::= { pktSwchPppChanEntry 1 }

pktSwchPppChanFlowCtlDuration OBJECT-TYPE
    SYNTAX Integer32 (0..255)
    MAX-ACCESS  read-write
    STATUS  current
    DESCRIPTION  " Hardware Flow Control Duration.
         1..254 - Duration (in 50ms intervals).
                  when timer expires, flow control stops.
              0 - No Hardware flow control.
            255 - Continuous Flow Control.
         Default value: 0.
         For Sync Links, return 0."
     ::= { pktSwchPppChanEntry 2 }

pktSwchPppChanStopBits OBJECT-TYPE
    SYNTAX  INTEGER  {
       one       (1),
       two       (2),
       oneAndHalf(3),
       notApplicable(255)
    }
    MAX-ACCESS  read-write
    STATUS  current
    DESCRIPTION
    "This entry indicates the number of stop bits per character.
     The options are either (1) one stop bit, (2) two stop bits,
     or (3) 1.5 stop bits.
     For Sync Links: notApplicable(255)."
    ::= { pktSwchPppChanEntry 3 }

pktSwchPppChanBitPerChar  OBJECT-TYPE
    SYNTAX Integer32 (0..8)
    MAX-ACCESS  read-write
    STATUS  current
    DESCRIPTION
    "The number of data bits per character supported by the ppp
     link. Legal values for Async channels: 5..8 .
     For Sync Links: 0"
    ::= { pktSwchPppChanEntry 4 }

pktSwchPppChanParity  OBJECT-TYPE
    SYNTAX  INTEGER  {
       space(1),
       mark(2),
       even(3),
       odd(4),
       none(255)
    }
    MAX-ACCESS  read-write
    STATUS  current
    DESCRIPTION
    "This entry selects the type of parity to be checked or
     generated.
     The options are (1) space parity, (2) mark parity,
     (3) even parity, (4) odd parity, or (255) no parity.
     For Sync Links: none(255)."
    ::= { pktSwchPppChanEntry 5 }

pktSwchPppChanNegotiationTrigger OBJECT-TYPE
    SYNTAX  INTEGER {
       hw-signal        (1),
       data-triggered   (2),
       hw-signal-or-data(3),
       after-reset      (255)
    }
    MAX-ACCESS  read-write
    STATUS  current
    DESCRIPTION
    "The trigger which is used in order to start the Negotiation.
     The HW signals which are used are:
     DCD (Data Carrier  Detect) - issued by DCE
     DSR (Data Set Ready)       - issued by DCE
     DTR (Data Terminal Ready)  - issued by DTE

   1 -   Start negotiation on signal assertion.
         The Peer will issue a DCD/DSR Signal if it is DCE or
         DTR if it is DTE.
         If the current channel/link is DCE, it will check the DTR.
         If the current channel/link is DTE, it will check the DCD/DSR.

         When the HW signal is issued, negotiation will begin.

   2 - Data Triggered.
         The current channel/link will issue a HW signal.
         Negotiation will begin when data is received.

   3   - Combination of option 1 and option 2.
   255 - Starts negotiation after reset. Ignore HW signals.

        Default Value for Async Channel: 255.
        Default Value for Sync Link:     3"
     ::= { pktSwchPppChanEntry 6 }

pktSwchPppChanMRU OBJECT-TYPE
    SYNTAX  Integer32 (1500..4096)
    MAX-ACCESS  read-write
    STATUS  current
    DESCRIPTION
    "Maximum Receive Unit.
     Size of the packet which is negotiated with the connected device.

     Default value: 1500 ."
    ::= { pktSwchPppChanEntry 7 }

pktSwchPppChanACCM OBJECT-TYPE
    SYNTAX  OCTET STRING (SIZE (4))
    MAX-ACCESS  read-write
    STATUS  current
    DESCRIPTION
    "Async Control Character Map -
     The ACCM value serves as a mask for the first 32 characters
     in the ASCII table.

     Control characters may cause problems when they are transferred
     on the network. This can be handled by escaping them
     ( adding escape character to them ).
     For example , when using modems in the network which can not
     receive X-on and X-off characters. The ACCM is a mask which shows
     which control characters will be handled with an escape sequence.
     Each bit represents one character.

     Possible values:
     Octet string of 4 bytes: 00000000 .
     A bit with value 1 will cause the character to be in an escape sequence.
     0 will leave the character as it is.
     Example : to use XON and XOFF as escape sequence : 000A0000

     Default value: 00000000.
     For Sync Links return the default."
    ::= { pktSwchPppChanEntry 8 }

pktSwchPppChanAuthentication OBJECT-TYPE
    SYNTAX  INTEGER {
       no-authentication(1),
       pap-or-chap      (2),
       chap-only        (3)
    }
    MAX-ACCESS  read-write
    STATUS  current
    DESCRIPTION
        "Port Authentication Type.
         1 - No Authentication: User side Only.
         2 - Configuration of the Host side.
             PAP (Password Authentication Protocol) or
             CHAP (Challenge Handshake Authentication Protocol)
             will be accepted by the current host.
         3 - Configuration of the host side as CHAP only.
             Only CHAP will be accepted by the current host.

         Default value: 1 ."
     ::= { pktSwchPppChanEntry 9 }

pktSwchPppChanInternalClock OBJECT-TYPE
    SYNTAX INTEGER {
       r3000bps (1),
       r4800bps (2),
       r9600bps (3),
       r14400bps(4),
       r19200bps(5),
       r38400bps(6),
       r48Kbps  (7),
       r56Kbps  (8),
       r64Kbps  (9),
       r128Kbps (10),
       r256Kbps (11),
       r384Kbps (12),
       r512Kbps (13),
       r768Kbps (14),
       r1024Kbps(15),
       r1445Kbps(16),
       r2048Kbps(17),
       external(255)
    }
    MAX-ACCESS  read-write
    STATUS  current
    DESCRIPTION
        "The internal clock rate of the MLPPP Link.
         Default value: 9.
         For Async channels: return 255."
     ::= { pktSwchPppChanEntry 10 }

pktSwchPppChanBundle OBJECT-TYPE
    SYNTAX  Integer32 (0..255)
    MAX-ACCESS  read-write
    STATUS  current
    DESCRIPTION
    "Bundle Number.
     It is possible to attach a few channels/links to a bundle.
     If the User enters a non existing bundle number, the PS will
     create a new bundle with this number.
     The bundle number may be: 1..255
     If the bundle number is 0 it means: do not attach to bundle.

     Default value: 0 ."
    ::= { pktSwchPppChanEntry 11 }

pktSwchpPppChanIsdnRoutId OBJECT-TYPE
    SYNTAX   Integer32 (0..200)
    MAX-ACCESS   read-write
    STATUS   current
    DESCRIPTION
       "ISDN destination. ID (1..200) in the ISDN routing table containing
        the outgoing ISDN address for this channel/link.

        For no destination: 0
        Default value: 0 "
    ::= { pktSwchPppChanEntry 12 }

pktSwchpPppChanLastEvent  OBJECT-TYPE
    SYNTAX DisplayString (SIZE (0..80))
    MAX-ACCESS  read-only
    STATUS  current
    DESCRIPTION
        "Status showing the last PPP event which occured on the line
         described in an ascii string.
         Examples:
         1. Received Configuration Request.
         2. Sent Protocol Reject.
         3. Error: Can Not Compress Frame.

         Default: 0 for no last event on this link or channel."
    ::= { pktSwchPppChanEntry 13 }

pktSwchpPppChanModemInitString  OBJECT-TYPE
    SYNTAX DisplayString (SIZE (0..29))
    MAX-ACCESS  read-write
    STATUS  current
    DESCRIPTION
        "This string is needed by the modem in order to be initiated, 
         before dialing."
    ::= { pktSwchPppChanEntry 14 }

pktSwchpPppChanModemDialString  OBJECT-TYPE
    SYNTAX DisplayString (SIZE (0..29)) 
    MAX-ACCESS  read-write
    STATUS  current
    DESCRIPTION
        "This string enables the modem to open a new call."
    ::= { pktSwchPppChanEntry 15 }


-- TRAPS for use by the PS

linkProtocolChanged        NOTIFICATION-TYPE
	OBJECTS { pktSwchPhyInterfaceIfIndex, pktSwchPhyInterfaceProtocolA}
    STATUS  current
	DESCRIPTION
	"Upon setting of a new protocol to a specific interface."
	::= { radSysPSEvents 1 }

enrollmentPS        NOTIFICATION-TYPE
    STATUS  current
    DESCRIPTION
    "Periodic trap to be sent to the list of managers."
    ::= { radSysPSEvents 2 }


rtsChange NOTIFICATION-TYPE
    OBJECTS  { pktSwchChannelNumberA }
    STATUS  current
    DESCRIPTION
    " "
    ::= { radSysPSEvents 3 }


ledStatusChange NOTIFICATION-TYPE
    OBJECTS  { agnLed }
    STATUS  current
    DESCRIPTION
    "The trap is sent when one of the Hazard LEDs has changed."
    ::= { radSysPSEvents 4 }
-- 
-- file :D:\Synergy\WorkArea\545\mib_rad\txt\dacs.txt
-- 
--Title:     RAD's DACS PRODUCTS MIB
--Date:      27.04.95
--By:        Smadar Tauber
--File:      dacs.txt 
--
--Last update: 5-May-2008 by Liora Gafni
dacsMux       OBJECT IDENTIFIER ::= {radWan 3}

systemDacsMux OBJECT IDENTIFIER ::= {dacsMux 1}
mdlDacsMux    OBJECT IDENTIFIER ::= {dacsMux 2}
prtDacsMux    OBJECT IDENTIFIER ::= {dacsMux 3}
genDacsMux    OBJECT IDENTIFIER ::= {dacsMux 4}
    

--System level of DACS MIB
--
--Sa  - data specific to a stand-alone unit
--Hub - data specific to a Hub unit
--Rest of the branches are common to both types of units.

sysSa         OBJECT IDENTIFIER ::= {systemDacsMux 1}
sysHub        OBJECT IDENTIFIER ::= {systemDacsMux 2}
sysStatus     OBJECT IDENTIFIER ::= {systemDacsMux 3}
sysCurrentAlr OBJECT IDENTIFIER ::= {systemDacsMux 4}
sysBufferAlr  OBJECT IDENTIFIER ::= {systemDacsMux 5}
sysConfig     OBJECT IDENTIFIER ::= {systemDacsMux 6}
sysDbase      OBJECT IDENTIFIER ::= {systemDacsMux 7}


--Stand-alone specific parameters

sysSaSwchStatus OBJECT-TYPE
      SYNTAX  Integer32
      MAX-ACCESS  read-only
      STATUS  current
      DESCRIPTION
      "This object indicates the status of the switches on 
       the SA unit.
       Each switch is represented by a bit. The status is a sum
       of 2**n, according to the bits.
       
	   For SMODs products see modem's specification.
	   
	   For DXC product see the following:
       There are 4 switches:
       bit 0  SP-PAR (LSB)  '1' - Default parameters    
       bit 1  PSWRD         '1' - Password=default
                            '0' - Password=user selected
       bit 2  DB-INIT       '1' - DB initiated with default
                            '0' - DB initiated with NVRAM contents 
       bit 3  PC-SP  (MSB)  '1' - Management by terminal only
                            '0' - Management by NMS
       Example: If SP-PAR  and PSWRD bits are set ('1'), the value
             will be 3 (2**1 + 2**0).
       When the status of the switches is unknown, the value of
       this object will be 255."
      ::= { sysSa 1}

sysSaSwRevision OBJECT-TYPE
      SYNTAX  DisplayString (SIZE (0..255))
      MAX-ACCESS  read-only
      STATUS  current
      DESCRIPTION
      "This object indicates the Software revision of the 
       system."
      ::= {sysSa 2}

sysSaHwVersion OBJECT-TYPE
      SYNTAX  DisplayString (SIZE (0..255))
      MAX-ACCESS  read-only
      STATUS  current
      DESCRIPTION
      "This object indicates the Hardware version of the 
       system."
      ::= {sysSa 3}

sysSaPorts OBJECT-TYPE
      SYNTAX  Integer32
      MAX-ACCESS  read-only
      STATUS  current
      DESCRIPTION
   "This object indicates the ports that are present in the 
    system.
    Each possible port is represented by a bit.
    The value of this object is a sum of 2**n, n=number of bits.
    '1' - means that the port exists
    '0' - means that the port does not exist
    For detailed bit assignment, see product's spec.
    Bit 0 = LSB
    When this object is not relevant, the value will be 0.
    In some cases, this object may represent ports configuration
    of the system AND its far-end unit."
   ::= {sysSa 4}

sysSaReadSwch OBJECT-TYPE
      SYNTAX  Integer32
      MAX-ACCESS  read-write
      STATUS  current
      DESCRIPTION
      "This object indicates wether the configuration will be read from the DIP switches
       on the SA (stand alone) unit.
       Each switch is represented by a bit.
       If the bit is 1: the configuration will be read from the HW switch position.
       If the bit is 0: the configuration will be read from the SW user configuration.
       
       The DIP switches are different in each of the RAD devices.
       In the Tiny Router (starting from the LSB) the following switches exist:
       Bit 0: WAN Loop
       Bit 1: LAN Full Duplex (When LAN AUI connector, it is SQE)
       Bit 2: PPP (When WAN 4 Wire connector, it is LONG)
       Bit 3: IP Learn"
   ::= {sysSa 5}

sysSaBuActivePort OBJECT-TYPE
      SYNTAX  INTEGER
	  {
	  notApplicable (1),
	  e1T1orSerial  (2),
	  eth           (3),
	  primary       (4),
	  secondary     (5),
	  third         (6),
	  fourth		(7)
	  }
      MAX-ACCESS  read-only
      STATUS  current
      DESCRIPTION
      "This object shows through which port the traffic is flowing
      (the current Active Port) when the Backup mechanism exists.
      When No Backup exists in the device, the value should be: notApplicable(1)."      
      ::= {sysSa 6}


--Hub specific parameters

--Hub Cassis data

sysChas  OBJECT IDENTIFIER ::= {sysHub 1}

chassTotalNoOfSlt  OBJECT-TYPE
      SYNTAX  Integer32
      MAX-ACCESS  read-only
      STATUS  current
      DESCRIPTION
      "This object indicates the number of physical slots in 
       the Hub chassis."
      ::= { sysChas 1 }

chassTotalNoOfIoSlt  OBJECT-TYPE
      SYNTAX  Integer32
      MAX-ACCESS  read-only
      STATUS  current
      DESCRIPTION
      "This object indicates the total number of physical IO slots 
       in the chassis, (not all slots must be occupied and active)."
      ::= { sysChas 2 }

chassTotalNoOfPsSlt  OBJECT-TYPE
      SYNTAX  Integer32
      MAX-ACCESS  read-only
      STATUS  current
      DESCRIPTION
      "This object indicates the number of physical Power Supply 
       slots in the chassis."
      ::= { sysChas 3 }

chassTotalNoOfClSlt  OBJECT-TYPE
      SYNTAX  Integer32
      MAX-ACCESS  read-only
      STATUS  current
      DESCRIPTION
      "This object indicates the number of physical Common Logic 
       slots in the chassis."
      ::= { sysChas 4 }

chassTotalNoOfMlSlt  OBJECT-TYPE
      SYNTAX  Integer32
      MAX-ACCESS  read-only
      STATUS  current
      DESCRIPTION
      "This object indicates the number of physical Main Link 
       slots in the chassis (Kmux)."
      ::= { sysChas 5 }


--Hub DCL parameters

sysDcl  OBJECT IDENTIFIER ::= {sysHub 2}


sysDclTable  OBJECT-TYPE
      SYNTAX SEQUENCE OF SysDclEntry
      MAX-ACCESS not-accessible
      STATUS  current
      DESCRIPTION
      "All the entries of this table are identical (have the 
       same value) for all the configurations (1..255) except 
       the TmpCnfg.
       The write operation into the Table Objects is valid only
       for the TmpCnfg entry."
       ::= { sysDcl 1}

sysDclEntry OBJECT-TYPE
      SYNTAX SysDclEntry
      MAX-ACCESS not-accessible
      STATUS current
	DESCRIPTION  "An entry in table."
	INDEX {sysDclCnfgIdx}
      ::= { sysDclTable 1}

SysDclEntry ::=
      SEQUENCE {
   		sysDclCnfgIdx        		Integer32,
   		sysDclRedundancy     		INTEGER,
   		sysDclActiveCl       		INTEGER,
   		sysDclFlipDelay      		Integer32,
		sysDclFlipUponStnClk 		INTEGER,
		sysDclChFailThreshold 		Integer32,
		sysDclChPriority 	 		OCTET STRING,
		sysDclConfigDownloadSrc  	INTEGER,
		sysDclSwDownloadSrc    	 	INTEGER,
		sysDclRedundancyStatus		BITS
      }

sysDclCnfgIdx OBJECT-TYPE
      SYNTAX Integer32 (1..255)
      MAX-ACCESS read-only
      STATUS current
      DESCRIPTION
      "This object indicates the Idx of the Cnfg(1..255) 
       being accessed ; Idx of 255 relates to the TmpCnfg.
       This object is identical for all the configurations (1..255).
       Only the TmpCnf(255) might have a  different value.
       For devices that work on line with NMS (no Temp configuration in NMS),
       Get and Set will be performed with index value of sysDclCnfgIdx = 1."
      ::= { sysDclEntry 1}
-- In phase I only the values 1 (Cnfg1) and 255 (temp) are valid.

sysDclRedundancy  OBJECT-TYPE
      SYNTAX  INTEGER
   {
   off (2),
   on  (3)
   }
      MAX-ACCESS  read-write
      STATUS  current
      DESCRIPTION
   " DCL redundancy desired state."
   ::= {sysDclEntry 2}

sysDclActiveCl  OBJECT-TYPE
      SYNTAX  INTEGER
   {
   auto (1),
   dclA (2),
   dclB (3)
   }
      MAX-ACCESS  read-write
      STATUS  current
      DESCRIPTION
   "Active desired DCL.
    When 'auto' is selected, the system automatically selects
    the active DCL."
   ::= {sysDclEntry 3}

sysDclFlipDelay  OBJECT-TYPE
      SYNTAX  Integer32
--   {
--   t1min (1),
--   t2min (2),
--   t3min (3),
--   t4min (4)
--   }    
      MAX-ACCESS  read-write
      STATUS  current
      DESCRIPTION
   "If one DCL flip occurred and a second one should be
    performed, the time from the previous flip is checked.
    If the time is shorter than the delay specified here,
    the system should delay the flip operation until time reaches the specified delay.
    For DXC the values are 1 minute to 4 minutes (1..4).
    For Optimux-155-1 and Optimux-155-3 the values are: 0...60 Sec.
	0 means No Delay."
   ::= {sysDclEntry 4}

sysDclFlipUponStnClk  OBJECT-TYPE
      SYNTAX  INTEGER
   {
   notApplicable (1),
   no            (2),
   yes           (3)
   }    
      MAX-ACCESS  read-write
      STATUS  current
      DESCRIPTION
   "This object allows user to decide (yes/no) if Agent should Flip from 
    one DCL card to another, when there is Station Clock Fail in 
    the Online DCL card."
   ::= {sysDclEntry 5}

sysDclChFailThreshold  OBJECT-TYPE
      SYNTAX  Integer32
      MAX-ACCESS  read-write
      STATUS  current
      DESCRIPTION
   "This object indicates the number of failed channels that will trigger the
    redundancy procedure."
   ::= {sysDclEntry 6}

sysDclChPriority  OBJECT-TYPE
      SYNTAX  OCTET STRING
      MAX-ACCESS  read-write
      STATUS  current
      DESCRIPTION
   "This object indicates the Priority for all the channels in the Main Access
    (Common Logic) card. Each channel is represented by 1 bit.
	The order of the bits in each byte is from Right to Left (LSB Bit to MSB)
	starting from BIT 0:    7  6  5  4  3  2  1  0 

    Channel no. 1 is represented by bit 0.
    Channel no. 2 is represented by bit 1.
    Channel no. n is represented by bit n-1.

    The value of the bit shows the priority.
    For bit value = 1, Priority = High.
    For bit value = 0, Priority = Low." 
    ::= {sysDclEntry 7}

sysDclConfigDownloadSrc  OBJECT-TYPE
      SYNTAX  INTEGER
   {
   off	(1),
   dclA (2),
   dclB (3)
   }
      MAX-ACCESS  read-write
      STATUS  current
      DESCRIPTION
      "In case of mismatch between the 2 CL card's configuration, the user can decide 
       which card has the suitable configuration.
       The selected configuration will be downloaded from card A to card B
       if the value is dclA(2) or from card B to card A if the value is dclB(3).
       off(1) is used by part of the devices. In this case, after operation ends -
        value should be automatically set to off(1), which is the default state."  
   ::= {sysDclEntry 8}


sysDclSwDownloadSrc    OBJECT-TYPE
      SYNTAX  INTEGER
   {
   off	(1),
   dclA (2),
   dclB (3)
   }
      MAX-ACCESS  read-write
      STATUS  current
      DESCRIPTION
      "In case of mismatch between the 2 CL card's software, the user can decide 
       which card has the suitable SW.
       The selected SW will be downloaded from card A to card B if the value is dclA(2)
       or from card B to card A if the value is dclB(3).
       off(1) is used by part of the devices. In this case, after operation ends -
       value should be automatically set to off(1), which is the default state."  
   ::= {sysDclEntry 9}

sysDclRedundancyStatus 	 OBJECT-TYPE
      SYNTAX      BITS
           {
			cnfgMismatch		(0),
			swMismatch			(1),
			cardAAbsent			(2),
			cardBAbsent			(3),
			lossOfCommunication	(4),
			hwMismatch			(5),
			cnfgUpdate			(6),
			swUpdate			(7)
           }
	  MAX-ACCESS  read-only
      STATUS  current
      DESCRIPTION
         "Bit map representing current Redundancy Status.
          bit 0 - Indicates mismatch between the 2 CL cards' Configuration
          bit 1 - Indicates mismatch between the 2 CL cards' Software.
		  bit 2 - Indicates CL card A Absence.
		  bit 3 - Indicates CL card B Absence.
          bit 4 - Indicates Loss of Communication between the 2 CL cards.
          bit 5 - Indicates mismatch between the 2 CL cards' Hardware.
          bit 6 - Indicates Configuraton update is in process.
          bit 7 - Indicates Software update is in process.
          "
   ::= {sysDclEntry 10}


sysDclOnline  OBJECT-TYPE
      SYNTAX  INTEGER
   {
   dclA (1),
   dclB (2)
   }
      MAX-ACCESS  read-only
      STATUS  current
      DESCRIPTION
   "The active Dcl card of the agent."
   ::= {sysDcl 2}

sysDclCopyDbTable  OBJECT-TYPE
      SYNTAX SEQUENCE OF SysDclCopyDbEntry
      MAX-ACCESS not-accessible
      STATUS  current
      DESCRIPTION
      "This table enables to copy a cofiguration from the Offline
       Dcl to the Online Dcl."
       ::= { sysDcl 3}

sysDclCopyDbEntry OBJECT-TYPE
      SYNTAX SysDclCopyDbEntry
      MAX-ACCESS not-accessible
      STATUS current
	DESCRIPTION  "An entry in table."
	INDEX {sysDclCopyDbIdx}
      ::= { sysDclCopyDbTable 1}

SysDclCopyDbEntry ::=
      SEQUENCE {
   		sysDclCopyDbIdx       Integer32,
   		sysDclCopyDbCmd       INTEGER
      }

sysDclCopyDbIdx OBJECT-TYPE
      SYNTAX Integer32 (1..255)
      MAX-ACCESS read-only
      STATUS current
      DESCRIPTION
      "This object indicates the Idx of the Cnfg(1..255) 
       being accessed. "
      ::= { sysDclCopyDbEntry 1}

sysDclCopyDbCmd OBJECT-TYPE
      SYNTAX INTEGER {
   off(2),
   on (3)
   }
      MAX-ACCESS read-write
      STATUS current
      DESCRIPTION
      "When this command is sent to the agent, on(3), the Database
       specified (Db Idx), will be copied from the Offline Dcl 
       to the Online Dcl. Afterwards the value of this object will 
       automatically change to off(2). "
      ::= { sysDclCopyDbEntry 2}

sysDclFlipCmd OBJECT-TYPE
      SYNTAX INTEGER {
      off  (2),
      flip (3)
      }
      MAX-ACCESS read-write
      STATUS current
      DESCRIPTION
      "When the 'flip(3)' command is received by Agent, it will flip (switch) 
       between Offline Dcl and Online Dcl cards. Afterwards the value of 
       this object will automatically change to off(2)."
      ::= { sysDcl 4}


--General System - General Status parameters 

sysSDateFormat  OBJECT-TYPE
      SYNTAX  INTEGER
       {
          ddMMYYYY (1),
          mmDDYYYY (2),
		  yyyyMMDD (4)
       }
      MAX-ACCESS  read-write
      STATUS  current
      DESCRIPTION
      "This object indicates the date and time format used for the
       sysSDateAndTimeCmd and for the alarm buffer report."
      ::= { sysStatus 1 }

sysSDateCmd  OBJECT-TYPE
      SYNTAX  DisplayString (SIZE (0..255))
      MAX-ACCESS  read-write
      STATUS  current
      DESCRIPTION
      "This object indicates the current date as it is known by the
       agent using its own real-time clock. The format would be as
       specified by the sysSDateFormat.
       This  parameter can be set for time synchronization between
       the NMS and the Agent.
       * For KM-2100 V1 and FCD-T1/E1 - the string should contain 
         '/' signs between day, month and year. Example: 12/08/1998.
       * For DXC and rest of the products - the string should contain 
         '-' signs between day, month and year. Example: 12-08-1998.
       The day value will be in the range: 1..31.
       The month value will be in the range: 1..12.
       The year value will be in the range: 1996..2050 for products
       supporting the '-' format."
      ::= { sysStatus 2 }

sysSTimeCmd  OBJECT-TYPE
      SYNTAX  DisplayString (SIZE (0..255))
      MAX-ACCESS  read-write
      STATUS  current
      DESCRIPTION
      "This object indicates the current time as it is known by the
       agent using its own real-time clock.
       This  parameter can be set for time synchronization between
       the NMS and the Agent.
       The string should contain ':' signs between hour, minute 
       and second. Example: 11:05:58."
      ::= { sysStatus 3 }

sysSActiveCnfg  OBJECT-TYPE
      SYNTAX  Integer32
      MAX-ACCESS  read-only
      STATUS  current
      DESCRIPTION
      "This object specifies the configuration number,
       that is currently  active and running."
      ::= { sysStatus 4 }
-- return 1 (db1) in phase I

sysSEditCnfg OBJECT-TYPE
      SYNTAX  Integer32
      MAX-ACCESS  read-only
      STATUS  current
      DESCRIPTION
      "This object indicates the  unique configuration number that
       is currently loaded into the tmp working space  for 
       manipulation and update operations. Value of 255 means no 
       config. is under editing process."
      ::= { sysStatus 5 }
-- return 1 (db1) in phase I


sysSEditBy OBJECT-TYPE
      SYNTAX  INTEGER
       {
           none            (1),
           snmp            (2),
           terCon1         (3),
           terCon2         (4),
           terInbandCon1   (5),
           terInbandCon2   (6),
           lcd             (7)
       }
      MAX-ACCESS  read-only
      STATUS  current
      DESCRIPTION
      "This entry indicates which MMI application is working on  
       the edited config.
       The editing phase starts at the first modify operation and 
       ends after a load operation."
      ::= { sysStatus 6 }

sysSClkSrc  OBJECT-TYPE
      SYNTAX  INTEGER
    {
        master  (1),
        fallback(2),
        internal(3),
        ml      (4) 
    }
      MAX-ACCESS  read-only
      STATUS  current
      DESCRIPTION
     "This entry indicates the source of the system clock."
      ::= { sysStatus 7 }

sysSAlrStatus OBJECT-TYPE
      SYNTAX  INTEGER
       {
  off      (2),
  major    (3),
  minor    (4),
  event    (5),
  warning  (6),
  critical (7)
       }
      MAX-ACCESS  read-only
      STATUS  current
      DESCRIPTION
      "Indicates the current alarm state only for system level.
       This object will be : 
       - critical(7): when there is at least one active (ON) critical 
                    alarm .
       - major (3): when there is no active critical alarm, but there is
                    at least one active (ON) major alarm .
       - minor (4): when there is no active major or critical alarm, but 
                    there is at least one active minor alarm.
       - warning (6): when there is no active major, critical or minor alarm, but 
                    there is at least one active warning alarm.
       - event (5): when there is no active alarm of another type, but 
                    there is at least one active event alarm.
       - off(2): when there is no active (ON) alarm (since last clear operation)."
      ::= { sysStatus 8 }

sysSAlrStatusAll OBJECT-TYPE
      SYNTAX  INTEGER
       {
  off      (2),
  major    (3),
  minor    (4),
  event    (5),
  warning  (6),
  critical (7)
       }
      MAX-ACCESS  read-only
      STATUS  current
      DESCRIPTION
      "Indicates the current alarm state including all levels: 
       system, card, port.
       - critical(7): when there is at least one active (ON) critical 
                    alarm .
       - major (3): when there is no active critical alarm, but there is
                    at least one active (ON) major alarm .
       - minor (4): when there is no active major or critical alarm, but 
                    there is at least one active minor alarm.
       - warning (6): when there is no active major, critical or minor alarm, but 
                    there is at least one active warning alarm.
       - event (5): when there is no active alarm of another type, but 
                    there is at least one active event alarm.
       - off(2): when there is no active (ON) alarm (since last clear operation)."
      ::= { sysStatus 9 }

sysSTestStatus OBJECT-TYPE
      SYNTAX  INTEGER
       {
  off(2),
  on (3)
       }
      MAX-ACCESS  read-only
      STATUS  current
      DESCRIPTION
      "Indicates the current test status (for all levels: system,
       card, port).
       This attribute will be set to: 
       - on(3): when there is at least one test in progress on the
                system/card/port
         otherwise the value will be off(2)."
      ::= { sysStatus 10 }


sysSSanityCheckStatus OBJECT-TYPE
      SYNTAX  INTEGER
       {
  unknown (1),
  fail    (2),
  warning (3),
  ok      (4)
       }
      MAX-ACCESS  read-only
      STATUS  current
      DESCRIPTION
      "Upon completion of the Sanity Check process on the TmpCnfg 
       this object will be set to:
       - fail(2): when there is at least one error (which is 
                  not just a warning) encountered
                  otherwise,
       - warning(3): when there are only warnings
                  otherwise,
       - ok(4).
       The value should be unknown(1), if the TmpCnfg was changed 
       after the last Sanity check."
      ::= { sysStatus 11 }

sysSNoOfSanityCheckErr OBJECT-TYPE
      SYNTAX  Integer32
      MAX-ACCESS  read-only
      STATUS  current
      DESCRIPTION
      "This object indicates the number of errors/warnings 
       discovered by the last Sanity Check process."
      ::= { sysStatus 12 }

sysSErrListTable OBJECT-TYPE
      SYNTAX SEQUENCE OF SysSErrListEntry
      MAX-ACCESS not-accessible
      STATUS current
	DESCRIPTION  "A table."
	::=  { sysStatus 13 }

sysSErrListEntry OBJECT-TYPE
      SYNTAX SysSErrListEntry
      MAX-ACCESS not-accessible
      STATUS current
	DESCRIPTION  "An entry in table."
	INDEX { sysSErrType, sysSErrIdx}
      ::= { sysSErrListTable 1}

SysSErrListEntry ::=
      SEQUENCE {
  sysSErrType         INTEGER,
  sysSErrIdx          Integer32,
  sysSErrDescription  DisplayString 
      }

sysSErrType OBJECT-TYPE
      SYNTAX  INTEGER
   {
   error    (1),
   warning  (2)
   }
      MAX-ACCESS  read-only
      STATUS  current
      DESCRIPTION
      "The errors are recorded in the agent, in two separate lists, 
       according to their type:  error or warning."
    ::= { sysSErrListEntry 1}

sysSErrIdx OBJECT-TYPE
      SYNTAX  Integer32
      MAX-ACCESS  read-only
      STATUS  current
      DESCRIPTION
      "Unique index number to identify an entry in the error 
       or warning list .
       The maximum value  cannot exceed the value of
       'sysSNoOfSanityCheckErr' (actually, the sum of the Errors
       list max. index and the Warning list max. index should
       equal the value of'sysSNoOfSanityCheckErr')."
    ::= { sysSErrListEntry 2}

sysSErrDescription OBJECT-TYPE
      SYNTAX  DisplayString (SIZE (0..255))
      MAX-ACCESS  read-only
      STATUS  current
      DESCRIPTION
      "This object is a full text description of the sanity check
       error including error code, IO slot and port numbers related to
       the code ."
  ::= { sysSErrListEntry 3}

sysSMaxNoOfCnfg OBJECT-TYPE
      SYNTAX  Integer32
      MAX-ACCESS  read-only
      STATUS  current
      DESCRIPTION
      "Maximum number of configurations that can be defined and 
       stored in the DACS agent.
       If the DACS agent has a large capacity, the maximum will be 
       limited to 254."
      ::= { sysStatus 14 }
-- return 1 (db1) in phase I

sysSSelfTestResult OBJECT-TYPE
      SYNTAX  Integer32
      MAX-ACCESS  read-only
      STATUS  current
      DESCRIPTION
      "The test is performed by the active Common Logic card.
       The result will be a sum of 2**n according to the following
       bit convention:
    For DXC:
    bit 0   Database 1 Checksum Error (LSB)
    bit 1   Database 2 Checksum Error
    bit 2   I/O Expander Error
    bit 3   Counter Error
    bit 4   Matrix DPR Error
    bit 5   PS-A  5 Volt Error
    bit 6   PS-A 12 Volt Error
    bit 7   PS-B  5 Volt Error
    bit 8   PS-B 12 Volt Error
    bit 9   EPROM Failure

    For FCD:
    bit 0   I/O Expander Error (LSB)
    bit 1   Counter Error
    bit 2   EPROM Failure
    bit 3   Illegal Sys Config
    bit 4   SFIFO
    bit 5   EPIC Failure (ISDN)
    bit 6   XL Flash Fail  -- for MSDSL interface
    bit 7   XL MITEL Fail  -- for MSDSL interface 
    bit 8   XL Framer Fail -- for MSDSL interface
    bit 9   XL DSP Fail    -- for MSDSL interface 

	For LRS52  - refer to product's spec
     
    When a bit is ('1'), the error exists.
    When NO ERROR is encountered, this object's value will be 0."
      ::= { sysStatus 15 }

sysSRelayState OBJECT-TYPE
      SYNTAX  INTEGER
       {
  notApplicable (1),
  off(2),
  on (3)
       }
      MAX-ACCESS  read-only
      STATUS  current
      DESCRIPTION
      "Indicates the current state of the alarm relay.
       notApplicable - for agents that do not support this object."
      ::= { sysStatus 16 }

sysSInvertedAlr OBJECT-TYPE
      SYNTAX  INTEGER
       {
  notApplicable (1),
  no  (2),
  yes (3)
       }
      MAX-ACCESS  read-only
      STATUS  current
      DESCRIPTION
      "Indicates if there is any Inverted alarm at any level of the 
       system (sys, card, port).
       notApplicable - for agents that do not support this object."
      ::= { sysStatus 17 }

--The following table reports all the Flip events due to I/O Redundancy
--since last Clear command of the table. 

sysSRdnFlipTable OBJECT-TYPE
      SYNTAX SEQUENCE OF SysSRdnFlipEntry
      MAX-ACCESS not-accessible
      STATUS current
      DESCRIPTION
      "This table includes all the Flip events due to I/O Redundancy since
       last Clear command of this table."
      ::= { sysStatus 18 }

sysSRdnFlipEntry OBJECT-TYPE
      SYNTAX SysSRdnFlipEntry
      MAX-ACCESS not-accessible
      STATUS current
	DESCRIPTION  "An entry in table."
	INDEX { sysSRdnFlipIdx}
      ::= { sysSRdnFlipTable 1}

SysSRdnFlipEntry ::=
      SEQUENCE {
     sysSRdnFlipIdx   Integer32,
     sysSRdnFlipSlot  INTEGER,
     sysSRdnFlipPort  Integer32,
     sysSRdnFlipCause DisplayString,
     sysSRdnFlipDate  DisplayString,
     sysSRdnFlipTime  DisplayString
      }

sysSRdnFlipIdx OBJECT-TYPE
      SYNTAX  Integer32
      MAX-ACCESS  read-only
      STATUS  current
      DESCRIPTION
      "Unique index number to identify an entry in the Redundancy Flip list."
      ::= { sysSRdnFlipEntry 1}

sysSRdnFlipSlot OBJECT-TYPE
      SYNTAX  INTEGER
       {
       io1   (5),
       io2   (6),
       io3   (7),
       io4   (8),
       io5   (9),
       io6  (10),
       io7  (11),
       io8  (12),
       io9  (13),
       io10 (14),
       io11 (15),
       io12 (16),
       io13 (17),
       io14 (18),
       io15 (19),
       notApplicable (255)
       }
      MAX-ACCESS  read-only
      STATUS  current
      DESCRIPTION
      "The slot number from which Flip was performed."      
      ::= { sysSRdnFlipEntry 2}

sysSRdnFlipPort OBJECT-TYPE
      SYNTAX  Integer32 
      MAX-ACCESS  read-only
      STATUS  current
      DESCRIPTION
      "The port number from which Flip was performed.
	   For DXC:
	   For external ports the convention used will be:
         - first two digits will be: (IO slot number+10)
         - last one/two digits will be the port number within the 
           card, in odd numbers:
           port1 = 1
           port2 = 3
           port3 = 5 
           etc...
           Example: port2 of IO slot 11 will be: 213 .
       For internal ports the convention used will be:
         - first two digits will be: (IO slot number+10)
         - last one/two digits will be the port number within the 
           card, in even numbers:
           port1 = 2
           port2 = 4
           port3 = 6 
           etc...
           Example: port2 of IO slot 11 will be: 214 .

       For MP:
	   For external ports, the value will be as that of the port in the
	       card. Example: external-3 -> 3
                          external-4 -> 4
	   For internal ports, the value will be 100 + the port in the
	       card. Example: internal-1 -> 101
                          internal-4 -> 104	       
    
       100=notApplicable (when Redundancy is at card level)."      
      ::= { sysSRdnFlipEntry 3 }

sysSRdnFlipCause OBJECT-TYPE
      SYNTAX  DisplayString 
      MAX-ACCESS  read-only
      STATUS  current
      DESCRIPTION
      "The last cause that caused the Flip from the Slot (Port)
       of sysSRdnSlot, sysSRdnPort."
      ::= { sysSRdnFlipEntry 4}

sysSRdnFlipDate OBJECT-TYPE
      SYNTAX  DisplayString 
      MAX-ACCESS  read-only
      STATUS  current
      DESCRIPTION
      "Flip event Date. The format will be the one selected by user for 
       sysSDateFormat."
      ::= { sysSRdnFlipEntry 5}

sysSRdnFlipTime OBJECT-TYPE
      SYNTAX  DisplayString 
      MAX-ACCESS  read-only
      STATUS  current
      DESCRIPTION
      "Flip event Time. The format will be hh:mm:ss."
      ::= { sysSRdnFlipEntry 6}

sysSRdnFlipTableClearCmd OBJECT-TYPE
      SYNTAX  INTEGER
       {
         off  (2),
         on   (3)
       }
      MAX-ACCESS  read-write
      STATUS  current
      DESCRIPTION
      "This command, when Set to 'on', clears the Redundancy  Flip 
       table (sysSRdnFlipTable).
       After clear is performed, the agent will turn the value to 'off'
       automatically."
      ::= { sysStatus 19 }

sysSRdnFlipCmd OBJECT-TYPE
      SYNTAX  OBJECT IDENTIFIER
      MAX-ACCESS  read-write
      STATUS  current
      DESCRIPTION
      "This object enables the user to send a command to the Agent, to Flip
       from a current Online IO card to its Redundant card.  
       The value sent will be an Object Identifier of an entry in the sysCRdnTable.
       This entry defines the Redundant couple of Slots on which the Flip
       is applied.
       Setting this object, will cause the Agent to Flip from current Online
       card to its Redundant card.
       This manual flip command is applicable only for entries having 
       Redundancy Mode=Y Cable.        
       
       For Vmux: This command will cause flipping from Secondary or Third Link to the
       Primary Link. If the active link is the primary link, the agent will flip to the
       secondary link. The value sent will be the Object Identifier of the following
       Table: agnCBuMlTable.
       
       Agent will send the value 0 for Get."
      ::= { sysStatus 20}

sysSBusTable OBJECT-TYPE
      SYNTAX SEQUENCE OF SysSBusEntry
      MAX-ACCESS not-accessible
      STATUS current
      DESCRIPTION
      "This table includes data and status about the internal DXC BUS."
      ::= { sysStatus 21 }

sysSBusEntry OBJECT-TYPE
      SYNTAX SysSBusEntry
      MAX-ACCESS not-accessible
      STATUS current
	DESCRIPTION  "An entry in table."
	INDEX { sysSBusPortIdx}
      ::= { sysSBusTable 1}

SysSBusEntry ::=
      SEQUENCE {
     sysSBusPortIdx     Integer32,
     sysSBusStatus      INTEGER,
     sysSBusCapturePort Integer32,
	 sysSBusUtilization Integer32 
	}

sysSBusPortIdx OBJECT-TYPE
      SYNTAX  Integer32 
      MAX-ACCESS  read-only
      STATUS  current
      DESCRIPTION
      "The DXC BUS port number:
         - first two digits will be: (IO slot number+10)
         - last one/two digits will be the Bus port number, in odd numbers:
           port1 = 1
           port2 = 3
           Example: port2 of IO slot 11 will be: 213."
      ::= { sysSBusEntry 1 }

sysSBusStatus OBJECT-TYPE
      SYNTAX  INTEGER 
       {
		 free    (1),
         physical(2),
         virtual (3)
       }
      MAX-ACCESS  read-only
      STATUS  current
      DESCRIPTION
      "The Status of sysSBusPortIdx.
       free    - not used
       physical - captured by the port of the card physically installed
       virtual  - captured virtually by another port. Example: DIM port 
                 (by Destination) or by Transparent T3/E3  port."
      ::= { sysSBusEntry 2}

sysSBusCapturePort OBJECT-TYPE
      SYNTAX  Integer32 
      MAX-ACCESS  read-only
      STATUS  current
      DESCRIPTION
      "The Port that Captured the sysSBusPortIdx.
       - if sysSBusStatus=free, the value will be 'none'=0
	   - else, if sysSBusStatus=fixed, the value will be: sysSBusPortIdx
       - else, the value will be according to the port index that captured
         this Bus Port (according to DXC port index convention):
         - xx1, xx3, xx11, xx13, xx31, xx33, xx2..xx56(even numbers)
         - xx = (IO slot number+10) "
      ::= { sysSBusEntry 3}

sysSBusUtilization OBJECT-TYPE
      SYNTAX  Integer32 
      MAX-ACCESS  read-only
      STATUS  current
      DESCRIPTION
      "Utilization of sysSBusPortIdx resources, in percent [%]."
      ::= { sysSBusEntry 4}

--IO Redundancy - Commands
--sysSRdnCmdTable was moved to be after sysCRdnTable, in order to solve
--an SNMPc limitation regarding forward reference of the indexes.

sysSAlrAttrIndication OBJECT-TYPE
      SYNTAX Integer32
      MAX-ACCESS read-only
      STATUS current
      DESCRIPTION
      "This object indicates the status of the Alarm Attributes 
       for the whole device.
       It is a sum of 2**(Bit-1). A Bit will be '1', when any alarm in the
	   device is Filtered/Masked/Inverted (respectively).
       The Bit assignment is:
       Bit 1: Filter (LSB)
       Bit 2: Mask
       Bit 3: Invert  (MSB).
       Examples:
       - Alarms are filtered and masked but not inverted: value=3
       - Alarm is Inverted (not filtered or masked): value=4
       - Alarm is masked (not inverted or filtered): value=2 "
      ::= { sysStatus 23 }


--System Current Alarm Table
--
--This table contains all Events and only the major/minor alarms
--whose status is ON.

sysSAlrTable OBJECT-TYPE
      SYNTAX SEQUENCE OF SysSAlrEntry
      MAX-ACCESS not-accessible
      STATUS current
      DESCRIPTION
      "List of system level current existing alarms ."
      ::= { sysCurrentAlr 1 }

sysSAlrEntry OBJECT-TYPE
      SYNTAX SysSAlrEntry
      MAX-ACCESS not-accessible
      STATUS current
	DESCRIPTION  "An entry in table."
	INDEX { sysSAlrIdx}
      ::= { sysSAlrTable 1}

SysSAlrEntry ::=
      SEQUENCE {
     	sysSAlrIdx       Integer32,
     	sysSAlrCode      Integer32,
     	sysSAlrState     INTEGER, --Severity
     	sysSAlarmMask    INTEGER,
     	sysSAlarmInvert  INTEGER,
		sysSAlarmOnOff   INTEGER,
		sysSAlarmCounter Integer32 
	}

sysSAlrIdx OBJECT-TYPE
      SYNTAX  Integer32
      MAX-ACCESS  read-only
      STATUS  current
      DESCRIPTION
      "An index number of the current system alarms."
      ::= { sysSAlrEntry 1 }

sysSAlrCode OBJECT-TYPE
      SYNTAX  Integer32
      MAX-ACCESS  read-only
      STATUS  current
      DESCRIPTION
      "This object indicates a code related to a specific
       alarm description. The list of codes and their related
       descriptions will be sent to NMS request (for display purpose)
       by alrGenTable."
      ::= { sysSAlrEntry 2 }

sysSAlrState OBJECT-TYPE
      SYNTAX  INTEGER {
   event    (3),
   minor    (4),
   major    (5),
   warning  (6),
   critical (7)
       }
      MAX-ACCESS  read-only
      STATUS  current
      DESCRIPTION
      "This object indicates the alarm Severity."      
      ::= { sysSAlrEntry 3 }

sysSAlarmMask OBJECT-TYPE
      SYNTAX  INTEGER {
  off(2),
  on (3)
       }
      MAX-ACCESS  read-only
      STATUS  current
      DESCRIPTION
      "Alarm Mask is : on/off."
      ::= { sysSAlrEntry 4 }

sysSAlarmInvert OBJECT-TYPE
      SYNTAX  INTEGER {
  off(2),
  on (3)
       }
      MAX-ACCESS  read-only
      STATUS  current
      DESCRIPTION
      "Alarm Invert is : on/off."
      ::= { sysSAlrEntry 5 }

sysSAlarmOnOff OBJECT-TYPE
      SYNTAX  INTEGER {
  off(2),
  on (3)
       }
      MAX-ACCESS  read-only
      STATUS  current
      DESCRIPTION
      "Alarm state is : on/off."
      ::= { sysSAlrEntry 6 }

sysSAlarmCounter OBJECT-TYPE
      SYNTAX  Integer32
      MAX-ACCESS  read-only
      STATUS  current
      DESCRIPTION
      "A counter - how many times the alarm occured (ON) since last
       clear operation or since last Reset."
      ::= { sysSAlrEntry 7 }

sysSAlrClearCmd  OBJECT-TYPE
      SYNTAX  INTEGER
       {
  off(2),
  on (3)
       }
      MAX-ACCESS  read-write
      STATUS  current
      DESCRIPTION
      "Setting this attribute to ON, will enforce a  clear 
       operation on the system level alarms . Upon completion, 
       the value will automatically change to off(2)."
      ::= { sysCurrentAlr 2 }


sysSAlrClearAllCmd  OBJECT-TYPE
      SYNTAX  INTEGER
       {
  off(2),
  on (3)
       }
      MAX-ACCESS  read-write
      STATUS  current
      DESCRIPTION
      "Setting this attribute to ON, will enforce a  clear 
       operation on all levels alarms . Upon completion, 
       the value will automatically change to off(2)."
      ::= { sysCurrentAlr 3 }

sysSAlrMaskAll  OBJECT-TYPE
      SYNTAX  INTEGER
       {
  off(2),
  on (3)
       }
      MAX-ACCESS  read-write
      STATUS  current
      DESCRIPTION
      "on(3)  - will cause masking of all the system level alarms.
                These alarms will not be sent to NMS and will not 
                be taken into account for Alarms Status.
       off(2) - will unmask all system level alarms except those 
                masked via the sysSAlrMask. "
      ::= { sysCurrentAlr 4 }

sysSAlrMask OBJECT-TYPE
      SYNTAX OCTET STRING  (SIZE (8))
      MAX-ACCESS read-write
      STATUS current
   DESCRIPTION
   "This object is a mask that indicates which system level 
    alarms are masked. The masked alarms (their bit is set to 
    '1') are neither sent to the manager, nor taken into account
    for alarm status and LEDs.
    Bit no. = Alarm code
    The bits that do not belong to the system level will be 0.
    This object is applicable only when sysSAlrMaskAll=off 
    (otherwise all system alarms are masked).
    Example: When Alarms having the codes 6 and 11 are masked,
             the value of this object will be 840 (hex)."
      ::= { sysCurrentAlr 5 }

sysSAlrDataUpdateCmd  OBJECT-TYPE
      SYNTAX  INTEGER
       {
        off(2),
        on (3)
       }
      MAX-ACCESS  read-write
      STATUS  current
      DESCRIPTION
      "on(3)  - will cause Update of the Alarms Severity, Attributes and Report
                tables.
       off(2) - Upon completion, the value will automatically change to off(2)."
      ::= { sysCurrentAlr 6 }


--System Buffer Alarm Table
--
--This table contains all Events and all the major/minor alarms
--The buffer is cyclic and contains the most recent alarms.
--Since this table contains also the alarms occurence time,
--(appearance/disappearance for major/minor alarms), an alarm may 
--appear several times in this table, with alternate state: major, 
--off, major, etc.. 

sysBufferAlrTable OBJECT-TYPE
      SYNTAX SEQUENCE OF SysBufferAlrEntry
      MAX-ACCESS not-accessible
      STATUS current
      DESCRIPTION
      "List of current existing alarms (of all levels)."
      ::= { sysBufferAlr 1 }

sysBufferAlrEntry OBJECT-TYPE
      SYNTAX SysBufferAlrEntry
      MAX-ACCESS not-accessible
      STATUS current
	DESCRIPTION  "An entry in table."
	INDEX { sysBufferAlrIdx}
      ::= { sysBufferAlrTable 1}

SysBufferAlrEntry ::=
      SEQUENCE {
     	sysBufferAlrIdx   Integer32,
     	sysBufferAlrCode  Integer32,
     	sysBufferAlrState INTEGER,
     	sysBufferAlrSlot  INTEGER,
     	sysBufferAlrPort  Integer32,
     	sysBufferAlrDate  DisplayString,
     	sysBufferAlrTime  DisplayString,
		sysBufferAlrUpTime  TimeTicks,
		sysBufferAlrInfo  SnmpAdminString
				      }

sysBufferAlrIdx OBJECT-TYPE
      SYNTAX  Integer32
      MAX-ACCESS  read-only
      STATUS  current
      DESCRIPTION
      "An index number of the current alarms."
      ::= { sysBufferAlrEntry 1 }

sysBufferAlrCode OBJECT-TYPE
      SYNTAX  Integer32
      MAX-ACCESS  read-only
      STATUS  current
      DESCRIPTION
      "This object indicates a code related to a specific
       alarm description. The list of codes and thir related
       descriptions will be known by the NMS (for display purpose)
       and will appear in the unit's user manual."
      ::= { sysBufferAlrEntry 2 }

sysBufferAlrState OBJECT-TYPE
      SYNTAX  INTEGER {
     off      (2),
     event    (3),
     minor    (4),
     major    (5),
	 warning  (6),
     critical (7)
       }
      MAX-ACCESS  read-only
      STATUS  current
      DESCRIPTION
      "This object indicates the alarm type.
       minor/major/warning/critical - indicates appearance of the problem 
                     and the type.
       event       - indicates occurence of an event.
       off         - indicates disappearance of an alarm. "      
      ::= { sysBufferAlrEntry 3 }


sysBufferAlrSlot OBJECT-TYPE
      SYNTAX  INTEGER 
       {
       psA   (1),
       psB   (2),
       clA   (3),
       clB   (4),
       io1   (5),
       io2   (6),
       io3   (7),
       io4   (8),
       io5   (9),
       io6  (10),
       io7  (11),
       io8  (12),
       io9  (13),
       io10 (14),
       io11 (15),
       io12 (16),
       io13 (17),
       io14 (18),
       io15 (19),
	  local (20),
	   psC  (21),
    kmxPsA (101),
    kmxPsB (102),
    kmxMlA (103),
    kmxMlB (104),
    kmxCl  (105),
    kmxOpt (106),
    kmxIO1 (107),
    kmxIO2 (108),
    kmxIO3 (109),
    kmxIO4 (110),
    kmxIO5 (111),
    kmxIO6 (112),
    kmxIO7 (113),
    kmxIO8 (114),
    kmxIO9 (115),
    kmxIO10(116),
    kmxIO11(117),
    kmxIO12(118),
	remote (120),
    notApplicable (255)
       }
      MAX-ACCESS  read-only
      STATUS  current
      DESCRIPTION
      "The slot number this alarm refers to.
       When the alarm refers to a system function OR the DACS agent 
       is a stand-alone unit, the value will be 'notApplicable(255)'.
       local/remote - for OP-4 device."      
      ::= { sysBufferAlrEntry 4 }

sysBufferAlrPort OBJECT-TYPE
      SYNTAX  Integer32 
      MAX-ACCESS  read-only
      STATUS  current
      DESCRIPTION
      "The port number this alarm refers to.
       If the port number is irrelevant to this alarm (if it is
       a system/card level alarm) the value will be 9999."     
      ::= { sysBufferAlrEntry 5 }

sysBufferAlrDate OBJECT-TYPE
      SYNTAX  DisplayString (SIZE (0..255))
      MAX-ACCESS  read-only
      STATUS  current
      DESCRIPTION
      "The date when the alarm occured. The format will be according
       to sysSDateFormat."     
      ::= { sysBufferAlrEntry 6 }


sysBufferAlrTime OBJECT-TYPE
      SYNTAX  DisplayString (SIZE (0..255))
      MAX-ACCESS  read-only
      STATUS  current
      DESCRIPTION
      "The time when the alarm occured." 
      ::= { sysBufferAlrEntry 7 }

sysBufferAlrUpTime OBJECT-TYPE
    SYNTAX  TimeTicks
    MAX-ACCESS  read-only
    STATUS  current
    DESCRIPTION
       "The time when the alarm occured.
       This parameter holds the sysUpTime value when the alarm occured."
    ::= { sysBufferAlrEntry 8 }

sysBufferAlrInfo OBJECT-TYPE
	SYNTAX      SnmpAdminString
	MAX-ACCESS  read-only
    STATUS      current
	DESCRIPTION
      "This parameter includes information about the alarm (additional to the Description)."
	::= { sysBufferAlrEntry 9}        


sysBufferAlrClearCmd OBJECT-TYPE
      SYNTAX  INTEGER
       {
  off(2),
  on (3)
       }
      MAX-ACCESS  read-write
      STATUS  current
      DESCRIPTION
      "Setting this attribute to ON, will enforce a  clear 
       operation on the Alarms Buffer. Upon completion, 
       the value will automatically change to off(2)."
      ::= { sysBufferAlr 2 }


--System Configuration Parameters

sysCClkSrcTable  OBJECT-TYPE
      SYNTAX SEQUENCE OF SysCClkSrcEntry
      MAX-ACCESS not-accessible
      STATUS  current
      DESCRIPTION
      "All the entries of this table are identical (have the 
       same value) for all the configurations (1..255) except 
       the TmpCnfg.
       For devices with more than one configuration:
       The write operation into the Table Objects is valid only
       for the TmpCnfg entry."
       ::= { sysConfig 1}

sysCClkSrcEntry OBJECT-TYPE
      SYNTAX SysCClkSrcEntry
      MAX-ACCESS not-accessible
      STATUS current
	DESCRIPTION  "An entry in table."
	INDEX {sysCClkCnfgIdx, sysCClkSrcIdx}
      ::= { sysCClkSrcTable 1}

SysCClkSrcEntry ::=
      SEQUENCE {
   sysCClkCnfgIdx              Integer32,
   sysCClkSrcIdx               INTEGER,
   sysCClkSrcMode              INTEGER,
   sysCClkSrcPrt               Integer32,
   sysCClkStationFreq          INTEGER,
   sysCClkRevertiveTimeout     Integer32,
   sysCClkStationIf            INTEGER,
   sysCClkStationCableMode 	   INTEGER,
   sysCClkStationOutState 	   INTEGER,
   sysCClkSsmBased 		       INTEGER,
   sysCClkSSubsystemSlot       INTEGER, 
   sysCClkRecoveredID     	   Unsigned32 
 	}

sysCClkCnfgIdx OBJECT-TYPE
      SYNTAX Integer32 (1..2147483647)
      MAX-ACCESS read-only
      STATUS current
      DESCRIPTION
      "This attribute indicates the Idx of the Cnfg being 
       accessed ; Idx of 255 relates to the TmpCnfg.
       It can be also a combination of the configuration number and the 
       Card/Port/Other System index."
      ::= { sysCClkSrcEntry 1}

sysCClkSrcIdx OBJECT-TYPE
      SYNTAX  INTEGER 
       {
     master    (1),
     fallback  (2)
    }
      MAX-ACCESS  read-only
      STATUS  current
      DESCRIPTION
      "An index in the table. There are only two entries in the 
       table. 
       master   - refers Master clock parameters 
       fallback - refers Fallback clock parameters"
      ::= { sysCClkSrcEntry 2}

sysCClkSrcMode OBJECT-TYPE
      SYNTAX  INTEGER
       {
     none            (1),
     internal        (2),
     rxClk           (3),
     station         (4),  -- station A (for IPmux1000)
     lbt             (5),
	 ntr             (6),
	 adaptive        (7),  
	 stationB        (8),
	 automatic		 (9),
	 system         (10),
	 sSubSystem     (11),
	 recovered		(12),  
     notApplicable (255)
       }
      MAX-ACCESS  read-write
      STATUS  current
      DESCRIPTION
      "This entry indicates the source the nodal timing is 
       locked to.
       none     - is an invalid option for Master clock.
       internal - is an invalid option for Fallback clock .
       station  - is an invalid option for a stand-alone unit. 
       lbt      - loop-back timing
	   ntr      - Network Time Reference 
	   adaptive - clock locking is achieved by altering the clock 
	              according to the data load
	   system   - irrelevant when sysCClkCnfgIdx refers to System Clock.
	   sSubSystem - SONET/SDH Sub System.   
	   recovered  - clock recovery.   
       notApplicable - for ML source of Kmux or ML Timing 
                       combinations when Master/Fallback clock are
                       not applicable."
      ::= { sysCClkSrcEntry 3}


sysCClkSrcPrt OBJECT-TYPE
      SYNTAX  Integer32
      MAX-ACCESS  read-write
      STATUS  current
      DESCRIPTION
      "This entry is valid only when working in rxClk mode
       (for IPmux1000 this entry will be valid whe working in LBT mode).
       
       For ACE2002 in case of invalid entry the return value 
       will be 0. 
       For other products in case of invalid entry the return 
       value will be 9999.

       The valid port number depends on the IO slot no.,  the 
       installed card type and the port type: outside, inside, 
       SP.
    * The SP ports will be numbered as follows:
     - SP port 1 :  1
     - SP port 2 :  2
	   For external ports the convention used will be (for DXC):
         - first two digits will be: (IO slot number+10)
         - last one/two digits will be the port number within the 
           card, in odd numbers:
           port1 = 1
           port2 = 3
           port3 = 5 
           etc...
           Example: port2 of IO slot 11 will be: 213 .
       For internal ports the convention used will be (for DXC):
         - first two digits will be: (IO slot number+10)
         - last one/two digits will be the port number within the 
           card, in even numbers:
           port1 = 2
           port2 = 4
           port3 = 6 
           etc...
           Example: port2 of IO slot 11 will be: 214 .

      For Kmux, the port will be according to : Slot*100+Ch.
      
      For ACE2002,  LA140 and IPmux1000 (GMUX), the port will be ifIndex."
      ::= { sysCClkSrcEntry 4}

sysCClkStationFreq OBJECT-TYPE
      SYNTAX  INTEGER
       {
     notApplicable   (1),
     f1544Khz        (2), -- DS1
     f2048Khz        (3)  -- E1
       }
      MAX-ACCESS  read-write
      STATUS  current
      DESCRIPTION
      "This entry indicates the frequency of the station clock 
       when the source is 'station'.  
       The value will be applicable only when the sysCClkSrcMode is 
       'station'. "
      ::= { sysCClkSrcEntry 5}

sysCClkRevertiveTimeout OBJECT-TYPE
      SYNTAX  Integer32
      MAX-ACCESS  read-write
      STATUS  current
      DESCRIPTION
      "The time in seconds in which the system will monitor the higher
       level clock source, before decision to revert to that clock.
       In case the time is zero, revertive mode will be disabled."
      ::= { sysCClkSrcEntry 6}

sysCClkStationIf OBJECT-TYPE
      SYNTAX  INTEGER
       {
       notApplicable (1),
       g703          (2), --E1 balanced
       rs422         (3), --E1
	   g703E1Unbalanced (4),
	   g703T1        (5),
	   rs422T1       (6)
       }
      MAX-ACCESS  read-write
      STATUS  current
      DESCRIPTION
      "This entry indicates the electrical interface connected to the
       station clock, when the source is 'station'.  
       The value will be applicable only when the sysCClkSrcMode is 
       'station'. "
      ::= { sysCClkSrcEntry 7}

sysCClkStationCableMode OBJECT-TYPE
      SYNTAX  INTEGER
       {
       notApplicable (1),
       normal        (2),
       yCable        (3)
       }
      MAX-ACCESS  read-write
      STATUS  current
      DESCRIPTION
      "This parameter indicates whether both Station clocks get their 
      clock from the same source (Y Cable)or each one get its clock independently.
       The value will be applicable only when the sysCClkSrcMode is 'station'. "
      ::= { sysCClkSrcEntry 8}

sysCClkStationOutState OBJECT-TYPE
      SYNTAX  INTEGER
       {
       notApplicable (1),
       disabled      (2),
       enabled       (3)
       }
      MAX-ACCESS  read-write
      STATUS  current
      DESCRIPTION
      "This parameter indicates whether station clock can 
      send its clock to another device.
	  The value will be applicable only when the sysCClkSrcMode is 'station'. "
      ::= { sysCClkSrcEntry 9}

sysCClkSsmBased    OBJECT-TYPE
      SYNTAX  INTEGER
       {
       notApplicable (1),
       no            (2),
       yes           (3)
       }
      MAX-ACCESS  read-write
      STATUS  current
      DESCRIPTION
      "This parameter indicates whether clock source 
       will be selected based on receive clock quality, 
       indicated in S1 byte inside SONET/SDH overhead, 
       (encoded as SSM - Synchronization Status Messaging).
       It is relevant only for sysCClkSrcIdx=master.
       When the value is Yes, sysCClkSrcMode must be notApplicable."
      ::= { sysCClkSrcEntry 10}
      
sysCClkSSubsystemSlot OBJECT-TYPE
      SYNTAX  INTEGER
       {
       notApplicable (1),
       clA           (3),
       clB           (4)
       }
      MAX-ACCESS  read-write
      STATUS  current
      DESCRIPTION
      "This entry indicates the Slot from which the S Subsytem Source
       will be taken.  
       The value will be applicable only when the sysCClkSrcMode is 
       'sSubsystem'. "
      ::= { sysCClkSrcEntry 11}	

sysCClkRecoveredID OBJECT-TYPE
      SYNTAX  Unsigned32
      MAX-ACCESS  read-write
      STATUS  current
      DESCRIPTION
      "This entry indicates the Recovered Clock ID.
       The value will be applicable only when sysCClkSrcMode is 'recovered'."
      ::= { sysCClkSrcEntry 12}


sysCnfgTable  OBJECT-TYPE
      SYNTAX SEQUENCE OF SysCnfgEntry
      MAX-ACCESS not-accessible
      STATUS  current
      DESCRIPTION
      "All the entries of this table are identical (have the 
       same value) for all the configurations (1..255) except 
       the TmpCnfg.
       The write operation into the Table Objects is valid only
       for the TmpCnfg entry."
       ::= { sysConfig 2}

sysCnfgEntry OBJECT-TYPE
      SYNTAX SysCnfgEntry
      MAX-ACCESS not-accessible
      STATUS current
	DESCRIPTION  "An entry in table."
	INDEX {sysCnfgIdx}
      ::= { sysCnfgTable 1}

SysCnfgEntry ::=
      SEQUENCE {
   sysCnfgIdx             Integer32,
   sysCMatrixMode         INTEGER,
   sysCIsdnFormat         INTEGER,
   sysCRoutingOnEth       INTEGER,
   sysCAutoConfigEnable   INTEGER,
   sysCIntTsAllocMode     INTEGER,
   sysCBuPrimaryPort	  INTEGER,
   sysCEnableLanOverTdm   INTEGER,
   sysCSs7FisuSuppression Integer32,
   sysCBuRecMode          INTEGER
      }

sysCnfgIdx OBJECT-TYPE
      SYNTAX Integer32 
      MAX-ACCESS read-only
      STATUS current
      DESCRIPTION
      "This attribute indicates the Idx of the Cnfg(1..255) being 
       accessed ; Idx of 255 relates to the TmpCnfg.
	   For Gmux2000 the range limitation (1..255) was discarded
       since the Idx is computed as: <IO Card No.> x 1000 + 255."
      ::= { sysCnfgEntry 1}

sysCMatrixMode OBJECT-TYPE
      SYNTAX  INTEGER
       {
  notApplicable  (1),
  bidirectional  (2),
  unidirectional (3)
       }
      MAX-ACCESS  read-write
      STATUS  current
      DESCRIPTION
      "Indicates the TS Matrix Mode:
    bidirectional  - TS Assignment Matrix is symmetric.
    unidirectional - TS Assignment Matrix can be asymmetric.
       notApplicable - for agents that do not support this feature."
      ::= { sysCnfgEntry 2}

sysCIsdnFormat OBJECT-TYPE
      SYNTAX  INTEGER
       {
  notApplicable (1),
  te  (2),
  nt  (3)
       }
      MAX-ACCESS  read-write
      STATUS  current
      DESCRIPTION
      "ISDN format. This parameter controls the operation mode of
    the ISDN ports.
    te - ISDN timing is derived from the signal received
         from the equipment it is connected to.
    nt - timing of the transmit path is locked to the nodal 
         timing source.
       notApplicable - for agents that do not support this feature."
      ::= { sysCnfgEntry 3}

sysCRoutingOnEth OBJECT-TYPE
      SYNTAX  INTEGER
       {
      notApplicable (1),
      none          (2),  
      proprietary   (3),
      rip2          (4),
	  rip1          (5),
	  rip1and2      (6)
       }
      MAX-ACCESS  read-write
      STATUS  current
      DESCRIPTION
      "Mng Routing Protocol on the online CL Ethernet port,
       or on device Ethernet  port dedicated for mangement."
      ::= { sysCnfgEntry 4}

sysCAutoConfigEnable OBJECT-TYPE
      SYNTAX  INTEGER
       {
      notApplicable (1),
      disable       (2),  
      enable        (3)
       }
      MAX-ACCESS  read-write
      STATUS  current
      DESCRIPTION
      "This object enables user to enable/disable activating
       the Auto Configuration. When Auto Configuration is activated,
       the device learns its configuration Automatically from the Net 
       it is connected to."
      ::= { sysCnfgEntry 5}

sysCIntTsAllocMode OBJECT-TYPE
      SYNTAX  INTEGER
       {
      notApplicable (1),
      static        (2),  
      dynamic       (3),
	  staticOneToOne(4)
       }
      MAX-ACCESS  read-write
      STATUS  current
      DESCRIPTION
      "This object enables user to select the mode of Internal TS 
       Allocation.
       static - user has to select for each Dynamic card port, the 
                Maximum TSs expected to be connected (including future
                growth). This number will be allocated to the ports,
                so that if number of connected TSs will grow within
                the limits of this Maximum TS limit, no disruption
                of data flow will occur for other ports.
       dynamic- TS allocation is done dynamically according to the 
                connected TSs. No future reservations are done. This mode
                may cause data disruption on other ports/slots if user
                will want to change the number of connected TSs for a
                Dynamic card port.
	   staticOneToOne - user has to select for each Dynamic card port, the 
                Maximum TSs expected to be connected (including future
                growth). In addition, the TSs themselves cannot be higher
                than this defined Maximum (e.g if Maximum TSs=5 user cannot 
                selects TSs higher than 5). This mode ensures that if number 
                of TSs grow within the limits of this Maximum TS limit, no 
                disruption of data flow will occur for other ports AND for 
                the selected port itself. 
       Default=static(2).         "
      ::= { sysCnfgEntry 6}

sysCBuPrimaryPort OBJECT-TYPE
      SYNTAX  INTEGER
       {
      noBackup     (2),
      e1T1orSerial (3),  
      eth          (4)
	   }
      MAX-ACCESS  read-write
      STATUS  current
      DESCRIPTION
      "This object enables the user to configure a Backup mechanism.
       If a backup mechanism exists, it is possible to configure the primary port.
       The traffic will flow via the primary port when the port functionality is OK.

       In Vmux-2100 device the backup mechanism is relevant for the Main Board only.
       The primary port can be the E1/T1/Serial port or the ETH port. "
      ::= { sysCnfgEntry 7}

  sysCEnableLanOverTdm  OBJECT-TYPE
      SYNTAX  INTEGER
       {
      enableAll         (2),
      enableVoiceOnly   (3),  
      enableVoiceAndMng (4)
	   }
      MAX-ACCESS  read-write
      STATUS  current
      DESCRIPTION
      "This object enables/disables transferring traffic from the LAN port
       to the TDM port. It is possible to enable only part of the traffic on the
       TDM port for security reasons or in order to minimize the bandwidth ."
       ::= { sysCnfgEntry 8}

  sysCSs7FisuSuppression  OBJECT-TYPE
      SYNTAX  Integer32
      MAX-ACCESS  read-write
      STATUS  current
      DESCRIPTION
      "SS7 Suppresion is used for SS7 Spoofing.
       The SS7 spoofing terminates the keep alive messages from the local VMUX
       without sending them over the network, thus improving the bandwidth utilization.
	   FISU means Fill in Service Unit - Keep alive that is sent when no one is talking
	   on the line.

       This object enables the configuration of the SS7 Keep Alive packet % that will
       be discarded.
       
       Legal Values: 0 - No Suppression, 10%, 20%, 30% .. 90%
       
       Example: For a value of 10, 1 keep alive packet will be discarded out of
                10 keep alive packets that were supposed to be sent over the network."
       ::= { sysCnfgEntry 9}

  sysCBuRecMode OBJECT-TYPE
      SYNTAX  INTEGER
       {
          auto        (2),
          manual      (3)
       }          
      MAX-ACCESS  read-write
      STATUS  current
      DESCRIPTION
      "Recovery Mode. This object determines if after recovery
       of the Primary Link (used in Vmux) it will become on-line again or not:
       auto - automatic. In this case, the failed Link will become
           on-line again after recovery, automatically.
       manual - In this case, the failed Link will not become
             on-line again after recovery but user can manually flip
             to this Link."
       ::= { sysCnfgEntry 10}


--System I/O Redundacy Table
--
--This table contains all I/O cards/ports that have redundancy,
--data about the redundant card/port and parameters regarding the
--redundancy operation.
--The table indexes are Cnfg and the Primary card&port 


sysCRdnTable OBJECT-TYPE
      SYNTAX SEQUENCE OF SysCRdnEntry
      MAX-ACCESS not-accessible
      STATUS current
      DESCRIPTION
      "Configuration of all Redundant I/O cards and ports.
       The write operation into the table objects is valid only
       for the TmpCnfg.
       A Slot/Port that have no Redundancy, will not exist in this
       table."
      ::= { sysConfig 3 }

sysCRdnEntry OBJECT-TYPE
      SYNTAX SysCRdnEntry
      MAX-ACCESS not-accessible
      STATUS current
	DESCRIPTION  "An entry in table."
	INDEX { sysCRdnCnfgIdx, sysCRdnPrimeSlot, sysCRdnPrimePort}
      ::= { sysCRdnTable 1}

SysCRdnEntry ::=
      SEQUENCE {
     sysCRdnCnfgIdx       				Integer32,
     sysCRdnPrimeSlot     				INTEGER,
     sysCRdnPrimePort     				Integer32,
     sysCRdnSecSlot       				INTEGER,
     sysCRdnSecPort       				Integer32,
     sysCRdnMode          				INTEGER,
     sysCRdnRecMode       				INTEGER,
     sysCRdnRecTime       				Integer32,
     sysCRdnHwSwFlip      				INTEGER,
     sysCRdnRowStatus     				RowStatus,
	 sysCRdnOnline        				INTEGER,
	 sysCRdnSwitchingMode 				INTEGER,
	 sysCRdnFlipUponEvent 				Integer32,
	 sysCRdnLosOrLofTime  				Integer32,
	 sysCRdnEventsTimeWindow			Integer32,
	 sysCRdnSequenceNumberThreshold		Integer32,
	 sysCRdnBufferErrorsThreshold		Integer32,
	 sysCRdnBuffUnderrunTime			Integer32,
	 sysCRdnPrimePriority 				INTEGER,
	 sysCRdnSecPriority 				INTEGER,
	 sysCRdnWTR                         Unsigned32,
	 sysCRdnName	 					SnmpAdminString,
	 sysCRdnTxDownDurationUponFlip	 	Unsigned32
     }

sysCRdnCnfgIdx OBJECT-TYPE
      SYNTAX  Integer32
      MAX-ACCESS  read-only
      STATUS  current
      DESCRIPTION
      "This object indicates the Idx of the Cnfg(1..255) being 
       accessed ; Idx of 255 relates to the TmpCnfg."
      ::= { sysCRdnEntry 1 }

sysCRdnPrimeSlot OBJECT-TYPE
      SYNTAX  INTEGER 
       {
       io1   (5),
       io2   (6),
       io3   (7),
       io4   (8),
       io5   (9),
       io6  (10),
       io7  (11),
       io8  (12),
       io9  (13),
       io10 (14),
       io11 (15),
       io12 (16),
       io13 (17),
       io14 (18),
       io15 (19),
       notApplicable (255)
       }
      MAX-ACCESS  read-only
      STATUS  current
      DESCRIPTION
      "The slot number of the Primary card of Redundancy.
       The Primary card should be the card that user wishes to be
       the online card (usually the more important one).
       For some Redundancy modes the importance of the redundant 
       cards/ports is the same. "      
      ::= { sysCRdnEntry 2 }

sysCRdnPrimePort OBJECT-TYPE
      SYNTAX  Integer32 
      MAX-ACCESS  read-only
      STATUS  current
      DESCRIPTION
      "The port number.
	   For DXC:
	   For external ports the convention used will be:
         - first two digits will be: (IO slot number+10)
         - last one/two digits will be the port number within the 
           card, in odd numbers:
           port1 = 1
           port2 = 3
           port3 = 5 
           etc...
           Example: port2 of IO slot 11 will be: 213 .
       For internal ports the convention used will be:
         - first two digits will be: (IO slot number+10)
         - last one/two digits will be the port number within the 
           card, in even numbers:
           port1 = 2
           port2 = 4
           port3 = 6 
           etc...
           Example: port2 of IO slot 11 will be: 214 .

       For MP:
	   For external ports, the value will be as that of the port in the
	       card. Example: external-3 -> 3
                          external-4 -> 4
	   For internal ports, the value will be 100 + the port in the
	       card. Example: internal-1 -> 101
                          internal-4 -> 104
       For IP Bundles, the value will be the Bundle ifIndex. For an IP Bundle 
       that is in an External Device (not in this MP), the value will be:
       70,000 + ifIndex of Secondary Bundle.                    	       

       For other products - refer to product specification.

       100=notApplicable (when Redundancy is at card level)."      
      ::= { sysCRdnEntry 3 }

sysCRdnSecSlot OBJECT-TYPE
      SYNTAX  INTEGER 
       {
       io1   (5),
       io2   (6),
       io3   (7),
       io4   (8),
       io5   (9),
       io6  (10),
       io7  (11),
       io8  (12),
       io9  (13),
       io10 (14),
       io11 (15),
       io12 (16),
       io13 (17),
       io14 (18),
       io15 (19),
       notApplicable (255)
       }
      MAX-ACCESS  read-create
      STATUS  current
      DESCRIPTION
      "The slot number of the Secondary card of Redundancy matching
       the Primary slot."      
      ::= { sysCRdnEntry 4 }

sysCRdnSecPort OBJECT-TYPE
      SYNTAX  Integer32 
      MAX-ACCESS  read-create
      STATUS  current
      DESCRIPTION
      "The port number.
	   For DXC:
	   For external ports the convention used will be:
         - first two digits will be: (IO slot number+10)
         - last one/two digits will be the port number within the 
           card, in odd numbers:
           port1 = 1
           port2 = 3
           port3 = 5 
           etc...
           Example: port2 of IO slot 11 will be: 213 .
       For internal ports the convention used will be:
         - first two digits will be: (IO slot number+10)
         - last one/two digits will be the port number within the 
           card, in even numbers:
           port1 = 2
           port2 = 4
           port3 = 6 
           etc...
           Example: port2 of IO slot 11 will be: 214 .

       For MP:
	   For external ports, the value will be as that of the port in the
	       card. Example: external-3 -> 3
                          external-4 -> 4
	   For internal ports, the value will be 100 + the port in the
	       card. Example: internal-1 -> 101
                          internal-4 -> 104	       
       For IP Bundles, the value will be the Bundle ifIndex. For an IP Bundle 
       that is in an External Device (not in this MP), the value will be: 0.                  	       

       For other products - refer to product specification.

       100=notApplicable (when Redundancy is at card level)."      
      ::= { sysCRdnEntry 5 }

sysCRdnMode OBJECT-TYPE
      SYNTAX  INTEGER
       {
          dualCableAIS        (2),
          yCable              (3),
          dualCableParallelTx (4),
          backup              (5),
          singleSlotProtection(6),
		  onePlusOne		  (7),
		  oneToOne			  (8),
		  linkAggregation     (9),  --802.3ad
		  manual              (10)		
       }
      MAX-ACCESS  read-create
      STATUS  current
      DESCRIPTION
      "Redundancy Mode.
       DXC supports: yCable(3), singleSlotProtection(6) and dualCableParallelTx(4)
       MP  supports: yCable(3), dualCableParallelTx(4), onePlusOne(7) and oneToOne(8).
	                 (dualCableAIS and backup were planned for MP but were not 
					  implemented).
       backup - will be used when a port is backup of more than one port.
       IPmux: onePlusOne(7) and oneToOne(8) are used for Bundle redundancy."
      ::= { sysCRdnEntry 6 }

sysCRdnRecMode OBJECT-TYPE
      SYNTAX  INTEGER
       {
          auto        (2),
          manual      (3),
		  nonRevertive(4)
       }
      MAX-ACCESS  read-create
      STATUS  current
      DESCRIPTION
      "Recovery Mode. This object determines if after recovery
       of the failed Primary card/port it will become on-line again or not:
       auto - automatic . In this case, the failed card/port will become
           on-line again after recovery, automatically.
       manual - In this case, the failed card/port will not become
             on-line again after recovery. But, user can manually flip
             to this card/port.
       nonRevertive - same as manual, but here user CANNOT manually flip
             to this card/port. It will become on-line again, only if the
             Secondary/Backup card/port will fail."
      ::= { sysCRdnEntry 7 }

sysCRdnRecTime OBJECT-TYPE
      SYNTAX  Integer32 
      MAX-ACCESS  read-create
      STATUS  current
      DESCRIPTION
      "Redundancy Recovery Time (sec). After switching to the current 
       online card, the next switch can be performed only after a 
       minimum time, indicated by this object.
	   Valid Values: 0..300, 65535.
       65535=NA.
       This object is applicable only when sysCRdnRecMode=auto."
      ::= { sysCRdnEntry 8 }

sysCRdnHwSwFlip OBJECT-TYPE
      SYNTAX  INTEGER
       {
          notApplicable(1),
          hw           (2),
          sw           (3)
       }
      MAX-ACCESS  read-create
      STATUS  current
      DESCRIPTION
      "HW or SW decision for Redundancy Flip. 
       This object is applicable only for sysCRdnMode=singleSlotProtection.
       HW - decision is by I/O card
       SW - decision is by CL SW."
      ::= { sysCRdnEntry 9 }

sysCRdnRowStatus  OBJECT-TYPE
     SYNTAX  RowStatus
     MAX-ACCESS   read-create
     STATUS   current
     DESCRIPTION
     "This parameter allows NMS to create/delete entries of this table.
      The possible supported RowStatus values are
      active (1) and destroy (6).
      
      For Vmux-2100 the supported values are:
      active (1), createAndGo (4) and destroy (6)." 
     ::= { sysCRdnEntry 10 }

sysCRdnOnline OBJECT-TYPE
      SYNTAX  INTEGER
       {
          notApplicable (1),
          primary       (2),
          secondary     (3)
       }
      MAX-ACCESS  read-only
      STATUS  current
      DESCRIPTION
      "Status - who is the Online (current) Redundancy Slot/Port. 
       This object shows only the Online Slot/Port regarding the Redundancy. 
       mdlSActivity or prtGenActiveStatus of the same Slot/Port may be Offline."
      ::= { sysCRdnEntry 11 }

sysCRdnSwitchingMode  OBJECT-TYPE
      SYNTAX  INTEGER
       {
          notApplicable    (1),
          biDirectional    (2),	--1+1
          uniDirectional   (3),	--1:1
		  linkAggregation  (4)  --802.3ad
       }
      MAX-ACCESS  read-create
      STATUS  current
      DESCRIPTION
      "This object defines which Self Healing Ring (SHR) SDH ring is used: 
       Uni Directional or BiDirectional. The type of the ring
       is defined according to the direction of traffic flow under 
       normal working conditions. 

       In Bi Directional ring, the duplex traffic is on the same path 
       and transverses the same set of nodes for both directions of transmission. 
       In Uni Directional ring, the duplex traffic travels over opposite path 
       (per direction) and all the node of the ring are involved.

       For Uni Directional  SHR Protection Switching (Single Ended Switching) 
       is controlled by one node of the SDH ring, and does not require a protocol.
       For Bi Directional SHR Protection Switching (Dual Ended switching) 
       is controlled by some nodes of  the ring and requires a protocol"
      ::= { sysCRdnEntry 12 }

sysCRdnFlipUponEvent  OBJECT-TYPE
     SYNTAX  Integer32
     MAX-ACCESS   read-create
     STATUS   current
     DESCRIPTION
     "This object allows user to define if Flip to the other port will
      be performed (or not), for certain possible events.
      Each event is represented by a bit. The value of the object is a sum
      of 2**n, according to the bits having '1' value.
	  '1' - means that Flip should occur due to this event.
      Bit 0 (LSB) = SD (Signal Degraded).
      For IPmux:
      Bit 0 (LSB) = TDM Line LOS/LOF.
      Bit 1       = Sequence Number.
      Bit 2		  = Jitter Buffer errors."
     ::= { sysCRdnEntry 13 }

sysCRdnLosOrLofTime OBJECT-TYPE
    SYNTAX  Integer32 
    MAX-ACCESS  read-create
    STATUS  current
    DESCRIPTION
    "This parameter determines how much time to wait before switching,
     after LOF or LOS are detected on the TDM Line.
     For Ipmux time is counted in msec."
    ::= { sysCRdnEntry 14 }

sysCRdnEventsTimeWindow OBJECT-TYPE
    SYNTAX  Integer32 
    MAX-ACCESS  read-create
    STATUS  current
    DESCRIPTION
    "This parameter determines the time window in which 
    to count events to trigger protection switching.
     For Ipmux time is counted in seconds."
    ::= { sysCRdnEntry 15 }

sysCRdnSequenceNumberThreshold OBJECT-TYPE
    SYNTAX  Integer32 
    MAX-ACCESS  read-create
    STATUS  current
    DESCRIPTION
    "This parameter determines the number of Sequence Number errors
     that should occur in the time window in order to cause switching."
    ::= { sysCRdnEntry 16 }

sysCRdnBufferErrorsThreshold OBJECT-TYPE
    SYNTAX  Integer32 
    MAX-ACCESS  read-create
    STATUS  current
    DESCRIPTION
    "This parameter determines the number of Buffer undeflow/ overflow events
     occured in the time window that cause switching."
    ::= { sysCRdnEntry 17 }

sysCRdnBuffUnderrunTime OBJECT-TYPE
    SYNTAX  Integer32 
    MAX-ACCESS  read-create
    STATUS  current
    DESCRIPTION
    "This parameter determines how much time to wait before switching,
     after jitter buffer underrun.
	 Switching occurs if no frame arrives within that time.
     For Ipmux time is counted in msec."
    ::= { sysCRdnEntry 18 }

sysCRdnPrimePriority OBJECT-TYPE
      SYNTAX  INTEGER
       {
          notApplicable (1),
          low       (2),
          high      (3)
       }
      MAX-ACCESS  read-create
      STATUS  current
      DESCRIPTION
      "The Primary port priority.
      
      In ETX2xx/2xxA: 
      When selecting sysCRdnMode = manual (10), 
      this parameter determines the forced active port:
	  low - means that the secondary port is selected to be active
	  high - means that the primary port is selected to be active. "
      ::= { sysCRdnEntry 19 }

sysCRdnSecPriority OBJECT-TYPE
      SYNTAX  INTEGER
       {
          notApplicable (1),
          low       (2),
          high      (3)
       }
      MAX-ACCESS  read-create
      STATUS  current
      DESCRIPTION
      "The Secondary port priority."
      ::= { sysCRdnEntry 20 }

sysCRdnWTR OBJECT-TYPE
      SYNTAX  Unsigned32 
      MAX-ACCESS  read-create
      STATUS  current
      DESCRIPTION
      "Redundancy Wait to Restore (sec).
       Valid Values: 0..999, 65535.
       65535=NA.
       When the value <> 65535, the value of sysCRdnRecTime must be 65535."
      ::= { sysCRdnEntry 21 }

sysCRdnName OBJECT-TYPE
    SYNTAX      SnmpAdminString
    MAX-ACCESS  read-create
    STATUS      current
    DESCRIPTION
        "A textual name for the redundancy group."
    ::= { sysCRdnEntry 22 }

sysCRdnTxDownDurationUponFlip	 OBJECT-TYPE
    SYNTAX  	Unsigned32	(0..30)
    MAX-ACCESS  read-create
    STATUS      current
    DESCRIPTION
    "This object defines the duration (in seconds) the active 
     port transmission is shut down after flip occurs.
	 The transmission is shut down and then opened again (after the duration
	 defined by this object), in order to cause the other side to flip 
	 to the new active port.
	 0 = no shut-down.
     This object is applicable only when sysCRdnMode = oneToOne(8)
     and mainly when each of the links of our device is connected to a different device."
     ::= { sysCRdnEntry 23 }



--IO Redundancy - Commands
--This table was moved here, so that its indexes will be defined before, 
--for SNMPc

sysSRdnCmdTable OBJECT-TYPE
      SYNTAX SEQUENCE OF SysSRdnCmdEntry
      MAX-ACCESS not-accessible
      STATUS current
      DESCRIPTION
      "This table includes commands used for IO Redundancy."
      ::= { sysStatus 22 }

sysSRdnCmdEntry OBJECT-TYPE
      SYNTAX SysSRdnCmdEntry
      MAX-ACCESS not-accessible
      STATUS current
	  DESCRIPTION  "An entry in table."
	  INDEX {sysCRdnPrimeSlot, sysCRdnPrimePort }
      ::= { sysSRdnCmdTable 1}

SysSRdnCmdEntry ::=
     SEQUENCE {
     sysSRdnEnforcedChannel      INTEGER,
	 sysSRdnLockFlip      		 INTEGER,
	 sysSRdnManualFlip      	 INTEGER
	}

sysSRdnEnforcedChannel OBJECT-TYPE
     SYNTAX       INTEGER {
     notApplicable 	(1),
     noEnforcement 	(2),
     primary	    (3),
	 secondary		(4)
        }
     MAX-ACCESS    read-write
     STATUS        current
     DESCRIPTION
     "This is a command to override all switching considerations
      and enforce use of primary/ secondary connection only.
	  noEnforcement - cancels the state of override and goes back to
	                  usual switching considerations.
      Default = noEnforcement(2)."
     ::= {sysSRdnCmdEntry 1 }

 sysSRdnLockFlip 	OBJECT-TYPE
     SYNTAX       INTEGER {
     notApplicable 	(1),
     off 			(2),
     on	    		(3)	 
        }
     MAX-ACCESS    read-write
     STATUS        current
     DESCRIPTION
     "This is a command to lock the Redundancy flip for this redundancy couple.
      Default = off(2)."
     ::= {sysSRdnCmdEntry 2 }

sysSRdnManualFlip 	OBJECT-TYPE
     SYNTAX       INTEGER {
     notApplicable 	(1),
     off 			(2),
     on	    		(3)	 
        }
     MAX-ACCESS    read-write
     STATUS        current
     DESCRIPTION
     "This is a command to move to manual Redundancy flip mode for this redundancy couple.
      Default = off(2)."
     ::= {sysSRdnCmdEntry 3 }

--System Database operations

sysDbaseSanityCheckCmd OBJECT-TYPE
      SYNTAX  INTEGER
       {
       off(2),
       on (3)
       }
      MAX-ACCESS  read-write
      STATUS  current
      DESCRIPTION
      "Setting this attribute to on(3) will initiate the process 
       of Sanity check on the TmpCnfg. Upon completion, the value 
       will automatically change to off(2)."
      ::= { sysDbase 1 }

sysDbaseDownloadCnfgIdxCmd OBJECT-TYPE
      SYNTAX  Integer32   (1..255)
      MAX-ACCESS  read-write
      STATUS  current
      DESCRIPTION
      "This attribute specifies the Id of the target RealCnfg to 
       which the TmpCnfg should be transferred. Upon set command, 
       the DACS agent will initiate the Sanity-Check  process.  
       If successful, the actual transfer will be performed. 
       If there will be errors, the user will have to perform
       the command again after errors correction.       
       The operation is valid only on configuration numbers
       that do not exceed sysSMaxNoOfCnfg."
      ::= { sysDbase 2 }
-- In phase I of DXC and FCD only the value 1 (Cnfg1) is valid.

sysDbaseUploadCnfgIdxCmd OBJECT-TYPE
      SYNTAX  Integer32  (1..255)
      MAX-ACCESS  read-write
      STATUS  current
      DESCRIPTION
      "This attribute specifies the Id of the source Cnfg to be 
       loaded into the TmpCnfg. Upon set operation the actual 
       transfer will be initiated.
       The operation is valid only on configuration numbers
       that do not exceed sysSMaxNoOfCnfg."
      ::= { sysDbase 3 }
-- In phase I of DXC and FCD only the value 1 (Cnfg1) is valid.

sysDbaseFlipTable  OBJECT-TYPE
      SYNTAX SEQUENCE OF SysDbaseFlipEntry
      MAX-ACCESS not-accessible
      STATUS  current
      DESCRIPTION
      "Dbase Flip time and activation for every configuration."
       ::= { sysDbase 4 }

sysDbaseFlipEntry OBJECT-TYPE
      SYNTAX SysDbaseFlipEntry
      MAX-ACCESS not-accessible
      STATUS current
	DESCRIPTION  "An entry in table."
	INDEX {sysDbaseFlipIdx}
      ::= { sysDbaseFlipTable 1}

SysDbaseFlipEntry ::=
      SEQUENCE {
   sysDbaseFlipIdx        Integer32,
   sysDbaseFlipTime       DisplayString,
   sysDbaseFlipActivation INTEGER      }

sysDbaseFlipIdx OBJECT-TYPE
      SYNTAX Integer32 (1..255)
      MAX-ACCESS read-only
      STATUS current
      DESCRIPTION
      "This attribute indicates the Idx of the Cnfg being 
       the target Configuration."
      ::= { sysDbaseFlipEntry 1}

sysDbaseFlipTime OBJECT-TYPE
      SYNTAX DisplayString (SIZE(0..255))
      MAX-ACCESS read-write
      STATUS current
      DESCRIPTION
      "This attribute indicates the time (HH:MM) when this data 
       base will start being used by the Tmp config."
      ::= { sysDbaseFlipEntry 2}

sysDbaseFlipActivation OBJECT-TYPE
      SYNTAX INTEGER {
      disable (1),
      enable  (2)
   }
      MAX-ACCESS read-write
      STATUS current
      DESCRIPTION
      "This attribute indicates if the Dbase flip will be 
       activated at the time specified for this configuration 
       (enable) or not (disable). 
       No more than one flip should be enabled for the same time."
      ::= { sysDbaseFlipEntry 3}


--Module (card) level of DACS MIB

mdlGen   OBJECT IDENTIFIER ::= {mdlDacsMux 1}
mdlCl   OBJECT IDENTIFIER ::=  {mdlDacsMux 2}
mdlPs   OBJECT IDENTIFIER ::=  {mdlDacsMux 3}

--DACS module (card) general parameters (common to all cards 
--type)

--General Card - Status information table 
--This table is NOT-APPLICABLE for a stand-alone unit  

mdlSTable  OBJECT-TYPE
      SYNTAX SEQUENCE OF MdlSEntry
      MAX-ACCESS not-accessible
      STATUS current
	DESCRIPTION  "A table."
	::=  { mdlGen 1 }

mdlSEntry OBJECT-TYPE
      SYNTAX MdlSEntry
      MAX-ACCESS not-accessible
      STATUS current
	DESCRIPTION  "An entry in table."
	INDEX { mdlSSltIdx }
      ::= { mdlSTable 1}

MdlSEntry ::=
      SEQUENCE {
  mdlSSltIdx            INTEGER,
  mdlSCardType          INTEGER,
  mdlSHwVer             DisplayString,
  mdlSSwVer             DisplayString,
  mdlSAlarmStatus       INTEGER,
  mdlSAlarmStatusAll    INTEGER,
  mdlSTestStatus        INTEGER,
  mdlSHwStatus          INTEGER,
  mdlSActivity          INTEGER,
  mdlSAlrClearCmd       INTEGER,
  mdlSAlrClearAllCmd    INTEGER,
  mdlSAlrMaskAll        INTEGER,
  mdlSCmd               Integer32,
  mdlSReset             INTEGER,
  mdlSRebuildFrame      INTEGER,
  mdlSBackupSwVer		DisplayString,
  mdlSSecondaryBackupSwVer		DisplayString,
  mdlSPiggybackVer      SnmpAdminString
        }

mdlSSltIdx OBJECT-TYPE
      SYNTAX  INTEGER
       {
       psA   (1),
       psB   (2),
       clA   (3),
       clB   (4),
       io1   (5),
       io2   (6),
       io3   (7),
       io4   (8),
       io5   (9),
       io6  (10),
       io7  (11),
       io8  (12),
       io9  (13),
       io10 (14),
       io11 (15),
       io12 (16),
       io13 (17),
       io14 (18),
       io15 (19),
	   psC  (20),
    kmxPsA (101),
    kmxPsB (102),
    kmxMlA (103),
    kmxMlB (104),
    kmxCl  (105),
    kmxOpt (106),
    kmxIO1 (107),
    kmxIO2 (108),
    kmxIO3 (109),
    kmxIO4 (110),
    kmxIO5 (111),
    kmxIO6 (112),
    kmxIO7 (113),
    kmxIO8 (114),
    kmxIO9 (115),
    kmxIO10(116),
    kmxIO11(117),
    kmxIO12(118),
	notApplicable(255)
       }
      MAX-ACCESS  read-only
      STATUS  current
      DESCRIPTION
      "A unique number to identify a slot position in the DACS.
       The Kilomux should use enumerated values starting with kmx.
       For IPmux100 use values 1-13, 20."
      ::= { mdlSEntry 1}


mdlSCardType OBJECT-TYPE
      SYNTAX  INTEGER
       {
  --
  -- General types
  --
  unknown        (1),
  empty          (2),


  -- Power Supply Modules
  --
        psAC           (10),
        psDC           (11),
        
  --
  -- Cl Modules
  --
        gCl1           (18),  -- IPmux1000 CL1
        gCl2           (19),  -- IPmux1000 CL2
        dCl            (20),
        kCl            (21),
        dcl2           (22),
		dcl2Eth        (23),
		kClEth         (24),
        dcl3           (25),
		dcl3Eth        (26),

  --
  -- T1/E1 Modules
  --
        d4T1		   (28),
		d8T1		   (29),
        dT1DSU         (30),
        dT1CSU         (31),
        dE1DSU         (32),
        dE1LTU         (33),
        dE1aDSU        (34),
        dE1aLTU        (35),
        dT1F           (36),
        dE1F           (37),
        d4E1		   (38),
		d8E1		   (39),
  
  --
  -- xDSL Modules
  
        dE1Hdsl        (40),  --Double Slot
        dT1Hdsl        (41),  --Double Slot   
        dE1HdslS       (42),  --Single Slot
        dT1HdslS       (43),  --Single Slot
        d16gsdsl       (44),  --Single Slot, for DXC3000 only
        d8sl           (45),  --Single Slot   
        d4slStuC       (46),  --Single Slot   
        d4slStuR       (47),  --Single Slot   

        -- KMUX Main Links
  --
  kML1           (50),
  kML2           (51),
  kML3           (52),
  kML4           (53),
  kML5           (54),
  kML6           (55),
  kML7           (56),
  kML8           (57),
  kML10          (59),
  kMLF           (60),
  kML10New       (61),
  kML11RJ45      (62),
  kML11FO        (63),
        --LS  Modules
  --
  kLS1           (70),
  kLS1New        (71),
  kLS2           (72),

        --LAN  Modules
  --
  kTRE           (80),
  kMBE           (81),
  kMBENew        (82),
  fLAN           (83), 	-- FCD STM LAN card

        --Optional  Modules
  --
  kai           (90),
  kdi           (91),
  kdiCH         (92),

  -- HS Modules
  --
  dHS2           (100),
  d8U            (101),
  d16U           (102),
  d4HS           (103),
  d8HS           (104),

  kHS1           (110),
  kHS2           (111),
  kHSU1          (112),
  kHSU2          (113),
  kHS703         (114),

  -- Voice Modules
  --
  kVC1EM         (130),
  kVC1FXO        (131),
  kVC1FXS        (132),
  kVC1MEM        (133),
  kVC1MFXO       (134),
  kVC1MFXS       (135),
  kVC1MFXSW      (136),
  kVC2EM         (137),
  kVC2FXO        (138),
  kVC2FXS        (139),
  kVC2s1EM       (140), --KVC2/1/E&M
  kVC2s1FXO      (141), --KVC2/1/FXO
  kVC2s1FXS      (142), --KVC2/1/FXS
  kVC3EM         (143),
  kVC3FXO        (144),
  kVC3FXS        (145),
  kVC3S0         (146),

  -- Fax Modules
  --     
  kVF1EM            (170),
  kVF1FXO           (171),
  kVF1FXS           (172),
  kVF3EM            (173),
  kVF3FXO           (174),
  kVF3FXS           (175),
  kVF4EM            (176),
  kVF4FXO           (177),
  kVF4FXS           (178),
  kVF4FXSW          (179),
  kVF4S0            (180),
  kVF5PbxE1         (181),
  kVF5E1PbxSlave    (182),
  kVF5PbxT1         (183),
  kVF5T1PbxSlave    (184),
  kVF5PbxE1New      (185),
  kVF5E1PbxSlaveNew (186),
  kVF5PbxT1New      (187),
  kVF5T1PbxSlaveNew (188),
  kVF4FXO3          (189), 
  kVF4FXS3          (190), 
  kVF4NS0           (191),
  kVF6E1s16         (192), --KVF.6/E1/16
  kVF6E1s31         (193), --KVF.6/E1/31
  kVF6T1s12         (194), --KVF.6/T1/12
  kVF6T1s24         (195), --KVF.6/T1/24
  kVF8EM            (196),
  kVF8FXO           (197),
  kVF8FXS           (198),


  -- DIM Modules
  --
  dimETUR        (200),
  dimV35         (201),
  dimRS422       (202),
  dimRS530       (203),
  dimHssi        (204),
  dimX21         (205),
  dim10BaseT     (206),
  dimE1          (207),
  dim100         (208), 

  --DACS T3/E3 Modules
  --
  dt3G747        (209),
  dt3            (210),
  dt3f           (211),
  de3            (212),
  de3f           (213),

  -- STM-1 Modules
  --
  dstm1s1        (214),	 --DSTM1/1 Fractional
  dstm1s2        (215),  --DSTM1/2 Fractional + Redundancy
  fSTM1          (216),  -- FCD STM STM1 card
  dstm1          (217),  --DSTM1 Full
  dstm1R         (218),  --DSTM1 Full + Redundancy
  f2stm1		 (219),   -- FCD STM 2 STM1 ports card 
  gstm1		 	 (220),   -- IPmux1000 (GMUX) STM1 card
  goc3		 	 (221),   -- IPmux1000 (GMUX) OC3 card
  gstm1D		 (222),   -- IPmux1000 (GMUX) STM1 card	with 2 ports
  goc3D 		 (223),   -- IPmux1000 (GMUX) OC3 card	with 2 ports

  
  -- LA Modules 
  --
  laSUB          (230),	 -- La-240
  laVEM          (231),	 -- LA-140 & La-240
  laVFXO         (232),	 -- LA-140 & La-240
  laVFXS         (233),	 -- LA-140 & La-240
  laV11          (234),	 -- LA-140 & La-240
  laV24          (235),	 -- LA-140 & La-240
  laV35          (236),	 -- LA-140 & La-240
  laT1           (237),	 -- LA-140
  laT1Vxx        (238),	 -- LA-140
  laE1           (239),	 -- LA-140
  laE1Vxx        (240),	 -- LA-140
  laISDN         (241),  -- LA-140 & La-240i
  laVxx          (242),  -- LA-140 
  laEth          (243),  -- LA-140
  laISDNwBU      (244),  --	LA-140  with backup  (lifeline bottom connector)	  
  laIsdnNT		 (245),  -- LA-140 ISDN NT
  laIsdnNTwBU	 (246),  -- LA-140 ISDN NT with backup (lifeline bottom connector)
  laIsdnTE		 (247),  --	LA-140 ISDN TE
  laFXSwBU		 (248),  -- LA-140 FXS with backup (lifeline bottom connector) 
  laFXSs		 (249),  -- LA-140 bottom row FXS 
  laFXSwBUs		 (250),  -- LA-140 bottom row FXS with backup (lifeline Top port) 
  laIsdnNTs		 (251),  -- LA-140 bottom row ISDN NT
  laIsdnNTwBUs	 (252),  -- LA-140 bottom row ISDN NT with backup (lifeline Top port)
  laIsdnTEs		 (253),  --	LA-140 bottom row ISDN TE
  laDp           (254),  -- LA-140 bottom single data port X21/V35/RS50 
  laSdsl         (255),	 -- LA-140 top SDSL port 
  laSdslDp		 (256),	 -- LA-140 top SDSL port with bottom X21 or V35 Data Port 
  laAdslA		 (257),  -- LA-140 bottom ADSLA port
  laAdslADp  	 (258),  -- LA-140 bottom ADSLA port with top X21 or V35 Data Port 
  laAdslB		 (259),	 -- LA-140 bottom ADSLB port
  laAdslBDp	     (260),	 -- LA-140 bottom ADSLB port with top X21 or V35 Data Port 
  laShdsl		 (261),	 -- LA-140 bottom SHDSL port
  laShdslDp 	 (262),	 -- LA-140 bottom SHDSL port with top X21 or V35 Data Port
  laT1b   		 (263),  -- LA-140 bottom T1 port
  laT1bDp        (264),  -- LA-140 bottom T1 port with top data port  
  laIsdnTEwBU    (265),  --	LA-140 ISDN TE with backup 
  laIsdnTEwBUs	 (266),  --	LA-140 bottom row ISDN TE with backup 
  laShdsl4w		 (267),	 -- LA-140 bottom 4 wires SHDSL port
  laShdsl4wDp 	 (268),	 -- LA-140 bottom 4 wires SHDSL port with top Data Port
  laEthSwitch    (269),	 -- FCD-IPM 


  -- Server Modules 
  --
  serverE1          (270),	 -- IPmux1000 (GMUX) Server E1 Card
  serverT1          (271),	 -- IPmux1000 (GMUX) Server T1 Card
  serverE1Pw        (272),   -- Gmux2000 Server E1 PW Card
  serverT1Pw        (273),   -- Gmux2000 Server T1 PW Card


 -- GiGabit ETH Modules 
  --
  gigabitEth        (280),	 -- Gmux2000 Gigabit ETH Card
  gigabitEth2       (281),	 -- Gmux2000 new Gigabit ETH Card - 2 GbE ports with SFP connector
  eth2              (282),	 -- Gmux2000 new ETH Card - 2 ETH ports with RJ45 connectors (10/100/1000)
  gigabitEth8       (283),	  -- Gmux2000 new Gigabit ETH Card	 - 8 GbE ports with SFP connector
  eth8              (284),	  -- Gmux2000 new ETH Card - 8 ETH ports with RJ45 connectors (10/100/1000)


-- CT3 Modules
  --
  channelizedT3Pw1  (290),	 -- Gmux2000 Channelized T3 PW Card

  -- T1/E1 Modules
  --
  cesT128		   (300),	 -- Gmux2000 CES T1 28 ports (external T1 ports) card.
  cesE128		   (301),	 -- Gmux2000 CES E1 28 ports (external E1 ports) card.
  cesT1Pw28        (302),	 -- Gmux2000 CES T1 PW ports (external T1 ports) card.
  cesE1Pw28        (303),    -- Gmux2000 CES E1 PW ports (external E1 ports) card.   

 

  -- Vmux Modules
  --
  vmxE1VeDe	  (310),   -- Gmux-2000 Vmux E1 card with 16 external voice + 2 external Data ports.
  vmxE1VeDi	  (311),   -- Gmux-2000 Vmux E1 card with 16 external voice + 2 internal Data ports.
  vmxE1ViDe	  (312),   -- Gmux-2000 Vmux E1 card with 16 internal voice + 2 external Data ports.
  vmxE1ViDi	  (313),   -- Gmux-2000 Vmux E1 card with 16 internal voice + 2 internal Data ports.
  vmxT1VeDe	  (314),   -- Gmux-2000 Vmux T1 card with 16 external voice + 2 external Data ports.
  vmxT1VeDi	  (315),   -- Gmux-2000 Vmux T1 card with 16 external voice + 2 internal Data ports.
  vmxT1ViDe	  (316),   -- Gmux-2000 Vmux T1 card with 16 internal voice + 2 external Data ports.
  vmxT1ViDi	  (317),   -- Gmux-2000 Vmux T1 card with 16 internal voice + 2 internal Data ports.
  vc12E1UeNe  (318),   -- Gmux-2000 Vmux E1 card with 12 external User (voice) + 2 external Network (Data) ports.
  vc12E1UeNi  (319),   -- Gmux-2000 Vmux E1 card with 12 external User (voice) + 2 internal Network (Data) ports.
  vc12E1UiNe  (320),   -- Gmux-2000 Vmux E1 card with 12 internal User (voice) + 2 external Network (Data) ports.
  vc12E1UiNi  (321),   -- Gmux-2000 Vmux E1 card with 12 internal User (voice) + 2 internal Network (Data) ports.
  vc12T1UeNe  (322),   -- Gmux-2000 Vmux T1 card with 12 external User (voice) + 2 external Network (Data) ports.
  vc12T1UeNi  (323),   -- Gmux-2000 Vmux T1 card with 12 external User (voice) + 2 internal Network (Data) ports.
  vc12T1UiNe  (324),   -- Gmux-2000 Vmux T1 card with 12 internal User (voice) + 2 external Network (Data) ports.
  vc12T1UiNi  (325),   -- Gmux-2000 Vmux T1 card with 12 internal User (voice) + 2 internal Network (Data) ports.

-- New Vmux Card Types
--
  vca16E1UeNe  (326),   -- Gmux-2000 VCA E1 card with 16 external User (voice) + 2 external Network (Data) ports.
  vca16E1UeNi  (327),   -- Gmux-2000 VCA E1 card with 16 external User (voice) + 2 internal Network (Data) ports.
  vca16E1UiNe  (328),   -- Gmux-2000 VCA E1 card with 16 internal User (voice) + 2 external Network (Data) ports.
  vca16E1UiNi  (329),   -- Gmux-2000 VCA E1 card with 16 internal User (voice) + 2 internal Network (Data) ports.
  vca16T1UeNe  (330),   -- Gmux-2000 VCA T1 card with 16 external User (voice) + 2 external Network (Data) ports.
  vca16T1UeNi  (331),   -- Gmux-2000 VCA T1 card with 16 external User (voice) + 2 internal Network (Data) ports.
  vca16T1UiNe  (332),   -- Gmux-2000 VCA T1 card with 16 internal User (voice) + 2 external Network (Data) ports.
  vca16T1UiNi  (333),   -- Gmux-2000 VCA T1 card with 16 internal User (voice) + 2 internal Network (Data) ports.
  vca12E1UeNe  (334),   -- Gmux-2000 VCA E1 card with 12 external User (voice) + 2 external Network (Data) ports.
  vca12E1UeNi  (335),   -- Gmux-2000 VCA E1 card with 12 external User (voice) + 2 internal Network (Data) ports.
  vca12E1UiNe  (336),   -- Gmux-2000 VCA E1 card with 12 internal User (voice) + 2 external Network (Data) ports.
  vca12E1UiNi  (337),   -- Gmux-2000 VCA E1 card with 12 internal User (voice) + 2 internal Network (Data) ports.
  vca12T1UeNe  (338),   -- Gmux-2000 VCA T1 card with 12 external User (voice) + 2 external Network (Data) ports.
  vca12T1UeNi  (339),   -- Gmux-2000 VCA T1 card with 12 external User (voice) + 2 internal Network (Data) ports.
  vca12T1UiNe  (340),   -- Gmux-2000 VCA T1 card with 12 internal User (voice) + 2 external Network (Data) ports.
  vca12T1UiNi  (341),   -- Gmux-2000 VCA T1 card with 12 internal User (voice) + 2 internal Network (Data) ports.
  vmg16E1Ue    (342),	-- Gmux-2000 VMG (Media Gateway) E1 card with 16 external User ports
  vmg16E1Ui    (343),	-- Gmux-2000 VMG (Media Gateway) E1 card with 16 internal User ports
  vmg16T1Ue    (344),	-- Gmux-2000 VMG (Media Gateway) T1 card with 16 external User ports
  vmg16T1Ui    (345),	-- Gmux-2000 VMG (Media Gateway) T1 card with 16 internal User ports
  vmg12E1Ue    (346),	-- Gmux-2000 VMG (Media Gateway) E1 card with 12 external User ports
  vmg12E1Ui    (347),	-- Gmux-2000 VMG (Media Gateway) E1 card with 12 internal User ports
  vmg12T1Ue    (348),	-- Gmux-2000 VMG (Media Gateway) T1 card with 12 external User ports
  vmg12T1Ui    (349)	-- Gmux-2000 VMG (Media Gateway) T1 card with 12 internal User ports
      }
      MAX-ACCESS  read-only
      STATUS  current
      DESCRIPTION
      "This attribute indicates the type of  the card installed
       in the specific slot position.
       Only PS's are possible in the PS slots.
       Only CL's are possible in the CL slots.
       Only IO modules are possible in the IO slots.
       Kmux card type start with the letter k.
       LA card type start with the letters la."
      ::= { mdlSEntry 2}

mdlSHwVer OBJECT-TYPE
      SYNTAX  DisplayString (SIZE (0..255))
      MAX-ACCESS  read-only
      STATUS  current
      DESCRIPTION
      "This attribute indicates the Hardware version of the 
       card installed in the specific slot position."
      ::= { mdlSEntry 3 }

mdlSSwVer OBJECT-TYPE
      SYNTAX  DisplayString (SIZE (0..255))
      MAX-ACCESS  read-only
      STATUS  current
      DESCRIPTION
      "This attribute indicates the Software version of the 
       card installed in the specific slot position."
      ::= {mdlSEntry 4}


mdlSAlarmStatus OBJECT-TYPE
      SYNTAX  INTEGER
       {
  off      (2),
  major    (3),
  minor    (4),
  event    (5),
  warning  (6),
  critical (7)
       }
      MAX-ACCESS  read-only
      STATUS  current
      DESCRIPTION
      "Indicates the current alarm state only for card level.
       This object will be set to: 
       - critical(7): when there is at least one active (ON) critical 
                    alarm .
       - major (3): when there is no active critical alarm, but there is
                    at least one active (ON) major alarm .
       - minor (4): when there is no active major or critical alarm, but 
                    there is at least one active minor alarm.
       - warning (6): when there is no active major, critical or minor alarm, but 
                    there is at least one active warning alarm.
       - event (5): when there is no active alarm of another type, but 
                    there is at least one active event alarm.
       - off(2): when there is no active (ON) alarm (since last clear operation)."
      ::= { mdlSEntry 5 }

mdlSAlarmStatusAll OBJECT-TYPE
      SYNTAX  INTEGER
       {
  off      (2),
  major    (3),
  minor    (4),
  event    (5),
  warning  (6),
  critical (7)
       }
      MAX-ACCESS  read-only
      STATUS  current
      DESCRIPTION
      "Indicates the current card alarm state including the 
       lower level:  card, port.
       This object will be set to: 
       - critical(7): when there is at least one active (ON) critical 
                    alarm .
       - major (3): when there is no active critical alarm, but there is
                    at least one active (ON) major alarm .
       - minor (4): when there is no active major or critical alarm, but 
                    there is at least one active minor alarm.
       - warning (6): when there is no active major, critical or minor alarm, but 
                    there is at least one active warning alarm.
       - event (5): when there is no active alarm of another type, but 
                    there is at least one active event alarm.
       - off(2): when there is no active (ON) alarm (since last clear operation)."
      ::= { mdlSEntry 6 }

mdlSTestStatus OBJECT-TYPE
      SYNTAX  INTEGER
       {
  off(2),
  on (3)
       }
      MAX-ACCESS  read-only
      STATUS  current
      DESCRIPTION
      "This attribute will be on(3) when there is at least 
       one test running on a port of the module; otherwise the value 
       will be off(2)."
      ::= { mdlSEntry 7 }

mdlSHwStatus OBJECT-TYPE
      SYNTAX  INTEGER
       {
  fail(2),
  ok  (3)
       }
      MAX-ACCESS  read-only
      STATUS  current
      DESCRIPTION
      "This attribute will be fail(2) when a HW FAIL exists
       on this module (discovered by periodic self test); 
       otherwise the value will be ok(3)."
      ::= { mdlSEntry 8 }

mdlSActivity OBJECT-TYPE
      SYNTAX  INTEGER
       {
  notApplicable (1),
  offline       (2),
  online        (3)
       }
      MAX-ACCESS  read-only
      STATUS  current
      DESCRIPTION
      "notApplicable - when the slot is empty (no module)
       offline(1) - when the module is not active (redundant) 
       online (2) - when the module is active ."
      ::= { mdlSEntry 9 }

mdlSAlrClearCmd  OBJECT-TYPE
      SYNTAX  INTEGER
       {
  off(2),
  on (3)
       }
      MAX-ACCESS  read-write
      STATUS  current
      DESCRIPTION
      "Setting this attribute to ON, will enforce a  clear 
       operation on the card level alarms . Upon completion, 
       the value will automatically change to off(2)."
      ::= { mdlSEntry 10 }


mdlSAlrClearAllCmd  OBJECT-TYPE
      SYNTAX  INTEGER
       {
  off(2),
  on (3)
       }
      MAX-ACCESS  read-write
      STATUS  current
      DESCRIPTION
      "Setting this attribute to ON, will enforce a  clear 
       operation on card and port level alarms . Upon completion, 
       the value will automatically change to off(2)."
      ::= { mdlSEntry 11 }

mdlSAlrMaskAll  OBJECT-TYPE
      SYNTAX  INTEGER
       {
  off(2),
  on (3)
       }
      MAX-ACCESS  read-write
      STATUS  current
      DESCRIPTION
      "on(3)  - will cause masking of all the card level alarms.
                These alarms will not be sent to NMS and will not 
                be taken into account for Alarms Status.
       off(2) - will unmask all card level alarms except those 
                masked via the mdlAlrMaskTable. "
      ::= { mdlSEntry 12 }

mdlSCmd  OBJECT-TYPE
      SYNTAX  Integer32
      MAX-ACCESS  read-write
      STATUS  current
      DESCRIPTION
      "General object for any special command at card level.
       0=NotApplicable, for cards that don't support this object.

       For KML.10(ISDN) card of KM-2100,  the object will indicate 
       Manual Call Command in Switch mode. It is applicable only when
       for KML.10, prtIsdnSwitchMode=manual.
       KML.10 valid values:
       '1' =  noOp, will be used by agents that do not support this 
              feature or object (old KM agents)
       '2' = off, Set call command mode to disconnect state. Disconnects the call.
       '3' = on,  Set call command mode to connect state. Connects the call.
       
       For DXC IO cards, the object will be used for IO Card Reset HW command:
       '2' = off, this will be always the Get value for these cards.
       '3' = on,  this is the Set command used to Reset the IO card. Upon 
             completing the operation, the value will automatically change to off(2),
             by Agent.
       For Slots that are NOT IO Slots and for empty IO Slots, the Get value will
       be always '0' (NotApplicable). "
      ::= { mdlSEntry 13 } 
      

mdlSReset  OBJECT-TYPE
      SYNTAX  INTEGER {
	                   off (2),
					   on  (3)   --HW
					  }
      MAX-ACCESS  read-write
      STATUS  current
      DESCRIPTION
            	"Reset action to be performed on the module."
      ::= { mdlSEntry 14 } 

mdlSRebuildFrame OBJECT-TYPE
      SYNTAX  INTEGER {notApplicable(1),
                       off          (2),
                       on           (3)
                              } 
      MAX-ACCESS  read-write
      STATUS  current
      DESCRIPTION
      "Applicable only for KiloMux Main Link cards only.
	   '2' = off, this will be always the Get value.
       '3' = on,  this is the Set command used to Rebuild the Frame. 
       Upon completing the operation, the value will automatically change 
       to off(2), by Agent."
      ::= { mdlSEntry 15}

mdlSBackupSwVer OBJECT-TYPE
      SYNTAX  DisplayString (SIZE (0..255))
      MAX-ACCESS  read-only
      STATUS  current
      DESCRIPTION
      "This attribute indicates the Backup Software version of the 
       card installed in the specific slot position."
      ::= {mdlSEntry 16}

mdlSSecondaryBackupSwVer OBJECT-TYPE
      SYNTAX  DisplayString (SIZE (0..255))
      MAX-ACCESS  read-only
      STATUS  current
      DESCRIPTION
      "This attribute indicates the Secondary Backup Software version of the 
       card installed in the specific slot position."
      ::= {mdlSEntry 17}

mdlSPiggybackVer OBJECT-TYPE
      SYNTAX  SnmpAdminString (SIZE (0..255))
      MAX-ACCESS  read-only
      STATUS  current
      DESCRIPTION
      "This attribute indicates the Piggyback version of the 
       card installed in the specific slot position."
      ::= { mdlSEntry 18 }


--General Card - Configuration table 
--This table is NOT-APPLICABLE for a stand-alone unit  

mdlCTable  OBJECT-TYPE
      SYNTAX SEQUENCE OF MdlCEntry
      MAX-ACCESS not-accessible
      STATUS current
	DESCRIPTION  "A table."
	::=  { mdlGen 2 }

mdlCEntry OBJECT-TYPE
      SYNTAX MdlCEntry
      MAX-ACCESS not-accessible
      STATUS current
	DESCRIPTION  "An entry in table."
	INDEX { mdlCConfigIdx, mdlCSlotIdx  }
      ::= { mdlCTable 1}

MdlCEntry ::=
      SEQUENCE {
   mdlCConfigIdx         Integer32,
   mdlCSlotIdx           INTEGER,
   mdlCProgCardType      INTEGER,
   mdlCNoOfExtPrt        Integer32,   -- RO
   mdlCNoOfIntPrt        Integer32,    -- RO
   mdlCParam             Integer32 
	}

mdlCConfigIdx OBJECT-TYPE
      SYNTAX  Integer32 (1..255)
      MAX-ACCESS  read-only
      STATUS  current
      DESCRIPTION
      "This object indicates the Configuration number (1..255) 
       referred.
       Value of  255 specifies the TmpCnfg (Scratch)."
      ::= { mdlCEntry 1}
-- In phase 1 only the values 1 (Cnfg1) and 255 (temp) are valid.

mdlCSlotIdx OBJECT-TYPE
      SYNTAX  INTEGER
       {
       psA   (1),
       psB   (2),
       clA   (3),
       clB   (4),
       io1   (5),
       io2   (6),
       io3   (7),
       io4   (8),
       io5   (9),
       io6  (10),
       io7  (11),
       io8  (12),
       io9  (13),
       io10 (14),
       io11 (15),
       io12 (16),
       io13 (17),
       io14 (18),
       io15 (19),
	   psC  (20),
    kmxPsA (101),
    kmxPsB (102),
    kmxMlA (103),
    kmxMlB (104),
    kmxCl  (105),
    kmxOpt (106),
    kmxIO1 (107),
    kmxIO2 (108),
    kmxIO3 (109),
    kmxIO4 (110),
    kmxIO5 (111),
    kmxIO6 (112),
    kmxIO7 (113),
    kmxIO8 (114),
    kmxIO9 (115),
    kmxIO10(116),
    kmxIO11(117),
    kmxIO12(118),
    notApplicable(255)
       }
      MAX-ACCESS  read-only
      STATUS  current
      DESCRIPTION
      "This object indicates a unique number of the slot position 
       in which the module is inserted.
       The Kilomux should use enumerated values starting with kmx."
      ::= { mdlCEntry 2}

mdlCProgCardType OBJECT-TYPE
      SYNTAX  INTEGER
       {
  --
  -- General types
  --
  unknown        (1),
  empty          (2),


  -- Power Supply Modules
  --
  psAC           (10),
  psDC           (11),
        
  --
  -- Cl Modules
  --
        gCl1           (18),  -- IPmux1000 CL1
        gCl2           (19),  -- IPmux1000 CL2
        dCl            (20),
        kCl            (21),
        dcl2           (22),
		dcl2Eth        (23),
		kClEth         (24),
        dcl3           (25),
		dcl3Eth        (26),

  --
  -- T1/E1 Modules
  --
        d4T1		   (28),
		d8T1		   (29),
        dT1DSU         (30),
        dT1CSU         (31),
        dE1DSU         (32),
        dE1LTU         (33),
        dE1aDSU        (34),
        dE1aLTU        (35),
        dT1F           (36),
        dE1F           (37),
        d4E1		   (38),
		d8E1		   (39),

  --
  -- xDSL Modules
  
        dE1Hdsl        (40),  --Double Slot
        dT1Hdsl        (41),  --Double Slot   
        dE1HdslS       (42),  --Single Slot
        dT1HdslS       (43),  --Single Slot   
        d16gsdsl       (44),  --Single Slot, for DXC3000 only   
        d8sl           (45),  --Single Slot   
        d4slStuC       (46),  --Single Slot   
        d4slStuR       (47),  --Single Slot   

        -- KMUX Main Links
  --
  kML1           (50),
  kML2           (51),
  kML3           (52),
  kML4           (53),
  kML5           (54),
  kML6           (55),
  kML7           (56),
  kML8           (57),
  kML10          (59),
  kMLF           (60),
  kML10New       (61),
  kML11RJ45      (62),
  kML11FO        (63),

        --LS  Modules
  --
  kLS1           (70),
  kLS1New        (71),
  kLS2           (72),

        --LAN  Modules
  --
  kTRE           (80),
  kMBE           (81),
  kMBENew        (82),
  fLAN           (83), -- FCD STM LAN moudle

        --Optional  Modules
  --
  kai           (90),
  kdi           (91),
  kdiCH         (92),

  -- HS Modules
  --
  dHS2           (100),
  d8U            (101),
  d16U           (102),
  d4HS           (103),
  d8HS           (104),

  kHS1           (110),
  kHS2           (111),
  kHSU1          (112),
  kHSU2          (113),
  kHS703         (114),


  -- Voice Modules
  --
  kVC1EM         (130),
  kVC1FXO        (131),
  kVC1FXS        (132),
  kVC1MEM        (133),
  kVC1MFXO       (134),
  kVC1MFXS       (135),
  kVC1MFXSW      (136),
  kVC2EM         (137),
  kVC2FXO        (138),
  kVC2FXS        (139),
  kVC2s1EM       (140), --KVC2/1/E&M
  kVC2s1FXO      (141), --KVC2/1/FXO
  kVC2s1FXS      (142), --KVC2/1/FXS
  kVC3EM         (143),
  kVC3FXO        (144),
  kVC3FXS        (145),
  kVC3S0         (146),

  -- Fax Modules
  --
  kVF1EM            (170),
  kVF1FXO           (171),
  kVF1FXS           (172),
  kVF3EM            (173),
  kVF3FXO           (174),
  kVF3FXS           (175),
  kVF4EM            (176),
  kVF4FXO           (177),
  kVF4FXS           (178),
  kVF4FXSW          (179),
  kVF4S0            (180),
  kVF5PbxE1         (181),
  kVF5E1PbxSlave    (182),
  kVF5PbxT1         (183),
  kVF5T1PbxSlave    (184),
  kVF5PbxE1New      (185),
  kVF5E1PbxSlaveNew (186),
  kVF5PbxT1New      (187),
  kVF5T1PbxSlaveNew (188),
  kVF4FXO3          (189), 
  kVF4FXS3          (190), 
  kVF4NS0           (191), 
  kVF6E1s16         (192), --KVF.6/E1/16
  kVF6E1s31         (193), --KVF.6/E1/31
  kVF6T1s12         (194), --KVF.6/T1/12
  kVF6T1s24         (195), --KVF.6/T1/24
  kVF8EM            (196),
  kVF8FXO           (197),
  kVF8FXS           (198),


  -- DIM Modules
  --
  dimETUR        (200),
  dimV35         (201),
  dimRS422       (202),
  dimRS530       (203),
  dimHssi        (204),
  dimX21         (205),
  dim10BaseT     (206),
  dimE1          (207),
  dim100         (208), 

  --DACS T3/E3 Modules
  --
  dt3G747        (209),
  dt3            (210),
  dt3f           (211),
  de3            (212),
  de3f           (213),

  -- STM-1 Modules
  --
  dstm1s1        (214),	 --DSTM1/1 Fractional
  dstm1s2        (215),  --DSTM1/2 Fractional + Redundancy
  fstm1          (216),	 --FCD STM STM1 card
  dstm1          (217),  --DSTM1 Full
  dstm1R         (218),   --DSTM1 Full + Redundancy
  f2stm1		 (219),   -- FCD STM 2 STM1 ports card 
  gstm1		 	 (220),   -- IPmux1000 (GMUX) STM1 card
  goc3		 	 (221),   -- IPmux1000 (GMUX) OC3 card
  gstm1D		 (222),   -- IPmux1000 (GMUX) STM1 card	with 2 ports
  goc3D		     (223),   -- IPmux1000 (GMUX) OC3 card	with 2 ports


  -- The following numbers are used in mdlSCardType, for LA modules:
  --
  -- laSUB          (230)
  -- laVEM          (231)
  -- laVFXO         (232)
  -- laVFXS         (233)
  -- laV11          (234)
  -- laV24          (235)
  -- laV35          (236)
  -- laT1           (237),	
  -- laT1Vxx        (238),	
  -- laE1           (239),	
  -- laE1Vxx        (240),	
  -- laISDN         (241),  
  -- laVxx          (242),   
  -- laEth          (243),
  -- laISDNwBU      (244),
  -- laIsdnNT		(245), LA-140 ISDN NT
  -- laIsdnNTwBU	(246), LA-140 ISDN NT with backup (lifeline bottom connector)
  -- laIsdnTE		(247), LA-140 ISDN TE
  -- laFXSwBU		(248), LA-140 FXS with backup (lifeline bottom connector) 
  -- laFXSs		    (249), LA-140 bottom row FXS 
  -- laFXSwBUs	    (250), LA-140 bottom row FXS with backup (lifeline Top port) 
  -- laIsdnNTs	    (251), LA-140 bottom row ISDN NT
  -- laIsdnNTwBUs	(252), LA-140 bottom row ISDN NT with backup (lifeline Top port)
  -- laIsdnTEs	    (253), LA-140 bottom row ISDN TE
  -- laDp           (254), LA-140 bottom single data port X21/V35/RS50 
  -- laSdsl         (255), LA-140 top SDSL port 
  -- laSdslDp	    (256), LA-140 top SDSL port with bottom X21 or V35 Data Port 
  -- laAdslA	    (257), LA-140 bottom ADSLA port
  -- laAdslADp      (258), LA-140 bottom ADSLA port with top X21 or V35 Data Port 
  -- laAdslB	    (259), LA-140 bottom ADSLB port
  -- laAdslBDp	    (260), LA-140 bottom ADSLB port with top X21 or V35 Data Port 
  -- laShdsl	    (261), LA-140 bottom SHDSL port
  -- laShdslDp	    (262), LA-140 bottom SHDSL port with top X21 or V35 Data Port 
  -- laT1b   	    (263), LA-140 bottom T1 port
  -- laT1bDp        (264), LA-140 bottom T1 port with top data port  
  -- laIsdnTEwBU    (265), LA-140 ISDN TE with backup 
  -- laIsdnTEwBUs   (266), LA-140 bottom row ISDN TE with backup
  -- laShdsl4w	    (267), LA-140 bottom 4 wires SHDSL port
  -- laShdsl4wDp    (268), LA-140 bottom 4 wires SHDSL port with top Data Port
  -- laEthSwitch    (269)  FCD-IPM
  
  -- Server Modules 
  --
  serverE1          (270),	 -- IPmux1000 (GMUX) Server E1 Card
  serverT1          (271),	 -- IPmux1000 (GMUX) Server T1 Card
  serverE1Pw        (272),   -- Gmux2000 Server E1 PW Card
  serverT1Pw        (273),   -- Gmux2000 Server T1 PW Card


 -- GiGabit ETH Modules 
  --
  gigabitEth        (280),	 -- Gmux2000 Gigabit ETH Card
  gigabitEth2       (281),	 -- Gmux2000 new Gigabit ETH Card - 2 GbE ports with SFP connector
  eth2              (282),	 -- Gmux2000 new ETH Card - 2 ETH ports with RJ45 connectors (10/100/1000)
  gigabitEth8       (283),	  -- Gmux2000 new Gigabit ETH Card	 - 8 GbE ports with SFP connector
  eth8              (284),	  -- Gmux2000 new ETH Card - 8 ETH ports with RJ45 connectors (10/100/1000)

-- CT3 Modules
  --
  channelizedT3Pw1  (290),	 -- Gmux2000 Channelized T3 PW Card

  -- T1/E1 Modules
  --
  cesT128		   (300),	 -- Gmux2000 CES T1 28 ports (external T1 ports) card.
  cesE128		   (301),	 -- Gmux2000 CES E1 28 ports (external E1 ports) card.
  cesT1Pw28        (302),	 -- Gmux2000 CES T1 PW ports (external T1 ports) card.
  cesE1Pw28        (303),    -- Gmux2000 CES E1 PW ports (external E1 ports) card.   



  -- Vmux Modules
  --
  vmxE1VeDe	  (310),	 -- Gmux-2000 Vmux E1 card with external voice + external Data ports.
  vmxE1VeDi	  (311),	 -- Gmux-2000 Vmux E1 card with external voice + internal Data ports.
  vmxE1ViDe	  (312),	 -- Gmux-2000 Vmux E1 card with internal voice + external Data ports.
  vmxE1ViDi	  (313),	 -- Gmux-2000 Vmux E1 card with internal voice + internal Data ports.
  vmxT1VeDe	  (314),	 -- Gmux-2000 Vmux T1 card with external voice + external Data ports.
  vmxT1VeDi	  (315),	 -- Gmux-2000 Vmux T1 card with external voice + internal Data ports.
  vmxT1ViDe	  (316),	 -- Gmux-2000 Vmux T1 card with internal voice + external Data ports.
  vmxT1ViDi	  (317),	 -- Gmux-2000 Vmux T1 card with internal voice + internal Data ports.
  vc12E1UeNe  (318),   -- Gmux-2000 Vmux E1 card with 12 external User (voice) + 2 external Network (Data) ports.
  vc12E1UeNi  (319),   -- Gmux-2000 Vmux E1 card with 12 external User (voice) + 2 internal Network (Data) ports.
  vc12E1UiNe  (320),   -- Gmux-2000 Vmux E1 card with 12 internal User (voice) + 2 external Network (Data) ports.
  vc12E1UiNi  (321),   -- Gmux-2000 Vmux E1 card with 12 internal User (voice) + 2 internal Network (Data) ports.
  vc12T1UeNe  (322),   -- Gmux-2000 Vmux T1 card with 12 external User (voice) + 2 external Network (Data) ports.
  vc12T1UeNi  (323),   -- Gmux-2000 Vmux T1 card with 12 external User (voice) + 2 internal Network (Data) ports.
  vc12T1UiNe  (324),   -- Gmux-2000 Vmux T1 card with 12 internal User (voice) + 2 external Network (Data) ports.
  vc12T1UiNi  (325),   -- Gmux-2000 Vmux T1 card with 12 internal User (voice) + 2 internal Network (Data) ports.

-- New Vmux Card Types
--
  vca16E1UeNe  (326),   -- Gmux-2000 VCA E1 card with 16 external User (voice) + 2 external Network (Data) ports.
  vca16E1UeNi  (327),   -- Gmux-2000 VCA E1 card with 16 external User (voice) + 2 internal Network (Data) ports.
  vca16E1UiNe  (328),   -- Gmux-2000 VCA E1 card with 16 internal User (voice) + 2 external Network (Data) ports.
  vca16E1UiNi  (329),   -- Gmux-2000 VCA E1 card with 16 internal User (voice) + 2 internal Network (Data) ports.
  vca16T1UeNe  (330),   -- Gmux-2000 VCA T1 card with 16 external User (voice) + 2 external Network (Data) ports.
  vca16T1UeNi  (331),   -- Gmux-2000 VCA T1 card with 16 external User (voice) + 2 internal Network (Data) ports.
  vca16T1UiNe  (332),   -- Gmux-2000 VCA T1 card with 16 internal User (voice) + 2 external Network (Data) ports.
  vca16T1UiNi  (333),   -- Gmux-2000 VCA T1 card with 16 internal User (voice) + 2 internal Network (Data) ports.
  vca12E1UeNe  (334),   -- Gmux-2000 VCA E1 card with 12 external User (voice) + 2 external Network (Data) ports.
  vca12E1UeNi  (335),   -- Gmux-2000 VCA E1 card with 12 external User (voice) + 2 internal Network (Data) ports.
  vca12E1UiNe  (336),   -- Gmux-2000 VCA E1 card with 12 internal User (voice) + 2 external Network (Data) ports.
  vca12E1UiNi  (337),   -- Gmux-2000 VCA E1 card with 12 internal User (voice) + 2 internal Network (Data) ports.
  vca12T1UeNe  (338),   -- Gmux-2000 VCA T1 card with 12 external User (voice) + 2 external Network (Data) ports.
  vca12T1UeNi  (339),   -- Gmux-2000 VCA T1 card with 12 external User (voice) + 2 internal Network (Data) ports.
  vca12T1UiNe  (340),   -- Gmux-2000 VCA T1 card with 12 internal User (voice) + 2 external Network (Data) ports.
  vca12T1UiNi  (341),   -- Gmux-2000 VCA T1 card with 12 internal User (voice) + 2 internal Network (Data) ports.
  vmg16E1Ue    (342),	-- Gmux-2000 VMG (Media Gateway) E1 card with 16 external User ports
  vmg16E1Ui    (343),	-- Gmux-2000 VMG (Media Gateway) E1 card with 16 internal User ports
  vmg16T1Ue    (344),	-- Gmux-2000 VMG (Media Gateway) T1 card with 16 external User ports
  vmg16T1Ui    (345),	-- Gmux-2000 VMG (Media Gateway) T1 card with 16 internal User ports
  vmg12E1Ue    (346),	-- Gmux-2000 VMG (Media Gateway) E1 card with 12 external User ports
  vmg12E1Ui    (347),	-- Gmux-2000 VMG (Media Gateway) E1 card with 12 internal User ports
  vmg12T1Ue    (348),	-- Gmux-2000 VMG (Media Gateway) T1 card with 12 external User ports
  vmg12T1Ui    (349)	-- Gmux-2000 VMG (Media Gateway) T1 card with 12 internal User ports

      }
      MAX-ACCESS  read-write
      STATUS  current
      DESCRIPTION
      "This object indicates the card type assigned to the specific 
       slot in the common configuration.
       This object is identical for all the configurations (1..255).
       Only the TmpCnf(255) might have a  different value.
       The write operation is valid only for the TmpCnfg entry."
      ::= { mdlCEntry 3}

mdlCNoOfExtPrt OBJECT-TYPE
      SYNTAX  Integer32
      MAX-ACCESS  read-only
      STATUS  current
      DESCRIPTION
      "Number of external ports in the programmed module of 
       the specific slot position"
      ::= { mdlCEntry 4}

mdlCNoOfIntPrt OBJECT-TYPE
      SYNTAX  Integer32
      MAX-ACCESS  read-only
      STATUS  current
      DESCRIPTION
      "Number of internal ports in the programmed module of 
       the specific slot position."
      ::= { mdlCEntry 5}

mdlCParam  OBJECT-TYPE
      SYNTAX  Integer32
      MAX-ACCESS  read-write
      STATUS  current
      DESCRIPTION
      "General configuration object at card level (per configuration).
       NotApplicable=0, for cards that don't support this object.

       For D8U and D16U cards of DXC,  the object will indicate 
       the port on which BERT will be performed. The port can be
       one of the external ports, any of its associated B1, B2, D ports
       or no port of the card (None=0).
       For port indexes see DXC R6 spec.
       
       For Gmux-2000, this parameter used for determining the Gigabit ETH exit port"
      ::= {mdlCEntry 6 } 


--Module level current alarms

mdlAlr OBJECT IDENTIFIER ::= {mdlGen 3}

mdlAlrTable OBJECT-TYPE
      SYNTAX SEQUENCE OF MdlAlrEntry
      MAX-ACCESS not-accessible
      STATUS current
      DESCRIPTION
      "The list of card alarms. "
      ::= { mdlAlr 1 }

mdlAlrEntry OBJECT-TYPE
      SYNTAX MdlAlrEntry
      MAX-ACCESS not-accessible
      STATUS current
	DESCRIPTION  "An entry in table."
	INDEX {mdlAlrSltIdx , mdlAlrIdx}
      ::= { mdlAlrTable 1}

MdlAlrEntry ::=
      SEQUENCE {
  mdlAlrSltIdx           INTEGER,
  mdlAlrIdx              Integer32,
  mdlAlrCode             Integer32,
  mdlAlrState            INTEGER,  --severity
  mdlAlarmMask           INTEGER,
  mdlAlarmInvert         INTEGER,
  mdlAlarmOnOff          INTEGER,
  mdlAlarmCounter        Integer32 
	}

mdlAlrIdx OBJECT-TYPE
      SYNTAX  Integer32
      MAX-ACCESS  read-only
      STATUS  current
      DESCRIPTION
      "A unique number to identify an entry in the alarm status 
       table.
       Users should use the get next function to read this table 
       because the indexes are not consecutive"
      ::= { mdlAlrEntry 1}

mdlAlrSltIdx OBJECT-TYPE
      SYNTAX  INTEGER
       {
       psA   (1),
       psB   (2),
       clA   (3),
       clB   (4),
       io1   (5),
       io2   (6),
       io3   (7),
       io4   (8),
       io5   (9),
       io6  (10),
       io7  (11),
       io8  (12),
       io9  (13),
       io10 (14),
       io11 (15),
       io12 (16),
       io13 (17),
       io14 (18),
       io15 (19),
	   psC  (20),
    kmxPsA (101),
    kmxPsB (102),
    kmxMlA (103),
    kmxMlB (104),
    kmxCl  (105),
    kmxOpt (106),
    kmxIO1 (107),
    kmxIO2 (108),
    kmxIO3 (109),
    kmxIO4 (110),
    kmxIO5 (111),
    kmxIO6 (112),
    kmxIO7 (113),
    kmxIO8 (114),
    kmxIO9 (115),
    kmxIO10(116),
    kmxIO11(117),
    kmxIO12(118)
       }
      MAX-ACCESS  read-only
      STATUS  current
      DESCRIPTION
      "This attribute indicates the  desired slot position. 
       The Kilomux should use enumerated values starting with kmx."
      ::= { mdlAlrEntry 2}

mdlAlrCode OBJECT-TYPE
      SYNTAX  Integer32
      MAX-ACCESS  read-only
      STATUS  current
      DESCRIPTION
      "This object indicates a code related to a specific
       alarm description. The list of codes and their related
       descriptions will be sent to NMS request (for display purpose)
       by alrGenTable."
      ::= { mdlAlrEntry 3 }

mdlAlrState OBJECT-TYPE
      SYNTAX  INTEGER {
   event    (3),
   minor    (4),
   major    (5),
   warning  (6),
   critical (7)
       }
      MAX-ACCESS  read-only
      STATUS  current
      DESCRIPTION
      "This object indicates the card alarm severity."      
      ::= { mdlAlrEntry 4 }

mdlAlarmMask OBJECT-TYPE
      SYNTAX  INTEGER {
  off(2),
  on (3)
       }
      MAX-ACCESS  read-only
      STATUS  current
      DESCRIPTION
      "Alarm Mask is : on/off."
      ::= { mdlAlrEntry 5 }

mdlAlarmInvert OBJECT-TYPE
      SYNTAX  INTEGER {
  off(2),
  on (3)
       }
      MAX-ACCESS  read-only
      STATUS  current
      DESCRIPTION
      "Alarm Invert is : on/off."
      ::= { mdlAlrEntry 6 }

mdlAlarmOnOff OBJECT-TYPE
      SYNTAX  INTEGER {
  off(2),
  on (3)
       }
      MAX-ACCESS  read-only
      STATUS  current
      DESCRIPTION
      "Alarm state is : on/off."
      ::= { mdlAlrEntry 7}

mdlAlarmCounter OBJECT-TYPE
      SYNTAX  Integer32
      MAX-ACCESS  read-only
      STATUS  current
      DESCRIPTION
      "A counter - how many times the alarm occured (ON) since last
       clear operation or since last Reset."
      ::= { mdlAlrEntry 8 }

mdlAlrMaskTable OBJECT-TYPE
      SYNTAX SEQUENCE OF MdlAlrMaskEntry
      MAX-ACCESS not-accessible
      STATUS current
      DESCRIPTION
      "The list of card masked alarms. "
      ::= { mdlAlr 2 }

mdlAlrMaskEntry OBJECT-TYPE
      SYNTAX MdlAlrMaskEntry
      MAX-ACCESS not-accessible
      STATUS current
	DESCRIPTION  "An entry in table."
	INDEX {mdlAlrMaskSltIdx}
      ::= { mdlAlrMaskTable 1}

MdlAlrMaskEntry ::=
      SEQUENCE {
     mdlAlrMaskSltIdx           INTEGER,
     mdlAlrMask            OCTET STRING    
      }

mdlAlrMaskSltIdx OBJECT-TYPE
      SYNTAX  INTEGER
       {
       psA   (1),
       psB   (2),
       clA   (3),
       clB   (4),
       io1   (5),
       io2   (6),
       io3   (7),
       io4   (8),
       io5   (9),
       io6  (10),
       io7  (11),
       io8  (12),
       io9  (13),
       io10 (14),
       io11 (15),
       io12 (16),
       io13 (17),
       io14 (18),
       io15 (19),
	   psC  (20),
    kmxPsA (101),
    kmxPsB (102),
    kmxMlA (103),
    kmxMlB (104),
    kmxCl  (105),
    kmxOpt (106),
    kmxIO1 (107),
    kmxIO2 (108),
    kmxIO3 (109),
    kmxIO4 (110),
    kmxIO5 (111),
    kmxIO6 (112),
    kmxIO7 (113),
    kmxIO8 (114),
    kmxIO9 (115),
    kmxIO10(116),
    kmxIO11(117),
    kmxIO12(118)
       }
      MAX-ACCESS  read-only
      STATUS  current
      DESCRIPTION
      "This attribute indicates the  desired slot position.
       The Kilomux should use enumerated values starting with kmx."
      ::= { mdlAlrMaskEntry 1}

mdlAlrMask OBJECT-TYPE
      SYNTAX OCTET STRING  (SIZE (8..10))
      MAX-ACCESS read-write
      STATUS current
   DESCRIPTION
   "This object is a mask that indicates which card level 
    alarms are masked. The masked alarms (their bit is set to 
    '1') are neither sent to the manager, nor taken into account
    for alarm status and LEDs.
    Bit no. = Alarm code
    The bits that do not belong to the card level will be 0.
    This object is applicable only when mdlSAlrMaskAll=off 
    (otherwise all card alarms are masked).
    Example: When Alarm having the code 8 is masked,
             the value of this object will be 100 (hex)."
     ::= { mdlAlrMaskEntry 2 } 


--DACS dcl (Common Logic) card specific parameters  

mdlClTable  OBJECT-TYPE
      SYNTAX SEQUENCE OF MdlClEntry
      MAX-ACCESS not-accessible
      STATUS current
	DESCRIPTION  "A table."
	::=  { mdlCl 1 }

mdlClEntry OBJECT-TYPE
      SYNTAX MdlClEntry
      MAX-ACCESS not-accessible
      STATUS current
	DESCRIPTION  "An entry in table."
	INDEX { mdlClIdx }
      ::= { mdlClTable 1}

MdlClEntry ::=
      SEQUENCE {
   mdlClIdx           INTEGER,
   mdlClSwchStatus    Integer32,
   mdlClLastFlipDate  DisplayString,
   mdlClLastFlipTime  DisplayString,
   mdlClLastFlipCause DisplayString
     }

mdlClIdx OBJECT-TYPE
      SYNTAX  INTEGER {
   clA   (3),
   clB   (4)
   }
      MAX-ACCESS  read-only
      STATUS  current
      DESCRIPTION
      "This object indicates the Cl slot referred."
      ::= { mdlClEntry 1}

mdlClSwchStatus OBJECT-TYPE
      SYNTAX  Integer32
      MAX-ACCESS  read-only
      STATUS  current
      DESCRIPTION
      "This object indicates the status of the switches on 
       the referred DCL card.
       Each switch is represented by a bit. The status is a sum
       of 2**n, according to the bits. There are 4 switches:
       bit 0  SP-PAR (LSB)  '1' - Default parameters    
       bit 1  PSWRD         '1' - Password=default
                         '0' - Password=user selected
       bit 2  DB-INIT       '1' - DB initiated with default
                         '0' - DB initiated with NVRAM contents 
       bit 3  PC-SP  (MSB)  '1' - Management by terminal only
                         '0' - Management by NMS
       Example: If SP-PAR  and PSWRD bits are set ('1'), the value
                will be 3 (2**1 + 2**0).
       When the status of the switches is unknown, the value of
       this object will be 255."
      ::= { mdlClEntry 2}

mdlClLastFlipDate  OBJECT-TYPE
      SYNTAX  DisplayString (SIZE (0..255))
      MAX-ACCESS  read-only
      STATUS  current
      DESCRIPTION
      "Date when last flip occured.
       The format would be as specified by the sysSDateFormat."
   ::= {mdlClEntry 3}

mdlClLastFlipTime  OBJECT-TYPE
      SYNTAX  DisplayString (SIZE (0..255))
      MAX-ACCESS  read-only
      STATUS  current
      DESCRIPTION
      "Time when last flip occured."
   ::= {mdlClEntry 4}

mdlClLastFlipCause  OBJECT-TYPE
      SYNTAX  DisplayString (SIZE (0..255))
      MAX-ACCESS  read-only
      STATUS  current
      DESCRIPTION
      "The cause of last flip."
   ::= {mdlClEntry 5}



--DACS Ps (Power Supply) card specific parameters  

mdlPsTable  OBJECT-TYPE
      SYNTAX SEQUENCE OF MdlPsEntry
      MAX-ACCESS not-accessible
      STATUS current
	DESCRIPTION  "A table."
	::=  { mdlPs 1 }

mdlPsEntry OBJECT-TYPE
      SYNTAX MdlPsEntry
      MAX-ACCESS not-accessible
      STATUS current
	DESCRIPTION  "An entry in table."
	INDEX { mdlPsIdx }
      ::= { mdlPsTable 1}

MdlPsEntry ::=
      SEQUENCE {
   mdlPsIdx          INTEGER,
   mdlPsStatus       INTEGER,
   mdlPsTestResult   INTEGER
     }

mdlPsIdx OBJECT-TYPE
      SYNTAX  INTEGER {
   psA   (1),
   psB   (2)
   }
      MAX-ACCESS  read-only
      STATUS  current
      DESCRIPTION
      "This object indicates the PS card referred."
      ::= { mdlPsEntry 1}

mdlPsStatus OBJECT-TYPE
      SYNTAX  INTEGER {
   notActive  (1),
   active     (2)
   }
      MAX-ACCESS  read-only
      STATUS  current
      DESCRIPTION
      "This object indicates the status of the PS card."
      ::= { mdlPsEntry 2}

mdlPsTestResult OBJECT-TYPE
      SYNTAX  INTEGER {
   ok   (1),
   f12V (2),
   f5V  (3)
   }
      MAX-ACCESS  read-only
      STATUS  current
      DESCRIPTION
      "This object indicates the result of the PS card test.
       ok   (1) - the test passed successfully.
       f12V (2) - 12V FAIL was detected
       f5V  (3) -  5V FAIL was detected."
      ::= { mdlPsEntry 3}



--Port level of DACS MIB

prtGen    OBJECT IDENTIFIER ::= {prtDacsMux 1}
prtT1E1   OBJECT IDENTIFIER ::= {prtDacsMux 2}
prtHS     OBJECT IDENTIFIER ::= {prtDacsMux 3}
prtSP     OBJECT IDENTIFIER ::= {prtDacsMux 4}
prtDim    OBJECT IDENTIFIER ::= {prtDacsMux 5}
prtI      OBJECT IDENTIFIER ::= {prtDacsMux 6} --ISDN port
prtHdsl   OBJECT IDENTIFIER ::= {prtDacsMux 7} --HDSL Line
prtT3E3   OBJECT IDENTIFIER ::= {prtDacsMux 8} --T3/E3 interface

--DACS port general parameters (common to all ports type except SP)
--The table contains both status and configuration information 

prtGenParamTable  OBJECT-TYPE
      SYNTAX SEQUENCE OF PrtGenEntry
      MAX-ACCESS not-accessible
      STATUS current
	DESCRIPTION  "A table."
	::=  { prtGen 1 }

prtGenEntry OBJECT-TYPE
      SYNTAX PrtGenEntry
      MAX-ACCESS not-accessible
      STATUS current
	DESCRIPTION  "An entry in table."
	INDEX { prtGenPrtIdx }
      ::= { prtGenParamTable 1}

PrtGenEntry ::=
     SEQUENCE {
  prtGenPrtIdx        Integer32,
  prtGenSlt           INTEGER,
  prtGenExtInt        INTEGER,
  prtGenIfIndex       Integer32,
  prtGenActiveStatus  INTEGER,
  prtGenAlrStatus     INTEGER,
  prtGenTestStatus    INTEGER,
  prtGenTestMask      Integer32,
  prtGenTestCmd       Integer32,
  prtGenTestRunning   Integer32,
  prtGenType          INTEGER,
  prtGenInterfaceType DisplayString,
  prtGenAlrClearCmd   INTEGER,
  prtGenAlrMaskAll    INTEGER,
  prtGenParamStatus   OCTET STRING,
  prtGenRdnStatus     INTEGER,
  prtGenTestMaskXP    OCTET STRING,
  prtGenTestCmdXP     OCTET STRING,
  prtGenTestRunningXP OCTET STRING

  }

 prtGenPrtIdx OBJECT-TYPE
      SYNTAX  Integer32
      MAX-ACCESS  read-only
      STATUS  current
      DESCRIPTION
      "This attribute indicates a unique number to identify a port. 
       The valid port number depends on the IO slot no.,  the 
       installed card type and the port type: outside/external, inside/internal. 

    In the Kilomux, the port index is calculated as follows:
    100*Slot+Ch. The external Ch numbers are 1..10, and the
    internal Ch numbers are 11..20.
       
    In the DXC :
      - first two digits will be: (IO slot number+10)
      - last one/two digits will be the port number within the 
        card in odd or even numbers, as follows:
      * For the outside/external ports, in odd numbers:
        port1 = 1
        port2 = 3
        port3 = 5 
        etc...
        Example: port2 of IO slot 11 will be: 213 .
      * The inside/internal ports, in even numbers:
        port1 = 2
        port2 = 4
        port3 = 6 
        etc...
        Example: port2 of IO slot 11 will be: 214 ."
      ::= { prtGenEntry 1}

prtGenSlt     OBJECT-TYPE
      SYNTAX  INTEGER
       {
       io1   (5),
       io2   (6),
       io3   (7),
       io4   (8),
       io5   (9),
       io6  (10),
       io7  (11),
       io8  (12),
       io9  (13),
       io10 (14),
       io11 (15),
       io12 (16),
       io13 (17),
       io14 (18),
       io15 (19),
    kmxMlA (103),
    kmxMlB (104),
    kmxCl  (105),
    kmxOpt (106),
    kmxIO1 (107),
    kmxIO2 (108),
    kmxIO3 (109),
    kmxIO4 (110),
    kmxIO5 (111),
    kmxIO6 (112),
    kmxIO7 (113),
    kmxIO8 (114),
    kmxIO9 (115),
    kmxIO10(116),
    kmxIO11(117),
    kmxIO12(118),
    standAlone (255)
       }
      MAX-ACCESS  read-only
      STATUS  current
      DESCRIPTION
      "This attribute indicates a unique number to identify the slot where
       the card is inserted in.
       When the unit is stand-alone, this object is not applicable
       and 255 will be used.
       The Kilomux should use the enumerated starting with kmx."
      ::= { prtGenEntry 2}

prtGenExtInt  OBJECT-TYPE
      SYNTAX  INTEGER
       {
  external (2),
  internal (3)
       }
      MAX-ACCESS  read-only
      STATUS  current
      DESCRIPTION
      "This attribute describes the type of the designated port. 
       Exteral  port is a port with  a physical connector. Internal 
       port might be of two types, one is a composite port which 
       collects data of a few external ports into a common 
       bandwidth (usually routed trough DS1 link); the other type is
       internal ports which get only part of external port data 
       (usually a few DS0's).
       In the Kilomux-2100, the internal(3) value is used for 
       composite channels or sub-channels of an ISDN Ch."
      ::= { prtGenEntry 3}

prtGenIfIndex  OBJECT-TYPE
      SYNTAX  Integer32
      MAX-ACCESS  read-only
      STATUS  current
      DESCRIPTION
      "This attribute indicates the  unique  interface number 
       assigned to the port. The specific interface of this 
       attribute is the same as the interface identified by the  
       value of ifindex in MIB-II.If there is no interface for the 
       specific prtIdx, the value will be '7fffffff'h."
      ::= { prtGenEntry 4}

prtGenActiveStatus   OBJECT-TYPE
      SYNTAX  INTEGER
       {
         unknown           (1),
         notUsed           (2),
         offLine           (3),
         onLine            (4),
         offLineRedundancy (5),
         onLineRedundancy  (6)
       }
      MAX-ACCESS  read-only
      STATUS  current
      DESCRIPTION
      "This attribute describes the activity status of the port.
       unknown(1) indicates that the information is not supported.
       notUsed(2) indicates that the port is not connected according
                  to the active config.
       offLine(3) indicates that the port is down (not working) 
                  due to any problem.
       onLine (4) indicates that the port is up (working)
       offLineRedundancy(5) indicates that the port is down because
                            it is a redundant port.
       onLineRedundancy (6) indicates that this is a redundant port 
                            which is up and works as the active link."
      ::= { prtGenEntry 5}

prtGenAlrStatus OBJECT-TYPE
      SYNTAX  INTEGER
       {
  off      (2),
  major    (3),
  minor    (4),
  event    (5),
  warning  (6),
  critical (7)
       }
      MAX-ACCESS  read-only
      STATUS  current
      DESCRIPTION
      "Indicates the alarm state at port (ch) agent level.
       This object will be: 
       - critical(7): when there is at least one active (ON) critical 
                    alarm .
       - major (3): when there is no active critical alarm, but there is
                    at least one active (ON) major alarm .
       - minor (4): when there is no active major or critical alarm, but 
                    there is at least one active minor alarm.
       - warning (6): when there is no active major, critical or minor alarm, but 
                    there is at least one active warning alarm.
       - event (5): when there is no active alarm of another type, but 
                    there is at least one active event alarm.
       - off(2): when there is no active (ON) alarm (since last clear operation)."
      ::= { prtGenEntry 6}

prtGenTestStatus OBJECT-TYPE
     SYNTAX  INTEGER
         {
       off(2),
       on (3)
         }
     MAX-ACCESS  read-only
     STATUS  current
     DESCRIPTION
     "This attribute will be on(3) when there is at least one test 
      in progress (running) on the port; otherwise the value will 
      be off(2)."
     ::= { prtGenEntry 7}

prtGenTestMask OBJECT-TYPE
      SYNTAX  Integer32
      MAX-ACCESS  read-only
      STATUS  current
      DESCRIPTION
      "This is a mask which indicates which tests from the
       'prtGenTestCmd' list are allowed for the selected port.
       If a specific test is allowed, its respective bit will be SET 
       in the mask :

         TEST                  BIT
        -----------            ---
        localLoop               1
        remoteLoop              2
        bert                    3
        plb                     4
        inband                  5

        prbs                    8
        loop2-v54  (RLB)        9
        loop3-v54  (LLB)       10

        Tone injection         13
        Tx-plb                 14
        Tx-llb                 15
        DTE loop (HSSI)        16

        HDSL-Tx-Inband         20
        HDSL-Rx-Inband         21
		Monitor                22  (test port)
		User Line Loopback	   23

        Rem-Loop-on-Rem-Unit   25
		LBBD                   26
		LB1                    27
		LB2                    28
        BERT-on-Rem-Unit       29
		TS Remote Loop         30
		LLB-on-Rem-Unit        31

        e.g : If the return value is 3 -> 0000000000000011  ->
              Bits 1 & 2 are set -> the allowed tests are :
                                           local-loop
                                           remote-loop  "
      ::= { prtGenEntry 8}


prtGenTestCmd OBJECT-TYPE
      SYNTAX  Integer32
      MAX-ACCESS  read-write
      STATUS  current
      DESCRIPTION
      "Setting this object to a value as detailed furter on 
       (except 0) will initiate a test on the specific port, 
       if the operation is allowed (according to TestMask). 
       If the operation is not allowed, the mux will ignore the 
       operation.
       The test/s requested will be set according to the respective
       bit:
         TEST                  BIT
        -----------            ---
        localLoop               1
        remoteLoop              2
        bert                    3
        plb                     4
        inband                  5

        prbs                    8
        loop2-v54  (RLB)        9
        loop3-v54  (LLB)       10

        Tone injection         13
        Tx-plb                 14
        Tx-llb                 15
        DTE loop (HSSI)        16

        HDSL-Tx-Inband         20
        HDSL-Rx-Inband         21
		Monitor                22  (test port)
		User Line Loopback	   23

        Rem-Loop-on-Rem-Unit   25
		LBBD                   26
		LB1                    27
		LB2                    28
        BERT-on-Rem-Unit       29
		TS Remote Loop         30
		LLB-on-Rem-Unit        31

        e.g : If the requested value is 3 -> 0000000000000011  ->
              Bits 1 & 2 are set -> the requested tests are :
                                           local-loop
                                           remote-loop  

       Setting this object to stop (value=0 ; all bits are 0), 
       will stop all the user requested tests running on the 
       selected port; it will NOT stop the tests initiated by 
       the system."
      ::= { prtGenEntry 9}

prtGenTestRunning OBJECT-TYPE
      SYNTAX  Integer32
      MAX-ACCESS  read-only
      STATUS  current
      DESCRIPTION
      "This object indicates which tests are running currently on 
       the selected port (initiated by user and/or by the system).
       If a specific test is currently running on the port, its 
       respective bit will be SET: 

         TEST                  BIT
        -----------            ---
        localLoop               1
        remoteLoop              2
        bert                    3
        plb                     4
        llb                     5
        txInband                6
        rxInband                7
        prbs                    8
        loop2-v54  (RLB)        9
        loop3-v54  (LLB)       10
        DDS DSU loop           11
        DDS CSU loop           12
        Tone injection         13
        Tx-plb                 14
        Tx-llb                 15
        DTE loop (HSSI)        16
        Local  DTE  loop (HSSI)17
        Local  Line loop (HSSI)18
        Remote Line loop (HSSI)19
        HDSL-Tx-Inband         20
        HDSL-Rx-Inband         21
		Monitor                22  (test port)
		User Line Loopback	   23
		Network Line Loopback  24
        Rem-Loop-on-Rem-Unit   25
		LBBD                   26
		LB1                    27
		LB2                    28
        BERT-on-Rem-Unit       29
		TS Remote Loop         30
		LLB-on-Rem-Unit        31

        e.g : If the return value is 3 -> 0000000000000011  ->
              Bits 1 & 2 are set -> the running tests are :
                                           local-loop
                                           remote-loop  
        llb (Bit 5) - can be initiated by system only!            "
      ::= { prtGenEntry 10}


prtGenType OBJECT-TYPE
      SYNTAX  INTEGER {
   unknown (1),
   t1      (2),
   e1      (3),
   hs      (4),
   t1Csu   (5),
   t1Dsu   (6),
   e1Ltu   (7),
   e1Dsu   (8),
   hdsl    (9),
   sp      (10),
   t1F     (11),  --T1 Fiber-optic
   e1F     (12),  --E1 Fiber-optic
   dim     (13),
   isdn    (14),
   t3      (15),
   e3      (16),
   t3f     (17),
   e3f     (18),
   idsl    (19),
   stm1    (20),
   vc4     (21),
   vc12    (22),
   msdsl   (23),
   vc11    (24), 
   vc3     (25),
   soh     (26), 
   eth     (27),
   shdsl   (28),
   other   (255)
   }
      MAX-ACCESS  read-only
      STATUS  current
      DESCRIPTION
      "This object describes the type of the selected port.
       idsl - applicable for external ports of HS-U cards (of DXC) when 
              interface is LT-1."
      ::= { prtGenEntry 11}

prtGenInterfaceType OBJECT-TYPE
      SYNTAX  DisplayString (SIZE (0..255))
      MAX-ACCESS  read-only
      STATUS  current
      DESCRIPTION
      "This attribute indicates a unique HW interface type of the
       selected port.
       Examples: 
       - for T1 cards: DSU, CSU
       - for E1 cards: DSU, LTU
       - for HS cards: v35, rs422, x21
       etc..."
      ::= { prtGenEntry 12}

prtGenAlrClearCmd  OBJECT-TYPE
      SYNTAX  INTEGER
       {
  noOp (1),
  off  (2),
  on   (3)
       }
      MAX-ACCESS  read-write
      STATUS  current
      DESCRIPTION
      "Setting this attribute to ON, will enforce a  clear 
       operation on the port level alarms . Upon completion, 
       the value will automatically change to off(2).
       noOp - will be used by agents that do not support this 
              feature or object."
      ::= { prtGenEntry 13 }

prtGenAlrMaskAll  OBJECT-TYPE
      SYNTAX  INTEGER
       {
  noOp (1),
  off  (2),
  on   (3)
       }
      MAX-ACCESS  read-write
      STATUS  current
      DESCRIPTION
      "on(3) - will mask all the alarms of the selected port
       off(2)- will unmask all alarms of the selected port except
               the ones selected by the prtAlrMaskTable.
       noOp - will be used by agents that do not support this 
              feature or object."
      ::= { prtGenEntry 14 }

prtGenParamStatus OBJECT-TYPE
      SYNTAX  OCTET STRING
      MAX-ACCESS  read-only
      STATUS  current
      DESCRIPTION
      "This object indicates Status of parameters specific to the 
       selected port.
       - For a port that has no special status or is supported
         by prtSExHsfStatTable - 1 Octet: 00hex

       - For HS cards (Dxc cards) - 1 octet:
         Bit 7 (MSB)..Bit 2 = 0 (NA)
		 Bit 0 and 1 indicates RTS control signal state:
		 Bit 1:       '1'=active  ; '0'=notActive
         Bit 0 (LSB): '1'=unknown ; '0'=NA

       - For HS-U/1 external port (MP card, used in FCD-M) - 1 Octet:
	     Bit 7  6  5  4  3  2  1  0 LSB
             |________|  |__|  |__|
               spare     modem  sync  
               
         modem: 00 = other         sync:  00 = not sync
                01 = unknown              01 = sync
                10 = ASMi-31/2            10 = reserved
                11 = reserved             11 = reserved 

       - For VC-6, VC-12, VC-12/6 external ports - 1 Octet :
         Bit 7 (MSB)..Bit 2 = 0 (NA)
         Bit 1:       Tx Signaling '1'=On ; '0'=Off
         Bit 0 (LSB): Rx Signaling '1'=On ; '0'=Off

       - For VC-2/R2(FXS) external ports - 1 Octet : 
         Bit  -   7 6 5 4 3 2 1 0
                  |_| |_________|
                  Call  Call State
             Direction     

         Bit 7 (MSB) and Bit 6  : Call Direction
         00 - Incoming
         01 - Outgoing
         Bit 5..Bit 0: Call State
         000000 - Idle
         000001 - Seized
         000010 - Both-Way Conflict
         000011 - Seizure Ack
         000100 - Answered
         000101 - Clear Backward
         000110 - Clear Forward
         000111 - Blocked
         001000 - Fault
         001001 - Fault 3
         001010 - Fault 4
         001011 - Fault 5
         001100 - Fault 6
         001101 - Fault 7 
   
       - For ML-20 external port - 3 Octets :
         - 1 MS Octet will represent the Real Rate used:
           Bit    - 7 6 5 4 3 2 1 0
                    |___| |_______|
                     spare  Rate
             
          Valid values: 0..31, meaning 0..31x64Kbps
          Invalid values: 32..255.
           - 2 LS Octets will represent the Status of 7 Control 
             Signals:
             Signal - ---  CTS  DSR  DCD   RJ   TM   DTR  RTS
             Bit   - 7 6  5 4  3 2  1 0    7 6  5 4  3 2  1 0
             Octet  -          2                     3 (LS)
             '---' will always have the value 00
             Rest of the Signals (2 bits each) can have the following
             values:
             00=NA   ;  01=Unused ; 10=Off  ; 11=On 
         
       - For ML-H/E1, ML-H/1/E1, ML-H/S/E1 internal port - 1 Octet
         Bit    - 7 6 5 4 3 2 1 0
                  |___________|
                        spare   Mode of Operation

         Mode of Operation: '1'=Central  ; '0'=Remote 

       - For KM2100, KVF.5 cards - indicates the status of A and B signaling
	                               for each internal channel.
	     1 Octet:

		 Bit  -   7 6 5 4 3 2 1 0
                  |_____| |_| |_| 
                   spare   B   A

		 Bit 0 (LSB) and Bit 1 : A status
		 Bit 2 and Bit 3       : B status

		 00 - Off
		 01 - On
		 11 - Unknown
		  
	   - For FCD-W, NETWORK and USER ports - 1 Octet
         Status of Control Signals: '1'=On  ; '0'=Off or when not applicable

         Bit    - 7 6 5 4 3 2 1 0

         Bit 7 (MSB) - Signal Loss (applicable only for G.703 interface)
         Bit 6       - CONTROL     (applicable only for X.21 interface)
         Bit 5       - INDICATION  (applicable only for X.21 interface)
         Bit 4       - DSR         (applicable only for V.35 interface)
         Bit 3       - RTS         (applicable only for V.35 interface)
         Bit 2       - CTS         (applicable only for V.35 interface)
         Bit 1       - DTR         (applicable only for V.35 interface)
         Bit 0       - DCD         (applicable only for V.35 interface)

       - For DXC R6 , D8U, D16U External ports - 1 Octet
	     Bit 7  6  5  4  3  2  1  0 LSB
             |________|  |__|  |__|
               spare     modem  sync  
               
         modem: 00 = other         sync:  00 = not sync
                01 = unknown              01 = sync
                10 = ASMi-31/2            10 = reserved
                11 = reserved             11 = reserved
         
       - For DXC DE1-HDSL, DT1-HDSL, D16GSDSL, D8SL External ports - 2 Octets

         MSB octet: far-end modem channel interface
		 LSB octet: Sub Link existence (Y/N), far-end modem type,   
		            synchronization with far-end modem

         MSB octet:  0000 0000 = no interface
					 0000 0001 = db15 (X21)
					 0000 0010 = IR-IP
					 0000 0011 = IR-ETH-Q
					 0000 0100 = V35
					 0000 0101 = ETH-RJ45
					 0000 0110 = G703
					 0000 0111 = db25 (RS530)
					 0000 1000 = ETH-BNC
					 0000 1001 = E1(Balanced)
					 0000 1010 = E1(Unbalanced) 
					 0000 1011 = IR-ETH-QN 
					 Rest of the combinations: reserved

         LSB octet:
		             
	     Bit 7  6  5  4  3  2  1  0 LSB
             |  |___________|  |__|
            SL       modem     sync
    or Box material     
               
         SL:          modem: 00000 = other      sync:  00 = not sync
         0=not exist         00001 = unknown           01 = sync
         1=exists            00010 = ASMi-31/2         10 = reserved
                             00011 = HCD-E1            11 = reserved
         Box material        00100 = HTU-E1             
         (for D8SL card):    00101 = HTU-2
		 0=metal			 00110 = ASMi-52 SA/2W/Slave
		 1=plastic			 00111 = ASMi-52 SA/2W/Master     
							 01000 = ASMi-52/CQ card of LRS-24
							 01001 = ASMi-52/CD card of LRS-24
							 01010 = D16GSDSL card of DXC-3000
							 01011 = LRS-52
							 01100 = FCD  
                             01110 = D8GSDSL card of DXC-3000 
                             01111 = ASMi-52A 
							 Rest  = reserved "
      ::= { prtGenEntry 15}

prtGenRdnStatus  OBJECT-TYPE
      SYNTAX  INTEGER
       {
       none (1),
       off  (2),
       on   (3)
       }
      MAX-ACCESS  read-only
      STATUS  current
      DESCRIPTION
      "This object indicates if this port is part of a redundant pair and in
       this case, if it is On or Off.
	   
       none(1) - No redundancy or Not Applicable
       off (2) - the port is part of a redundant pair and it is Off from 
                 Redundancy point of view (not the port used).
       on  (3) - the port is part of a redundant pair and it is On from 
                 Redundancy point of view (it is the port used)."
      ::= { prtGenEntry 16 }

prtGenTestMaskXP OBJECT-TYPE
      SYNTAX  OCTET STRING
      MAX-ACCESS  read-only
      STATUS  current
      DESCRIPTION
      "This is an Expanded test mask of the prtGenTestMask object.
       The prtGenTestMask object reached its maximum, being an Integer with 31 bits.
       This object indicates which tests from the  'prtGenTestCmdXP' list are 
       allowed for the selected port.
       If a specific test is allowed, its respective bit will be SET 
       in the mask :

         TEST                  BIT
        -----------            ---
        localLoop               1	  =LSB
        remoteLoop              2
        bert                    3
        plb                     4
        inband                  5

        prbs                    8
        loop2-v54  (RLB)        9
        loop3-v54  (LLB)       10

        Tone injection         13
        Tx-plb                 14
        Tx-llb                 15
        DTE loop (HSSI)        16

        HDSL-Tx-Inband         20
        HDSL-Rx-Inband         21
		Monitor                22  (test port)
		User Line Loopback	   23

        Rem-Loop-on-Rem-Unit   25
		LBBD                   26
		LB1                    27
		LB2                    28
        BERT-on-Rem-Unit       29
		TS Remote Loop         30
		LLB-on-Rem-Unit        31
		Downstream-AIS         32
		Upstream-AIS           33
		Send-RDI               34
		Test Per TS            35 

        e.g : If the return value is  00000003 hex  ->
              Bits 1 & 2 are set -> the allowed tests are :
                                           local-loop
                                           remote-loop  "
      ::= { prtGenEntry 17}


prtGenTestCmdXP OBJECT-TYPE
      SYNTAX  OCTET STRING
      MAX-ACCESS  read-write
      STATUS  current
      DESCRIPTION
	  "This is an Expanded test command of the prtGenTestCmd object.
       The prtGenTestCmd object reached its maximum, being an Integer with 31 bits.
       Setting this object to a value as detailed furter on 
       (except 0) will initiate a test on the specific port, 
       if the operation is allowed (according to TestMaskXP). 
       If the operation is not allowed, the mux will ignore the 
       operation.
       The test/s requested will be set according to the respective
       bit:
         TEST                  BIT
        -----------            ---
        localLoop               1	=LSB
        remoteLoop              2
        bert                    3
        plb                     4
        inband                  5

        prbs                    8
        loop2-v54  (RLB)        9
        loop3-v54  (LLB)       10

        Tone injection         13
        Tx-plb                 14
        Tx-llb                 15
        DTE loop (HSSI)        16

        HDSL-Tx-Inband         20
        HDSL-Rx-Inband         21
		Monitor                22  (test port)
		User Line Loopback	   23

        Rem-Loop-on-Rem-Unit   25
		LBBD                   26
		LB1                    27
		LB2                    28
        BERT-on-Rem-Unit       29
		TS Remote Loop         30
		LLB-on-Rem-Unit        31
		Downstream-AIS         32
		Upstream-AIS           33
		Send-RDI               34 
		Test Per TS            35

        e.g : If the requested value is 00000003 hex  ->
              Bits 1 & 2 are set -> the requested tests are :
                                           local-loop
                                           remote-loop  

       Setting this object to stop (value=0 ; all bits are 0), 
       will stop all the user requested tests running on the 
       selected port; it will NOT stop the tests initiated by 
       the system."
      ::= { prtGenEntry 18}

prtGenTestRunningXP OBJECT-TYPE
      SYNTAX  OCTET STRING
      MAX-ACCESS  read-only
      STATUS  current
      DESCRIPTION
	  "This is an Expanded object of the prtGenTestRunning object.
       The prtGenTestRunning object reached its maximum, being an Integer with 31 bits.
       This object indicates which tests are running currently on 
       the selected port (initiated by user and/or by the system).
       If a specific test is currently running on the port, its 
       respective bit will be SET: 

         TEST                  BIT
        -----------            ---
        localLoop               1	 =LSB
        remoteLoop              2
        bert                    3
        plb                     4
        llb                     5
        txInband                6
        rxInband                7
        prbs                    8
        loop2-v54  (RLB)        9
        loop3-v54  (LLB)       10
        DDS DSU loop           11
        DDS CSU loop           12
        Tone injection         13
        Tx-plb                 14
        Tx-llb                 15
        DTE loop (HSSI)        16
        Local  DTE  loop (HSSI)17
        Local  Line loop (HSSI)18
        Remote Line loop (HSSI)19
        HDSL-Tx-Inband         20
        HDSL-Rx-Inband         21
		Monitor                22  (test port)
		User Line Loopback	   23
		Network Line Loopback  24
        Rem-Loop-on-Rem-Unit   25
		LBBD                   26
		LB1                    27
		LB2                    28
        BERT-on-Rem-Unit       29
		TS Remote Loop         30
		LLB-on-Rem-Unit        31
		Downstream-AIS         32
		Upstream-AIS           33
		Send-RDI               34 
		Test Per TS            35

        e.g : If the return value is 00000003 hex  ->
              Bits 1 & 2 are set -> the running tests are :
                                           local-loop
                                           remote-loop  
        llb (Bit 5) - can be initiated by system only!            "
      ::= { prtGenEntry 19}


--prtGenTestDuration - Setting Duration of tests

prtGenTestDurationTable  OBJECT-TYPE
      SYNTAX SEQUENCE OF PrtGenTestDurationEntry
      MAX-ACCESS not-accessible
      STATUS current
	DESCRIPTION  "A table."
	::=  { prtGen 2 }

prtGenTestDurationEntry OBJECT-TYPE
      SYNTAX PrtGenTestDurationEntry
      MAX-ACCESS not-accessible
      STATUS current
	DESCRIPTION  "An entry in table."
	INDEX { prtGenTestPrtIdx, prtGenTestIdx }
      ::= { prtGenTestDurationTable 1}

PrtGenTestDurationEntry ::=
     SEQUENCE {
  prtGenTestPrtIdx     Integer32,
  prtGenTestIdx        INTEGER,
  prtGenTestDuration   Integer32 
	}

prtGenTestPrtIdx OBJECT-TYPE
      SYNTAX  Integer32
      MAX-ACCESS  read-only
      STATUS  current
      DESCRIPTION
      "This attribute indicates a unique number to identify a port. 
       The valid port number depends on the IO slot no.,  the 
       installed card type and the port type: outside/external, inside/internal. 

    In the Kilomux, the port index is calculated as follows:
    100*Slot+Ch. The external Ch numbers are 1..10, and the
    internal Ch numbers are 11..20.
       
    In the DXC :
      - first two digits will be: (IO slot number+10)
      - last one/two digits will be the port number within the 
        card in odd or even numbers, as follows:
      * For the outside/external ports, in odd numbers:
        port1 = 1
        port2 = 3
        port3 = 5 
        etc...
        Example: port2 of IO slot 11 will be: 213 .
      * The inside/internal ports, in even numbers:
        port1 = 2
        port2 = 4
        port3 = 6 
        etc...
        Example: port2 of IO slot 11 will be: 214 ."
      ::= { prtGenTestDurationEntry 1}

prtGenTestIdx OBJECT-TYPE
   SYNTAX  INTEGER  
   {
   localLoop  (1),
   remoteLoop (2),
   bert       (3),
   plb        (4),
   rlb        (5),
   llb        (6),
   toneInjection (7),
   txInband (8),
   rxInband (9),
   remLoopOnRemUnit (10), 
   bertOnRemUnit (11),
   llbOnRemUnit (12),

   txPlb        (14),
   txLlb        (15),
   dteLoop      (16), --HSSI

   hdslTxInband (20),
   hdslRxInband (21),
   monitor      (22),
   userLineLoopback(23),

   lbbd         (26),
   lb1          (27),
   lb2          (28),

   tsRemoteLoop (30),

   downstreamAis(32),
   upstreamAis  (33),
   sendRdi      (34)
   }
   MAX-ACCESS  read-only
   STATUS  current
   DESCRIPTION
   "This attribute indicates the test, the duration refers. "
   ::= { prtGenTestDurationEntry 2}

prtGenTestDuration OBJECT-TYPE
      SYNTAX  Integer32
      MAX-ACCESS  read-write
      STATUS  current
      DESCRIPTION
      "This attribute indicates the maximum duration of executing
       a test on the specific port. This entry applies to the
       specified test . The resolution will be a minute, and the
       maximum duration is limited to 30 minutes .
       A zero  value specifies no time limitation.
       When the test isn't active the agent initiates this object to
       2 min. when the duration is needed and to 0 if it's not 
       required."
      ::= { prtGenTestDurationEntry 3}
       

--prtGen TS (TimeSlot) Assignment Table - for all ports of IO cards

prtGenTsTable  OBJECT-TYPE
     SYNTAX SEQUENCE OF PrtGenTsEntry
     MAX-ACCESS not-accessible
     STATUS  current
     DESCRIPTION
      "The write operation into the Table's Objects is valid only
       for the TmpCnfg entry (Scratch),exept some products 
       which enable direct writing to the ActiveCnfg. 
       This is written in the respective product's spec. "
  ::= { prtGen 3}

prtGenTsEntry OBJECT-TYPE
      SYNTAX PrtGenTsEntry
      MAX-ACCESS not-accessible
      STATUS current
	DESCRIPTION  "An entry in table."
	INDEX {prtGenTsCnfgIdx, prtGenTsPrtIdx, prtGenTsIdx }
      ::= { prtGenTsTable 1}

PrtGenTsEntry ::=
      SEQUENCE {
      prtGenTsCnfgIdx        Integer32,
      prtGenTsPrtIdx         Integer32,
      prtGenTsIdx            Integer32,
      prtGenTsType           INTEGER,
      prtGenTsIConPrt        Integer32,
      prtGenTsIConTs         Integer32 
	}

prtGenTsCnfgIdx OBJECT-TYPE
      SYNTAX  Integer32  (1..255)
      MAX-ACCESS  read-only
      STATUS  current
      DESCRIPTION
      "This attribute indicates the Idx of the Cnfg(1..255) being 
       accessed.
       Idx of 255 relates to the TmpCnfg. "
      ::= { prtGenTsEntry 1}


prtGenTsPrtIdx OBJECT-TYPE
      SYNTAX  Integer32
     MAX-ACCESS  read-only
      STATUS  current
      DESCRIPTION
      "This attribute indicates a unique  port number.
       The valid port number depends on the IO slot no.,  the 
       installed card type and the port type: outside, inside, 
       SP.
      In the DXC :
      - first two digits will be: (IO slot number+10)
      - last one/two digits will be the port number within the 
        card in odd or even numbers, as follows:
      * For the outside/external ports, in odd numbers:
        port1 = 1
        port2 = 3
        port3 = 5 
        etc...
        Example: port2 of IO slot 11 will be: 213 .
      * The inside/internal ports, in even numbers:
        port1 = 2
        port2 = 4
        port3 = 6 
        etc...
        Example: port2 of IO slot 11 will be: 214 ."
      ::= { prtGenTsEntry 2}

prtGenTsIdx OBJECT-TYPE
      SYNTAX  Integer32
      MAX-ACCESS  read-only
      STATUS  current
      DESCRIPTION
      "This attribute indicates a unique time slot  position.
       The valid time slots are 
       1..25 for T1 Card (25=Fbit)
       0..31 for E1 or HS Card . 
       In G732S-E1 lines time slot 16 is not valid for data, 
       it is dedicated for multiframe synchronization bits
       and voice signaling."
      ::= { prtGenTsEntry 3}

prtGenTsType  OBJECT-TYPE
      SYNTAX  INTEGER
   {
   unknown       (1),
   voice         (2),
   data          (3),
   vcMP          (4),
   nc            (5),
   mng           (6)
   }
      MAX-ACCESS  read-write
      STATUS  current
      DESCRIPTION
   "The type of Timeslot. 
    If the source or destination port is an HS port,'TS Type'    
    must be 'data'.
    nc - means that this TimeSlot is not connected.
    voice, data, vcMP - also mean that this TS is connected.
    mng - means that this TS is dedicated to Management (not 
          connected to another port."
          
   ::= { prtGenTsEntry 4}

prtGenTsIConPrt OBJECT-TYPE
      SYNTAX  Integer32
      MAX-ACCESS  read-write
      STATUS  current
      DESCRIPTION
      "This attribute indicates the internally (In Mux) 
       connected port.
       The valid port number depends on the IO slot no.,  the 
       installed card type and the port type: outside, inside, 
       SP.
       * The outside ports will be the T1/E1 cards ports. 
         The convention used will be (for DXC):
         - first two digits will be: (IO slot number+10)
           for a stand-alone unit, the IO slot will be considered 1.
         - last one/two digits will be the port number within the 
           card, in odd numbers:
        port1 = 1
        port2 = 3
        port3 = 5 
        etc...
        Example: port2 of IO slot 11 will be: 213 .
       * The inside ports will be for example, the HS cards ports. 
         The convention used will be (for DXC):
         - first two digits will be: (IO slot number+10)
           for a stand-alone unit, the IO slot will be considered 1.
         - last one/two digits will be the port number within the 
           card, in even numbers:
           port1 = 2
           port2 = 4
           port3 = 6 
           etc...
           Example: port2 of IO slot 11 will be: 214 .
       * noConnection - will be indicated as 10 for DXC and FCD-E1/T1.
                      - will be indicated as 100 for FCD-E1/I and SMODs.   
       * Split TS (same TS is Split to several ports) - 11. 
	   * notApplicable- will be indicated as 100 for LRS IMODs.
       
       All HS port's timeslots must have the same destination
       port."
      ::= {prtGenTsEntry 5}

prtGenTsIConTs OBJECT-TYPE
      SYNTAX  Integer32
      MAX-ACCESS  read-write
      STATUS  current
      DESCRIPTION
      "This attribute indicates a unique time slot  position.
       The valid time slots are 
       1..25 for T1 Card (25=Fbit)
       0..31 for E1 (or HS) Card. 
       In G732S-E1 lines time slot 16 is not valid for data, it is 
       dedicated for multiframe synchronization bits and voice 
       signaling.
       * For DXC: All HS port's timeslots must start with Timeslot 
         no.1 "
      ::= {prtGenTsEntry 6}

--Port current alarms table

prtAlr  OBJECT IDENTIFIER ::= {prtGen 4}

prtSAlarmTable OBJECT-TYPE
      SYNTAX SEQUENCE OF PrtSAlarmEntry
      MAX-ACCESS not-accessible
      STATUS current
	DESCRIPTION  "A table."
	::=  { prtAlr 1 }

prtSAlarmEntry OBJECT-TYPE
      SYNTAX PrtSAlarmEntry
      MAX-ACCESS not-accessible
      STATUS current
	DESCRIPTION  "An entry in table."
	INDEX { prtSAlarmPrtIdx, prtSAlarmIdx}
      ::= { prtSAlarmTable 1}

PrtSAlarmEntry ::=
      SEQUENCE {
  prtSAlarmPrtIdx            Integer32,
  prtSAlarmIdx               Integer32,
  prtSAlarmCode              Integer32,
  prtSAlarmState             INTEGER, --severity
  prtSAlarmMask              INTEGER,
  prtSAlarmInvert            INTEGER,
  prtSAlarmOnOff             INTEGER,
  prtSAlarmCounter           Integer32 
	}        

prtSAlarmIdx OBJECT-TYPE
      SYNTAX  Integer32
      MAX-ACCESS  read-only
      STATUS  current
      DESCRIPTION
      "A unique number to identify an entry in the alarm status 
       table.
       Users should use the get next function to read this table 
       because the indexes are not consecutive."
      ::= { prtSAlarmEntry 1}

prtSAlarmPrtIdx OBJECT-TYPE
      SYNTAX  Integer32
      MAX-ACCESS  read-only
      STATUS  current
      DESCRIPTION
      "This attribute indicates a unique number to identify a port. 
       The valid port number depends on the IO slot no.,  the 
       installed card type and the port type: outside/external, inside/internal. 

    In the Kilomux, the port index is calculated as follows:
    100*Slot+Ch. The external Ch numbers are 1..10, and the
    internal Ch numbers are 11..20.
       
    In the DXC :
      - first two digits will be: (IO slot number+10)
      - last one/two digits will be the port number within the 
        card in odd or even numbers, as follows:
      * For the outside/external ports, in odd numbers:
        port1 = 1
        port2 = 3
        port3 = 5 
        etc...
        Example: port2 of IO slot 11 will be: 213 .
      * The inside/internal ports, in even numbers:
        port1 = 2
        port2 = 4
        port3 = 6 
        etc...
        Example: port2 of IO slot 11 will be: 214 ."
    ::= { prtSAlarmEntry 2}

prtSAlarmCode OBJECT-TYPE
      SYNTAX  Integer32
      MAX-ACCESS  read-only
      STATUS  current
      DESCRIPTION
      "This object indicates a code related to a specific
       alarm description. The list of codes and their related
       descriptions will be sent to NMS request (for display purpose)
       by alrGenTable."
      ::= { prtSAlarmEntry 3 }

prtSAlarmState OBJECT-TYPE
      SYNTAX  INTEGER {
   event    (3),
   minor    (4),
   major    (5),
   warning  (6),
   critical (7)
       }
      MAX-ACCESS  read-only
      STATUS  current
      DESCRIPTION
      "This object indicates the port alarm severity."      
      ::= { prtSAlarmEntry 4 }

prtSAlarmMask OBJECT-TYPE
      SYNTAX  INTEGER {
  off(2),
  on (3)
       }
      MAX-ACCESS  read-only
      STATUS  current
      DESCRIPTION
      "Alarm Mask is : on/off."
      ::= { prtSAlarmEntry 5 }

prtSAlarmInvert OBJECT-TYPE
      SYNTAX  INTEGER {
  off(2),
  on (3)
       }
      MAX-ACCESS  read-only
      STATUS  current
      DESCRIPTION
      "Alarm Invert is : on/off."
      ::= { prtSAlarmEntry 6 }

prtSAlarmOnOff OBJECT-TYPE
      SYNTAX  INTEGER {
  off(2),
  on (3)
       }
      MAX-ACCESS  read-only
      STATUS  current
      DESCRIPTION
      "Alarm state is : on/off."
      ::= { prtSAlarmEntry 7 }

prtSAlarmCounter OBJECT-TYPE
      SYNTAX  Integer32
      MAX-ACCESS  read-only
      STATUS  current
      DESCRIPTION
      "A counter - how many times the alarm occured (ON) since last
       clear operation or since last Reset."
      ::= { prtSAlarmEntry 8 }

prtAlrMaskTable OBJECT-TYPE
      SYNTAX SEQUENCE OF PrtAlrMaskEntry
      MAX-ACCESS not-accessible
      STATUS current
	DESCRIPTION  "A table."
	::=  { prtAlr 2 }

prtAlrMaskEntry OBJECT-TYPE
      SYNTAX PrtAlrMaskEntry
      MAX-ACCESS not-accessible
      STATUS current
	DESCRIPTION  "An entry in table."
	INDEX { prtAlrMaskPrtIdx}
      ::= { prtAlrMaskTable 1}

PrtAlrMaskEntry ::=
      SEQUENCE {
  prtAlrMaskPrtIdx         Integer32,
  prtAlrMask               OCTET STRING
      }        


prtAlrMaskPrtIdx OBJECT-TYPE
      SYNTAX  Integer32
      MAX-ACCESS  read-only
      STATUS  current
      DESCRIPTION
      "This attribute indicates a unique number to identify a port. 
       The valid port number depends on the IO slot no.,  the 
       installed card type and the port type: outside/external, inside/internal. 

    In the Kilomux, the port index is calculated as follows:
    100*Slot+Ch. The external Ch numbers are 1..10, and the
    internal Ch numbers are 11..20.
       
    In the DXC :
      - first two digits will be: (IO slot number+10)
      - last one/two digits will be the port number within the 
        card in odd or even numbers, as follows:
      * For the outside/external ports, in odd numbers:
        port1 = 1
        port2 = 3
        port3 = 5 
        etc...
        Example: port2 of IO slot 11 will be: 213 .
      * The inside/internal ports, in even numbers:
        port1 = 2
        port2 = 4
        port3 = 6 
        etc...
        Example: port2 of IO slot 11 will be: 214 ."
    ::= { prtAlrMaskEntry 1}

prtAlrMask OBJECT-TYPE
      SYNTAX OCTET STRING  (SIZE (8))
      MAX-ACCESS read-write
      STATUS current
   DESCRIPTION
   "This object is a mask that indicates which port level 
    alarms are masked. The masked alarms (their bit is set to 
    '1') are neither sent to the manager, nor taken into account
    for alarm status and LEDs.
    Bit no. = Alarm code
    The bits that do not belong to the port level will be 0.
    This object is applicable only when prtGenAlrMaskAll=off 
    (otherwise all port alarms are masked).
    Example: When Alarms having the codes 31 and 40 are masked,
             the value of this object will be 10080000000 (hex)."
      ::= { prtAlrMaskEntry 2 }
      
      
--Port BERT table


prtBertTable OBJECT-TYPE
      SYNTAX SEQUENCE OF PrtBertEntry
      MAX-ACCESS not-accessible
      STATUS current
   DESCRIPTION   
      "This table includes the BERT parameters, counters and 
       commands.
    The configurable parameters:
    - prtBertPattern
    - prtBertInjectRate
    - prtBertTs
    are not Set per configuration (same for all Configurations)
    but start being applied by the Agent only upon successful
    Update/Download operation. Therefore, Set will enter the 
    values to the Temporary Configuration of the agent, while
    Get will get the values of the Active Configuration."
    ::= { prtGen 5 }

prtBertEntry OBJECT-TYPE
      SYNTAX PrtBertEntry
      MAX-ACCESS not-accessible
      STATUS current
	DESCRIPTION  "An entry in table."
	INDEX { prtBertPrtIdx}
      ::= { prtBertTable 1}

PrtBertEntry ::=
      SEQUENCE {
  prtBertPrtIdx             Integer32,
  prtBertPattern            INTEGER,
  prtBertInjectRate         INTEGER,
  prtBertInjectErrRateCmd   INTEGER,
  prtBertInjectSingleErrCmd INTEGER,
  prtBertRunTime            Integer32,
  prtBertESs                Integer32,
  prtBertSyncLoss           Integer32,
  prtBertErrorBits          Integer32,
  prtBertClearCounters      INTEGER,
  prtBertSyncStatus         INTEGER,     
  prtBertTs                 OCTET STRING,
  prtBertResult 		    DisplayString,
  prtBertTxBits		        Integer32,
  prtBertRxBits			    Integer32,
  prtBertTxErrorBits		Integer32
      }        

prtBertPrtIdx OBJECT-TYPE
      SYNTAX  Integer32
      MAX-ACCESS  read-only
      STATUS  current
      DESCRIPTION
      "This attribute indicates a unique number to identify a port. 
       The valid port number depends on the IO slot no.,  the 
       installed card type and the port type: outside/external, inside/internal. 

    In the Kilomux, the port index is calculated as follows:
    100*Slot+Ch. The external Ch numbers are 1..10, and the
    internal Ch numbers are 11..20.
       
    In the DXC :
      - first two digits will be: (IO slot number+10)
      - last one/two digits will be the port number within the 
        card in odd or even numbers, as follows:
      * For the outside/external ports, in odd numbers:
        port1 = 1
        port2 = 3
        port3 = 5 
        etc...
        Example: port2 of IO slot 11 will be: 213 .
      * The inside/internal ports, in even numbers:
        port1 = 2
        port2 = 4
        port3 = 6 
        etc...
        Example: port2 of IO slot 11 will be: 214 .

    In the MP :   
      - first two digits will be: (IO slot number+10)
      - last one/two digits will be according to the external port 
        number within the card:
        exPrt1 -> 1
        exPrt2 -> 3
        exPrt3 -> 5
        exPrt4 -> 7 . "
    ::= { prtBertEntry 1}

prtBertPattern OBJECT-TYPE
      SYNTAX  INTEGER
    {
     p2E3m1   (1),
     p2E4m1   (2),
     p2E5m1   (3),
     p2E6m1   (4),
     p2E7m1   (5),
     p511     (6),
     p2E10m1  (7),
     p2047    (8),
     p2E15m1  (9),
     p2E17m1 (10),
     p2E18m1 (11),
     p2E20m1 (12),
     qrss    (13),
     p2E21m1 (14),
     p2E22m1 (15),
     p2E23m1 (16),
     p2E25m1 (17),
     p2E28m1 (18),
     p2E29m1 (19),
     p2E31m1 (20),
     p2E32m1 (21),
     rj011   (22),  
     p63     (23),  
     p1M7S   (24),  
     p1S7M   (25),  
     alternate(26), 
     mark    (27),  
     space   (28),
     p2E11m1 (29),
     notApplicable (255)
    }    
      MAX-ACCESS  read-write
      STATUS  current
      DESCRIPTION
      "This object indicates the pattern of the BERT.
       p2Exxm1 = 2Exx-1.
       pxx     = pattern xx.
       This object is the same for all configurations.
       notApplicable - when this object is not supported."
      ::= { prtBertEntry 2}

prtBertInjectRate OBJECT-TYPE
      SYNTAX  INTEGER
    {
     noError  (1),
     r10Em1   (2),
     r10Em2   (3),
     r10Em3   (4),
     r10Em4   (5),
     r10Em5   (6),
     r10Em6   (7),
     r10Em7   (8),
     single   (9),
     notApplicable (255)
    }    
      MAX-ACCESS  read-write
      STATUS  current
      DESCRIPTION
      "This object indicates the error rate injection of the BERT.
       r10Emx = 10E-x
       This object is the same for all configurations.
       single - single error injection.
       notApplicable - when this object is not supported."
      ::= { prtBertEntry 3}

prtBertInjectErrRateCmd OBJECT-TYPE
      SYNTAX  INTEGER
    {
     off  (2),
     on   (3)
    }    
      MAX-ACCESS  read-write
      STATUS  current
      DESCRIPTION
      "This object controls activation/deactivation of the Error 
       Rate Injection during BERT."   
      ::= { prtBertEntry 4}

prtBertInjectSingleErrCmd OBJECT-TYPE
      SYNTAX  INTEGER
    {
     off  (2),
     on   (3)
    }    
      MAX-ACCESS  read-write
      STATUS  current
      DESCRIPTION
      "This object enables to initiate a Single Error Injection 
       during BERT (on). Upon completion, the value will 
       automatically change to off(2)."   
      ::= { prtBertEntry 5}

prtBertRunTime OBJECT-TYPE
      SYNTAX  Integer32
      MAX-ACCESS  read-only
      STATUS  current
      DESCRIPTION
      "This object indicates how much time (seconds) passed since
       BERT started to run."   
      ::= { prtBertEntry 6}

prtBertESs OBJECT-TYPE
      SYNTAX  Integer32
      MAX-ACCESS  read-only
      STATUS  current
      DESCRIPTION
      "How many Errored Seconds were detected since BERT started
       to run.
       Counter for Kmux and MP."  
      ::= { prtBertEntry 7}
       
prtBertSyncLoss OBJECT-TYPE
      SYNTAX  Integer32
      MAX-ACCESS  read-only
      STATUS  current
      DESCRIPTION
      "How many times Sync Loss was detected since BERT started
       to run.
       For some products: number of seconds in which Sync Loss occured 
       since BERT started to run. See product specification."   
      ::= { prtBertEntry 8}
         
prtBertErrorBits OBJECT-TYPE
      SYNTAX  Integer32
      MAX-ACCESS  read-only
      STATUS  current
      DESCRIPTION
      "How many Error Bits were detected since BERT started
       to run."   
      ::= { prtBertEntry 9}

prtBertClearCounters  OBJECT-TYPE
      SYNTAX  INTEGER
       {
       off(2),
       on (3)
       }
      MAX-ACCESS  read-write
      STATUS  current
      DESCRIPTION
      "Setting this object to ON, will enforce a  clear 
       operation of some BERT Counters. Upon completion, 
       the value will automatically change to off(2)."
      ::= { prtBertEntry 10}

prtBertSyncStatus  OBJECT-TYPE
      SYNTAX  INTEGER
       {
  notApplicable(1),
  syncLoss     (2),
  sync         (3)
       }
      MAX-ACCESS  read-only
      STATUS  current
      DESCRIPTION
      "Sync Status while BERT runs."
      ::= { prtBertEntry 11}

prtBertTs  OBJECT-TYPE
      SYNTAX  OCTET STRING (SIZE(0..4))
      MAX-ACCESS  read-write
      STATUS  current
      DESCRIPTION
     "This object indicates on which TSs of the selected port, BERT 
      should be applied. 
      Each Bit of the Octet represents a TS:
      31 ......0
      MSB     LSB

      Bit 0 will not be used.
      If the bit value is '1' - BERT should be applied on this TS.
      For a  T1 port, the valid raised bits ('1') are: 1..25.
      For an E1 port, the valid raised bits ('1') are: 1..31.
      
      Agents that do not support this feature will send SIZE 0."
      ::= { prtBertEntry 12}

prtBertResult     OBJECT-TYPE
      SYNTAX      DisplayString (SIZE (0..255)) 
      MAX-ACCESS  read-only
      STATUS      current
      DESCRIPTION
     "This object indicates Result of BERT 
      for the selected port
      (number of error bits divided to the total
      number of data bits.)
      Applicable only if BERT is running on this port

      Agents that do not support this feature will send SIZE 0."
      ::= { prtBertEntry 13}


prtBertTxBits  OBJECT-TYPE
      SYNTAX      Integer32
      MAX-ACCESS  read-only
      STATUS       current
      DESCRIPTION
      "How many data bits were transmitted since BERT started
       to run, or since last counter clear 
       (prtBertClearCounters set to on)."
      ::= { prtBertEntry 14}

prtBertRxBits  OBJECT-TYPE
      SYNTAX      Integer32
      MAX-ACCESS  read-only
      STATUS       current
      DESCRIPTION
      "How many data bits were Received since BERT started
       to run, or since last counter clear 
       (prtBertClearCounters set to on)."
      ::= { prtBertEntry 15}


prtBertTxErrorBits  OBJECT-TYPE
      SYNTAX      Integer32
      MAX-ACCESS  read-only
      STATUS       current
      DESCRIPTION
      "Number of injected error bits since BERT started
       to run, or since last counter clear 
       (prtBertClearCounters set to on)."
      ::= { prtBertEntry 16}



--Port Monitoring Table - for Monitoring ports
--The table is applicable only for DXC T1/E1/HS ports and Optimux-T3

prtMonTable  OBJECT-TYPE
     SYNTAX SEQUENCE OF PrtMonEntry
     MAX-ACCESS not-accessible
     STATUS  current
     DESCRIPTION
      "For DXC, the write operation into the Table's Objects is valid only
       for the TmpCnfg entry (Scratch)."
  ::= { prtGen 6}

prtMonEntry OBJECT-TYPE
      SYNTAX PrtMonEntry
      MAX-ACCESS not-accessible
      STATUS current
	DESCRIPTION  "An entry in table."
	INDEX {prtMonCnfgIdx, prtMonitoringIdx }
      ::= { prtMonTable 1}

PrtMonEntry ::=
      SEQUENCE {
      prtMonCnfgIdx        Integer32,
      prtMonitoringIdx     Integer32,
	  prtMonitoringEnable  INTEGER,
      prtMonitoringTSs     OCTET STRING,
      prtMonitoredPort     Integer32,
      prtMonitoredTSs      OCTET STRING
      }

prtMonCnfgIdx OBJECT-TYPE
      SYNTAX  Integer32  (1..255)
      MAX-ACCESS  read-only
      STATUS  current
      DESCRIPTION
      "This object indicates the Idx of the Cnfg(1..255) being 
       accessed.
       Idx of 255 relates to the TmpCnfg.
       For products that do not support configurations, 1 will be always used."
      ::= { prtMonEntry 1}

prtMonitoringIdx OBJECT-TYPE
      SYNTAX  Integer32
      MAX-ACCESS  read-only
      STATUS  current
      DESCRIPTION
      "This object indicates the Monitoring Port Index.
	   For DXC:
         The valid port number depends on the IO slot no.,  the 
         installed card type and the port type: external, internal.
         * The external ports will according to the convention (for DXC):
         - first two digits will be: (IO slot number+10)
         - last one/two digits will be the port number within the 
           card, in odd numbers:
           port1 = 1
           port2 = 3
           port3 = 5 
           etc...
           Example: port2 of IO slot 11 will be: 213 .
         * The internal ports will be according to the convention (for DXC):
           - first two digits will be: (IO slot number+10)
           - last one/two digits will be the port number within the 
             card, in even numbers:
             port1 = 2
             port2 = 4
             port3 = 6 
             etc...
           Example: port2 of IO slot 11 will be: 214 .
        For Optimux-T3: 
          255 (Not Applicable) will be always used. The Monitoring port is always 
		  the Station Clock (not considered an interface)."
      ::= { prtMonEntry 2}

prtMonitoringEnable  OBJECT-TYPE
      SYNTAX  INTEGER
       {
      notApplicable(1),
      disabled     (2),
      enabled      (3)
       }
      MAX-ACCESS  read-write
      STATUS  current
      DESCRIPTION
      "This object indicates if the prtMonitoringIdx is configured as 
       a monitoring port or not.
       disabled = the port is NOT configured to monitor. Setting this object
	              to this value will cause reset (to 0) of the prtMonitoringTSs
				  and prtMonitoredTSs objects.
       enabled  = the port IS configured to monitor.
       For Optimux-T3: always enabled (RO supported)."
      ::= {prtMonEntry 3}

prtMonitoringTSs OBJECT-TYPE
      SYNTAX  OCTET STRING (SIZE(0..4))
      MAX-ACCESS  read-write
      STATUS  current
      DESCRIPTION
     "This object indicates which TSs of the Monitoring port, 
      the test equipment should monitor. 
      Each Bit of the Octet represents a TS:
      31 ......0
      MSB     LSB

      Bit 0 will not be used.
      If the bit value is '1' - this TS should be monitored.
      For a  T1 port, the valid raised bits ('1') are: 1..24.
      For an E1 port, the valid raised bits ('1') are: 1..31.
      Default: all bits='0'
      Agents that do not support this feature will send SIZE 0.
      This object can be Set as described only if prtMonitoringEnable=enabled. "
      ::= {prtMonEntry 4}

prtMonitoredPort  OBJECT-TYPE
      SYNTAX  Integer32
      MAX-ACCESS  read-write
      STATUS  current
      DESCRIPTION
      "This object indicates the MONITORED Port Index that the Monitoring
       port monitors.
	   For DXC:
         The valid port number depends on the IO slot no.,  the 
         installed card type and the port type: external, internal.
         * The external ports will according to the convention (for DXC):
           - first two digits will be: (IO slot number+10)
           - last one/two digits will be the port number within the 
             card, in odd numbers:
             port1 = 1
             port2 = 3
             port3 = 5 
             etc...
           Example: port2 of IO slot 11 will be: 213 .
         * The internal ports will be according to the convention (for DXC):
           - first two digits will be: (IO slot number+10)
           - last one/two digits will be the port number within the 
             card, in even numbers:
             port1 = 2
             port2 = 4
             port3 = 6 
             etc...
           Example: port2 of IO slot 11 will be: 214 .
         * 100 - no port monitored
       For Optimux-T3:
	     The valid channels are:
         0 =  no Ch monitored
         1..21 or 1..28 (=CH1..CH21 or CH1..CH28) according to product's 
         configuration."
   ::= { prtMonEntry 5}

prtMonitoredTSs OBJECT-TYPE
      SYNTAX  OCTET STRING (SIZE(0..4))
      MAX-ACCESS  read-write
      STATUS  current
      DESCRIPTION
     "This object indicates which TSs of the Monitored port, should be monitored. 
      Each Bit of the Octet represents a TS:
      31 ......0
      MSB     LSB

      Bit 0 will not be used.
      If the bit value is '1' - this TS should be monitored.
      For a  T1 port, the valid raised bits ('1') are: 1..24.
      For an E1 port, the valid raised bits ('1') are: 1..31.
      Default: all bits='0'
      Agents that do not support this feature will send SIZE 0.
      This object can be Set as described only if prtMonitoringEnable=enabled."
      ::= {prtMonEntry 6}


-- Port Configuration Table
-- This table is applicable  for KMUX, FCD-T1/E1 , FCD-T1L/E1L and FCD-U ports 

prtCfgParam  OBJECT IDENTIFIER  ::=  {prtGen 7}

prtCfgParamTable OBJECT-TYPE
      SYNTAX SEQUENCE OF PrtCfgParamEntry
      MAX-ACCESS not-accessible
      STATUS  current
      DESCRIPTION
       "The write operation into the Table Objects is valid only
        to the TmpCnfg entry.
        KMUX parameters are for the cards: KMBE/New, KVF.6 family."
      ::= { prtCfgParam 1}

prtCfgParamEntry OBJECT-TYPE
      SYNTAX PrtCfgParamEntry
      MAX-ACCESS not-accessible
      STATUS current
	DESCRIPTION  "An entry in table."
	INDEX {prtCfgParamCnfgIdx, prtCfgParamIdx }
      ::= { prtCfgParamTable 1}

PrtCfgParamEntry ::=
      SEQUENCE {
        prtCfgParamCnfgIdx        Integer32,
        prtCfgParamIdx            Integer32,
        prtCfgParamSlt            INTEGER,
        prtCfgParamOperatedMl     INTEGER,
        prtCfgParamMlAtoMlBPrio   INTEGER,
        prtCfgParamMlBtoMlAPrio   INTEGER,
		prtCfgParamInbandLoopDetection    INTEGER,
		prtCfgParamInbandLoopPatternCfg	  INTEGER,
		prtCfgParamInbandLoopActPattern   DisplayString,
		prtCfgParamInbandLoopDeactPattern DisplayString
        }

prtCfgParamCnfgIdx OBJECT-TYPE
      SYNTAX  Integer32  (1..255)
      MAX-ACCESS  read-only
      STATUS  current
      DESCRIPTION
      "This attribute indicates the Idx of the Cnfg (1..100) being 
       accessed.
       Idx  255 relates to the TmpCnfg."
      ::= {prtCfgParamEntry 1}

prtCfgParamIdx OBJECT-TYPE
      SYNTAX  Integer32
      MAX-ACCESS  read-only
      STATUS  current
      DESCRIPTION
      "A unique identifier of the port (within the card when applicable).
       - For KM-2100:  Slot*100+Ch
         external ports:  Ch=1..10
         internal ports (sub-channels): Ch=11..20.
       - For FCD-T1/E1(L): MAIN=111, SUB=113, CH1=122, CH2=124.
       - For other devices, see specific device's spec. "
      ::= {prtCfgParamEntry 2}

prtCfgParamSlt OBJECT-TYPE
      SYNTAX  INTEGER
 {
       io1   (5),
       io2   (6),
       io3   (7),
       io4   (8),
       io5   (9),
       io6  (10),
       io7  (11),
       io8  (12),
       io9  (13),
    kmxIO1 (107),
    kmxIO2 (108),
    kmxIO3 (109),
    kmxIO4 (110),
    kmxIO5 (111),
    kmxIO6 (112),
    kmxIO7 (113),
    kmxIO8 (114),
    kmxIO9 (115),
    kmxIO10(116),
    kmxIO11(117),
    kmxIO12(118),
	notApplicable(255)
       }
      MAX-ACCESS  read-only
      STATUS  current
      DESCRIPTION
      "This attribute indicates a unique number to identify the slot where
       the card is inserted in.
       In the 2104 Unit the entries kmxIO5(111)..kmxIO12(118) are not valid.
       notApplicable(255) - for products that do not have Slots."
      ::= {prtCfgParamEntry 3}

 prtCfgParamOperatedMl OBJECT-TYPE
      SYNTAX  INTEGER {
                  notApplicable(1),
                  kmxMlA     (103),
                  kmxMlB     (104)				  
        }
      MAX-ACCESS  read-write
      STATUS  current
      DESCRIPTION
      "The main link for this channel.
       The field is relevant only for ML modes of Dual, Priority 
       Bumping and Switched Backup."
      ::= {prtCfgParamEntry 4}

prtCfgParamMlAtoMlBPrio OBJECT-TYPE
      SYNTAX  INTEGER {
                       notApplicable(1),
                       low          (2),
                       high         (3)
        }
      MAX-ACCESS  read-write
      STATUS  current
      DESCRIPTION
      "ML-A to ML-B Priority.
       The field is relevant only for ML modes of Priority Bumping
       and Switched Backup."
      ::= {prtCfgParamEntry 5}

prtCfgParamMlBtoMlAPrio OBJECT-TYPE
      SYNTAX  INTEGER {
                     notApplicable(1),
                     low          (2),
                     high         (3)
        }
      MAX-ACCESS  read-write
      STATUS  current
      DESCRIPTION
      "ML-B to ML-A Priority.
       The field is relevant only for ML modes of Priority Bumping."
      ::= {prtCfgParamEntry 6}

prtCfgParamInbandLoopDetection OBJECT-TYPE
      SYNTAX  INTEGER {
                     notApplicable(1),
                     disabled     (2),
                     enabled      (3)
        }
      MAX-ACCESS  read-write
      STATUS  current
      DESCRIPTION
      "Inband Loop Detection.
       The field is relevant for FCD-T1/E1(L) ports."
      ::= {prtCfgParamEntry 7}

prtCfgParamInbandLoopPatternCfg OBJECT-TYPE
      SYNTAX  INTEGER
       {
       notApplicable   (1),
       rdlLoop         (2),
       userConfig      (3)
       }
      MAX-ACCESS  read-write
      STATUS  current
      DESCRIPTION
      "This object indicates if Inband Loop polynomial pattern
       will be according to RDL Loop (the standard) or User Configurated
       according to prtCfgParamInbandLoopActPattern and 
       prtCfgParamInbandLoopDeactPattern."
      ::= {prtCfgParamEntry 8}

prtCfgParamInbandLoopActPattern OBJECT-TYPE
      SYNTAX DisplayString
      MAX-ACCESS read-write
      STATUS current
      DESCRIPTION
      "This object is a binary string of up to 8 bits.
	   Though the syntax allows for any ASCII characters, for this object
	   only '0' or '1' characters are valid.
       The string determines coefficients of the polynomial pattern
       sent to the port in order to Activate the Inband Loop.
       This object is relevant only when prtCfgParamInbandLoopPatternCfg=userConfig."
      ::= {prtCfgParamEntry 9}

prtCfgParamInbandLoopDeactPattern OBJECT-TYPE
      SYNTAX DisplayString
      MAX-ACCESS read-write
      STATUS current
      DESCRIPTION
      "This object is a binary string of up to 8 bits.
	   Though the syntax allows for any ASCII characters, for this object
	   only '0' or '1' characters are valid.
       The string determines coefficients of the polynomial pattern
       sent to the port in order to Deactivate the Inband Loop.
       This object is relevant only when prtCfgParamInbandLoopPatternCfg=userConfig."
      ::= {prtCfgParamEntry 10}


--DACS T1/E1 port specific parameters  

--DACS T1/E1 port statistics parameters.
--These parameters are in addition to those of RFC-1406 MIB. 

prtT1E1StatTable OBJECT-TYPE
  SYNTAX  SEQUENCE OF PrtT1E1StatEntry
  MAX-ACCESS  not-accessible
  STATUS  current
  DESCRIPTION
  "T1/E1 port statistics table."
  ::= { prtT1E1 1}

prtT1E1StatEntry   OBJECT-TYPE
  SYNTAX  PrtT1E1StatEntry
  MAX-ACCESS  not-accessible
  STATUS  current
  DESCRIPTION
  " An entry in the T1/E1 port statistics table."
  INDEX { prtT1E1SPrtIdx }
  ::= { prtT1E1StatTable 1}

PrtT1E1StatEntry ::=
     SEQUENCE {
  prtT1E1SPrtIdx    Integer32,
  prtT1E1SSlt	    INTEGER,
  prtT1E1OosCount   Gauge32,
  prtT1E1BpvLastMin	Gauge32,
  prtT1E1BpvMax	    Gauge32
  }

prtT1E1SPrtIdx OBJECT-TYPE
      SYNTAX  Integer32
      MAX-ACCESS  read-only
      STATUS  current
      DESCRIPTION
      "This attribute indicates a unique  port number.
       The same numbering as for prtGenPrtIdx.
       The valid port number depends on the IO slot no.,  the 
       installed card type and the port type: outside, inside. 
      * The outside ports will be the T1/E1 cards ports. 
        The convention used will be (for DXC):
        - first two digits will be: (IO slot number+10)
        - last one/two digits will be the port number within the 
          card, in odd numbers:
          port1 = 1
          port2 = 3
          port3 = 5 
          etc...
        Example: port2 of IO slot 11 will be: 213 ."
      ::= { prtT1E1StatEntry 1}

prtT1E1SSlt     OBJECT-TYPE
      SYNTAX  INTEGER
       {
       clA   (3),
       clB   (4),
       io1   (5),
       io2   (6),
       io3   (7),
       io4   (8),
       io5   (9),
       io6  (10),
       io7  (11),
       io8  (12),
       io9  (13),
       io10 (14),
       io11 (15),
       io12 (16),
    io13 (17),
    io14 (18),
    io15 (19),
    standAlone (255)
       }
      MAX-ACCESS  read-only
      STATUS  current
      DESCRIPTION
      "This attribute indicates a unique number to identify the slot where
       the card is inserted in.
       When the unit is stand-alone, this object is not applicable
       and 255 will be used."
      ::= { prtT1E1StatEntry 2}

prtT1E1OosCount  OBJECT-TYPE
   SYNTAX  Gauge32
      MAX-ACCESS  read-only
      STATUS  current
      DESCRIPTION
   "This object is applicable only for an E1 active port.
    It provides the number of red alarm events since the last
    count clearing."
   ::= { prtT1E1StatEntry 3 }

prtT1E1BpvLastMin  OBJECT-TYPE
   SYNTAX  Gauge32
      MAX-ACCESS  read-only
      STATUS  current
      DESCRIPTION
   "This object is applicable only for an E1 active port.
    It provides the number of BPV (BiPolar Violation) events 
    detected during the last minute."
   ::= { prtT1E1StatEntry 4 }

prtT1E1BpvMax  OBJECT-TYPE
   SYNTAX  Gauge32
      MAX-ACCESS  read-only
      STATUS  current
      DESCRIPTION
   "This object is applicable only for an E1 active port.
    It provides the maximal number of BPV (BiPolar Violation) 
    events (per minute), detected during the worst minute."
   ::= { prtT1E1StatEntry 5 }


--DACS T1/E1 port configuration parameters.
--
--Objects 2..9 appear in RFC-1406 MIB (dsx1ConfigTable) as RW
--objects. They were entered in this private MIB, because in
--RFC-1406 MIB there is no reference to configuration number.


prtT1E1CnfgTable OBJECT-TYPE
  SYNTAX  SEQUENCE OF PrtT1E1CnfgEntry
  MAX-ACCESS  not-accessible
  STATUS  current
  DESCRIPTION
  "T1/E1 port configuration table."
  ::= { prtT1E1 2}

prtT1E1CnfgEntry   OBJECT-TYPE
  SYNTAX  PrtT1E1CnfgEntry
  MAX-ACCESS  not-accessible
  STATUS  current
  DESCRIPTION
  " An entry in the T1/E1 port configuration table."
  INDEX { prtT1E1CnfgIdx, prtT1E1PrtIdx }
  ::= { prtT1E1CnfgTable 1}

PrtT1E1CnfgEntry ::=
     SEQUENCE {
  prtT1E1CnfgIdx    Integer32,
  prtT1E1PrtIdx	    Integer32,
  prtT1E1Slt	    INTEGER,
  prtT1E1LineType   INTEGER,
  prtT1E1LineCode   INTEGER,
  prtT1E1SignalMode INTEGER,
  prtT1E1Fdl	    INTEGER,
  prtT1E1FdlMode    INTEGER,
  prtT1E1Sync	    INTEGER,
  prtT1E1CGA	    INTEGER,
  prtT1E1IdleCode   OCTET STRING,
  prtT1E1OosSignal  INTEGER,
  prtT1E1VoiceOos   OCTET STRING,
  prtT1E1DataOos    OCTET STRING,
  prtT1E1LineLengthMask	INTEGER,
  prtT1E1TxGainMask	INTEGER,
  prtT1E1InbandMng  INTEGER,
  prtT1E1InbandMngRate  INTEGER,
  prtT1E1DedicatedTs  Integer32,
  prtT1E1InbandMngRoutProt INTEGER,
  prtT1E1LinkMode   INTEGER,
  prtT1E1Multiplier INTEGER,
  prtT1E1RxGain     INTEGER,
  prtT1E1RAI        INTEGER, 
  prtT1E1LineMode   INTEGER,
  prtT1E1TS0SaBits  OCTET STRING,
  prtT1E1ConnectedTS INTEGER,
  prtT1E1Ts0SaBit    INTEGER,
  prtT1E1SameFeCnfg	 INTEGER,
  prtT1E1RemCrc4     INTEGER,
  prtT1E1MaxTSs	     Integer32,
  prtT1E1EocTsConfig INTEGER,
  prtT1E1Role	     INTEGER,
  prtT1E1PppEchoFailDetection INTEGER
  }

prtT1E1CnfgIdx OBJECT-TYPE
      SYNTAX  Integer32 (1..255)
      MAX-ACCESS  read-only
      STATUS  current
      DESCRIPTION
      "This attribute indicates the Idx of the Config being accessed.
       Idx of 255 relates to the Temporary (Scratch) Config. "
      ::= { prtT1E1CnfgEntry 1}

prtT1E1PrtIdx OBJECT-TYPE
      SYNTAX  Integer32
      MAX-ACCESS  read-only
      STATUS  current
      DESCRIPTION
      "This attribute indicates a unique  port number.
    The same numbering as for prtGenPrtIdx.
       The valid port number depends on the IO slot no.,  the 
       installed card type and the port type: outside, inside. 
       In the DXC :
      - first two digits will be: (IO slot number+10)
      - last one/two digits will be the port number within the 
        card in odd or even numbers, as follows:
      * For the outside/external ports, in odd numbers:
        port1 = 1
        port2 = 3
        port3 = 5 
        etc...
        Example: port2 of IO slot 11 will be: 213 .
      * The inside/internal ports, in even numbers:
        port1 = 2
        port2 = 4
        port3 = 6 
        etc...
        Example: port2 of IO slot 11 will be: 214 .
   
       In the Kilomux, the port index is calculated as follows:
       100*Slot+Ch. The external Ch numbers are 1..10, and the
       internal Ch numbers are 11..20."
      ::= { prtT1E1CnfgEntry 2}

prtT1E1Slt     OBJECT-TYPE
      SYNTAX  INTEGER
       {
       clA   (3),
       clB   (4),
       io1   (5),
       io2   (6),
       io3   (7),
       io4   (8),
       io5   (9),
       io6  (10),
       io7  (11),
       io8  (12),
       io9  (13),
       io10 (14),
       io11 (15),
       io12 (16),
       io13 (17),
       io14 (18),
       io15 (19),
   
    kmxMlA (103),
    kmxMlB (104),

    kmxOpt (106),
    kmxIO1 (107),
    kmxIO2 (108),
    kmxIO3 (109),
    kmxIO4 (110),
    kmxIO5 (111),
    kmxIO6 (112),
    kmxIO7 (113),
    kmxIO8 (114),
    kmxIO9 (115),
    kmxIO10(116),
    kmxIO11(117),
    kmxIO12(118),
    standAlone (255)
       }
      MAX-ACCESS  read-only
      STATUS  current
      DESCRIPTION
      "This attribute indicates a unique number to identify the slot where
       the card is inserted in.
       When the unit is stand-alone, this object is not applicable
       and 255 will be used."
      ::= { prtT1E1CnfgEntry 3}

prtT1E1LineType OBJECT-TYPE
    SYNTAX  INTEGER {
                other    (1),
                esf      (2),
                d4       (3), --sf
                e1       (4),
                e1Crc    (5),
                e1MF     (6),
                e1CrcMF  (7),
                unframed (8)
            }
    MAX-ACCESS  read-write
    STATUS  current
    DESCRIPTION
       "This variable indicates  the  variety  of T1/E1
        Line  implementing  this  circuit.  The type of
        circuit affects the number of bits  per  second
        that  the circuit can reasonably carry, as well
        as the interpretation of the  usage  and  error
        statistics.  The values, in sequence, describe:

       TITLE:        SPECIFICATION:
       esf       Extended SuperFrame DS1
       d4        AT&T D4 format DS1  - SF
       e1        CCITT Recommendation G.704
                 (Table 4a) - G732N
       e1Crc     CCITT Recommendation G.704
                 (Table 4b) - G732N with CRC
       e1MF      G.704 (Table 4a) with TS16
                 multiframing enabled - G732S
       e1CrcMF   G.704 (Table 4b) with TS16
                 multiframing enabled - G732S with CRC
       unframed  
     
       T1 - applicable values: (1),(2),(3),(8)
       E1 - applicable values: (1),(4),(5),(6),(7),(8) "
    ::= { prtT1E1CnfgEntry 4 }

prtT1E1LineCode OBJECT-TYPE
    SYNTAX  INTEGER {
                jbzs (1),
                b8zs (2),
                hdb3 (3),
                zbtsi(4),
                ami  (5),
                other(6)
            }
    MAX-ACCESS  read-write
    STATUS  current
    DESCRIPTION
       "This variable describes the  variety  of  Zero
       Code  Suppression  used  on  the link, which in
       turn affects a number of its characteristics.

       jbzs=b7zs refers the Jammed  Bit  Zero  Suppres-
       sion,  in  which  the  AT&T specification of at
       least one pulse every 8 bit periods is literal-
       ly  implemented  by forcing a pulse in bit 8 of
       each channel.  Thus, only seven bits per  chan-
       nel, or 1.344 Mbps, is available for data (used for T1).

       b8zs refers to the use of a specified pattern
       of  normal  bits  and  bipolar violations
       which are used to replace a sequence  of  eight
       zero bits (used for T1).

       ANSI Clear Channels may use zbtsi, or  Zero
       Byte Time Slot Interchange.

       E1 links, with or without CRC, use hdb3  or
       ami (= TRAN).

       amI (=TRAN) refers to a mode wherein no zero code
       suppression  is  present  and the line encoding
       does not solve the problem directly. In this
       application, the higher layer must provide data
       which meets or exceeds the  pulse  density  re-
       quirements, such as inverting HDLC data."
   ::= { prtT1E1CnfgEntry 5 }

prtT1E1SignalMode OBJECT-TYPE
    SYNTAX  INTEGER {
                none            (1),
                robbedBit       (2),
                bitOriented     (3),  --CAS
                messageOriented (4)   --CCS
            }
    MAX-ACCESS  read-write
    STATUS  current
    DESCRIPTION
       "'none' indicates that no bits are reserved for
               signaling on this channel.

        'robbedBit' indicates that T1 Robbed Bit Signaling is in use.

        'bitOriented' indicates that E1 Channel  Associated 
               Signaling (CAS) is in use.

        'messageOriented' indicates that Common  Channel Signaling 
               (CCS) is in use either on channel 16 of an E1 link or 
               channel 24 of a T1."
   ::= { prtT1E1CnfgEntry 6 }

prtT1E1Fdl OBJECT-TYPE
    SYNTAX  INTEGER {
                  other      (1),
                  ansi-T1-403(2),
                  att-54016  (4),
                  fdl-none   (8),
                  transFdl   (16)
            }
    MAX-ACCESS  read-write
    STATUS  current
    DESCRIPTION
       "This bitmap describes the use of  the  facili-
        ties data link, and is the sum of the capabili-
        ties:

        'other' indicates that a protocol  other  than
         one following is used.

        'ansi-T1-403' refers to the  FDL  exchange
         recommended by ANSI.

        'att-54016' refers to ESF FDL exchanges.

        'fdl-none' indicates that the device  does
         not use the FDL.
        'transFdl' indicates transition between two ports of 
         the same card. "
   ::= { prtT1E1CnfgEntry 7 }

prtT1E1FdlMode OBJECT-TYPE
    SYNTAX  INTEGER {
      other     (1),
      user      (2),
      carrier   (3),
      notApplicable (255)
            }
    MAX-ACCESS  read-write
    STATUS  current
    DESCRIPTION
    " Fdl Mode of the T1 selected port.
      notApplicable - will be used for an E1 port."
   ::= { prtT1E1CnfgEntry 8 }


prtT1E1Sync OBJECT-TYPE
    SYNTAX  INTEGER {
    other  (1),
    tr62411(2),
    ccitt  (3),
    fast   (4)                 
            }
    MAX-ACCESS  read-write
    STATUS  current
    DESCRIPTION
    "This object enables returning to normal operation, after 
     the end of a main/sub link red alarm event, in reduced time.
        'tr62411' - complies with AT&T TR-62411 (after 10 seconds).
              Applicable for both T1 and E1 interfaces.
    'ccitt'   - complies with CCITT standard. Applicable only
              for E1 interfaces.
    'fast'    - after 1 second."
    ::= { prtT1E1CnfgEntry 9 }

prtT1E1CGA OBJECT-TYPE
    SYNTAX  INTEGER {
      none (1),
      trans(2),
      full (3)                                   
            }
    MAX-ACCESS  read-write
    STATUS  current
    DESCRIPTION
    "This object selects the method used to signal the CGA state
     to the other end, through the main/sub link. 
     'none'  - non-transparent mode. When one of the links 
               (main/sub) will be in Out Of Service state, both 
               'Data/Voice Oos' and 'Oos Signal' will be 
               transmitted to the other end.
     'trans' - when one of the links (main/sub) will be in Out
               Of Service state, 'Data/Voice Oos' will be 
               transmitted to the other end.
     'full'  - fully-transparent mode. When one of the links 
                  (main/sub) will be in Out Of Service state, 
                  neither 'Data/Voice Oos' nor 'Oos Signal' will 
                  be transmitted to the other end."
    ::= { prtT1E1CnfgEntry 10 }

prtT1E1IdleCode OBJECT-TYPE
    SYNTAX  OCTET STRING (SIZE (0..4))
    MAX-ACCESS  read-write
    STATUS  current
    DESCRIPTION
    "This object selects the code transmitted to fill idle 
     (unused) time slots in the main link frame. 
     Valid range: (0 - FF HEX) ."
    ::= { prtT1E1CnfgEntry 11 }

prtT1E1OosSignal  OBJECT-TYPE
      SYNTAX  INTEGER
       {
        notsupported  (2),
        forcedIdle    (3),
        forcedBusy    (4),
        busyIdle      (5),
        idleBusy      (6)
       }
      MAX-ACCESS  read-write
      STATUS  current
      DESCRIPTION
      "'idle' = '0' = on-hook, idle state
       'busy' = '1' = off-hook, busy state
       'forcedIdle' = SP = both A and B signaling bits are forced
                      to '0' during out-of-service periods.
       'forcedBusy' = MK = both A and B signaling bits are forced
                      to '1' during out-of-service periods.
       'busyIdle'   = MK_SP = A and B bits are forced to '1' for
                      2.5 seconds; then they are switched to '0'
                      until out-of-service condition disappears.
       'idleBusy'   = SP_MK = A and B bits are forced to '0' for
                      2.5 seconds; then they are switched to '1'
                      until out-of-service condition disappears.
       - for T1:    '0'=0   ;  '1'=1                         
       - for E1:    '0'=1   ;  '1'=0   "
   ::= { prtT1E1CnfgEntry 12 }

prtT1E1VoiceOos  OBJECT-TYPE
    SYNTAX  OCTET STRING (SIZE (0..4))
    MAX-ACCESS  read-write
    STATUS  current
    DESCRIPTION
    "Voice Out-Of-Service code. Valid range: (0 - FF HEX).
     For agents that do not support this feature, the value will
     always be 0."
   ::= { prtT1E1CnfgEntry 13 }

prtT1E1DataOos  OBJECT-TYPE
    SYNTAX  OCTET STRING (SIZE (0..4))
    MAX-ACCESS  read-write
    STATUS  current
    DESCRIPTION
    "Data Out-Of-Service code. Valid range: (0 - FF HEX).
     For agents that do not support this feature, the value will
     always be 0."
   ::= { prtT1E1CnfgEntry 14 }

prtT1E1LineLengthMask  OBJECT-TYPE
      SYNTAX  INTEGER
       {
        unknown      (1),
        len0p133ft   (2),
        len134p266ft (3),
        len267p399ft (4),
        len400p533ft (5),
        len534p655ft (6),
        fcc68        (7)
       }
      MAX-ACCESS  read-write
      STATUS  current
      DESCRIPTION
      "This attribute is the line length mask parameter used only 
       for T1/DSU interfaces.
       len400p533ft=length range: 400ft to 533ft 
       'fcc68' - provides compliance with the FCC 68.308 Option A
                 output pulse mask. "
      ::= { prtT1E1CnfgEntry 15 }

prtT1E1TxGainMask  OBJECT-TYPE
      SYNTAX  INTEGER
       {
          notApplicable     (1),
          txGain0db         (2),
          txGain7dot5db     (3),
          txGain15db        (4),
          txGain22dot5db    (5)
       }
      MAX-ACCESS  read-write
      STATUS  current
      DESCRIPTION
      "This attribute is the tx gain mask parameter (dB), used 
       only for T1/CSU interfaces."
   ::= { prtT1E1CnfgEntry 16 }

prtT1E1InbandMng  OBJECT-TYPE
      SYNTAX  INTEGER
       {
          off         (2),
          fdlOrTs0    (3),
          dedicatedTs (4),
          dedicatedPpp(5),
          dedicatedFr (6),
          internal    (7)		  
       }
      MAX-ACCESS  read-write
      STATUS  current
      DESCRIPTION
      "A unique number to identify an Inband management over the 
       link.
       internal - supported by KM-2100 only. It means that the management is internal
                  to the frame. It takes part of the ML Frame bits (instead of data)."
      ::= {prtT1E1CnfgEntry 17}

prtT1E1InbandMngRate  OBJECT-TYPE
      SYNTAX  INTEGER
       {
          notApplicable(1),
          r4k   (2),
          r8k   (3),
          r12k  (4),
          r16k  (5),
          r32k  (6),
          r64k  (7),
          r20k  (8)
       }
      MAX-ACCESS  read-write
      STATUS  current
      DESCRIPTION
      "A unique number to identify the rate of the Inband management.
       It is required only for E1 links and is applicable only when 
       prtExT1E1InbandMng selected is FdlOrTs0 or dedicatedTs."
      ::= {prtT1E1CnfgEntry 18}

prtT1E1DedicatedTs  OBJECT-TYPE
      SYNTAX  Integer32
      MAX-ACCESS  read-write
      STATUS  current
      DESCRIPTION

      "The value is differently determined for different products.
       There are two methods:

       1) A unique number to identify Dedicated TS of the T1/E1 port.
          It is applicable only when prtExT1E1InbandMng selected is 
          dedicatedTs.
          1..24 - Dedicated TS of T1
          1..31 - Dedicated TS of E1
          255   - notApplicable (for agents that do not support this 
                  feature)
          Other values are invalid.

       2) For FCD-STM,  up to five TSs may be dedicated to management.
          This object value is the Sum (sigma) of 2**n, where n =TS-1
          e.g. 	  Time slots 3,5,7,9,11 are dedicated to management:
            	   2** 2
          		  +2** 4
          		  +2** 6 
          		  +2** 8
          		  +2**10  = 4+16+64+256+1024=1364 
       
       User should consult the product specification, to find out 
       the method employed."
	   ::= {prtT1E1CnfgEntry 19}

prtT1E1InbandMngRoutProt  OBJECT-TYPE
      SYNTAX  INTEGER
       {
       notApplicable (1),
       none          (2),  
       proprietary   (3),
       rip2          (4)
       }
      MAX-ACCESS  read-write
      STATUS  current
      DESCRIPTION
      "Inband Mng Routing Protocol of the port.
       When prtT1E1InbandMng is 'dedicatedPpp'-'proprietary' and
                                               'rip2' are applicable.
       For other values  - only 'proprietary' is applicable.
       
       For FCD-M and FCD-A:
       When prtT1E1InbandMng is 'dedicatedPpp' or 'dedicatedFr':
                             'None', 'proprietary' and 'rip2' are applicable.
       When prtT1E1InbandMng is 'fdlOrTS0' or 'dedicatedTs':
                             'None' and 'proprietary' are applicable.
       When prtT1E1InbandMng is 'off':
                             'None' is applicable."             
      ::= {prtT1E1CnfgEntry 20}

prtT1E1LinkMode  OBJECT-TYPE
      SYNTAX  INTEGER
       {
       notApplicable (1),
       regular       (2),  
       transparent   (3)
       }
      MAX-ACCESS  read-write
      STATUS  current
      DESCRIPTION
      "regular - TSs are connected by user via TS Assignment only
       transparent - when a port with this Link Mode is connected to an 
                     internal T1/E1 port of a T3/E3 card, TS0, TS16 and Fbit
                     are transparently transferred to the E3/T3 stream."             
      ::= {prtT1E1CnfgEntry 21}

prtT1E1Multiplier OBJECT-TYPE
      SYNTAX  INTEGER { 
      notApplicable (1), 
      br56 (2),
      br64 (3)
      }
      MAX-ACCESS  read-write
      STATUS  current
      DESCRIPTION
      "The data rate of each TS. The multiplier values
       can be 56 kbps or 64 kbps. For T1 only."
      ::= { prtT1E1CnfgEntry 22 }

prtT1E1RxGain OBJECT-TYPE
      SYNTAX  INTEGER
       {
       notApplicable  (1),
       rxGain12dB     (2),
       rxGain30dB     (3),
       rxGain36dB     (4),
	   shortHaul      (5),
	   longHaul       (6),
	   rxGain20dB     (7)
       }
      MAX-ACCESS  read-write
      STATUS  current
      DESCRIPTION
      "This attribute is the rx volume (dB)."
   ::= { prtT1E1CnfgEntry 23 }

 prtT1E1RAI  OBJECT-TYPE
      SYNTAX  INTEGER
       {
        notApplicable  (1),
        off (2),
        on  (3)
       }
      MAX-ACCESS  read-write
      STATUS  current
      DESCRIPTION
      "Remote Alarm Signal"
   ::= { prtT1E1CnfgEntry 24 }

prtT1E1LineMode OBJECT-TYPE
      SYNTAX  INTEGER 
       {
        notApplicable	(1), 
        csu				(2),
        dsu				(3),
		ltu				(4)
       }
        MAX-ACCESS  read-write
        STATUS  current
        DESCRIPTION
      "Interface type of the port.
       For T1 - csu, dsu are the valid values
       For E1 - dsu, ltu are the valid values"
   ::= { prtT1E1CnfgEntry 25 }

prtT1E1TS0SaBits OBJECT-TYPE
    SYNTAX  OCTET STRING 
    MAX-ACCESS  read-write
    STATUS  current
    DESCRIPTION
    "This object is applicable only for E1 ports. For T1, string size will be 0.
     For E1, it enables user to select the use of TS0 Sa Bits 4..8, by 3 octets:
	 The order (in hexa display):
	 free Sa-Bit-4  Sa-Bit-5  Sa-Bit-6  Sa-Bit-7  Sa-Bit-8
	 |___________|  |________________|  |________________|
	     MSByte                                 LSByte
	     
	 Each Sa Bit will be represented by a nibble, having the following meaning:
	 0000 = zero
	 0001 = one
	 0010 = management
	 0011 = transparent
	 the rest are reserved for future use."      
   ::= { prtT1E1CnfgEntry 26 }

prtT1E1ConnectedTS OBJECT-TYPE
      SYNTAX  INTEGER 
       {
        notApplicable	(1), 
        no				(2),
        yes				(3)
       }
        MAX-ACCESS  read-only
        STATUS  current
        DESCRIPTION
      "This parameter indicates if there is any connected TS for this interface."
   ::= { prtT1E1CnfgEntry 27 }

prtT1E1Ts0SaBit OBJECT-TYPE
      SYNTAX  INTEGER 
       {
        notApplicable	(1), 
        noMng	(2),
        mng		(3)
       }
        MAX-ACCESS  read-write
        STATUS  current
        DESCRIPTION
      "This parameter indicates whether to send TS 0, or not.
       noMng= TS 0 is looped, therefore not sent.
       mng= TS 0 isn't looped, therefore it is sent."
   ::= { prtT1E1CnfgEntry 28 }
	   
prtT1E1SameFeCnfg OBJECT-TYPE
      SYNTAX  INTEGER 
       {
        notApplicable	(1), 
        no              (2),
        yes             (3)
       }
      MAX-ACCESS  read-write
      STATUS  current
      DESCRIPTION
      "This parameter indicates whether the same E1 configuration 
       parameters and TS assignment are set both to the local
       and remote device.
       Read-Write access is applicable only in G732N framed mode.
       For G732S and UNFRAMED this parameter is set by 
       agent to YES and is Read Only.
       In Case of conflict during power-up between the central 
       and remote, the value set by the central unit is the valid one."
      ::= { prtT1E1CnfgEntry 29 }

prtT1E1RemCrc4 OBJECT-TYPE
      SYNTAX  INTEGER 
       {
        notApplicable	(1), 
        no              (2),
        yes             (3)
       }
      MAX-ACCESS  read-write
      STATUS  current
      DESCRIPTION
      "This object indicates whether the E1 of the Remote device
       connected to this E1 port, will have CRC-4 or not."
      ::= { prtT1E1CnfgEntry 30 }

prtT1E1MaxTSs OBJECT-TYPE
      SYNTAX  Integer32 
      MAX-ACCESS  read-write
      STATUS  current
      DESCRIPTION
      "This object is applicable only for DXC D4T1, D4E1, D8T1, D8E1 
       external ports and D8GSL internal E1 ports.
	   It is relevant only when sysCIntTsAllocMode=static(2).
       255=not applicable
       If prtT1E1LineType=unframed(8), the value of this object must be 32.
       Else, the valid values are 0..31."
      ::= { prtT1E1CnfgEntry 31}

prtT1E1EocTsConfig OBJECT-TYPE
      SYNTAX  INTEGER 
       {
        notApplicable (1), 
        disabled      (2),
        enabled       (3)
       }
      MAX-ACCESS  read-write
      STATUS  current
      DESCRIPTION
      "This object indicates whether the use of EOC for TS Configuration
       is enabled or not."
      ::= { prtT1E1CnfgEntry 32 }

prtT1E1Role OBJECT-TYPE
      SYNTAX  INTEGER 
       {
        notApplicable 	(1), 
        sub      		(2),
        main       		(3)
       }
      MAX-ACCESS  read-write
      STATUS  current
      DESCRIPTION
      "This object indicates whether this port behaves as SUB or Main link."
      ::= { prtT1E1CnfgEntry 33 }

prtT1E1PppEchoFailDetection OBJECT-TYPE
      SYNTAX  INTEGER 
       {
        notApplicable	(1), 
        disable         (2),
        enable          (3)
       }
      MAX-ACCESS  read-write
      STATUS  current
      DESCRIPTION
      "This object indicates whether the PPP Echo is taken into account
       for its Fail Detection.  
       This object is relevant when Inband Mng between devices is Dedicated TS PPP.
       Default=Disable.
	   Enable - will be selected mainly when a T1/E1 Ring exists and between 2 adjacent 
	            Ring devices there is another device or Net, that causes these Ring devices
	            not to sense that the PPP connection between them is lost. In this case,
	            Echo Request should be initiated by the port."
      ::= { prtT1E1CnfgEntry 34 }


--prtT1E1 Last FDL Message Table - Statistics

prtT1E1FdlMsgTable  OBJECT-TYPE
     SYNTAX SEQUENCE OF PrtT1E1FdlMsgEntry
     MAX-ACCESS not-accessible
     STATUS  current
     DESCRIPTION
      "This table is applicable for a T1 interface with 'esf'
       LineType or E1 interface, when CRC is enabled (LineType)."
  ::= { prtT1E1 3}

prtT1E1FdlMsgEntry OBJECT-TYPE
      SYNTAX PrtT1E1FdlMsgEntry
      MAX-ACCESS not-accessible
      STATUS current
	DESCRIPTION  "An entry in table."
	INDEX {prtT1E1FdlMsgPrtIdx, prtT1E1FdlMsgFdlType}
      ::= { prtT1E1FdlMsgTable 1}

PrtT1E1FdlMsgEntry ::=
      SEQUENCE {
      prtT1E1FdlMsgPrtIdx    Integer32,
      prtT1E1FdlMsgFdlType   INTEGER,
      prtT1E1FdlMsgSlt       INTEGER,
      prtT1E1FdlMsg          OCTET STRING   
      }

prtT1E1FdlMsgPrtIdx OBJECT-TYPE
      SYNTAX  Integer32
      MAX-ACCESS  read-only
      STATUS  current
      DESCRIPTION
      "This attribute indicates a unique  port number.
    The same numbering as for prtGenPrtIdx.
       The valid port number depends on the IO slot no.,  the 
       installed card type and the port type: outside, inside. 
      * The outside ports will be the T1/E1 cards ports. 
        The convention used will be (for DXC):
      - first two digits will be: (IO slot number+10)
         - last one/two digits will be the port number within the 
           card, in odd numbers:
     port1 = 1
     port2 = 3
     port3 = 5 
     etc...
   Example: port2 of IO slot 11 will be: 213 ."
      ::= { prtT1E1FdlMsgEntry 1}

prtT1E1FdlMsgFdlType OBJECT-TYPE
      SYNTAX  INTEGER
       {
          send    (1),
    receive (2)
    }
      MAX-ACCESS  read-only
      STATUS  current
      DESCRIPTION
   "The Fdl type reference of the Fdl message."
      ::= { prtT1E1FdlMsgEntry 2}

prtT1E1FdlMsgSlt    OBJECT-TYPE
      SYNTAX  INTEGER
       {
       io1   (5),
       io2   (6),
       io3   (7),
       io4   (8),
       io5   (9),
       io6  (10),
       io7  (11),
       io8  (12),
       io9  (13),
       io10 (14),
       io11 (15),
       io12 (16),
       io13 (17),
       io14 (18),
       io15 (19),
       standAlone (255)
      }
      MAX-ACCESS  read-only
      STATUS  current
      DESCRIPTION
      "This attribute indicates a unique number to identify the slot where
       the card is inserted in.
       When the unit is stand-alone, this object is not applicable
       and 255 will be used."
      ::= { prtT1E1FdlMsgEntry 3}

prtT1E1FdlMsg  OBJECT-TYPE
   SYNTAX  OCTET STRING
      MAX-ACCESS  read-only
      STATUS  current
      DESCRIPTION
      "FDL message."
      ::= { prtT1E1FdlMsgEntry 4}


--prtHS specific parameters (configuration & status) table

prtHSParamTable  OBJECT-TYPE
      SYNTAX SEQUENCE OF PrtHSParamEntry
      MAX-ACCESS not-accessible
      STATUS current
	DESCRIPTION  "A table."
	::=  { prtHS 1 }

prtHSParamEntry OBJECT-TYPE
      SYNTAX PrtHSParamEntry
      MAX-ACCESS not-accessible
      STATUS current
	DESCRIPTION  "An entry in table."
	INDEX { prtHSCnfgIdx, prtHSPrtIdx }
      ::= { prtHSParamTable 1}

PrtHSParamEntry ::=
      SEQUENCE {
      prtHSCnfgIdx               Integer32,
      prtHSPrtIdx                Integer32,
      prtHSSlt                   INTEGER,
      prtHSRate                  INTEGER,
      prtHSFifoSize              INTEGER,
      prtHSClkMode               INTEGER,
      prtHSCTS                   INTEGER,
      prtHSRtsState              INTEGER,
      prtHSInbandLoopback        INTEGER,
	  prtHSInbandLoopPatternCfg	 INTEGER,
	  prtHSInbandLoopActPattern  DisplayString,
	  prtHSInbandLoopDeactPattern DisplayString,
	  prtHSDCD		         	 INTEGER,
	  prtHSClkPolarity           INTEGER,
	  prtHSInterfaceType         INTEGER,
   	  prtHSUnframed              INTEGER  
   }    
   
prtHSCnfgIdx OBJECT-TYPE
      SYNTAX  Integer32 (1..255)
      MAX-ACCESS  read-only
      STATUS  current
      DESCRIPTION
      "This attribute indicates the Idx of the Config being accessed.
       Idx of 255 relates to the Temporary (Scratch) Config. "
      ::= { prtHSParamEntry 1}

prtHSPrtIdx OBJECT-TYPE
      SYNTAX  Integer32
      MAX-ACCESS  read-only
      STATUS  current
      DESCRIPTION
      "This attribute indicates a unique number to identify a port. 
       The valid port number depends on the IO slot no.,  the 
       installed card type and the port type: outside, inside, 
       SP.
    * The inside ports will be the HS cards ports. The 
      convention used will be (for DXC):
      - first two digits will be: (IO slot number+10)
         - last one/two digits will be the port number within the 
           card, in even numbers:
     port1 = 2
     port2 = 4
     port3 = 6 
     etc...
   Example: port2 of IO slot 11 will be: 214 ."
      ::= { prtHSParamEntry 2}

prtHSSlt      OBJECT-TYPE
      SYNTAX  INTEGER
       {
       io1   (5),
       io2   (6),
       io3   (7),
       io4   (8),
       io5   (9),
       io6  (10),
       io7  (11),
       io8  (12),
       io9  (13),
       io10 (14),
       io11 (15),
       io12 (16),
       io13 (17),
       io14 (18),
       io15 (19),
       standAlone (255)
       }
      MAX-ACCESS  read-only
      STATUS  current
      DESCRIPTION
      "This attribute indicates a unique number to identify the slot where
       the card is inserted in.
       When the unit is stand-alone, this object is not applicable
       and 255 will be used."
      ::= { prtHSParamEntry 3}

prtHSRate     OBJECT-TYPE
      SYNTAX  INTEGER {
        r0x56eq0Kbps     (1),
        r1x56eq56Kbps    (2),
        r2x56eq112Kbps   (3),
        r3x56eq168Kbps   (4),
        r4x56eq224Kbps   (5),
        r5x56eq280Kbps   (6),
        r6x56eq336Kbps   (7),
        r7x56eq392Kbps   (8),
        r8x56eq448Kbps   (9),
        r9x56eq504Kbps  (10),
        r10x56eq560Kbps (11),
        r11x56eq616Kbps (12),
        r12x56eq672Kbps (13),
        r13x56eq728Kbps (14),
        r14x56eq784Kbps (15),
        r15x56eq840Kbps (16),
        r16x56eq896Kbps (17),
        r17x56eq952Kbps (18),
        r18x56eq1008Kbps(19),
        r19x56eq1064Kbps(20),
        r20x56eq1120Kbps(21),
        r21x56eq1176Kbps(22),
        r22x56eq1232Kbps(23),
        r23x56eq1288Kbps(24),
        r24x56eq1344Kbps(25),
        r25x56eq1400Kbps(26),
        r26x56eq1456Kbps(27),
        r27x56eq1512Kbps(28),
        r28x56eq1568Kbps(29),
        r29x56eq1624Kbps(30),
        r30x56eq1680Kbps(31),
        r31x56eq1736Kbps(32),
        r0x64eq0Kbps    (33),
        r1x64eq64Kbps   (34),
        r2x64eq128Kbps  (35),
        r3x64eq192Kbps  (36),
        r4x64eq256Kbps  (37),
        r5x64eq320Kbps  (38),
        r6x64eq384Kbps  (39),
        r7x64eq448Kbps  (40),
        r8x64eq512Kbps  (41),
        r9x64eq576Kbps  (42),
        r10x64eq640Kbps (43),
        r11x64eq704Kbps (44),
        r12x64eq768Kbps (45),
        r13x64eq832Kbps (46),
        r14x64eq896Kbps (47),
        r15x64eq960Kbps (48),
        r16x64eq1024Kbps(49),
        r17x64eq1088Kbps(50),
        r18x64eq1152Kbps(51),
        r19x64eq1216Kbps(52),
        r20x64eq1280Kbps(53),
        r21x64eq1344Kbps(54),
        r22x64eq1408Kbps(55),
        r23x64eq1472Kbps(56),
        r24x64eq1536Kbps(57),
        r25x64eq1600Kbps(58),
        r26x64eq1664Kbps(59),
        r27x64eq1728Kbps(60),
        r28x64eq1792Kbps(61),
        r29x64eq1856Kbps(62),
        r30x64eq1920Kbps(63),
        r31x64eq1984Kbps(64),
        r32x64eq2048Kbps(65),

        r32x56eq1792Kbps(66),
        r64x64eq4096Kbps(67),

        auto           (200)
     }
      MAX-ACCESS  read-write
      STATUS  current
      DESCRIPTION
      "This object indicates the port rate (speed).
       auto - rate is selected automatically by system."
      ::= { prtHSParamEntry 4}

prtHSFifoSize OBJECT-TYPE
      SYNTAX  INTEGER {
   auto    (1),
   b32bit  (2),
   b60bit  (3),
   b104bit (4),
   b144bit (5),
   notApplicable (255)
   }
      MAX-ACCESS  read-write
      STATUS  current
      DESCRIPTION
   "This object selects the size of the user data channel buffer
    FIFO used in the DTE2 mode. In the other modes, buffer 
    size is automatically set by the DACS agent. 
    Buffer FIFO size in bits, corresponds to FIFO lengths of 
    +/-16, +/-30, +/-52, +/-72 bits."
      ::= { prtHSParamEntry 5}

prtHSClkMode OBJECT-TYPE
      SYNTAX  INTEGER {
   dce   (1),
   dte1  (2),
   dte2  (3),
   notApplicable (255)
   }
      MAX-ACCESS  read-write
      STATUS  current
      DESCRIPTION
   "Clock Mode of the user data channel. 
    dce - DACS operates as a DCE and provides transmit 
          and receive clocks to the synchronous user DTE.
    dte1- DACS supplies the receive clock to the user 
          equipment and accepts the user transmit clock.
    dte2- DACS requires transmit and receive clocks from 
          the user equipment."
      ::= { prtHSParamEntry 6}

prtHSCTS OBJECT-TYPE
      SYNTAX  INTEGER {
   on   (1),
   rts  (2),
   notApplicable (255)
   }
      MAX-ACCESS  read-write
      STATUS  current
      DESCRIPTION
    "Selection of CTS line state in the user data channel.
     on  - CTS continuously ON.
     rts - CTS line follows the RTS line."
      ::= { prtHSParamEntry 7}

prtHSRtsState OBJECT-TYPE
      SYNTAX  INTEGER {
   off   (2),
   on    (3),
   notApplicable (255)
   }
      MAX-ACCESS  read-only
      STATUS  current
      DESCRIPTION
      "RTS state of the port." 
      ::= { prtHSParamEntry 8}

prtHSInbandLoopback OBJECT-TYPE
      SYNTAX  INTEGER
       {
       notApplicable   (1),
       disabled        (2),
       enabled         (3)
       }
      MAX-ACCESS  read-write
      STATUS  current
      DESCRIPTION
      "This object indicates if Inband Loopback from the Network
       should be enabled or disabled."
      ::= {prtHSParamEntry 9}

prtHSInbandLoopPatternCfg OBJECT-TYPE
      SYNTAX  INTEGER
       {
       notApplicable   (1),
       rdlLoop         (2),
       userConfig      (3)
       }
      MAX-ACCESS  read-write
      STATUS  current
      DESCRIPTION
      "This object indicates if Inband Loop polynomial pattern
       will be according to RDL Loop (the standard) or User Configurated
       according to prtHSActivatePolyPattern and prtHSDeactivatePolyPattern."
      ::= {prtHSParamEntry 10}

prtHSInbandLoopActPattern OBJECT-TYPE
      SYNTAX DisplayString
      MAX-ACCESS read-write
      STATUS current
      DESCRIPTION
      "This object is a binary string of up to 8 bits.
	   Though the syntax allows for any ASCII characters, for this object
	   only '0' or '1' characters are valid.
       The string determines coefficients of the polynomial pattern
       sent to the port in order to Activate the Inband Loop.
       This object is relevant only when prtHSInbandLoopPatternCfg=userConfig."
      ::= {prtHSParamEntry 11}

prtHSInbandLoopDeactPattern OBJECT-TYPE
      SYNTAX DisplayString
      MAX-ACCESS read-write
      STATUS current
      DESCRIPTION
      "This object is a binary string of up to 8 bits.
	   Though the syntax allows for any ASCII characters, for this object
	   only '0' or '1' characters are valid.
       The string determines coefficients of the polynomial pattern
       sent to the port in order to Deactivate the Inband Loop.
       This object is relevant only when prtHSInbandLoopPatternCfg=userConfig."
      ::= {prtHSParamEntry 12}

prtHSDCD OBJECT-TYPE
      SYNTAX  INTEGER {
      notApplicable (1),
      linkOK  (2),
      on   (3)
      }
      MAX-ACCESS  read-write
      STATUS  current
      DESCRIPTION
      "Selection of DCD line state in the user data channel.
       linkOK - DCD line is ON only when active link is OK.
       on  - DCD continuously ON."
      ::= { prtHSParamEntry 13}

prtHSClkPolarity OBJECT-TYPE
      SYNTAX  INTEGER
       {
       notApplicable   (1),
       normal          (2),
       invert          (3)
       }
      MAX-ACCESS  read-write
      STATUS  current
      DESCRIPTION
      "This object indicates the clock polarity."
      ::= {prtHSParamEntry 14}

prtHSInterfaceType OBJECT-TYPE
      SYNTAX  INTEGER
       {
       notApplicable (1),
       rs530         (2), --EIA 530
       v35           (3),
	   rs422         (4),
	   x21           (5),
	   v24           (6),
	   rs530a        (7), --EIA 530A 
	   rs232		 (8),
	   rs449		 (9)
       }
      MAX-ACCESS  read-write
      STATUS  current
      DESCRIPTION
      "This object indicates the selected electrical interface type."
      ::= {prtHSParamEntry 15}

prtHSUnframed OBJECT-TYPE
      SYNTAX  INTEGER {
      notApplicable (1),
      no  (2),
      yes (3)
      }
      MAX-ACCESS  read-write
      STATUS  current
      DESCRIPTION
      "Unframed line for HS ports.
       yes - means that all TSs must be transferred, including TS0.
             In this case, prtHSRate must be r31x56eq1736Kbps OR 
             r31x64eq1984Kbps."
      ::= { prtHSParamEntry 16}



prtHSBertTable  OBJECT-TYPE
      SYNTAX SEQUENCE OF PrtHSBertEntry
      MAX-ACCESS not-accessible
      STATUS current
	DESCRIPTION  "A table."
	::=  { prtHS 2 }

prtHSBertEntry OBJECT-TYPE
      SYNTAX PrtHSBertEntry
      MAX-ACCESS not-accessible
      STATUS current
	DESCRIPTION  "An entry in table."
	INDEX { prtHSBertPrtIdx }
      ::= { prtHSBertTable 1}

PrtHSBertEntry ::=
     SEQUENCE {
  prtHSBertPrtIdx        Integer32,
  prtHSBertSlt           INTEGER,
  prtHSBertCountClr      INTEGER,
  prtHSBertTestResult    Integer32 
	}

prtHSBertPrtIdx OBJECT-TYPE
      SYNTAX  Integer32
      MAX-ACCESS  read-only
      STATUS  current
      DESCRIPTION
      "This attribute indicates a unique number to identify a port. 
       The valid port number depends on the IO slot no.,  the 
       installed card type and the port type: outside, inside, 
       SP.
    * The inside ports will be the HS cards ports. The 
      convention used will be (for DXC):
      - first two digits will be: (IO slot number+10)
         - last one/two digits will be the port number within the 
           card, in even numbers:
     port1 = 2
     port2 = 4
     port3 = 6 
     etc...
   Example: port2 of IO slot 11 will be: 214 ."
      ::= { prtHSBertEntry 1}

prtHSBertSlt  OBJECT-TYPE
      SYNTAX  INTEGER
       {
       io1   (5),
       io2   (6),
       io3   (7),
       io4   (8),
       io5   (9),
       io6  (10),
       io7  (11),
       io8  (12),
       io9  (13),
       io10 (14),
       io11 (15),
       io12 (16),
       io13 (17),
       io14 (18),
       io15 (19),
       standAlone (255)
       }
      MAX-ACCESS  read-only
      STATUS  current
      DESCRIPTION
      "This attribute indicates a unique number to identify the slot where
       the card is inserted in.
       When the unit is stand-alone, this object is not applicable
       and 255 will be used."
      ::= { prtHSBertEntry 2}


prtHSBertCountClr OBJECT-TYPE
      SYNTAX  INTEGER {
     off(2),
     on (3)
      }
      MAX-ACCESS  read-write
      STATUS  current
      DESCRIPTION
      "Setting this object (to on) initiate bert counter clear 
       operation.
       Valid only when bert test is active on the specific port.
       (Every time a new bert test starts, the counter is 
       automatically cleared; this command enables clearing 
       the counter while the test is running)."
      ::= { prtHSBertEntry 3}

prtHSBertTestResult   OBJECT-TYPE
      SYNTAX  Integer32
      MAX-ACCESS  read-only
      STATUS  current
      DESCRIPTION
      "This object indicates the number of Bit Error Rate indicated 
       during the BERT test.
       Active only when bert test is running on the selected port."
      ::= { prtHSBertEntry 4}



--prt SP specific configuration parameters

prtSpCnfgTable OBJECT-TYPE
      SYNTAX SEQUENCE OF PrtSpCnfgEntry
      MAX-ACCESS not-accessible
      STATUS current
	DESCRIPTION  "A table."
	::=  {prtSP 1}

prtSpCnfgEntry OBJECT-TYPE
      SYNTAX PrtSpCnfgEntry
      MAX-ACCESS not-accessible
      STATUS current
      DESCRIPTION
      "All the entries at this table are identical(have the same value)
       at all the configurations(1..255) except at the TmpCnfg.
       - For products supporting more than one configuration, the write operation 
         into the Table Objects is valid only at the TmpCnfg entry.
       - For products that do not support configurations, the write operation 
         into the Table Objects will be to prtSpCnfgIdx=1."
      INDEX {prtSpCnfgIdx, prtSpPrtIdx }
      ::= { prtSpCnfgTable 1}

PrtSpCnfgEntry ::=
      SEQUENCE {
   prtSpCnfgIdx     Integer32,
   prtSpPrtIdx      Integer32,
   prtSpUsage       INTEGER,
   prtSpRate        INTEGER,
   prtSpDataBits    INTEGER,
   prtSpParity      INTEGER,
   prtSpCallOutMode INTEGER,
   prtSpInterface   INTEGER,
   prtSpCTS         INTEGER,
   prtSpDcdDelay    INTEGER,
   prtSpDsr         INTEGER,
   prtSpNoOfRetries Integer32,
   prtSpWaitForConnect INTEGER,
   prtSpDialMode    INTEGER,
   prtSpAltNumMode  INTEGER,
   prtSpPrimaryNum  DisplayString,
   prtSpAltNum      DisplayString,
   prtSpRoutProtocol INTEGER,
   prtSpCmd          OCTET STRING,
   prtSpActCallOut   INTEGER,
   prtSpAlrRelayMode INTEGER,
   prtSpStopBits     INTEGER
      }      
       

prtSpCnfgIdx OBJECT-TYPE
      SYNTAX  Integer32 (1..255)
      MAX-ACCESS  read-only
      STATUS  current
      DESCRIPTION
      "This attribute indicates the Idx of the Cnfg(1..255) being 
       accessed.
       Idx of 255 relates to the TmpCnfg."
      ::= { prtSpCnfgEntry 1}

prtSpPrtIdx OBJECT-TYPE
      SYNTAX  Integer32
      MAX-ACCESS  read-only
      STATUS  current
      DESCRIPTION
      "This attribute indicates a unique port number of the SPor DP port.
       For DXC, it is the port in the active DCL card: 
       - SP = 1
       - NP ; DP = 2 
                
       For Kilomux, the port index is calculated as follows:
       100*Slot+Ch.
       
       For FCD, PRBi,  the SP port index=1.
       For Optimux-T3, the SP port index=71."
      ::= { prtSpCnfgEntry 2}

prtSpUsage OBJECT-TYPE
      SYNTAX  INTEGER
       {
  unknown (1),
  noUse   (2),
  nmsSlip (3),
  nmsPpp  (4),
  muxSlip (5),
  muxPpp  (6),
  terminal(7),
  dialOut (8)
       }
      MAX-ACCESS  read-write
      STATUS  current
      DESCRIPTION
      "This attribute indicates what is the usage of the port."
      ::= { prtSpCnfgEntry 3}

prtSpRate     OBJECT-TYPE
      SYNTAX  INTEGER
       {
        auto      (1),
        s300bps   (2),
        s1200bps  (3),
        s2400bps  (4),
        s4800bps  (5),
        s9600bps  (6),
        s19200bps (7),
        s38400bps (8),
        s57600bps (9),
		s115200bps(10)
       }
      MAX-ACCESS  read-write
      STATUS  current
      DESCRIPTION
      "This attribute indicates the operation rate (speed) of the port.
       auto - automatic rate selection, by the agent."
      ::= { prtSpCnfgEntry 4}

prtSpDataBits OBJECT-TYPE
      SYNTAX  INTEGER
       {
        dataBits7 (1),
        dataBits8 (2)
       }
      MAX-ACCESS  read-write
      STATUS  current
      DESCRIPTION
      "This attribute indicates the number of data bits in async 
       frame"
      ::= { prtSpCnfgEntry 5}

prtSpParity OBJECT-TYPE
      SYNTAX  INTEGER
       {
        none  (1),
        odd   (2),
        even  (3)
       }
      MAX-ACCESS  read-write
      STATUS  current
      DESCRIPTION
      "This attribute indicates the parity mode in async frame"
      ::= { prtSpCnfgEntry 6}

prtSpCallOutMode OBJECT-TYPE
      SYNTAX  INTEGER
       {
        notApplicable  (1),
        none           (2),
        all            (3),
        major          (4)
       }
      MAX-ACCESS  read-write
      STATUS  current
      DESCRIPTION
      "This attribute indicates the call-out mode.
       For DXC - this object is applicable only for the DP port (2)."
      ::= { prtSpCnfgEntry 7}


prtSpInterface OBJECT-TYPE
      SYNTAX  INTEGER
       {
          dce  (1),
          dte  (2)
       }
      MAX-ACCESS  read-write
      STATUS  current
      DESCRIPTION
      "This attribute indicates the supervisory port interface.
       dce - the DACS appears as a DCE for the port.
       dte - the DACS operates as a DTE, for connection via modem,
             for the port."
      ::= { prtSpCnfgEntry 8}

prtSpCTS OBJECT-TYPE
      SYNTAX  INTEGER
       {
          notApplicable (1),
          on            (2),
          rts           (3)
       }
      MAX-ACCESS  read-write
      STATUS  current
      DESCRIPTION
   "CTS line state. This object is applicable only for 
    port (1) = SP"
      ::= { prtSpCnfgEntry 9}

prtSpDcdDelay OBJECT-TYPE
      SYNTAX  INTEGER
       {
          notApplicable (1),
          d0   (2),
          d10  (3),
          d50  (4),
          d100 (5),
          d200 (6),
          d300 (7)
       }
      MAX-ACCESS  read-write
      STATUS  current
      DESCRIPTION
   "DCD delay in msec. 
    d10 = delay of 10msec.
    This object is applicable only for  port (1) = SP"
      ::= { prtSpCnfgEntry 10}

prtSpDsr OBJECT-TYPE
      SYNTAX  INTEGER
       {
          notApplicable (1),
          on   (2),
          dtr  (3)
       }
      MAX-ACCESS  read-write
      STATUS  current
      DESCRIPTION
   "DSR line state. This object is applicable only for 
    port (1) = SP"
      ::= { prtSpCnfgEntry 11}

prtSpNoOfRetries OBJECT-TYPE
      SYNTAX  Integer32  (0..8)
      MAX-ACCESS  read-write
      STATUS  current
      DESCRIPTION
   "For DXC - this object is applicable only for port (2) = DP.
    The number of dialing retries requested.
    Default = 0"
      ::= { prtSpCnfgEntry 12}

prtSpWaitForConnect OBJECT-TYPE
      SYNTAX  INTEGER
       {
          notApplicable (1),
          t30sec        (2),
          t45sec        (3), 
          t60sec        (4)
       }
      MAX-ACCESS  read-write
      STATUS  current
      DESCRIPTION
   "For DXC - this object is applicable only for port (2) = DP.
    Waiting time for connect, in seconds.
    Default = 30 sec."
      ::= { prtSpCnfgEntry 13}

prtSpDialMode OBJECT-TYPE
      SYNTAX  INTEGER
       {
          notApplicable (1),
          tone          (2),
          pulse         (3)
    }
      MAX-ACCESS  read-write
      STATUS  current
      DESCRIPTION
   "For DXC - this object is applicable only for port (2) = DP.
    Dialing mode.
    Default=tone"
      ::= { prtSpCnfgEntry 14}

prtSpAltNumMode OBJECT-TYPE
      SYNTAX  INTEGER
       {
          no  (2),
          yes (3)
       }
      MAX-ACCESS  read-write
      STATUS  current
      DESCRIPTION
   "For DXC - this object is applicable only for port (2) = DP.
    It determines wether to use the alternate number or not.
    Default = no."
      ::= { prtSpCnfgEntry 15}

prtSpPrimaryNum OBJECT-TYPE
      SYNTAX  DisplayString (SIZE(0..20))
      MAX-ACCESS  read-write
      STATUS  current
      DESCRIPTION
   "For DXC - this object is applicable only for port (2) = DP.
    It is the Primary dialing number. "
      ::= { prtSpCnfgEntry 16}

prtSpAltNum OBJECT-TYPE
      SYNTAX  DisplayString (SIZE(0..20))
      MAX-ACCESS  read-write
      STATUS  current
      DESCRIPTION
   "For DXC - this object is applicable only for port (2) = DP.
    It is the Alternate dialing number. This number 
    is applicable only if prtSpAltNumMode is 'yes'."
      ::= { prtSpCnfgEntry 17}

prtSpRoutProtocol     OBJECT-TYPE
      SYNTAX  INTEGER
       {
        notApplicable (1),
        none          (2),
        proprietary   (3),
        rip2          (4)
       }
      MAX-ACCESS  read-write
      STATUS  current
      DESCRIPTION
      "This attribute indicates the routing protocol of the port.
       notApplicable - for DP."
      ::= { prtSpCnfgEntry 18}

prtSpCmd     OBJECT-TYPE
      SYNTAX OCTET STRING  (SIZE (20))
      MAX-ACCESS  read-write
      STATUS  current
      DESCRIPTION
      "SP Command.
      For LRS this parameter will be used for a Modem Command. 
      Upon NMS's Get operation for devices that this parameter 
      is notApplicable, agent will send NULL string."
      ::= { prtSpCnfgEntry 19}

prtSpActCallOut     OBJECT-TYPE
      SYNTAX  INTEGER
       {
        notApplicable (1),
        always        (2),
        linkFail      (3)
       }
      MAX-ACCESS  read-write
      STATUS  current
      DESCRIPTION
      "This object indicates when to Activate Call-Out.
	   It is used by FCD-T1/E1.
       always - to activate call-out always.
       linkFail - to activate call-out only when Link of Inband Management fails."
      ::= { prtSpCnfgEntry 20}


prtSpAlrRelayMode OBJECT-TYPE
      SYNTAX  INTEGER
       {
  	    notApplicable (1),	
  		normal        (2),
        invert        (3)
       }
      MAX-ACCESS  read-write
      STATUS  current
      DESCRIPTION
      "This attribute indicates the Alarm Relay Mode.
       notApplicable - for DP."
      ::= { prtSpCnfgEntry 21}


prtSpStopBits OBJECT-TYPE
      SYNTAX  INTEGER
	      {
		notApplicable  (1),
        stopBits1      (2),
        stopBits1dot5  (3),
        stopBits2      (4)
	      }
      MAX-ACCESS  read-write
      STATUS  current
      DESCRIPTION
      "This attribute indicates number of stop bits in an async frame."
      ::= { prtSpCnfgEntry 22}





--prt DIM (DXC Inverse Multiplexer) specific parameters

prtDimCnfgTable OBJECT-TYPE
      SYNTAX SEQUENCE OF PrtDimCnfgEntry
      MAX-ACCESS not-accessible
      STATUS current
	DESCRIPTION  "A table."
	::=  {prtDim 1}

prtDimCnfgEntry OBJECT-TYPE
      SYNTAX PrtDimCnfgEntry
      MAX-ACCESS not-accessible
      STATUS current
      DESCRIPTION
      "The write operation into the Table Objects is valid only
       for the TmpCnfg entry (prtDimCnfgIdx=255)."
      INDEX {prtDimCnfgIdx, prtDimIdx }
      ::= { prtDimCnfgTable 1}

PrtDimCnfgEntry ::=
      SEQUENCE {
   prtDimCnfgIdx  Integer32,
   prtDimIdx      Integer32,
   prtDimTxMode   INTEGER,
   prtDimPolarity INTEGER,
   prtDimClkMode  INTEGER,
   prtDimMaxDelay INTEGER,
   prtDimMng      INTEGER,
   prtDimMngRoutProt INTEGER
   }      
       

prtDimCnfgIdx OBJECT-TYPE
      SYNTAX  Integer32 (1..255)
      MAX-ACCESS  read-only
      STATUS  current
      DESCRIPTION
      "This attribute indicates the Idx of the Cnfg(1..255) being 
       accessed.
       Idx of 255 relates to the TmpCnfg."
      ::= { prtDimCnfgEntry 1}

prtDimIdx OBJECT-TYPE
      SYNTAX  Integer32
      MAX-ACCESS  read-only
      STATUS  current
      DESCRIPTION
      "This attribute indicates a unique  port number of the
       DIM card. 
       The convention used for DXC:
       (IO slot number+10)*10 + 1
       Example: port1 of IO slot 11 will be: 211 ."
      ::= { prtDimCnfgEntry 2}


prtDimTxMode OBJECT-TYPE
      SYNTAX  INTEGER
       {
       regularTx   (2),
       broadcast   (3)
       }
      MAX-ACCESS  read-write
      STATUS  current
      DESCRIPTION
      "Tx mode.
       regularTx - the links are connected to a similar outfit on 
                   the other side. In this mode, if a link fails, 
                   the transmitted bandwidth is decreased 
                   accordingly.
       broadcast - the links are connected to MORE than one similar
                   outfit on the other side. In this mode, if a link 
                   fails, the transmitted bandwidth is not affected "
      ::= { prtDimCnfgEntry 3}

prtDimPolarity OBJECT-TYPE
      SYNTAX  INTEGER
       {
       normalClk (2),
       inverted  (3)
       }
      MAX-ACCESS  read-write
      STATUS  current
      DESCRIPTION
      "Polarity."
      ::= { prtDimCnfgEntry 4}

prtDimClkMode OBJECT-TYPE
      SYNTAX  INTEGER
       {
       extDce   (2),
       dce      (3),
	   smooth   (4),
	   extSmooth(5)
       }
      MAX-ACCESS  read-write
      STATUS  current
      DESCRIPTION
      "Clock Mode.
       smooth - a clock that is not 'pulsed'(has no 'gaps'). In this mode
	            the DXC does NOT receive back the clock signal.
       extSmooth - same as 'smooth' but in this mode, the DXC receives back
                the clock signal."
      ::= { prtDimCnfgEntry 5}

prtDimMaxDelay OBJECT-TYPE
      SYNTAX  INTEGER
       {
       t16msec (2),
       t64msec (3)
       }
      MAX-ACCESS  read-write
      STATUS  current
      DESCRIPTION
      "Max Delay permitted between the links, in msec."
      ::= { prtDimCnfgEntry 6}

prtDimMng OBJECT-TYPE
      SYNTAX  INTEGER
       {
       disabled   (2), --none
       ts1        (3), --dedicated
	   dedicatedFr(4) 
       }
      MAX-ACCESS  read-write
      STATUS  current
      DESCRIPTION
      "Use of DIM port for management.
       disabled - no management on DIM
       ts1      - 1 bit of TS1 is used for management."
      ::= { prtDimCnfgEntry 7}

prtDimMngRoutProt  OBJECT-TYPE
      SYNTAX  INTEGER
       {
       notApplicable (1),
       none          (2),  
       proprietary   (3)
       }
      MAX-ACCESS  read-write
      STATUS  current
      DESCRIPTION
      "Mng Routing Protocol of the port.
       none - when prtDimMng is 'disabled'."             
      ::= { prtDimCnfgEntry 8}


prtDimDestTable OBJECT-TYPE
      SYNTAX SEQUENCE OF PrtDimDestEntry
      MAX-ACCESS not-accessible
      STATUS current
	DESCRIPTION  "A table."
	::=  {prtDim 2}

prtDimDestEntry OBJECT-TYPE
      SYNTAX PrtDimDestEntry
      MAX-ACCESS not-accessible
      STATUS current
      DESCRIPTION
      "The write operation is valid only for the TmpCnfg entry 
       (prtDimDestCnfgIdx=255)."
      INDEX {prtDestCnfgIdx, prtDestDimIdx, prtDestIdx }
      ::= { prtDimDestTable 1}

PrtDimDestEntry ::=
      SEQUENCE {
   prtDestCnfgIdx Integer32,
   prtDestDimIdx  Integer32,
   prtDestIdx     Integer32,
   prtDest        Integer32,
   prtDestConnect INTEGER
   }      
       

prtDestCnfgIdx OBJECT-TYPE
      SYNTAX  Integer32 (1..255)
      MAX-ACCESS  read-only
      STATUS  current
      DESCRIPTION
      "This attribute indicates the Idx of the Cnfg(1..255) being 
       accessed.
       Idx of 255 relates to the TmpCnfg."
      ::= { prtDimDestEntry 1}

prtDestDimIdx OBJECT-TYPE
      SYNTAX  Integer32
      MAX-ACCESS  read-only
      STATUS  current
      DESCRIPTION
      "This attribute indicates a unique  port number of the
       DIM card. 
       The convention used for DXC:
       (IO slot number+10) & 1
       Example: port1 of IO slot 11 will be: 211 ."
      ::= { prtDimDestEntry 2}

prtDestIdx OBJECT-TYPE
      SYNTAX  Integer32 (1..8)
      MAX-ACCESS  read-only
      STATUS  current
      DESCRIPTION
      "This attribute indicates a destination number of the
       DIM card. "
      ::= { prtDimDestEntry 3}


prtDest OBJECT-TYPE
      SYNTAX  Integer32
      MAX-ACCESS  read-write
      STATUS  current
      DESCRIPTION
      "Destination port,(of a T1/E1 port), that is connected to the 
    DIM card, for the specified Destination number.
    0 = No destination port.
    Else:
	For external ports:
    (IO Slot+10) & 1    for port 1 
    (IO Slot+10) & 3    for port 2 
       Example: port2 of IO slot 12 will be: 223 .
    For internal ports :
    (IO Slot+10) & 2    for port 1
    (IO Slot+10) & 4    for port 2
    (IO Slot+10) & 6    for port 3
    (IO Slot+10) & 8    for port 4, etc..."
      ::= { prtDimDestEntry 4}

prtDestConnect OBJECT-TYPE
      SYNTAX  INTEGER
       {
       no (2),
       yes(3)
       }
      MAX-ACCESS  read-only
      STATUS  current
      DESCRIPTION
      "Connection Status of the specified destination number.
    For a specified destination port, it depends both on the 
    status of the port and on the status of the far-end port.
    Since this is a RO object, same value will be received for
    all configurations."
      ::= { prtDimDestEntry 5}


--prtI - ISDN specific parameters table

prtICnfgTable  OBJECT-TYPE
      SYNTAX SEQUENCE OF PrtICnfgEntry
      MAX-ACCESS not-accessible
      STATUS current
	DESCRIPTION  "A table."
	::=  { prtI 1 }

prtICnfgEntry OBJECT-TYPE
      SYNTAX PrtICnfgEntry
      MAX-ACCESS not-accessible
      STATUS current
	DESCRIPTION  "An entry in table."
	INDEX { prtICnfgIdx, prtIIdx }
      ::= { prtICnfgTable 1}

PrtICnfgEntry ::=
      SEQUENCE {
      prtICnfgIdx  Integer32,
      prtIIdx      Integer32,
      prtIRate     INTEGER,
      prtIConnect  INTEGER
      }    

   
prtICnfgIdx OBJECT-TYPE
      SYNTAX  Integer32 (1..255)
      MAX-ACCESS  read-only
      STATUS  current
      DESCRIPTION
      "This attribute indicates the Idx of the Config being accessed.
       Idx of 255 relates to the Temporary (Scratch) Config. "
      ::= {prtICnfgEntry 1}

prtIIdx OBJECT-TYPE
      SYNTAX  Integer32
      MAX-ACCESS  read-only
      STATUS  current
      DESCRIPTION
      "This attribute indicates a unique number to identify a port. 
       The valid port number depends on the IO slot no.,  the 
       installed card type and the port type: outside, inside, 
       SP.
    * The ISDN B1, B2, D channels will be inside ports. 
      For port index, see product specification."
      ::= {prtICnfgEntry 2}

prtIRate     OBJECT-TYPE
      SYNTAX  INTEGER {
        notApplicable (1),
        nc            (2),
        r2bit         (3),
        r4bit         (4),
        r8bit         (5)
        }
      MAX-ACCESS  read-write
      STATUS  current
      DESCRIPTION
      "This object indicates the port rate in bits.
       Each TS contains 8 bits. Thus, 1 bit is equivalent to 8Kbps
       rate."
      ::= {prtICnfgEntry 3}

prtIConnect     OBJECT-TYPE
      SYNTAX  INTEGER {
        notApplicable (1),
        no            (2),
        yes           (3)
        }
      MAX-ACCESS  read-write
      STATUS  current
      DESCRIPTION
      "D channel connection.
       no  - disconnected
       yes - connected. "
      ::= {prtICnfgEntry 4}


--prtHdsl - HDSL specific parameters table

prtHdslTable  OBJECT-TYPE
      SYNTAX SEQUENCE OF PrtHdslEntry
      MAX-ACCESS not-accessible
      STATUS current
	  DESCRIPTION  "HDSL port table."
	::=  { prtHdsl 1 }

prtHdslEntry OBJECT-TYPE
      SYNTAX PrtHdslEntry
      MAX-ACCESS not-accessible
      STATUS current
	  DESCRIPTION  "An entry in table."
	  INDEX { prtHdslIdx }
      ::= { prtHdslTable 1}

PrtHdslEntry ::=
      SEQUENCE {
      prtHdslIdx       Integer32,
      prtHdslMode      INTEGER,
      prtHdslRptrType  INTEGER,
	  prtHdslMaxRate   INTEGER,
	  prtHdslLinkType  INTEGER,
	  prtHdslCompSwVer DisplayString,
	  prtHdslCompHwVer DisplayString
      }    
   
prtHdslIdx OBJECT-TYPE
      SYNTAX  Integer32
      MAX-ACCESS  read-only
      STATUS  current
      DESCRIPTION
      "This attribute indicates a unique number to identify a port. 
       The valid port number depends on the IO slot no.,  the 
       installed card type and the port type: outside, inside.
    * The HDSL ports will be external. 
      For port index, see product specification."
      ::= {prtHdslEntry 1}

prtHdslMode   OBJECT-TYPE
      SYNTAX  INTEGER {
        notApplicable (1),
        central       (2),
        remote        (3)
        }
      MAX-ACCESS  read-write
      STATUS  current
      DESCRIPTION
      "This object indicates the HDSL mode."
      ::= {prtHdslEntry 2}

prtHdslRptrType     OBJECT-TYPE
      SYNTAX  INTEGER {
      notApplicable (1),
      none    (2), 
      hrpt    (3)
        }
      MAX-ACCESS  read-only
      STATUS  current
      DESCRIPTION
      "The Repeater between Near and Far modem.
       none - no repeater exists between the modems
       hrpt - HRPT repeater exists between the modems."
      ::= {prtHdslEntry 3}

prtHdslMaxRate     OBJECT-TYPE
      SYNTAX  INTEGER {
      notApplicable (1),
      r192          (2), 
      r256          (3),
	  r320          (4),
	  r384          (5),
      r448          (6), 
      r512          (7),
	  r576          (8),
	  r640          (9),
      r768          (10), 
      r896          (11),
	  r1024         (12),
	  r1152         (13),
      r1280         (14), 
      r1536         (15),
	  r1920         (16),
	  r2048         (17)
        }
      MAX-ACCESS  read-write
      STATUS  current
      DESCRIPTION
      "Maximum Rate of the xDSL Line, in Kbps units.
       This object can be Set only for a Central unit."
      ::= {prtHdslEntry 4}

prtHdslLinkType     OBJECT-TYPE
      SYNTAX  INTEGER {
      notApplicable (1),
      msdsl2w       (2), 
      hdsl2w        (3),
	  hdsl4w        (4),
	  gDsl          (5)
        }
      MAX-ACCESS  read-only
      STATUS  current
      DESCRIPTION
      "The Link Type.
       msdsl2w - MSDSL 2 Wire
       hdsl2w  - HDSL  2 Wire
       hdsl4w  - HDSL  4 Wire
       gDsl    - G.DSL "
      ::= {prtHdslEntry 5}

prtHdslCompSwVer OBJECT-TYPE
      SYNTAX  DisplayString (SIZE (0..255))
      MAX-ACCESS  read-only
      STATUS  current
      DESCRIPTION
      "This object indicates the Software Version of the 
       component (Piggyback card) supporting this interface."
      ::= {prtHdslEntry 6}

prtHdslCompHwVer OBJECT-TYPE
      SYNTAX  DisplayString (SIZE (0..255))
      MAX-ACCESS  read-only
      STATUS  current
      DESCRIPTION
      "This object indicates the Hardware Version of the 
       component (Piggyback card) supporting this interface."
      ::= {prtHdslEntry 7}


--DACS T3/E3 port configuration parameters. Applicable also for Optimux-T3 Links.
--
--These objects were entered in this private MIB, because they do not 
--appear in RFC1407 (except prtT3E3LineLength which appears in meters) and in
--RFC-1407 MIB there is no reference to configuration number.


prtT3E3CnfgTable OBJECT-TYPE
  SYNTAX  SEQUENCE OF PrtT3E3CnfgEntry
  MAX-ACCESS  not-accessible
  STATUS  current
  DESCRIPTION
  "T3/E3 port configuration table."
  ::= { prtT3E3 1}

prtT3E3CnfgEntry   OBJECT-TYPE
  SYNTAX  PrtT3E3CnfgEntry
  MAX-ACCESS  not-accessible
  STATUS  current
  DESCRIPTION
  " An entry in the T3/E3 port configuration table."
  INDEX { prtT3E3CnfgIdx, prtT3E3PrtIdx }
  ::= { prtT3E3CnfgTable 1}

PrtT3E3CnfgEntry ::=
     SEQUENCE {
  prtT3E3CnfgIdx
  Integer32,
  prtT3E3PrtIdx
  Integer32,
  prtT3E3Slt
  INTEGER,
  prtT3E3LineLength
  INTEGER,
  prtT3E3InbandMng
  INTEGER,
  prtT3E3AisFrame
  INTEGER,
  prtT3E3TxClockSource
  INTEGER,
  prtT3E3RoutProt
  INTEGER,
  prtT3E3AisTransmit
  INTEGER
  }
 
prtT3E3CnfgIdx OBJECT-TYPE
      SYNTAX  Integer32 (1..255)
      MAX-ACCESS  read-only
      STATUS  current
      DESCRIPTION
      "This attribute indicates the Idx of the Config being accessed.
       Idx of 255 relates to the Temporary (Scratch) Config.
       For DXC, write operations can be performed only on the Temp Config.
       For products that do not support configurations, always 1 will be used."
      ::= { prtT3E3CnfgEntry 1}

prtT3E3PrtIdx OBJECT-TYPE
      SYNTAX  Integer32
      MAX-ACCESS  read-only
      STATUS  current
      DESCRIPTION
      "This attribute indicates a unique  port number.
	   For DXC:
          The same numbering as for prtGenPrtIdx.
          The valid port number depends on the IO slot no.,  the 
          installed card type and the port type: outside, inside. 
          * The external ports convention used will be (for DXC):
           - first two digits will be: (IO slot number+10)
           - last one/two digits will be the port number within the 
               card, in odd numbers:
               port1 = 1
               port2 = 3
               port3 = 5 
               etc...
               Example: port2 of IO slot 11 will be: 213 .
       For Optimux-T3:
          Link-A: 51 
          Link-B: 61 . "
      ::= { prtT3E3CnfgEntry 2}

prtT3E3Slt     OBJECT-TYPE
      SYNTAX  INTEGER
       {
       clA   (3),
       clB   (4),
       io1   (5),
       io2   (6),
       io3   (7),
       io4   (8),
       io5   (9),
       io6  (10),
       io7  (11),
       io8  (12),
       io9  (13),
       io10 (14),
       io11 (15),
       io12 (16),
       io13 (17),
       io14 (18),
       io15 (19),
       standAlone (255)
       }
      MAX-ACCESS  read-only
      STATUS  current
      DESCRIPTION
      "This attribute indicates a unique number to identify the slot where
       the card is inserted in.
       When the unit is stand-alone, this object is not applicable
       and 255 will be used."
      ::= { prtT3E3CnfgEntry 3}

prtT3E3LineLength  OBJECT-TYPE
      SYNTAX  INTEGER
       {
        notApplicable(1),
        len0p450ft   (2),
        len451p900ft (3)
       }
      MAX-ACCESS  read-write
      STATUS  current
      DESCRIPTION
      "This object is the length of the ds3 line in feet.  
       It provides information for line build out circuitry if it exists 
       and can use this object to adjust the line build out. 
       len0p450ft   = 0   - 450 feet
       len451p900ft = 451 - 900 feet."
   ::= { prtT3E3CnfgEntry 4}

prtT3E3InbandMng  OBJECT-TYPE
      SYNTAX  INTEGER
       {
          notApplicable(1),
          off          (2),
          cBit         (3), --Cbit-Tx-Rx
          cBitTxRxMng  (4),
          cBitTx       (5),
          cBitTxMng    (6),
          m13          (7),
          cdpv		   (8),
          nationalBit  (9) 
       }
      MAX-ACCESS  read-write
      STATUS  current
      DESCRIPTION
      "A unique number to identify the Frame Type over the link.
       For Optimux-T3: only values (4), (7) are supported."
      ::= {prtT3E3CnfgEntry 5}

prtT3E3AisFrame  OBJECT-TYPE
      SYNTAX  INTEGER
       {
        notApplicable(1),
        unframed     (2),
        framed       (3)
       }
      MAX-ACCESS  read-write
      STATUS  current
      DESCRIPTION
      "This object is applicable only for Optimux-T3.  
       It allows user to select whether the AIS sent will be framed or unframed."
   ::= { prtT3E3CnfgEntry 6}

prtT3E3TxClockSource  OBJECT-TYPE
      SYNTAX  INTEGER
       {
        external(1),  -- loopTiming
        internal(2),  -- localTiming
        notApplicable(255)
       }
      MAX-ACCESS  read-write
      STATUS  current
      DESCRIPTION
      "Tx Clock Source."
   ::= { prtT3E3CnfgEntry 7}

prtT3E3RoutProt  OBJECT-TYPE
      SYNTAX  INTEGER
       {
        notApplicable (1),
        none          (2),  
        proprietary   (3),
        rip2          (4)
       }
      MAX-ACCESS  read-write
      STATUS  current
      DESCRIPTION
      "Routing Protocol of the port.
       This object is applicable only for T3 ports."             
      ::= { prtT3E3CnfgEntry 8}

  prtT3E3AisTransmit  OBJECT-TYPE
      SYNTAX  INTEGER
       {
        notApplicable (1),
        disable       (2),  
        enable        (3)        
       }
      MAX-ACCESS  read-write
      STATUS  current
      DESCRIPTION
      "Indicates if AIS signal will be transmitted over the tributary E3/DS3
       upon failure."             
      ::= { prtT3E3CnfgEntry 9}


--DACS General data, unrelated to a specific level or unit type

--Compressed data table - applicable for all the MIB leafs,
--Used only by NMS station

cmprTable  OBJECT-TYPE
      SYNTAX SEQUENCE OF CmprEntry
      MAX-ACCESS not-accessible
      STATUS current
	DESCRIPTION  "A table."
	::=  { genDacsMux 1 }

cmprEntry OBJECT-TYPE
      SYNTAX CmprEntry
      MAX-ACCESS not-accessible
      STATUS current
	DESCRIPTION  "An entry in table."
	INDEX {cmprTypeIdx, cmprCnfgIdx,cmprVersion,cmprSltIdx,cmprPrtIdx}
      ::= {cmprTable  1}

CmprEntry ::=
      SEQUENCE {
  cmprTypeIdx      Integer32,
  cmprCnfgIdx      Integer32,
  cmprVersion      Integer32,
  cmprSltIdx       INTEGER,
  cmprPrtIdx       Integer32,
  cmprObj          OCTET STRING
      }

cmprTypeIdx OBJECT-TYPE
      SYNTAX  Integer32
      MAX-ACCESS  read-only
      STATUS  current
      DESCRIPTION
      "This object indicates the Type of the Compressed 
       data referred (which table, which level, etc).
       The type is a code according to a convention between
       agent and NMS."
      ::= { cmprEntry 1}

cmprCnfgIdx OBJECT-TYPE
      SYNTAX  Integer32
      MAX-ACCESS  read-only
      STATUS  current
      DESCRIPTION
      "This object indicates the configuration number the
       Compressed information relates to."
      ::= { cmprEntry 2}

cmprVersion OBJECT-TYPE
      SYNTAX  Integer32
      MAX-ACCESS  read-only
      STATUS  current
      DESCRIPTION
      "This object indicates the version of the internal format of
       the Compressed data (the version of the convention used)."
      ::= { cmprEntry 3}

cmprSltIdx  OBJECT-TYPE
     SYNTAX  INTEGER
         {
         psA   (1),
         psB   (2),
         clA   (3),
         clB   (4),
         io1   (5),
         io2   (6),
         io3   (7),
         io4   (8),
         io5   (9),
         io6  (10),
         io7  (11),
         io8  (12),
         io9  (13),
         io10 (14),
         io11 (15),
         io12 (16),
         io13 (17),
         io14 (18),
         io15 (19),
         notApplicable (255)
         }
     MAX-ACCESS  read-only
     STATUS  current
     DESCRIPTION
     "This attribute indicates a unique number of  the slot  
      position where the card is inserted.
      When the unit is stand-alone or this object is not applicable,
      255 will be used."
     ::= { cmprEntry 4}


cmprPrtIdx  OBJECT-TYPE
      SYNTAX  Integer32
      MAX-ACCESS  read-only
      STATUS  current
      DESCRIPTION
      "This object indicates a unique identifier of the port,
       the compressed information relates to.
    For DXC - according to the order in the card of cmprSltIdx:
      - first two digits will be: (IO slot number+10)
      - last one/two digits will be the port number within the 
        card in odd or even numbers, as follows:
      * For the outside/external ports, in odd numbers:
        port1 = 1
        port2 = 3
        port3 = 5 
        etc...
        Example: port2 of IO slot 11 will be: 213 .
      * The inside/internal ports, in even numbers:
        port1 = 2
        port2 = 4
        port3 = 6 
        etc...
        Example: port2 of IO slot 11 will be: 214 .
    For FCD: see product's specification.
       If the port number is irrelevant to this parameter (if it is
       a system/card level alarm) the value will be 9999."
      ::= { cmprEntry 5}

cmprObj OBJECT-TYPE
      SYNTAX  OCTET STRING
      MAX-ACCESS  read-write
      STATUS  current
      DESCRIPTION
      "This object is the compressed information itself, 
       according to a predefined format, both agent and NMS agreed
       about."
      ::= { cmprEntry 6}


--mapLinkTable

mapLinkTable OBJECT-TYPE
      SYNTAX SEQUENCE OF MapLinkEntry
      MAX-ACCESS not-accessible
      STATUS current
	DESCRIPTION  "A table."
	::=  { genDacsMux 2}

mapLinkEntry OBJECT-TYPE
      SYNTAX MapLinkEntry
      MAX-ACCESS not-accessible
      STATUS current
	DESCRIPTION  "An entry in table."
	INDEX {mapLinkIdx}
      ::= {mapLinkTable 1}

MapLinkEntry ::=
      SEQUENCE {
      mapLinkIdx               Integer32,
      mapLinkSlotIdx           INTEGER,
      mapLinkPortIdx           Integer32,
      mapLinkState             INTEGER
      }

mapLinkIdx     OBJECT-TYPE
      SYNTAX  Integer32
      MAX-ACCESS  read-only
      STATUS  current
      DESCRIPTION
      "A unique identifier of the link"
::=  {mapLinkEntry 1}

mapLinkSlotIdx    OBJECT-TYPE
      SYNTAX  INTEGER
        {
         io1   (5),
         io2   (6),
         io3   (7),
         io4   (8),
         io5   (9),
         io6  (10),
         io7  (11),
         io8  (12),
         io9  (13),
         io10 (14),
         io11 (15),
         io12 (16),
         io13 (17),
         io14 (18),
         io15 (19),
         standAlone (255)
     }
      MAX-ACCESS  read-write
      STATUS  current
      DESCRIPTION
      "This attribute indicates a unique  slot  position where
       the module is inserted."       
::=  {mapLinkEntry 2}

mapLinkPortIdx  OBJECT-TYPE
      SYNTAX  Integer32
      MAX-ACCESS  read-write
      STATUS  current
      DESCRIPTION
      "This attribute indicates a unique  port number.
       The valid port number depends on the IO slot no.,  the 
       installed card type and the port type: outside, inside, 
       SP.
       In the DXC :
      - first two digits will be: (IO slot number+10)
      - last one/two digits will be the port number within the 
        card in odd or even numbers, as follows:
      * For the outside/external ports, in odd numbers:
        port1 = 1
        port2 = 3
        port3 = 5 
        etc...
        Example: port2 of IO slot 11 will be: 213 .
      * The inside/internal ports, in even numbers:
        port1 = 2
        port2 = 4
        port3 = 6 
        etc...
        Example: port2 of IO slot 11 will be: 214 ."
::=  {mapLinkEntry 3}

mapLinkState   OBJECT-TYPE
      SYNTAX  INTEGER
 {
 unknown(1),
 down(2),
 up(3)
 }
      MAX-ACCESS  read-only
      STATUS  current
      DESCRIPTION
      "This attribute indicates the status of the link between 
       the two muxes"
::=  {mapLinkEntry 4}

 
--Alarms List - 
--              
--              

alrGenTable  OBJECT-TYPE
      SYNTAX SEQUENCE OF AlrGenEntry
      MAX-ACCESS not-accessible
      STATUS current
	DESCRIPTION  "A table."
	::=  { genDacsMux 3 }

alrGenEntry OBJECT-TYPE
      SYNTAX AlrGenEntry
      MAX-ACCESS not-accessible
      STATUS current
	DESCRIPTION  "An entry in table."
	INDEX { alrGenCode }
      ::= { alrGenTable 1}

AlrGenEntry ::=
      SEQUENCE {
     alrGenCode          Integer32,
     alrGenDescription  DisplayString,
     alrGenLevel         INTEGER,
	 alrGenSlotType      INTEGER,
	 alrGenSeverity      INTEGER,
	 alrGenDebounce      Integer32,
	 alrGenDefSeverity   INTEGER
      }

alrGenCode OBJECT-TYPE
      SYNTAX  Integer32
      MAX-ACCESS  read-only
      STATUS  current
      DESCRIPTION
      "This object is a unique code number, identifying 
       a certain alarm."
    ::= { alrGenEntry 1}

alrGenDescription  OBJECT-TYPE
      SYNTAX  DisplayString (SIZE (0..255))
      MAX-ACCESS  read-only
      STATUS  current
      DESCRIPTION
      "This entry is a unique text description, of the alarm 
       corresponding to the specified code."
       ::= { alrGenEntry 2}
       
alrGenLevel   OBJECT-TYPE
      SYNTAX  INTEGER
      {
       notApplicable(1),
       system       (2),
       card         (3),
       port         (4)
      }
      MAX-ACCESS  read-only
      STATUS  current
      DESCRIPTION
      "Alarm level."
      ::=  {alrGenEntry 3}

alrGenSlotType   OBJECT-TYPE
      SYNTAX  INTEGER
      {
       notApplicable(1),
       ps           (2),
       cl           (3),
       io           (4),
	   clAndIo      (5)
      }
      MAX-ACCESS  read-only
      STATUS  current
      DESCRIPTION
      "Slot type that the alarm is relevant to.
       clAndIo - an alarm that is relevant for both CL and IO slots."
      ::=  {alrGenEntry 4}

alrGenSeverity   OBJECT-TYPE
      SYNTAX  INTEGER
      {
       notApplicable (1),
       event    (3),
       minor    (4),
       major    (5),
       warning  (6),
       critical (7)
       }
      MAX-ACCESS  read-write
      STATUS  current
      DESCRIPTION
      "This object enables the user to select a severity for each alarm.
       The severity is set per alarm code (same for all slots/ports
       using this code)."
      ::=  {alrGenEntry 5}

alrGenDebounce   OBJECT-TYPE
      SYNTAX  Integer32 (0..255)
      MAX-ACCESS  read-write
      STATUS  current
      DESCRIPTION
      "Debounce time for each alarm code, in seconds.
       The meaning is, that an alarm will be 'declared' as ON (or OFF), only 
       after it was actually ON/OFF the Debouncing time selected by user.
       0 = default debounce selection (each alarm has a default value).
	   250 = maximum value of seconds for debounce.
	   253 = mask = the alarm will Never be reported.
	   254 = default debounce selection (each alarm has a default value).
	   255 = not applicable "
      ::=  {alrGenEntry 6}

alrGenDefSeverity OBJECT-TYPE
      SYNTAX  INTEGER
       {
      notApplicable (1),
      event    (3),
      minor    (4),
      major    (5),
	  warning  (6),
	  critical (7)
       }
      MAX-ACCESS  read-only
      STATUS  current
      DESCRIPTION
      "This object reports the default severity of each alarm.
       User can change the  severity of the alarms defined by
       this default via the alrGenSeverity object."
      ::= {alrGenEntry 7}



-- Traps

--NOTIFICATIONS

     dacsMuxEvents OBJECT-IDENTITY
	    STATUS  current
	    DESCRIPTION
	    "The events for DACS MUX."
	    ::= { dacsMux 0 }

     sanityCheckTrap  NOTIFICATION-TYPE
        OBJECTS { sysSSanityCheckStatus, sysDbaseDownloadCnfgIdxCmd }
        STATUS current
        DESCRIPTION     
        "This trap is sent after a data base download attempt. 
         It returns the sanity result status and the configuration
         no.checked."
        ::= { dacsMuxEvents 1 }

     dacsMuxAlarmsTrap  NOTIFICATION-TYPE
       STATUS current
       DESCRIPTION     
       "This trap is sent when an alarm occurs."
       ::= { dacsMuxEvents 2 }

     mdlConnectTrap  NOTIFICATION-TYPE
       OBJECTS       {mdlSCardType, mdlSActivity}
       STATUS current
       DESCRIPTION     
       "This trap is sent when a card is removed."
       ::= { dacsMuxEvents 3 }

     sysAlrStatusTrap  NOTIFICATION-TYPE
       OBJECTS       { sysSAlrStatusAll, sysSAlrStatus }
       STATUS current
       DESCRIPTION     
       "This trap is sent upon any change in the value of any of 
        the variables."
       ::= { dacsMuxEvents 4 }
 

     sysStatusChangedTrap  NOTIFICATION-TYPE
       OBJECTS       {agnLed}
       STATUS current
       DESCRIPTION     
       "This trap is sent when Leds status is changed."
       ::= { dacsMuxEvents 5 }


     cnfgUpdateTrap  NOTIFICATION-TYPE
       STATUS current
       DESCRIPTION     
       "This trap is sent upon change of the active Configuration DB."  
       ::= { dacsMuxEvents 6 }
 

	sysRedundancyStatusTrap NOTIFICATION-TYPE
		OBJECTS  { sysDclRedundancyStatus }
		STATUS  current
		DESCRIPTION
		"The trap is sent upon change in Redundancy Status."
		::= { dacsMuxEvents 7 }

	sysRedundancyActiveCardTrap NOTIFICATION-TYPE
		OBJECTS  { sysDclOnline }
		STATUS  current
		DESCRIPTION
		"The trap is sent upon change of Active Main/CL Card."
		::= { dacsMuxEvents 8 }

	sysRedundancyActivePortTrap NOTIFICATION-TYPE
		OBJECTS  { sysCRdnOnline }
		STATUS  current
		DESCRIPTION
		"The trap is sent upon change of Active Port of Redundancy Group."
		::= { dacsMuxEvents 9 }
-- 
-- file :D:\Synergy\WorkArea\545\mib_rad\txt\modem.txt
-- 
--                 MODMSYS MIB	(MODEMS)

--Title:     RAD's Modems MIB
--Version:   1.0
--Date:      24.12.95
--By:        Yair Arian	and Smadar Tauber
--File:      modem.txt
--
--Last update: 15-May-2007 by Shay Harari 
		  

modmSys  OBJECT IDENTIFIER  ::=  {radWan 4}


modmSystem  OBJECT IDENTIFIER  ::=  {modmSys 1}

modmSa	OBJECT IDENTIFIER  ::=  {modmSystem 1}
modmHub OBJECT IDENTIFIER  ::=  {modmSystem 2}

modmSaConfigTable  OBJECT-TYPE
      SYNTAX SEQUENCE OF ModmSaConfigEntry
      MAX-ACCESS not-accessible
      STATUS  current
      DESCRIPTION
      "Configuration parameters of the Central and Remote Modems.
       The table will be RW for a Central agent and RO for a 
       Remote agent."
       ::= { modmSa 1 }

modmSaConfigEntry OBJECT-TYPE
      SYNTAX ModmSaConfigEntry
      MAX-ACCESS not-accessible
      STATUS current
	DESCRIPTION  "An entry in table."
	INDEX {modmSaConfigMode}
      ::= { modmSaConfigTable 1}

ModmSaConfigEntry ::=
      SEQUENCE {
	  modmSaConfigMode             INTEGER,
	  modmSaConfigLoopback         INTEGER,
	  modmSaConfigAlrClearOnCmd    INTEGER,
	  modmSaConfigAlrClearAllCmd   INTEGER,
	  modmSaConfigTestClearCmd     INTEGER,
	  modmSaConfigClkMaster        INTEGER,
	  modmSaConfigResetStatistics  INTEGER,
	  modmSaConfigActiveTs         Integer32,
	  modmSaConfigReset            INTEGER,
	  modmSaConfigRemote           INTEGER,
	  modmSaConfigPsType	       INTEGER,
	  
	  modmSaConfigWorkMode		   INTEGER	
	  
      }

modmSaConfigMode OBJECT-TYPE
      SYNTAX INTEGER {
                central(1),
      		    remote (2),
				remote2(3),
				remote3(4),
				remote4(5),
				remote5(6),
				remote6(7),
				remote7(8),
				remote8(9),
				remote9(10),
				remote10(11)

		            }
      MAX-ACCESS read-only
      STATUS current
      DESCRIPTION
      "The mode indicates if the configuration parameters refer 
       the Central or the Remote Modem.
       For AMC 102 the remote means regenerator. 
       There can be some regenerators connecting one by the other."
      ::= { modmSaConfigEntry 1}

modmSaConfigLoopback OBJECT-TYPE
      SYNTAX INTEGER {  noLoopback(1),
      					localPortLoop(2),
      					localLineLoop(3),
      					remPortLoop(4)
      				}
      MAX-ACCESS read-write
      STATUS current
      DESCRIPTION
      "The possible loopbacks. It is not possible to have a 
       remPortLoop(4) in both, Central and Remote units 
       simultaneously."
      ::= { modmSaConfigEntry 2}

modmSaConfigAlrClearOnCmd  OBJECT-TYPE
      SYNTAX  INTEGER
	      {
		off(2),
		on (3)
	      }
      MAX-ACCESS  read-write
      STATUS  current
      DESCRIPTION
      "Setting this attribute to on, clears all the events, 
       both from the active alarms list and from the alarms buffer. 
       Upon completion, the value will automatically change to 
       off(2)."
      ::= { modmSaConfigEntry 3 }

modmSaConfigAlrClearAllCmd  OBJECT-TYPE
      SYNTAX  INTEGER
	      {
		off(2),
		on (3)
	      }
      MAX-ACCESS  read-write
      STATUS  current
      DESCRIPTION
      "Setting this attribute to on, clears all the alarms of the
       alarm buffer and active alarms list. Upon completion, the 
       value will automatically change to off(2)."
      ::= { modmSaConfigEntry 4 }

modmSaConfigTestClearCmd  OBJECT-TYPE
      SYNTAX  INTEGER
	      {
		off(2),
		on (3)
	      }
      MAX-ACCESS  read-write
      STATUS  current
      DESCRIPTION
      "Setting this attribute to on, clears all the user-initiated
       tests and loopbacks. The variable modmSaConfigLoopback should
       automatically change to noLoopback. Upon completion, the 
       value will automatically change to off(2)."
      ::= { modmSaConfigEntry 5 }

modmSaConfigClkMaster  OBJECT-TYPE
      SYNTAX  INTEGER
	      {
		external(2),
		internal(3),
		station (4)
	      }
      MAX-ACCESS  read-write
      STATUS  current
      DESCRIPTION
      "Modem configured as Central: 
       External - Locked to the clock signal provided by the user's
                  equipment by user's port.       
       Internal - Internal oscillator.
	   Station  - Station clock (is relevant only for cards).
       Modem configured as Remote: 
       External - Always locked to the recovered receive clock of 
       the HDSL line."
      ::= { modmSaConfigEntry 6 }

modmSaConfigResetStatistics  OBJECT-TYPE
      SYNTAX  INTEGER
	      {
	    off(2),
		on (3),
		notApplicable (255)
	      }
      MAX-ACCESS  read-write
      STATUS  current
      DESCRIPTION
      "In the on state all statistics counters (including E1 
       counters) are zeroed.  Upon completion, the value will 
       automatically change to off(2).
       Modems that do not support statistics - the value will 
       always be off (this object is not applicable for them).
       notApplicable - for modems with no statistics support."
      ::= { modmSaConfigEntry 7 }

modmSaConfigActiveTs  OBJECT-TYPE
      SYNTAX  Integer32 (1..255)
      MAX-ACCESS  read-write
      STATUS  current
      DESCRIPTION
      "This object will be RO for the Remote modem.
       This is the number of active HDSL Time Slots, that 
       determines user's data rate.
       Valid values: 1..maximum supported by the specific modem.
       255 = notApplicable."
      ::= { modmSaConfigEntry 8 }

modmSaConfigReset  OBJECT-TYPE
      SYNTAX  INTEGER
	      {
	    off         (2),
		hw          (3),
		hwAndConfig (4),
		notApplicable (255)
	      }
      MAX-ACCESS  read-write
      STATUS  current
      DESCRIPTION
      "Reset of modem.
	   hw - HW Reset. The configured values will not change.
	   hwAndConfig - HW Reset and initializing the default values.
       notApplicable - for modems with no Reset support.
       After 'hw' or 'hwAndConfig' is Set, agent will turn the 
       value to 'off'."
      ::= { modmSaConfigEntry 9 }

modmSaConfigRemote  OBJECT-TYPE
      SYNTAX  INTEGER
	      {
           notApplicable (1),
		   off           (2),
		   on            (3)
	      }
      MAX-ACCESS  read-write
      STATUS  current
      DESCRIPTION
      "This parameter enables or disables automatic configuration
       of the remote moden in Proxy mode."
      ::= { modmSaConfigEntry 10 }

modmSaConfigPsType OBJECT-TYPE
      SYNTAX  INTEGER
	      {
		  notApplicable (1),
	      ac            (2),
	      dc            (3),
	      ac-dc         (4)
	      }
      MAX-ACCESS  read-only
      STATUS  current
      DESCRIPTION
      "The type of PS."
      ::= {modmSaConfigEntry 11}


modmSaConfigWorkMode OBJECT-TYPE
      SYNTAX INTEGER {
                notApplicable(1),
      		    transparent (2),
				termination(3)
		            }
      MAX-ACCESS read-write
      STATUS current
      DESCRIPTION
      "The work mode indicates if devices work in transparent mode or termination mode."
       
      ::= { modmSaConfigEntry 12}


      

modmSaStatTable  OBJECT-TYPE
      SYNTAX SEQUENCE OF ModmSaStatEntry
      MAX-ACCESS not-accessible
      STATUS  current
      DESCRIPTION
      "Status of the Central and Remote Modems."
       ::= { modmSa 2 }

modmSaStatEntry OBJECT-TYPE
      SYNTAX ModmSaStatEntry
      MAX-ACCESS not-accessible
      STATUS current
	DESCRIPTION  "An entry in table."
	INDEX {modmSaConfigMode}
      ::= { modmSaStatTable 1}

ModmSaStatEntry ::=
      SEQUENCE {
	  modmSaStatHwTest            Integer32,
	  modmSaStatAlarms            OCTET STRING,
	  modmSaStatClkSrc            INTEGER,
	  modmSaStatAlarmsMask        OCTET STRING,
	  modmSaStatDeviceType		  INTEGER,
	  modmSaStatSwVersion		  DisplayString,
	  modmSaStatHwVersion		  DisplayString
      }

modmSaStatHwTest OBJECT-TYPE
      SYNTAX Integer32 
      MAX-ACCESS read-only
      STATUS current
      DESCRIPTION
      "The variable contains the results of the last hardware test.
       It is a sum of 2**n where n is as follows:
       0 - EPROM Failure  (or Database chksum error)
       1 - I/O Expander Error
       2 - Counter Error
       3 - HDSL Framer Failure
       4 - Transceiver Failure
       5 - NVRAM Failure  (applicable only for HCD-E1>=r3) 
       6 - NSFIFO Failure (applicable for HCD-E1>=r3 and HCD-4)
       7 - BERT Failure	  (applicable only for HCD-E1>=r3)
       8 - E1 Framer Failure (applicable only for HCD-E1>=r3)
       9 - XRT Failure    (applicable only for HCD-E1>=r3)
	   10- HDSL Framer 1 Failure (applicable only for HCD-4)
	   11- HDSL Framer 2 Failure (applicable only for HCD-4)
	   12- DSP 1 Failure (applicable only for HCD-4)
	   13- DSP 2 Failure (applicable only for HCD-4)
	   14- XRT 1 Failure (applicable only for HCD-4)
	   15- XRT 2 Failure (applicable only for HCD-4)
       if the variable is 0 then there are No Errors "
      ::= { modmSaStatEntry 1}

modmSaStatAlarms OBJECT-TYPE
      SYNTAX OCTET STRING (SIZE(10)) 
      MAX-ACCESS read-only
      STATUS current
      DESCRIPTION
      "The variable contains the status of the Alarms in the alarm 
       buffer.
       For bit location of each Alarm in the OctetString see Modem's
	   specification.
       If the value is 0 then there are No 'On' Alarms in the alarm 
       buffer."
      ::= { modmSaStatEntry 2}

modmSaStatClkSrc  OBJECT-TYPE
      SYNTAX  INTEGER
    {
        master   (1),
        fallback (2)
	}
      MAX-ACCESS  read-only
      STATUS  current
      DESCRIPTION
     "This entry indicates the source of the modem clock."
      ::= { modmSaStatEntry 3}

modmSaStatAlarmsMask OBJECT-TYPE
      SYNTAX OCTET STRING (SIZE(10)) 
      MAX-ACCESS read-write
      STATUS current
      DESCRIPTION
      "This variable uses to mask alarms.
       Location of each Alarm Mask in the OctetString, 
       is identical to the Alarm OctetString. 
       If the value is 0 then none of the alarms is masked."
      ::= { modmSaStatEntry 4}

modmSaStatDeviceType  OBJECT-TYPE
      SYNTAX  INTEGER
    {
        notApplicable 	 (1),
        amc102SA		 (2),
		amc102Card		 (3)
	}
      MAX-ACCESS  read-only
      STATUS  current
      DESCRIPTION
     "This entry indicates the device type (or utility)."
      ::= { modmSaStatEntry 5}

modmSaStatSwVersion  OBJECT-TYPE
      SYNTAX      DisplayString
      MAX-ACCESS  read-only
      STATUS  current
      DESCRIPTION
      "Display String of the modem SW version.
	   Format: W.      X       Y         Z
	           0..9	   0..99   A,B,E     0..99
		(Z+P are optional.)
		A=alpha, B=beta, E=end of development.
       Examples: 2.23A8 
				 3.4  "
      ::= {modmSaStatEntry 6}

modmSaStatHwVersion	  OBJECT-TYPE
      SYNTAX      DisplayString
      MAX-ACCESS  read-only
      STATUS  current
      DESCRIPTION
      "Display String of the modem HW version."
      ::= {modmSaStatEntry 7}

modmSaAlarmBuffTable  OBJECT-TYPE
      SYNTAX SEQUENCE OF ModmSaAlarmBuffEntry
      MAX-ACCESS not-accessible
      STATUS  current
      DESCRIPTION
      "The alarm buffer of the Central and Remote Modems."
       ::= { modmSa 3 }

modmSaAlarmBuffEntry OBJECT-TYPE
      SYNTAX ModmSaAlarmBuffEntry
      MAX-ACCESS not-accessible
      STATUS current
	DESCRIPTION  "An entry in table."
	INDEX {modmSaConfigMode,modmSaAlarmBuffIndex}
      ::= { modmSaAlarmBuffTable 1}

ModmSaAlarmBuffEntry ::=
      SEQUENCE {
	  modmSaAlarmBuffIndex Integer32,
	  modmSaAlarmBuffCode  Integer32,
	  modmSaAlarmBuffTime  DisplayString,
	  modmSaAlarmBuffState INTEGER
      }

modmSaAlarmBuffIndex OBJECT-TYPE
      SYNTAX Integer32 
      MAX-ACCESS read-only
      STATUS current
      DESCRIPTION
      "The index of the alarm buffer Table."
      ::= { modmSaAlarmBuffEntry 1}

modmSaAlarmBuffCode OBJECT-TYPE
      SYNTAX Integer32
      MAX-ACCESS read-only
      STATUS current
      DESCRIPTION
      "The code of the alarm. For text description of each Alarm 
       code see Modem's	specification."
      ::= { modmSaAlarmBuffEntry 2}

modmSaAlarmBuffTime OBJECT-TYPE
      SYNTAX DisplayString
      MAX-ACCESS read-only
      STATUS current
      DESCRIPTION
      "The time stamp at which the alarm has occurred. The format
       is hh:mm:ss "
      ::= { modmSaAlarmBuffEntry 3}

modmSaAlarmBuffState OBJECT-TYPE
      SYNTAX INTEGER  { off(2),
	                    on(3)
					  }
      MAX-ACCESS read-only
      STATUS current
      DESCRIPTION
      "The new status of the alarm."
      ::= { modmSaAlarmBuffEntry 4}

-- Modem parameters - all parameters refer the Agent itself only

modmSaParam OBJECT IDENTIFIER  ::=  {modmSa 4}

modmSaMode OBJECT-TYPE
      SYNTAX INTEGER  
      { 
      central (1),
	  remote  (2),
	  remote2  (3),
	  remote3  (4),
	  remote4  (5),
	  remote5  (6),
	  remote6  (7),
	  remote7  (8),
	  remote8  (9),
	  remote9  (10),
	  remote10  (11)
	   
  	  }
      MAX-ACCESS read-only
      STATUS current
      DESCRIPTION
      "The agent's current mode.
      For AMC 102 remote means regenerator. 
      There can be some regenerators connecting one by the other."
      ::= {modmSaParam 1}

modmSaFarEndIpAddress OBJECT-TYPE
      SYNTAX IpAddress
      MAX-ACCESS read-write
      STATUS current
      DESCRIPTION
      "The IP address of the agent on the far end. If the Remote 
       modem is NOT an agent, the variable will be 0.0.0.0.
       Set - will be enabled only to a Central modem that works as
             Proxy."
      ::= {modmSaParam 2}

modmSaFarEndType OBJECT-TYPE
      SYNTAX INTEGER  
      { 
      unknown   (1),
	  sa        (2),  --same product as near-end
	  card      (3),  --same product as near-end
	  saLowCost (4),  --same product as near-end
	  hcdSa     (5),
	  hcdSaL    (6),
	  hcdCard   (7),
	  htu2Sa    (8),
	  htu2Card  (9),
	  htuE1Sa  (10),
	  htuE1SaL (11),
	  htuE1Card(12),
	  hcd4Sa   (13),
	  hcdPF    (14),
      unmanaged(100)  --MP/DXC card
  	  }
      MAX-ACCESS read-only
      STATUS current
      DESCRIPTION
      "The type of the Far-End modem."
      ::= {modmSaParam 3}

modmSaRptrType OBJECT-TYPE
      SYNTAX INTEGER  
      { 
	  none    (2), 
	  hrpt    (3),
	  flexDsl (4),
	  notApplicable (255)
	  }
      MAX-ACCESS read-only
      STATUS current
      DESCRIPTION
      "The Repeater between the Near and Far modem.
       none - no repeater exists between the modems.
       notApplicable - for modems that do not support this feature."
      ::= {modmSaParam 4}

modmSaLearnLineMode OBJECT-TYPE
      SYNTAX INTEGER  
      { 
	  notApplicable (1),
	  manually		(2),
	  automatic		(3)
	  
	  }
      MAX-ACCESS read-write
      STATUS current
      DESCRIPTION
      "This parameter is for the central unit only.
       Indicates if learn the regenerator order and number every time there 
       is a fail in line or manually by user."
       ::= {modmSaParam 5}

modmSaNumOfUnits  OBJECT-TYPE
      SYNTAX  Integer32 
      MAX-ACCESS  read-only
      STATUS  current
      DESCRIPTION
      "This object will hold the number of regenerators in the line."
      ::= {modmSaParam 6}


-- Repeater Table
modmSaRptrTable  OBJECT-TYPE
      SYNTAX SEQUENCE OF ModmSaRptrEntry
      MAX-ACCESS not-accessible
      STATUS  current
      DESCRIPTION
      "The Repeaters parameters known to the central modem."
       ::= { modmSa 5 }

modmSaRptrEntry OBJECT-TYPE
      SYNTAX ModmSaRptrEntry
      MAX-ACCESS not-accessible
      STATUS current
	DESCRIPTION  "An entry in table."
	INDEX {modmSaIndex, modmSaRptrIndex}
      ::= { modmSaRptrTable 1}

ModmSaRptrEntry ::=
      SEQUENCE {
      modmSaIndex                Integer32,
      modmSaRptrIndex            Integer32,
      modmSaRptrTest             INTEGER,
      modmSaRptrActiveAlarms     OCTET STRING,
      modmSaRptrAlrClear         INTEGER,
	  modmSaRptrVersion	         DisplayString
      }

modmSaIndex OBJECT-TYPE
      SYNTAX  Integer32
      MAX-ACCESS  read-only
      STATUS  current
      DESCRIPTION
      "A unique number to identify the modem that reports about the repeater."
      ::= {modmSaRptrEntry 1}

modmSaRptrIndex OBJECT-TYPE
      SYNTAX Integer32
      MAX-ACCESS read-only
      STATUS current
      DESCRIPTION
      "The index of the Repeater."
      ::= { modmSaRptrEntry 2 }

modmSaRptrTest OBJECT-TYPE
      SYNTAX INTEGER {
            none      (1),
            loopLHrpt (2)
          }
      MAX-ACCESS read-write
      STATUS current
      DESCRIPTION
      "The possible loopbacks."
::= { modmSaRptrEntry 3 }

modmSaRptrActiveAlarms OBJECT-TYPE
      SYNTAX OCTET STRING
      MAX-ACCESS read-only
      STATUS current
      DESCRIPTION
      "Status of the Alarms. Each bit represents a specific
       alarm .
       For bit location of each alarm in the
       Octet String see modem's specification.
       If the value is 0 then there are No Alarms."
::= { modmSaRptrEntry 4 }

modmSaRptrAlrClear OBJECT-TYPE
      SYNTAX INTEGER {
            off      (1),
            on       (2)
          }
      MAX-ACCESS read-write
      STATUS current
      DESCRIPTION
      "Setting this attribute to on, clears all the active (On) 
       alarms of the repeater. Upon completion, the value will 
       automatically change to off(2).."
      ::= { modmSaRptrEntry 5 }

modmSaRptrVersion  OBJECT-TYPE
      SYNTAX  DisplayString
      MAX-ACCESS  read-only
      STATUS  current
      DESCRIPTION
      "SW/HW version of the repeater"
      ::= { modmSaRptrEntry 6 }
 
       
--modmHub OBJECT IDENTIFIER  ::=  {modmSystem 2}

--Modem - Hub Parameters

modmHubParam OBJECT IDENTIFIER  ::=  {modmHub 1}

modmHubTermConnect OBJECT-TYPE
      SYNTAX INTEGER  
              {
                no  (2),
                yes (3)
              }
      MAX-ACCESS read-only
      STATUS current
      DESCRIPTION
      "Status: is the Terminal connected or not."
      ::= {modmHubParam 1}

modmHubController OBJECT-TYPE
      SYNTAX INTEGER  
              {
                nms      (1),
                terminal (2)
              }
      MAX-ACCESS read-write
      STATUS current
      DESCRIPTION
      "Selection of Hub controller during normal operation. If 
       'terminal' is selected, NMS can still return control to 
       itself by setting this object to 'nms'. While terminal is
       the controller, NMS can perform Get operations and Set trap
       masks."
      ::= {modmHubParam 2}

modmHubId OBJECT-TYPE
      SYNTAX OCTET STRING (SIZE(2))  
      MAX-ACCESS read-write
      STATUS current
      DESCRIPTION
      "4 Hex characters, identifying the Hub. The last two 
       characters (least significant) will be displayed on the 
       Hub's CL card by a 7 segment display."
      ::= {modmHubParam 3}

modmHubT1E1 OBJECT-TYPE
      SYNTAX INTEGER  
              {
                other (1),
                t1    (2),
				e1    (3)
              }
      MAX-ACCESS read-only
      STATUS current
      DESCRIPTION
      "The T1/E1 value determines the Hub's clock rate."
      ::= {modmHubParam 4}

modmHubClockSource OBJECT-TYPE
      SYNTAX INTEGER  
              {
                other         (1),
                external      (2),
				internal      (3),
				g703Section10 (4),
				receive       (5),
				station       (6)
              }
      MAX-ACCESS read-write
      STATUS current
      DESCRIPTION
      "Clock source."
      ::= {modmHubParam 5}

modmHubClockRate OBJECT-TYPE
      SYNTAX INTEGER  
              {
                e1r2048000 (1),
                e1r1024000 (2),
				e1r512000  (3),
				e1r256000  (4),
				e1r128000  (5),
				e1r64000   (6),
				e1r32000   (7),
				e1r16000   (8),
				e1r8000    (9),

                t1r1544000 (31),
				t1r772000  (32),
				t1r386000  (33),
				t1r193000  (34),
				t1r96500   (35),
				t1r48250   (36),

                notApplicable (255)
              }
      MAX-ACCESS read-write
      STATUS current
      DESCRIPTION
      "Clock Rate in bps. The rates are the original T1/E1 rates
       or the rates divided by 2n.
       For modmHubT1E1=e1, instances (1)-(9) are applicable.
       For modmHubT1E1=t1, instances (31)-(36) are applicable.
       For modmHubT1E1=other, instance (255) is applicable."
      ::= {modmHubParam 6}

modmHubIpMode OBJECT-TYPE
      SYNTAX INTEGER  
              {
                single        (1), 
                multi         (2)
              }
      MAX-ACCESS read-write
      STATUS current
      DESCRIPTION
      "single - Upon BootP request from S-MOD, CM-2 will 
       assign a 'private IP' (CM-2 IP + slot number of S-MOD),
       which will be applicable only between the S-MOD and CM-2.
       multi - CM-2 assigns up to 12/24 consequent IP addresses. 
       One for each S-MOD according to the slot number."
      ::= {modmHubParam 7}

modmHubInstallation OBJECT-TYPE
      SYNTAX OCTET STRING  
      MAX-ACCESS read-write
      STATUS current
      DESCRIPTION
      "The string will be a multiple set of 16 bit corresponds 
      to its card position, and each set corresponds to a modem, 
      where set #1 is the first modem on each card, and set n is 
      the n-st modem in each card.
     
      1........10.....16|1........10.....16|
        modem 1         |    modem 2       |

      MSB								LSB  

      Bits 1-3 and 16 will be ignored.
      For LRS-52 detailed bit assignment see product's spec."
      ::= {modmHubParam 8}


--Modem - Hub Alarms

modmHubAlarms OBJECT IDENTIFIER  ::=  {modmHub 2}

modmHubActiveAlarms OBJECT-TYPE
      SYNTAX OCTET STRING  
      MAX-ACCESS read-only
      STATUS current
      DESCRIPTION
      "Status of the Alarms for each Slot. Each bit represents a 
       Slot of the Hub. For bit location of each Alarm in the 
       Octet String see Hub's specification.
	   A bit is '1' (On) if at least one 'On' alarm exists for this
	   Slot.
       If the value is 0 then there are No 'On' Alarms in any Slot.
       For LRS52  - read 'modem' instead of the word 'slot'"
      ::= {modmHubAlarms 1}

modmHubAlrClear  OBJECT-TYPE
      SYNTAX  INTEGER
	      {
		off(2),
		on (3)
	      }
      MAX-ACCESS  read-write
      STATUS  current
      DESCRIPTION
      "Setting this attribute to on, clears all the active (On) 
       alarms of the Hub. Upon completion, the value will 
       automatically change to off(2)."
      ::= {modmHubAlarms 2}

modmHubMaskAlarms OBJECT-TYPE
      SYNTAX OCTET STRING  
      MAX-ACCESS read-write
      STATUS current
      DESCRIPTION
      "Mask of Alarms per Slot. Each bit represents a 
       Slot of the Hub. For bit location of each Slot in the 
       Octet String see Hub's specification (same as 
       modmHubActiveAlarms).
	   When a bit is '1' (On) it is masked ; all alarms of this Slot
	   should not be sent and Alarm LED should not be lit. This 
	   mask overrides the mask on the specific alarms of each Slot
	   or modem.
	   If the value is 0 then all alarms should be sent.
	   For LRS52  - read 'modem' instead of the word 'slot'."
      ::= {modmHubAlarms 3}


modmMdl  OBJECT IDENTIFIER  ::=  {modmSys 2}

modmMdlParam OBJECT IDENTIFIER  ::=  {modmMdl 1}

mdlParamTable  OBJECT-TYPE 
      SYNTAX SEQUENCE OF MdlParamEntry
      MAX-ACCESS not-accessible
      STATUS  current
      DESCRIPTION
      "Parameters table of cards in the Hub."
      ::= { modmMdlParam 1 }

mdlParamEntry OBJECT-TYPE
      SYNTAX MdlParamEntry
      MAX-ACCESS not-accessible
      STATUS current
	DESCRIPTION  "An entry in table."
	INDEX { mdlSIdx }
      ::= { mdlParamTable 1}

MdlParamEntry ::=
      SEQUENCE {
      mdlSIdx               INTEGER,
	  mdlSNoOfModems        Integer32,
      mdlCardType           INTEGER,
      mdlSPanelType         INTEGER,
	  mdlSLed               OCTET STRING,
	  mdlSActiveAlarms      OCTET STRING,
	  mdlAlrClear           INTEGER,
	  mdlSConfigMismatch    INTEGER,
	  mdlConfigSource       INTEGER,
	  mdlConfigGround       INTEGER,
	  mdlCapabilities		OCTET STRING,
	  mdlClockSource        INTEGER
      }

mdlSIdx OBJECT-TYPE
      SYNTAX  INTEGER
	      {
	      psA   (1),
	      psB   (2),
	      cl    (3),
	      io1   (4),
	      io2   (5),
	      io3   (6),
	      io4   (7),
	      io5   (8),
	      io6   (9),
	      io7  (10),
	      io8  (11),
	      io9  (12),
	      io10 (13),
	      io11 (14),
	      io12 (15)
	      }
      MAX-ACCESS  read-only
      STATUS  current
      DESCRIPTION
      "A unique number to identify a slot position in the modems 
       Hub."
      ::= { mdlParamEntry 1}

mdlSNoOfModems  OBJECT-TYPE
      SYNTAX  Integer32
      MAX-ACCESS  read-only
      STATUS  current
      DESCRIPTION
      "Number of modems on this card.
       255 = notApplicable. "
      ::= { mdlParamEntry 2 }

mdlCardType  OBJECT-TYPE
      SYNTAX  INTEGER
	      {
		unknown   (1),
		empty     (2),
		ps48V     (3),
		ps110V    (4),
		ps230V    (5),
		cm2       (6),
		smod      (7),
		asmi24    (8),
		asmi31    (9),
		asmi32    (10),
		asmi50    (11),
		mtmi20    (12),
		fomi40    (13),
		fomiE1T1  (14),
		asm40cd     (15),
		asmi50cd    (16),
		fomi40cd    (17),
		fomiE1T1cd  (18),
        ps110V-24   (19),
		ps230V-24   (20),
		ps48V-24    (21),
		asmi31cq    (22),
		asmi51cq    (23),
		asmi51cd    (24),
		asmi52cd    (25),
		asmi52cq    (26),
		asmi52cd4W  (27), -- ASMi52CD with 4 wire
	 	asmi52cqEth (28),
		asmi52cd4wNew   (29), -- ASMi52CD New with 4 wire
	 	asmi52cd4wNewEth(30),

--SMODs
		fomiE3      (51),
		fomiT3      (52),
		optimux4E1  (53),
		optimux4T1  (54),
		amc102		(55),

		notApplicable (255)
	      }
      MAX-ACCESS  read-only
      STATUS  current
      DESCRIPTION
      "Card's type."
      ::= { mdlParamEntry 3 }


mdlSPanelType  OBJECT-TYPE
      SYNTAX  INTEGER
	      {
		empty           (1),
		f2              (2),   --rj45AndDb25
		f3              (3),   --rj45AndG703
		f5              (5),   --2*rj45And2*26HD
		f6              (6),   --rj45+2BNCAnd2*26HD
		f7              (7),   --asmi32
		f9              (9),   --rj45AndV35
		f10            (10),   --rj45AndRj45 
		f11            (11),   --rj45And2rj45
		f12            (12),   --rj45AndX21
		f13            (13),   --2*rj45And2*rj45
		f14            (14),   --2*4381And2*rj45
		f18            (15),   --scsi68And4*rj11
		f19            (16),   --scsi68And4*TB
		f22            (17),   --iripRj45
		f20			   (18),   --4TB2And4RJ45 for CQ
		f21			   (19),   --4TB2AndDB25 for CQ
		f23			   (20),   --2RJ45And2IP for CD
-- (see cont. later)

-- Panels with an Optical connector
        fO1            (21),   --stAndDb25
        fO2            (22),   --stAndV35
        fO3            (23),   --stAndDb15
        fO4            (24),   --stAndG703
        fO5            (25),   --scAndDb25
        fO6            (26),   --scAndV35
        fO7            (27),   --scAndDb15
        fO8            (28),   --scAndG703
        fO9            (29),   --stAndEthernet
        fO10           (30),   --scAndEthernet
        fO11           (31),   --2*st/fcAnd2*SCSI
        fO12           (32),   --2*st/fcAnd2*rj45
        fO13           (33),   --2*scAnd2*SCSI
        fO14           (34),   --2*scAndr2*j45
        fO15           (35),   --(2*st/fcAnd2*4381)eth
        fO16           (36),   --(2*scAnd2*4381)eth 
        fO17           (37),   --(2*st/fcAndBNC)e3/t3 
        fO18           (38),   --(2*scAndBNC)e3/t3 
        fO19           (39),   --(2*st/fcAnd2*bnc)wdm
        fO20           (40),   --(2*scAnd2*scsi)wdm 
        fO21           (41),   --(4*MBNC And 2*st/fc)e1/t1 
        fO22           (42),   --(4*MBNC And 2*sc)e1/t1 
		
--Power Supply panels
		ps230And115    (81),   --PS 230V, 115V without phantom
		psp230And115   (82),   --PS 230V, 115V with phantom
		ps48           (83),   --PS 48V without phantom
		psp48          (84),   --PS 48V with phantom

--Panels of CM2 card (CL)
		f1Cm2          (91),   --CM2 UTP
		f2Cm2          (92),   --CM2 BNC
		f3Cm2          (93),   --CM2 V35
		f4Cm2          (94),   --CM2 RS-530
		f5Cm2          (95),   --CM2 X21
		f1Cm2New	   (96),   --CM2 UTP with embedded LEDs

--Regular panels (cont.)
		f24			   (121),   --2RJ45And2RJ11 for CD
		f25			   (122),   --2RJ45AndDB25 for CD	
		f27			   (123),   --4RJ45And4TB for CQ (Line connectors first)	
		f28			   (124),   --2RJ45And4RJ11 balance for CQ (Line connectors first) 	
		f29			   (125),   --2RJ45AndDB25 unbalance for CQ (Line connectors first) 	
		f30			   (126),   --2RJ45And4TB for CD 4W New
		f31            (127),   --SCSI68And4RJ11 for CD 4W New
		f32            (128),   --SCSI68And4TB2 for CD 4W New 	
 
		notApplicable (255)
	      }
      MAX-ACCESS  read-only
      STATUS  current
      DESCRIPTION
      "LRS-12 Card connectors' panel type.
       fx    - IMOD panels
       psxxx - PS panels
       fxCm2 - CM-2 panels."
      ::= { mdlParamEntry 4 }

mdlSLed  OBJECT-TYPE   
      SYNTAX  OCTET STRING 
      MAX-ACCESS  read-only
      STATUS  current
      DESCRIPTION
	  "LEDs status on the card . Each led will be represented by 4 
	   bits where the first 2 bits (left) will specify  the Status :
	   (00=NA, 01=OFF, 10=ON, 11=BLINK),
       and the next two bits (right) will specify the Color :
       (00=GREEN, 01=RED, 10=YELLOW, 11=ORANGE).
       This object is not applicable for the 'smod', 'empty' and 
       'unknown' card types. For them 0 will be sent. "
      ::= { mdlParamEntry 5}

mdlSActiveAlarms OBJECT-TYPE
      SYNTAX OCTET STRING  
      MAX-ACCESS read-only
      STATUS current
      DESCRIPTION
      "This object is applicable only for PS and CL cards.
       It gives the status of the Alarms for each Slot. Each bit 
       represents an alarm in the slot. For bit location of each 
       Alarm in the Octet String see Hub's specification.
	   A bit is '1' if the alarm is On. 
	   If the value is 0 then there are No 'On' Alarms in the Slot."
      ::= {mdlParamEntry 6}

mdlAlrClear  OBJECT-TYPE
      SYNTAX  INTEGER
	      {
		off(2),
		on (3)
	      }
      MAX-ACCESS  read-write
      STATUS  current
      DESCRIPTION
      "Setting this attribute to on, clears all the active (On) 
       alarms of the Slot. Upon completion, the value will 
       automatically change to off(2)."
      ::= {mdlParamEntry 7}

mdlSConfigMismatch  OBJECT-TYPE
      SYNTAX  INTEGER
	      {
		off   (2),
		on    (3),
		line1 (4),
		line2 (5),
		notApplicable (255)
	      }
      MAX-ACCESS  read-only
      STATUS  current
      DESCRIPTION
      "This object is applicable only for slots containing 
       IMOD cards.
       ON - when CM-2 realizes that the configuration of the 
            Near-End modem1 is different from that of its Far-End 
            modem. 
            In this case it expects user to decide which of the 
            modems' configuration is the correct one (by 
            'mdlConfigSource'), or change the incorrect modem 
            configuration.  
			When one of these conditions is fulfilled, the value 
			will automatically turn to OFF. Applicable for a single 
			modem.
       Line1 - The same as for ON but for modem-1 line. Applicable 
            for a double modem.
       Line2 - The same as for ON but for modem-2 line. Applicable
            for a double modem.
       OFF - Near-End and Far-End modems have the same 
            configuration (OK). "
      ::= {mdlParamEntry 8}

mdlConfigSource  OBJECT-TYPE
      SYNTAX  INTEGER
	      {
		nearEnd (1),
		farEnd  (2),
		nearEnd2 (3),
		farEnd2  (4),
		notApplicable (255)
	      }
      MAX-ACCESS  read-write
      STATUS  current
      DESCRIPTION
      "This object is applicable only for slots containing 
       IMOD cards, when mdlSConfigMismatch=on/on1/on2.
       nearEnd - Near End - 1 modem has the correct configuration
       farEnd  - Far  End - 1 has the correct configuration  
       nearEnd - Near End - 2 has the correct configuration
       farEnd  - Far  End - 2 has the correct configuration."
      ::= {mdlParamEntry 9}

mdlConfigGround OBJECT-TYPE
      SYNTAX  INTEGER
	      {
	       notApplicable (1),
		   disconnect    (2),
		   connect       (3)
	      }
      MAX-ACCESS  read-only
      STATUS  current
      DESCRIPTION
      "Enables to connect or disconnect an IMOD card to the 
        ground.
       disconnect    -  not connected to ground.
       connect       -  connected to ground.
       notApplicable -  for other cards."
      ::= {mdlParamEntry 10}

mdlCapabilities  OBJECT-TYPE   
      SYNTAX  OCTET STRING 
      MAX-ACCESS  read-only
      STATUS  current
      DESCRIPTION
      "Indicates the optional capabilities that are implemented by this module
       and are manageable through this MIB. 
	   For each capability 1 BIT is allocated in each Octet starting from the LSB.
       If the value of the BIT = 1, the capability is Enabled.
       If the value of the BIT = 0, the capability is Disabled.
       For bit assignment, refer to device specification.	 
	   Capabilities example:
	   Low Speed Operation - BIT 0 
	   CPE Operation - BIT 1"
      ::= { mdlParamEntry 11}

mdlClockSource OBJECT-TYPE
      SYNTAX INTEGER 
	      {
-- (1)-(8) are reserved for values similar to modmPrtLineClkSrc 
		   internal       (9),
		   external      (10),
		   system        (11),
		   receive       (12),
		   
		   notApplicable (255)
	      }
	  MAX-ACCESS read-write
      STATUS current
      DESCRIPTION
      "The Clock Source of the Card.
       Applicable for ASMi-52 modems only.
       internal - means that the card uses its own Internal Clock 
       external - means that the card uses the Clock received from an 
                  External DTE port of a modem. The modem used has to be 
				  specified in a separate MIB object (modmPrtLineClkSrcPort
				  of the 1st modem in the card).
       system   - means that the card uses the Clock of the CM2 card of LRS-24.
       receive  - means that every modem of the card will use the Clock
                  received from its own Line." 
      ::= { mdlParamEntry 12}


--Modem data - the modem can either belong to the Hub or
--             be a Far-End modem connected to a modem of 
--             the Hub.	The data applies mainly for IMOD cards.
--             This table is used also by DXC and MP, for data about 
--             far unit	of each external port of D8SL/MSL card.
--             For DXC and MP, modemIdx=ifIndex of External port of D8SL/MSL card.

modem    OBJECT IDENTIFIER  ::=  {modmSys 3}

modemParam OBJECT IDENTIFIER  ::=  {modem 1}

modemParamTable  OBJECT-TYPE 
      SYNTAX SEQUENCE OF ModemParamEntry
      MAX-ACCESS not-accessible
      STATUS  current
      DESCRIPTION
      "This parameters table is applicable mainly for modems that are
       not agents."
      ::= { modemParam 1 }

modemParamEntry OBJECT-TYPE
      SYNTAX ModemParamEntry
      MAX-ACCESS not-accessible
      STATUS current
	DESCRIPTION  "An entry in table."
	INDEX { modemIdx }
      ::= { modemParamTable 1}

ModemParamEntry ::=
      SEQUENCE {
      modemIdx                 Integer32,
	  modemType                INTEGER,
	  modemConfigMode          INTEGER,
	  modemModeTemporary       INTEGER,
	  modemNoOfDte             Integer32,
	  modemWire                INTEGER,
      modemMngLink			   INTEGER,
	  modemReset     		   INTEGER,
	  modemSlot                INTEGER,
	  modemHubId               OCTET STRING,
	  modemIpAddress           IpAddress,
	  modemPsType              INTEGER,
	  modemMaskTraps           Integer32,
	  modemActiveAlarms		   OCTET STRING,
	  modemAlrClear			   INTEGER,
	  modemAlrBufClear		   INTEGER,
	  modemMaskSignaling       OCTET STRING,
	  modemPanelType           INTEGER,
	  modemIType               INTEGER,
	  modemRcvPower            Integer32,
	  modemSwVersion           Integer32,
	  modemLed                 OCTET STRING,
	  modemRemoteType          INTEGER,
	  modemConfigPhantom       INTEGER,
	  modemRemoteTestEnable    INTEGER,
	  modemSwVerString		   DisplayString,
	  modemRemoteIdx		   Integer32,
	  modemHwVerString		   DisplayString,
	  modemResetStatistics	   INTEGER,
	  modemMaxRate             INTEGER,
	  modemBoxMaterial 		   INTEGER,
	  modemLowSpeed			   INTEGER,
	  modemDevicePorts		   Integer32,	
	  modemUserName		       DisplayString,
	  modemRowValidity		   INTEGER,
	  modemTftpCmd             INTEGER	
      }

modemIdx OBJECT-TYPE
      SYNTAX  Integer32
      MAX-ACCESS  read-only
      STATUS  current
      DESCRIPTION
      "For LRS:
         A unique number to identify a modem in the Hub or its 
         far-end modem.
       For DXC:
         This will be the ifIndex of the External Port of D8SL card,
         that works with this modem/product.
       For MP:
         This will be the ifIndex of the External Port of MSL card,
         that works with this modem/product."
      ::= {modemParamEntry 1}

modemType OBJECT-TYPE
      SYNTAX  INTEGER
	      {
	       unknown    (1),
	       asmi24c    (2),
		   asmi31c    (3),
		   asmi32c    (4),
		   asmi50c    (5),
		   mtmi20c    (6),
		   fomi40c    (7),
		   fomiE1T1c  (8), 
		   asm40cd    (9),
		   asmi31cq   (10),
		   asmi51cq   (11),
		   asmi51cd   (12),
		   asmi52cq   (13),
		   asmi52cd   (14),
		   asmi52cd4W (15),
		   asmi52cqEth(16),
		   asmi52cd4wNew   (17),
		   asmi52cd4wNewEth(18),

	       asmi24r    (22),
		   asmi31r    (23),
		   asmi32r    (24),
		   asmi50r    (25),
		   mtmi20r    (26),

	       asmi24     (42),
		   asmi31     (43),
		   asmi32     (44),
		   asmi50     (45),
		   mtmi20     (46),
		   fomi40     (47),
		   fomiE1T1   (48),
		   asmi51     (49),
		   asmi52S    (50),	 --Slave
		   asmi52M    (51),	 --Master
		   asmi52L    (52),  --SA Low Cost
		   asmi54     (53),  --SA 

           lrs52      (71)
 	      }
      MAX-ACCESS  read-only
      STATUS  current
      DESCRIPTION
      "Modem type.
       xxxxxx  - Stand-Alone modem.
       xxxxxxc - Modem on a Card within a Hub having an Agent.
       xxxxxxr - Modem on a Card within a Hub having no Agent.
       xxxxxxcd - Modem on a Double-Modem Card within a Hub  
                  having an Agent. Each modem has it's own CPU.
       xxxxxxcq - Modem on a Quad-Modem Card within a Hub  
                  having an Agent. One CPU for all modems.
       lrs52 - Modem within the LRS-52 device."
      ::= {modemParamEntry 2}

modemConfigMode OBJECT-TYPE
      SYNTAX INTEGER {
                master (1),
      		    slave  (2)
		            }
      MAX-ACCESS read-write
      STATUS current
      DESCRIPTION
      "The mode identifies if the Modem operates as the Master 
       unit or as the Slave unit.
       For modems having a jumper for this function, this object 
       will be RO. 
	   This object can be Set only to the Master unit when 
	   modemModeTemporary=no (the Far-End unit will receive its 
	   new mode from the Central unit, via management link 
	   between the modems).	   
	   Regarding other objects (except modemModeTemporary):
       If Modem is Master, it can perform RW operations for 
       both Master and Slave modem. 
       If Modem is Slave, it can perform RO operations for 
       both Master and Slave modem." 
      ::= {modemParamEntry 3}

modemModeTemporary OBJECT-TYPE
      SYNTAX INTEGER {
                no  (2),
      		    yes (3)
		            }
      MAX-ACCESS read-write
      STATUS current
      DESCRIPTION
      "This object specifies if the Modem operates as 
       modemConfigMode value (Master/Slave) temporarily or
       permanently. 
	   This object can be Set only when:
	   - modemConfigMode=master AND modemModeTemporary=no
	   - modemConfigMode=slave  AND modemModeTemporary=yes
	     this is an exception to the fact that all other objects
		 in this case are RO.
	   The other unit will receive its value for this object
	   from the Set unit, via management link between the modems." 
      ::= {modemParamEntry 4}

modemNoOfDte OBJECT-TYPE
      SYNTAX  Integer32
      MAX-ACCESS  read-only
      STATUS  current
      DESCRIPTION
      "Number of DTE ports in the modem."
      ::= {modemParamEntry 5}

modemWire OBJECT-TYPE
      SYNTAX  INTEGER
	      {
          w2wire   (1),
          w4wire   (2),
		  notApplicable (255)
	      }
      MAX-ACCESS  read-write
      STATUS  current
      DESCRIPTION
      "Modem wiring."
      ::= {modemParamEntry 6}

modemMngLink  OBJECT-TYPE
      SYNTAX  INTEGER
	      {
		off(2),
		on (3)
	      }
      MAX-ACCESS  read-only
      STATUS  current
      DESCRIPTION
      "Communication status between the pair of modems."
      ::= {modemParamEntry 7}

modemReset  OBJECT-TYPE
      SYNTAX  INTEGER
	      {
           off        (2),
           hwReset    (3),
		   configReset(4),
		   factoryReset (5)
             }
      MAX-ACCESS  read-write
      STATUS  current
      DESCRIPTION
      "When this object is set to the value of hwReset(3),
       the module performs HW Reset. 
	   When this object is set to the value of configReset(4),
       the modem performs Configuration Reset, which will set 
       the modem to the last parameters it was configured. 
       For LRS 24, this value used for Resetting Modem Line.
       When this object is set to the value of factoryReset (5),
       the modem performs factory Reset, which will set 
       the modem to the factory configuration"
      ::= {modemParamEntry 8}

modemSlot OBJECT-TYPE
      SYNTAX  INTEGER
	      {
	      io1   (4),
	      io2   (5),
	      io3   (6),
	      io4   (7),
	      io5   (8),
	      io6   (9),
	      io7  (10),
	      io8  (11),
	      io9  (12),
	      io10 (13),
	      io11 (14),
	      io12 (15),
	      io13 (16),
	      io14 (17),
	      io15 (18),
		  notApplicable (255)
	      }
      MAX-ACCESS  read-only
      STATUS  current
      DESCRIPTION
      "A unique number to identify the slot position of the  
       modem (card)in its Hub.
       notApplicable - for a stand-alone modem or Rack 214
                       card.
       io13..io15 - are for DXC use in case of a Far-Unit that is D8SL card."
      ::= {modemParamEntry 9}

modemHubId OBJECT-TYPE
      SYNTAX OCTET STRING (SIZE(2))  
      MAX-ACCESS read-only
      STATUS current
      DESCRIPTION
      "4 Hex characters, identifying the Hub. The last two 
       characters (least significant) will be displayed on the 
       Hub's CL card by a 7 segment display.
       This object is applicable only for LRS-12 modems."
      ::= {modemParamEntry 10}

modemIpAddress OBJECT-TYPE
      SYNTAX IpAddress
      MAX-ACCESS read-write		-- originally read-only
      STATUS current
      DESCRIPTION
      "For LRS:
       The IP address of the LRS-12 agent . If the modem is NOT 
       an LRS-12 card, the variable will be 0.0.0.0.
       For DXC and MP: the IP Address of the Far-End unit."
      ::= {modemParamEntry 11}

modemPsType OBJECT-TYPE
      SYNTAX  INTEGER
	      {
	      ac   (1),
	      dc   (2),
		  notApplicable (255)
	      }
      MAX-ACCESS  read-only
      STATUS  current
      DESCRIPTION
      "The type of PS, for a stand-alone modem. 
       notApplicable - for LRS-12 or Rack 214 card."
      ::= {modemParamEntry 12}

modemMaskTraps OBJECT-TYPE
      SYNTAX  Integer32
      MAX-ACCESS  read-write
      STATUS  current
      DESCRIPTION
      "The value determines the modem traps the agent should mask 
       and not send to the management console. 
       The value is a sum of 2**n, where n is a bit assigned to a 
       certain trap. For bit assignment see modem's specification.
       Value of '0', means that no trap should be masked."
      ::= {modemParamEntry 13}

modemActiveAlarms OBJECT-TYPE
      SYNTAX OCTET STRING  
      MAX-ACCESS read-only
      STATUS current
      DESCRIPTION
      "Status of the Alarms for each modem. Each bit represents an 
       alarm. For bit location of each Alarm in the Octet String 
       see modem's specification.
	   A bit is '1' if the alarm is On.
       If the value is 0 then there are no 'On' alarms on this
       modem."
      ::= {modemParamEntry 14}

modemAlrClear  OBJECT-TYPE
      SYNTAX  INTEGER
	      {
		off(2),
		on (3)
	      }
      MAX-ACCESS  read-write
      STATUS  current
      DESCRIPTION
      "Setting this attribute to on, clears all the active (On) 
       alarms of the modem. Upon completion, the value will 
       automatically change to off(2)."
      ::= {modemParamEntry 15}

modemAlrBufClear  OBJECT-TYPE
      SYNTAX  INTEGER
	      {
		off(2),
		on (3)
	      }
      MAX-ACCESS  read-write
      STATUS  current
      DESCRIPTION
      "Setting this attribute to on, clears all the alarms in the 
       buffer alarm of the modem. Upon completion, the value will 
       automatically change to off(2)."
      ::= {modemParamEntry 16}

modemMaskSignaling OBJECT-TYPE
      SYNTAX OCTET STRING  
      MAX-ACCESS read-write
      STATUS current
      DESCRIPTION
      "Mask of Signals per modem. When a signal is masked,  
	   the agent will not send the modemSignalingChange TRAP, upon 
	   change of this signal's value and it will not enter 
	   the History Log. 
       Each bit represents a signal of the modem. 
       For bit location of each signal in the Octet String see 
       modem's specification.
	   When a bit is '1' (On) it is masked ."
      ::= {modemParamEntry 17}

modemPanelType OBJECT-TYPE
      SYNTAX  INTEGER
	      {
	      f2      (2),   --rj45AndDb25
	   	  f3      (3),   --rj45AndG703
		  f7      (7),   --asmi32
		  f9      (9),   --rj45AndV35
		  f10    (10),   --rj45AndRj45 
		  f11    (11),   --rj45And2rj45
		  f12    (12),   --rj45AndX21
	      f13    (13),   --2*rj45And2*rj45
		  f14    (14),   --2*4381And2*rj45
		  f18    (15),   --scsi68And4*rj11
		  f19    (16),   --scsi68And4*TB
		  f22    (17),   --iripRj45
		  f20    (18),   --4TB2And4RJ45 for CQ
		  f21    (19),   --4TB2AndDB25 for CQ
		  f23    (20),   --2RJ45And2IP for CD
-- (see cont. later)

-- Panels with an Optical connector
          fO1    (21),   --stAndDb25
          fO2    (22),   --stAndV35
          fO3    (23),   --stAndDb15
          fO4    (24),   --stAndG703
          fO5    (25),   --scAndDb25
          fO6    (26),   --scAndV35
          fO7    (27),   --scAndDb15
          fO8    (28),   --scAndG703
          fO9    (29),   --stAndEthernet
          fO10   (30),   --scAndEthernet
          fO11   (31),   --2*st/fcAnd2*SCSI
          fO12   (32),   --2*st/fcAnd2*rj45
          fO13   (33),   --2*scAnd2*SCSI
          fO14   (34),   --2*scAndr2*j45
          fO15   (35),   --(2*st/fcAnd2*4381)eth
          fO16   (36),   --(2*scAnd2*4381)eth 
          fO17   (37),   --(2*st/fcAndBNC)e3/t3 
          fO18   (38),   --(2*scAndBNC)e3/t3 
          fO19   (39),   --(2*st/fcAnd2*bnc)wdm
          fO20   (40),   --(2*scAnd2*scsi)wdm 
          fO21   (41),   --(4*MBNC And 2*st/fc)e1/t1 
          fO22   (42),   --(4*MBNC And 2*sc)e1/t1 

	      pcu   (101),
	      lcd   (102),

--Regular panels (cont.)
		  f24   (121),   --2RJ45And2RJ11 for CD
		  f25   (122),   --2RJ45AndDB25 for CD	
		  f27   (123),   --4RJ45And4TB for CQ (Line connectors first)	
		  f28   (124),   --2RJ45And4RJ11 balance for CQ (Line connectors first) 	
		  f29   (125),   --2RJ45AndDB25 unbalance for CQ (Line connectors first) 	
		  f30   (126),   --2RJ45And4TB for CD 4W New 	
	      f31   (127),   --SCSI68And4RJ11 for CD 4W New
		  f32   (128),   --SCSI68And4TB2 for CD 4W New 	

		  notApplicable (255)
	      }
      MAX-ACCESS  read-only
      STATUS  current
      DESCRIPTION
      "The panel type of the modem.
       This parameter is applicable only for Far-End modems that 
       are stand-alone or cards of another LRS-12. It enables 
       displaying the correct panel of the modem.
       - Stand-alone : applicable only for ASMi-24 and ASMi-50 
         modems.
              pcu - with connector for Portable Control Unit 
              lcd - LCD display and buttons.
       - LRS-12 card : fx is the connectors panel of the modem. "
      ::= {modemParamEntry 18}

modemIType  OBJECT-TYPE
      SYNTAX  INTEGER
	      {
		notApplicable (1),
		no            (2),
		yes           (3)
	      }
      MAX-ACCESS  read-write
      STATUS  current
      DESCRIPTION
      "Is the modem Intelligent (ASMi-xx) ; or not - (ASM-xx).
       This object is used only for the Far-End modem (with the 
       relevant modemIdx).
       notApplicable - for ASMi-32, ASMi-50
       no -  modem is NOT I-Type so it doesn't have a management 
             link to its pair-modem.
       yes - modem is I-Type so it has a management link to its 
             pair-modem."
      ::= {modemParamEntry 19} 

modemRcvPower  OBJECT-TYPE
      SYNTAX  Integer32
      MAX-ACCESS  read-only
      STATUS  current
      DESCRIPTION
      "The Rx Level of the modem, in dBm.
       Valid values: -99 .. 0.
       255=not applicable. "
      ::= {modemParamEntry 20}
      
modemSwVersion  OBJECT-TYPE
      SYNTAX  Integer32
      MAX-ACCESS  read-only
      STATUS  current
      DESCRIPTION
      "SW version of the modem, multiplied by 100.
	   Example: 115 means SW ver: 1.15
       0 = notApplicable. "
      ::= {modemParamEntry 21}
 
modemLed  OBJECT-TYPE   
      SYNTAX  OCTET STRING 
      MAX-ACCESS  read-only
      STATUS  current
      DESCRIPTION
	  "LEDs status on the card . Each led will be represented by 4 
	   bits where the first 2 bits (left) will specify  the Status :
	   (00=NA, 01=OFF, 10=ON, 11=BLINK),
       and the next two bits (right) will specify the Color :
       (00=GREEN, 01=RED, 10=YELLOW, 11=ORANGE).
       This object is applicable for modems located on a card that contains
       more than one modem. When not applicable 0 will be sent. "
      ::= { modemParamEntry 22}

modemRemoteType  OBJECT-TYPE
      SYNTAX  INTEGER
	      {
		notApplicable     (1),
		unknown           (2),
		sa                (3),
		single            (4),
		double            (5),
		rack              (6),
		quad              (7),
		saSlave           (8),
		fcdIp             (9),
		dxcCard4p        (10), --DXC 4 links 
		dxcCard8p        (11), --DXC 8 links
		lrs52			 (12),
		double4W         (13), -- double with 4 wire.
		asmi52A          (14), -- SA
		fcdIpM           (15),
		mpShdslCard      (16),
		sa4W			 (17), -- SA with 4 wire.
		asmi52L          (18), -- SA Low Cost
		quadEth          (19),
		double4wNew      (20),
		double4wNewEth   (21) 	
	      }
      MAX-ACCESS  read-only
      STATUS  current
      DESCRIPTION
      "Remote modem card type. Not applicable to near - end modems.
       For LRS-52, sa(3)=saMaster."
      ::= {modemParamEntry 23}

modemConfigPhantom OBJECT-TYPE
      SYNTAX  INTEGER
	      {
	      notApplicable (1),
	      off           (2),
		  on            (3),
		  notValid      (4)
	      }
      MAX-ACCESS  read-write
      STATUS  current
      DESCRIPTION
      "Enables to supply electric power to remote devices (SA modem,  
       repeaters), through the current module.
       off - remote devices will not get PS through the current modem.
       on  - remote devices will get PS through the current modem.
       notApplicable - for a modem without a phantom unit.
       notValid - In case the unit exists but is not functioning."
      ::= {modemParamEntry 24}

modemRemoteTestEnable OBJECT-TYPE
      SYNTAX INTEGER {
	            notApplicable (1),
                no   (2),
      		    yes  (3)
		            }
      MAX-ACCESS read-write
      STATUS current
      DESCRIPTION
      "This parameter identifies if the remote Modem allowed to operates 
       tests.
       For Near-End modems this parameter will be ON." 
      ::= {modemParamEntry 25}

modemSwVerString  OBJECT-TYPE
      SYNTAX      DisplayString
      MAX-ACCESS  read-only
      STATUS  current
      DESCRIPTION
      "Display String of the modem SW version.
	   Format: X.      Y       Z         P
	           0..9	   0..99   A,B,E     0..99
		(Z+P are optional.)
		A=alpha, B=beta, E=end of development.
       Examples: 2.23A8 
				 3.4  "
      ::= {modemParamEntry 26}

modemRemoteIdx  OBJECT-TYPE
      SYNTAX  Integer32
      MAX-ACCESS  read-only
      STATUS  current
      DESCRIPTION
      "0 = notApplicable.
       For LRS: 
         The Remote modem index.
         Applicable only for modemRemoteType=double(5) or quad(7). 
       For DXC, LRS-52 and MP:
         - if Remote unit is an LRS Quad card: remote modem index (1..4)
         - if Remote unit is a DXC D8SL card: external port index (1..8).
		 - if Remote unit is an LRS-52 modem: 1..24.
	     - if Remote unit is a MP MSL card: external port index (1..4 or 1..8)."
      ::= {modemParamEntry 27}

modemHwVerString  OBJECT-TYPE
      SYNTAX      DisplayString
      MAX-ACCESS  read-only
      STATUS  current
      DESCRIPTION
      "Display String of the modem HW version."
      ::= {modemParamEntry 28}

modemResetStatistics  OBJECT-TYPE
      SYNTAX  INTEGER
	      {
	    notApplicable (1),
	    off(2),
		on (3)
	      }
      MAX-ACCESS  read-write
      STATUS  current
      DESCRIPTION
      "In the on state all statistics counters (including E1 
       counters) are zeroed.  Upon completion, the value will 
       automatically change to off(2).
       notApplicable - for modems with no statistics support."
      ::= {modemParamEntry 29}

modemMaxRate        OBJECT-TYPE
      SYNTAX  INTEGER
	  {
	  notApplicable (1),
	  r2Mbps        (2),
	  r4Mbps        (3)
	  }
      MAX-ACCESS  read-only
      STATUS  current
      DESCRIPTION
      "Maximum rate supported by the modem "
      ::= {modemParamEntry 30}

modemBoxMaterial        OBJECT-TYPE
      SYNTAX  INTEGER
	  {
	  notApplicable  (1),
	  plastic        (2),
	  metal          (3)
	  }
      MAX-ACCESS  read-only
      STATUS  current
      DESCRIPTION
      "Shape (picture) of modem box is related to box material.
       Applicable for ASMi52 SA "
      ::= {modemParamEntry 31}

modemLowSpeed			OBJECT-TYPE
      SYNTAX  INTEGER
	  {
	  notApplicable (1),
	  no            (2),
	  yes           (3)
	  }
      MAX-ACCESS  read-only
      STATUS  current
      DESCRIPTION
      "This parameter enables working at low rates,
       when working with a serial interface (V.35,X.21) modem
       opposite to a E1/T1 interface modem."
      ::= {modemParamEntry 32}

modemDevicePorts OBJECT-TYPE
      SYNTAX  Integer32
      MAX-ACCESS  read-only
      STATUS  current
      DESCRIPTION
      "The value indicates the existence of optional ports (which are not Line or DTE). 
       The value is a sum of 2**n, where n is a bit assigned to a 
       certain port. For bit assignment see modem's specification.
	   For ASMi-52 SA, the bit assigned for Alarm Relay port is 0, 
	   therefore Agent will return '1' if this optional port exists.
       Value of '0', means that no such optional port exists."
      ::= {modemParamEntry 33}

modemUserName  OBJECT-TYPE
      SYNTAX      DisplayString
      MAX-ACCESS  read-write
      STATUS  current
      DESCRIPTION
      "This object allows the user to configure a name 
      for the selected modem."
      ::= {modemParamEntry 34}

modemRowValidity  OBJECT-TYPE
      SYNTAX  INTEGER
	  {
	  		invalid		(1),
	  		valid		(2)
	  }
      MAX-ACCESS  read-write
      STATUS  current
      DESCRIPTION
      "This parameter defines whether this row is valid or not.
       It is an optional parameter."
      ::= {modemParamEntry 35}

modemTftpCmd  OBJECT-TYPE
      SYNTAX  INTEGER
	  {
	  		noOp		(1),
	  		swdl		(2)
	  }
      MAX-ACCESS  read-write
      STATUS  current
      DESCRIPTION
      "This parameter defines the TFTP Command.
	   After performing the command, the Agent will automatically set
	   this variable to noOp(1)."
      ::= {modemParamEntry 36}


modemAlrBuffer OBJECT IDENTIFIER  ::=  {modem 2}

modemAlrBufTable  OBJECT-TYPE 
      SYNTAX SEQUENCE OF ModemAlrBufEntry
      MAX-ACCESS not-accessible
      STATUS  current
      DESCRIPTION
      "This parameters table is applicable only for modems that are
       not agents."
      ::= { modemAlrBuffer 1 }

modemAlrBufEntry OBJECT-TYPE
      SYNTAX ModemAlrBufEntry
      MAX-ACCESS not-accessible
      STATUS current
	DESCRIPTION  "An entry in table."
	INDEX { modemIdx, modemAlrBufIdx }
      ::= { modemAlrBufTable 1}

ModemAlrBufEntry ::=
      SEQUENCE {
     modemAlrBufIdx          Integer32,
     modemAlrBufCode         Integer32,
     modemAlrBufState        INTEGER,
     modemAlrBufDate         DisplayString,
     modemAlrBufTime         DisplayString,
	 modemAlrBufSysUpTime    TimeTicks
      }

modemAlrBufIdx OBJECT-TYPE
      SYNTAX  Integer32
      MAX-ACCESS  read-only
      STATUS  current
      DESCRIPTION
      "Running index of the alarm buffer table."
      ::= {modemAlrBufEntry 1}

modemAlrBufCode OBJECT-TYPE
      SYNTAX Integer32
      MAX-ACCESS read-only
      STATUS current
      DESCRIPTION
      "The code of the alarm. For text description of each Alarm 
       code see Modem's	specification."
      ::= {modemAlrBufEntry 2}

modemAlrBufState OBJECT-TYPE
      SYNTAX INTEGER  { off(2),
	                    on(3)
					  }
      MAX-ACCESS read-only
      STATUS current
      DESCRIPTION
      "The new status of the alarm."
      ::= {modemAlrBufEntry 3}

modemAlrBufDate OBJECT-TYPE
      SYNTAX DisplayString
      MAX-ACCESS read-only
      STATUS current
      DESCRIPTION
      "The Date at which the alarm has occurred. The format
       is according to the entered systemDate format."
      ::= {modemAlrBufEntry 4}

modemAlrBufTime OBJECT-TYPE
      SYNTAX DisplayString
      MAX-ACCESS read-only
      STATUS current
      DESCRIPTION
      "The time stamp at which the alarm has occurred. The format
       is hh:mm:ss "
      ::= {modemAlrBufEntry 5}


modemAlrBufSysUpTime  OBJECT-TYPE
      SYNTAX 	      TimeTicks
      MAX-ACCESS      read-only
      STATUS          current
      DESCRIPTION
      "The value of sysUpTime at the time the alarm has occurred.
      This object is applicable only for products that cannot support 
      calendar date (modemAlrBufDate) and time (modemAlrBufTime)
      When not applicable, this object contains a zero value" 
      ::= {modemAlrBufEntry 6}


modemStatistics OBJECT IDENTIFIER  ::=  {modem 3}

modemGeneralTable  OBJECT-TYPE
      SYNTAX SEQUENCE OF ModemGeneralEntry
      MAX-ACCESS not-accessible
      STATUS  current
      DESCRIPTION
      "The IMOD General data Table. The data is specific to each 
       modem."
       ::= { modemStatistics 1 }

modemGeneralEntry OBJECT-TYPE
      SYNTAX ModemGeneralEntry
      MAX-ACCESS not-accessible
      STATUS current
      DESCRIPTION
      "An entry in the modemGeneralTable. This entry is per modem. 
       Each modem has a specific index, which identifies it."
      INDEX {modemIdx}
      ::= { modemGeneralTable 1}

ModemGeneralEntry ::=
      SEQUENCE {
	  modemCurrentElapsedTime Integer32,
	  modemValidIntervals     Integer32
      }


modemCurrentElapsedTime	 OBJECT-TYPE
	  SYNTAX  Integer32 (0..899)
      MAX-ACCESS  read-only
      STATUS  current
      DESCRIPTION
	  "The number of seconds that have elapsed since the beginning
	   of the current error-measurement period."
	  ::= {modemGeneralEntry 1}

modemValidIntervals	 OBJECT-TYPE
	  SYNTAX  Integer32 (0..96)
      MAX-ACCESS  read-only
      STATUS  current
      DESCRIPTION
	  "The number of previous intervals for which data was 
	   collected.
	   The value will be 96 unless the interface was brought on-line 
	   within the last 24 hours, in which case the value will be the 
	   number of complete 15 minute intervals since the interface 
	   has been online."
	  ::= {modemGeneralEntry 2}


modemIntervalTable  OBJECT-TYPE
      SYNTAX SEQUENCE OF ModemIntervalEntry
      MAX-ACCESS not-accessible
      STATUS  current
      DESCRIPTION
      "The IMOD Interval Table. The data is specific to each 
       modem."
       ::= { modemStatistics 2 }

modemIntervalEntry OBJECT-TYPE
      SYNTAX ModemIntervalEntry
      MAX-ACCESS not-accessible
      STATUS current
      DESCRIPTION
      "An entry in the modemIntervalTable. This entry is per modem 
       and per interval selected." 
      INDEX {modemIdx, modemIntervalNumber}
      ::= { modemIntervalTable 1}

ModemIntervalEntry ::=
      SEQUENCE {
	  modemIntervalNumber     Integer32,
	  modemSyncLoss           Integer32,
	  modemLineQuality        INTEGER,
	  modemLineUtility        Integer32,
	  modemRTS                Integer32,
	  modemCD                 Integer32,
	  modemBertResult   DisplayString,
	  modemBpvError      OCTET STRING,
	  modemFoError       OCTET STRING
      }

modemIntervalNumber	 OBJECT-TYPE
	  SYNTAX  Integer32 (1..96)
      MAX-ACCESS  read-only
      STATUS  current
      DESCRIPTION
	  "The number between 1 and 96, where 1 is the most recently 
	   completed 15 minute interval and 96 is the least recently 
	   completed 15 minutes interval (assuming that all 96 
	   intervals are valid). Maximum valid number is 
	   modemValidIntervals."
	  ::= {modemIntervalEntry 1}

modemSyncLoss	 OBJECT-TYPE
	  SYNTAX  Integer32 (0..101)
      MAX-ACCESS  read-only
      STATUS  current
      DESCRIPTION
	  "Percent of interval, SyncLoss signal is ON.
	   101 = notApplicable/unknown. "
	  ::= {modemIntervalEntry 2}

modemLineQuality   OBJECT-TYPE
	  SYNTAX  INTEGER
	      {
		   notApplicable (1),
		   bad  (2),
		   mid  (3),
		   good (4),
		   unknown (5),
		   syncLoss(6)
	      }
      MAX-ACCESS  read-only
      STATUS  current
      DESCRIPTION
      "Quality of Line for the selected modem, in the selected valid 
       interval."
	  ::= {modemIntervalEntry 3}

modemLineUtility	 OBJECT-TYPE
	  SYNTAX  Integer32 (0..101)
      MAX-ACCESS  read-only
      STATUS  current
      DESCRIPTION
	  "Percent of interval, Line is utilized.
	   101 = notApplicable/unknown. "
	  ::= {modemIntervalEntry 4}

modemRTS	 OBJECT-TYPE
	  SYNTAX  Integer32 (0..101)
      MAX-ACCESS  read-only
      STATUS  current
      DESCRIPTION
	  "Percent of interval, RTS signal is ON.
	   101 = notApplicable/unknown. "
	  ::= {modemIntervalEntry 5}

modemCD	 OBJECT-TYPE
	  SYNTAX  Integer32 (0..101)
      MAX-ACCESS  read-only
      STATUS  current
      DESCRIPTION
	  "Percent of interval, CD signal is ON.
	   101 = notApplicable/unknown. "
	  ::= {modemIntervalEntry 6}

modemBertResult	 OBJECT-TYPE
	  SYNTAX  DisplayString 
      MAX-ACCESS  read-only
      STATUS  current
      DESCRIPTION
	  "Result of BERT for the selected modem, in the selected 
	   valid interval."
	  ::= {modemIntervalEntry 7}

modemBpvError OBJECT-TYPE
      SYNTAX OCTET STRING (SIZE(0..1)) 
      MAX-ACCESS read-only
      STATUS current
      DESCRIPTION
      "BPV Error.
       The Octet will be built as follows:
       MSB 7  6  5  4  3  2  1  0 LSB
           |__|  |______________|
         y=0..3      x=0..63
         
         
         BPV Error = x * (10**y)
         
       An Agent that does not support this object will send Size=0."
      ::= {modemIntervalEntry 8}

modemFoError OBJECT-TYPE
      SYNTAX OCTET STRING (SIZE(0..1)) 
      MAX-ACCESS read-only
      STATUS current
      DESCRIPTION
      "FO Error.
       The Octet will be built as follows:
       MSB 7  6  5  4  3  2  1  0 LSB
           |__|  |______________|
         y=0..3      x=0..63
         
         
         FO Error = x * (10**y)
         
       An Agent that does not support this object will send Size=0."
      ::= {modemIntervalEntry 9}



modmPrt  OBJECT IDENTIFIER  ::=  {modmSys 4}


-- Supervisory Port (SP) 

modmSpPort  OBJECT IDENTIFIER  ::=  {modmPrt 1}

modmPrtSpTable  OBJECT-TYPE
      SYNTAX SEQUENCE OF ModmPrtSpEntry
      MAX-ACCESS not-accessible
      STATUS  current
      DESCRIPTION
      "Configuration parameters of the Local or Remote Modem
       Supervisory Ports. The port will be identified by its 
       specific ifIndex value."
       ::= { modmSpPort 1 }

modmPrtSpEntry OBJECT-TYPE
      SYNTAX ModmPrtSpEntry
      MAX-ACCESS not-accessible
      STATUS current
	DESCRIPTION  "An entry in table."
	INDEX {ifIndex}
      ::= { modmPrtSpTable 1}

ModmPrtSpEntry ::=
      SEQUENCE {
	  modmPrtSpUsage       INTEGER,
	  modmPrtSpRate        INTEGER,
	  modmPrtSpDataBits    INTEGER,
	  modmPrtSpParity      INTEGER,
	  modmPrtSpInterface   INTEGER,
	  modmPrtSpCTS		   INTEGER,
	  modmPrtSpDcdDelay	   INTEGER,
	  modmPrtSpDsr		   INTEGER
      }

modmPrtSpUsage OBJECT-TYPE
      SYNTAX  INTEGER
	      {
		nmsSlip   (2),
		terminal  (3),
		agentSlip (4),
		nmsPpp    (5),
		agentPpp  (6)
	      }
      MAX-ACCESS  read-write
      STATUS  current
      DESCRIPTION
      "This attribute indicates what is the usage of the port."
      ::= { modmPrtSpEntry 1}

modmPrtSpRate     OBJECT-TYPE
      SYNTAX  INTEGER
	      {
        auto      (1),
        s300bps   (2),
        s1200bps  (3),
        s2400bps  (4),
        s4800bps  (5),
        s9600bps  (6)
	      }
      MAX-ACCESS  read-write
      STATUS  current
      DESCRIPTION
      "This attribute indicates the operation rate (speed) of the 
       port.
       auto - automatic rate selection, by the agent."
      ::= {modmPrtSpEntry 2}

modmPrtSpDataBits OBJECT-TYPE
      SYNTAX  INTEGER
	      {
        dataBits7 (1),
        dataBits8 (2)
	      }
      MAX-ACCESS  read-write
      STATUS  current
      DESCRIPTION
      "This attribute indicates the number of data bits in the 
       word format."
      ::= {modmPrtSpEntry 3}

modmPrtSpParity OBJECT-TYPE
      SYNTAX  INTEGER
	      {
        none  (1),
        odd   (2),
        even  (3)
	      }
      MAX-ACCESS  read-write
      STATUS  current
      DESCRIPTION
      "This attribute indicates the parity mode in async frame"
      ::= { modmPrtSpEntry 4}

modmPrtSpInterface OBJECT-TYPE
      SYNTAX  INTEGER
	      {
          dce  (1),
          dte  (2)
	      }
      MAX-ACCESS  read-write
      STATUS  current
      DESCRIPTION
      "This attribute indicates the supervisory port interface.
       dce - the modem appears as a DCE for the SP port.
       dte - the modem operates as a DTE, for connection via modem,
             for the SP port."
      ::= { modmPrtSpEntry 5}

modmPrtSpCTS OBJECT-TYPE
      SYNTAX  INTEGER
	      {
          on            (2),
          rts           (3)
	      }
      MAX-ACCESS  read-write
      STATUS  current
      DESCRIPTION
	  "CTS line state. "
      ::= {modmPrtSpEntry 6}

modmPrtSpDcdDelay OBJECT-TYPE
      SYNTAX  INTEGER
	      {
          d0   (2),
          d10  (3),
		  d50  (4),
		  d100 (5),
		  d200 (6),
		  d300 (7)
	      }
      MAX-ACCESS  read-write
      STATUS  current
      DESCRIPTION
	  "DCD delay in msec. 
	   d10 = delay of 10msec."
      ::= { modmPrtSpEntry 7}

modmPrtSpDsr OBJECT-TYPE
      SYNTAX  INTEGER
	      {
          on   (2),
          dtr  (3)
	      }
      MAX-ACCESS  read-write
      STATUS  current
      DESCRIPTION
	  "DSR line state."
      ::= {modmPrtSpEntry 8}

-- Ds1 Port (T1/E1)

modmDs1Port  OBJECT IDENTIFIER  ::=  {modmPrt 2}

modmPrtDs1Table  OBJECT-TYPE
      SYNTAX SEQUENCE OF ModmPrtDs1Entry
      MAX-ACCESS not-accessible
      STATUS  current
      DESCRIPTION
      "Statistics parameters of the Local and Remote modem Ds1 ports.
       The port will be identified by its specific ifIndex value."
       ::= { modmDs1Port 1 }

modmPrtDs1Entry OBJECT-TYPE
      SYNTAX ModmPrtDs1Entry
      MAX-ACCESS not-accessible
      STATUS current
	DESCRIPTION  "An entry in table."
	INDEX {ifIndex}
      ::= { modmPrtDs1Table 1}

ModmPrtDs1Entry ::=
      SEQUENCE {
	  modmPrtDs1HdslPriorityBumping OCTET STRING,
	  modmPrtDs1Sync        INTEGER,
	  modmPrtDs1BpvLastMin    Gauge32,
	  modmPrtDs1BpvMax        Gauge32,
	  modmPrtDs1LineLength    INTEGER,
	  modmPrtDs1CRCAvgError	  Gauge32,
	  modmPrtDs1DtsToRemote   INTEGER						 
      }

modmPrtDs1HdslPriorityBumping	 OBJECT-TYPE
	  SYNTAX  OCTET STRING (SIZE(4))
      MAX-ACCESS  read-write
      STATUS  deprecated
      DESCRIPTION
	  "The 4 bytes represent the 32 time slots of the E1 frame.
	   Each bit can be set to one, making the corresponding time
	   slot a HIGH priority. Bits 16 and 32 cannot be modified by the
	   user. The maximum number of HIGH priority time slots is 16.
	   The default value is LOW, i.e., 0. This variable is RO in the
	   Remote unit."
--  DEFVAL  { 0 }
	  ::= { modmPrtDs1Entry 1 }

modmPrtDs1Sync	 OBJECT-TYPE
	  SYNTAX  INTEGER { itu(2),
	                    fast(3),
						s62411(4)
					  }
      MAX-ACCESS  read-write
      STATUS  current
      DESCRIPTION
	  "The standard used for the time required for the E1 port to return
	   to normal operation after local loss of synchronization. Default:
	   itu(2)."
--  DEFVAL  { 2 }
	  ::= { modmPrtDs1Entry 2 }

modmPrtDs1BpvLastMin	 OBJECT-TYPE
	  SYNTAX  Gauge32
      MAX-ACCESS  read-only
      STATUS  current
      DESCRIPTION
	  "This object is applicable only for an E1 active port.
	   It provides the number of BPV (BiPolar Violation) events 
	   detected during the last	minute."
	  ::= { modmPrtDs1Entry 3 }

modmPrtDs1BpvMax	 OBJECT-TYPE
	  SYNTAX  Gauge32
      MAX-ACCESS  read-only
      STATUS  current
      DESCRIPTION
	  "This object is applicable only for an E1 active port.
	   It provides the maximal number of BPV (BiPolar Violation) 
	   events (per minute), detected during the worst minute."
	  ::= { modmPrtDs1Entry 4 }

modmPrtDs1LineLength  OBJECT-TYPE
      SYNTAX  INTEGER
       {
		unknown      (1),
        len0p133ft   (2),
        len134p266ft (3),
        len267p399ft (4),
        len400p533ft (5),
        len534p655ft (6),
        fcc68        (7),
		notApplicable(255)
	      }
      MAX-ACCESS  read-write
      STATUS  current
      DESCRIPTION
      "This attribute is the line length mask parameter used only 
       for T1/DSU interfaces.
       len400p533ft=length range: 400ft to 533ft 
       'fcc68' - provides compliance with the FCC 68.308 Option A
                 output pulse mask. "
   ::= { modmPrtDs1Entry 5 }

modmPrtDs1CRCAvgError OBJECT-TYPE
      SYNTAX Gauge32 
      MAX-ACCESS  read-only
      STATUS  current
      DESCRIPTION
      "Counts the average number of CRC error events per second.
       The average is updated every second"
      ::= { modmPrtDs1Entry 6 }

modmPrtDs1DtsToRemote  OBJECT-TYPE
      SYNTAX  INTEGER
      {
      disable		(2),
      enable		(3)
	  }
      MAX-ACCESS  read-write
      STATUS  current
      DESCRIPTION
      "This attribute indicates whether DTS (Dedicated TS)
       is transmitted to remote unit."
   ::= { modmPrtDs1Entry 7 }


modmHdslPort  OBJECT IDENTIFIER  ::=  {modmPrt 3}

modmPrtHdslCurrentTable  OBJECT-TYPE
      SYNTAX SEQUENCE OF ModmPrtHdslCurrentEntry
      MAX-ACCESS not-accessible
      STATUS  current
      DESCRIPTION
      "The HDSL Current Table. The data collected is for the current
       15-minute interval."
       ::= { modmHdslPort 1 }

modmPrtHdslCurrentEntry OBJECT-TYPE
      SYNTAX ModmPrtHdslCurrentEntry
      MAX-ACCESS not-accessible
      STATUS current
      DESCRIPTION
      "An entry in the HDSL Current Table. This entry is per HDSL 
       interface (LOOP1 or LOOP2). Each modem (Central/Remote) has
       a specific ifIndex value for the port, which identifies it.
       For FDSL it is used for any xDSL interface."
      INDEX {ifIndex}
      ::= { modmPrtHdslCurrentTable 1}

ModmPrtHdslCurrentEntry ::=
      SEQUENCE {
	  modmPrtHdslCurrentElapsedTime Integer32,
	  modmPrtHdslCurrentESs           Gauge32,
	  modmPrtHdslCurrentSESs          Gauge32,
	  modmPrtHdslCurrentBBEs          Gauge32,
	  modmPrtHdslCurrentUASs          Gauge32,
	  modmPrtHdslCurrentNoiseMargin	Integer32,
	  modmPrtHdslCurrentAttenuation	Integer32
      }

modmPrtHdslCurrentElapsedTime	 OBJECT-TYPE
	  SYNTAX  Integer32 (0..899)
      MAX-ACCESS  read-only
      STATUS  current
      DESCRIPTION
	  "The number of seconds that have elapsed since the beginning
	   of the current error-measurement period."
	  ::= { modmPrtHdslCurrentEntry 1 }

modmPrtHdslCurrentESs	 OBJECT-TYPE
	  SYNTAX  Gauge32
      MAX-ACCESS  read-only
      STATUS  current
      DESCRIPTION
	  "The number of Errored Seconds encountered by an HDSL 
	   interface in the current 15 minute interval. An Errored 
	   Second is any second containing one or more Errored Blocks 
	   or an occurrence of an SDP."
	  ::= { modmPrtHdslCurrentEntry 2 }

modmPrtHdslCurrentSESs	 OBJECT-TYPE
	  SYNTAX  Gauge32
      MAX-ACCESS  read-only
      STATUS  current
      DESCRIPTION
	  "The number of Severely Errored Seconds encountered by an HDSL 
	   interface in the current 15 minute interval. An SES is any 
	   second containing more than 30% Errored Blocks (50 blocks) or 
	   one or more SDPs."
	  ::= { modmPrtHdslCurrentEntry 3 }

modmPrtHdslCurrentBBEs	 OBJECT-TYPE
	  SYNTAX  Gauge32
      MAX-ACCESS  read-only
      STATUS  current
      DESCRIPTION
	  "The number of Background Block Errors encountered by an HDSL 
	   interface in the current 15 minute interval. A BBE is an 
	   errored block not occurring as part of an SES."
	  ::= { modmPrtHdslCurrentEntry 4 }

modmPrtHdslCurrentUASs	 OBJECT-TYPE
	  SYNTAX  Gauge32
      MAX-ACCESS  read-only
      STATUS  current
      DESCRIPTION
	  "The number of Unavailable Seconds encountered by an HDSL 
	   interface in the current 15 minute interval. A UAS is any 
	   second in which a failed signal state exists. A failure state 
	   is declared when 10 consecutive SESs occur, and is cleared 
	   after 10 consecutive seconds free of an SES."
	  ::= { modmPrtHdslCurrentEntry 5 }

modmPrtHdslCurrentNoiseMargin   OBJECT-TYPE
	  SYNTAX  Integer32 
      MAX-ACCESS  read-only
      STATUS  current
      DESCRIPTION
	  "The current noise margin in DB.
	   This object is not an accumulative one, therefore
	   it's value will appear only in this table."
	  ::= { modmPrtHdslCurrentEntry 6 }

modmPrtHdslCurrentAttenuation   OBJECT-TYPE
	  SYNTAX  Integer32 
      MAX-ACCESS  read-only
      STATUS  current
      DESCRIPTION
	  "The current attenuation in DB.
	   This object is not an accumulative one, therefore
	   it's value will appear only in this table."
	  ::= { modmPrtHdslCurrentEntry 7 }



modmPrtHdslIntervalTable  OBJECT-TYPE
      SYNTAX SEQUENCE OF ModmPrtHdslIntervalEntry
      MAX-ACCESS not-accessible
      STATUS  current
      DESCRIPTION
      "The HDSL Interval Table. The data collected is for the last 96
       completed 15-minute intervals."
       ::= { modmHdslPort 2 }

modmPrtHdslIntervalEntry OBJECT-TYPE
      SYNTAX ModmPrtHdslIntervalEntry
      MAX-ACCESS not-accessible
      STATUS current
      DESCRIPTION
      "An entry in the HDSL Interval Table. This entry is per an HDSL 
       interface (LOOP1 or LOOP2) and per 15 minute interval. The 
       port and unit (Central/Remote) is identified by its specific 
       ifIndex value.
       For FDSL it is used for any xDSL interface."
      INDEX {ifIndex, modmPrtHdslIntervalNumber}
      ::= { modmPrtHdslIntervalTable 1}

ModmPrtHdslIntervalEntry ::=
      SEQUENCE { 
	  modmPrtHdslIntervalNumber        Integer32,
	  modmPrtHdslIntervalESs           Gauge32,
	  modmPrtHdslIntervalSESs          Gauge32,
	  modmPrtHdslIntervalBBEs          Gauge32,
	  modmPrtHdslIntervalUASs          Gauge32,
	  modmPrtHdslIntervalESR           Integer32,
	  modmPrtHdslIntervalSESR          Integer32,
	  modmPrtHdslIntervalBBER          Integer32,
	  modmPrtHdslIntervalValidData     TruthValue
      }

modmPrtHdslIntervalNumber	 OBJECT-TYPE
	  SYNTAX  Integer32 (1..96)
      MAX-ACCESS  read-only
      STATUS  current
      DESCRIPTION
	  "The number between 1 and 96, where 1 is the most recently completed
	   15 minute interval and 96 is the least recently completed 15 minutes
	   interval (assuming that all 96 intervals are valid)."
	  ::= { modmPrtHdslIntervalEntry 1 }

modmPrtHdslIntervalESs	 OBJECT-TYPE
	  SYNTAX  Gauge32
      MAX-ACCESS  read-only
      STATUS  current
      DESCRIPTION
	  "The number of Errored Seconds encountered by an HDSL interface in
	   one of the previous 96, individual 15 minute, intervals."
	  ::= { modmPrtHdslIntervalEntry 2 }

modmPrtHdslIntervalSESs	 OBJECT-TYPE
	  SYNTAX  Gauge32
      MAX-ACCESS  read-only
      STATUS  current
      DESCRIPTION
	  "The number of Severely Errored Seconds encountered by an HDSL interface in
	   one of the previous 96, individual 15 minute, intervals."
	  ::= { modmPrtHdslIntervalEntry 3 }

modmPrtHdslIntervalBBEs	 OBJECT-TYPE
	  SYNTAX  Gauge32
      MAX-ACCESS  read-only
      STATUS  current
      DESCRIPTION
	  "The number of Background Block Errors encountered by an HDSL interface in
	   one of the previous 96, individual 15 minute, intervals."
	  ::= { modmPrtHdslIntervalEntry 4 }

modmPrtHdslIntervalUASs	 OBJECT-TYPE
	  SYNTAX  Gauge32
      MAX-ACCESS  read-only
      STATUS  current
      DESCRIPTION
	  "The number of Unavailable Seconds encountered by an HDSL interface in
	   one of the previous 96, individual 15 minute, intervals."
	  ::= { modmPrtHdslIntervalEntry 5 }

modmPrtHdslIntervalESR	 OBJECT-TYPE
	  SYNTAX  Integer32 (0..100)
      MAX-ACCESS  read-only
      STATUS  current
      DESCRIPTION
	  "The ratio of ESs to 900 seconds, encountered by an HDSL interface in
	   one of the previous 96, individual 15 minute, intervals."
	  ::= { modmPrtHdslIntervalEntry 6 }

modmPrtHdslIntervalSESR	 OBJECT-TYPE
	  SYNTAX  Integer32 (0..100)
      MAX-ACCESS  read-only
      STATUS  current
      DESCRIPTION
	  "The ratio of SESs to 900 seconds, encountered by an HDSL interface in
	   one of the previous 96, individual 15 minute, intervals."
	  ::= { modmPrtHdslIntervalEntry 7 }

modmPrtHdslIntervalBBER	 OBJECT-TYPE
	  SYNTAX  Integer32 (0..100)
      MAX-ACCESS  read-only
      STATUS  current
      DESCRIPTION
	  "The ratio of BBEs to 900 seconds, encountered by an HDSL interface in
	   one of the previous 96, individual 15 minute, intervals."
	  ::= { modmPrtHdslIntervalEntry 8 }

modmPrtHdslIntervalValidData OBJECT-TYPE
      SYNTAX TruthValue
      MAX-ACCESS read-only
      STATUS current
      DESCRIPTION
      "This variable indicates if the data for this interval is valid."
      ::= { modmPrtHdslIntervalEntry 9 }


modmPrtHdslTotalTable  OBJECT-TYPE
      SYNTAX SEQUENCE OF ModmPrtHdslTotalEntry
      MAX-ACCESS not-accessible
      STATUS  current
      DESCRIPTION
      "The HDSL Total Table. The data collected is the cumulative 
       sum of the various statistics for the 24 hour period 
       preceding the current interval."
       ::= { modmHdslPort 3 }

modmPrtHdslTotalEntry OBJECT-TYPE
      SYNTAX ModmPrtHdslTotalEntry
      MAX-ACCESS not-accessible
      STATUS current
      DESCRIPTION
      "An entry in the HDSL Total Table. This entry is per an HDSL 
       interface (LOOP1 or LOOP2). The port and unit (Central/Remote) 
       is identified by its specific ifIndex value.
       For FDSL it is used for any xDSL interface."
      INDEX {ifIndex}
      ::= { modmPrtHdslTotalTable 1}

ModmPrtHdslTotalEntry ::=
      SEQUENCE { 
	  modmPrtHdslTotalValidIntervals Integer32,
	  modmPrtHdslTotalESs              Gauge32,
	  modmPrtHdslTotalSESs             Gauge32,
	  modmPrtHdslTotalBBEs             Gauge32,
	  modmPrtHdslTotalUASs             Gauge32
      }

modmPrtHdslTotalValidIntervals	 OBJECT-TYPE
	  SYNTAX  Integer32 (0..96)
      MAX-ACCESS  read-only
      STATUS  current
      DESCRIPTION
	  "The number of previous intervals for which valid data was 
	   collected.
	   The value will be 96 unless the interface was brought on-line 
	   within the last 24 hours, in which case the value will be the 
	   number of complete 15 minute intervals since the interface 
	   has been online."
	  ::= { modmPrtHdslTotalEntry 1 }

modmPrtHdslTotalESs	 OBJECT-TYPE
	  SYNTAX  Gauge32
      MAX-ACCESS  read-only
      STATUS  current
      DESCRIPTION
	  "The number of Errored Seconds encountered by an HDSL 
	   interface in	the previous 24 hour interval."
	  ::= { modmPrtHdslTotalEntry 2 }

modmPrtHdslTotalSESs	 OBJECT-TYPE
	  SYNTAX  Gauge32
      MAX-ACCESS  read-only
      STATUS  current
      DESCRIPTION
	  "The number of Severely Errored Seconds encountered by an HDSL 
	   interface in	the previous 24 hour interval."
	  ::= { modmPrtHdslTotalEntry 3 }

modmPrtHdslTotalBBEs	 OBJECT-TYPE
	  SYNTAX  Gauge32
      MAX-ACCESS  read-only
      STATUS  current
      DESCRIPTION
	  "The number of Background Block Errors encountered by an HDSL 
	   interface in	the previous 24 hour interval."
	  ::= { modmPrtHdslTotalEntry 4 }

modmPrtHdslTotalUASs	 OBJECT-TYPE
	  SYNTAX  Gauge32
      MAX-ACCESS  read-only
      STATUS  current
      DESCRIPTION
	  "The number of Unavailable Seconds encountered by an HDSL 
	   interface in the previous 24 hour interval."
	  ::= { modmPrtHdslTotalEntry 5 }


modmPrtHdslTable  OBJECT-TYPE
      SYNTAX SEQUENCE OF ModmPrtHdslEntry
      MAX-ACCESS not-accessible
      STATUS  current
      DESCRIPTION
      "The HDSL Table."
       ::= { modmHdslPort 4 }

modmPrtHdslEntry OBJECT-TYPE
      SYNTAX ModmPrtHdslEntry
      MAX-ACCESS not-accessible
      STATUS current
      DESCRIPTION
      "An entry in the HDSL Table. The port and unit (Central/Remote) 
       is identified by its specific modmPrtHdslIndex value."
      INDEX {modmPrtHdslIndex}
      ::= { modmPrtHdslTable 1}

ModmPrtHdslEntry ::=
      SEQUENCE { 
	  modmPrtHdslIndex		     		Integer32,
	  modmPrtHdslDedicatedTs     		Integer32,
	  modmPrtHdslPriorityBumping 		OCTET STRING,
      modmPrtHdslMngProtocol     		INTEGER, 
      modmPrtHdslRoutProtocol    		INTEGER, 
      modmPrtHdslInbandMngRate 	 		INTEGER,
	  modmPrtHdslPriorityBumpingEnable	INTEGER,
	  modmPrtHdslPriorityBumpingTimeout	Integer32
	  }

modmPrtHdslIndex OBJECT-TYPE
      SYNTAX Integer32
      MAX-ACCESS read-only
      STATUS current
      DESCRIPTION
      "The HDSL port index. In some cases it can equal ifIndex." 
      ::= { modmPrtHdslEntry 1}

modmPrtHdslDedicatedTs	 OBJECT-TYPE
	  SYNTAX  Integer32 (0..255)
      MAX-ACCESS  read-only
      STATUS  current
      DESCRIPTION
	  "The HDSL Current Dedicated TS.
	   Valid values: 0..31.
	   255 = None (no dedicated TS)."
	  ::= { modmPrtHdslEntry 2 } 

modmPrtHdslPriorityBumping	 OBJECT-TYPE
	  SYNTAX  OCTET STRING (SIZE(4))
      MAX-ACCESS  read-write
      STATUS  current
      DESCRIPTION
	  "The 4 bytes represent time slots 0..31 of the E1 frame.
	   Each bit can be set to '1', making the corresponding time slot a HIGH priority.
	   Bit 0 is always HIGH (cannot be modified by the user).
	   The maximum number of HIGH priority time slots is: 16 for E1 ; 13 for T1 
	   (including TS0).
	   The default value is LOW, i.e., 0."
--  DEFVAL  { 0 }
	  ::= { modmPrtHdslEntry 3 }

modmPrtHdslMngProtocol	 OBJECT-TYPE
	  SYNTAX  INTEGER {
              off         (2),
              dedicatedTs (4),
              dedicatedPpp(5),
              dedicatedFr (6)
                        }
      MAX-ACCESS  read-write
      STATUS  current
      DESCRIPTION
	  "A unique number to identify an Inband management over the 
       link."
	  ::= { modmPrtHdslEntry 4 } 

modmPrtHdslRoutProtocol  OBJECT-TYPE
      SYNTAX  INTEGER
       {
             notApplicable (1),
             none          (2),  
             proprietary   (3),
             rip2          (4)
       }
      MAX-ACCESS  read-write
      STATUS  current
      DESCRIPTION
      "Inband Mng Routing Protocol of the port.
       When modmPrtHdslMngProtocol is 'dedicatedPpp'-'proprietary' and
                                               'rip2' are applicable.
       For other values  - only 'proprietary' is applicable."             
      ::= {modmPrtHdslEntry 5}

modmPrtHdslInbandMngRate  OBJECT-TYPE
      SYNTAX  INTEGER
       {
          notApplicable(1),
          r4k   (2),
          r8k   (3),
          r12k  (4),
          r16k  (5),
          r32k  (6),
          r64k  (7)
       }
      MAX-ACCESS  read-write
      STATUS  current
      DESCRIPTION
      "A unique number to identify the rate of the Inband management.
       It is applicable only when modmPrtHdslDedicatedTs <> (255 Or 0)."
      ::= {modmPrtHdslEntry 6}

modmPrtHdslPriorityBumpingEnable  OBJECT-TYPE
      SYNTAX  INTEGER
       {
          no	(2),
          yes	(3)
       }
      MAX-ACCESS  read-write
      STATUS  current
      DESCRIPTION
      "This attribute indicates the Priority Bumping Mode.
       It is relevant only for 4W interfaces."
      ::= { modmPrtHdslEntry 7}

modmPrtHdslPriorityBumpingTimeout	 OBJECT-TYPE
	  SYNTAX  Integer32
      MAX-ACCESS  read-write
      STATUS  current
      DESCRIPTION
	  "This attribute indicates the Priority Bumping Timeout in minutes.
	   It is relevant only for 4W interfaces (2 lines of 2W each).
	   Upon failure of one of the 2W lines,
	   Timeout is the time period that the agent should wait
	   until moving the traffic to the working 2W line."
	  ::= { modmPrtHdslEntry 8 }


-- DTE (User) Port  

modmDtePort  OBJECT IDENTIFIER  ::=  {modmPrt 4}

modmPrtDteTable  OBJECT-TYPE
      SYNTAX SEQUENCE OF ModmPrtDteEntry
      MAX-ACCESS not-accessible
      STATUS  current
      DESCRIPTION
      "Configuration parameters of the Master and Slave Modem DTE 
       Ports. The port and unit (Master/Slave) is identified by 
       its specific modmPrtDteIndex value."
       ::= { modmDtePort 1 }

modmPrtDteEntry OBJECT-TYPE
      SYNTAX ModmPrtDteEntry
      MAX-ACCESS not-accessible
      STATUS current
	DESCRIPTION  "An entry in table."
	INDEX {modmPrtDteIndex}
      ::= { modmPrtDteTable 1}

ModmPrtDteEntry ::=
      SEQUENCE {
	  modmPrtDteIndex		   Integer32,
	  modmPrtDteProtocol       INTEGER,
	  modmPrtDteDataBits       INTEGER,
	  modmPrtDteStopBits       INTEGER,
	  modmPrtDteRate           INTEGER,
	  modmPrtDteCtsDelay       INTEGER,
	  modmPrtDteParity         INTEGER,
	  modmPrtDteIfType         INTEGER,
	  modmPrtDteRlbEnable      INTEGER,
	  modmPrtDteAlbEnable      INTEGER,
	  modmPrtDteRtsDcdEnable   INTEGER,
	  modmPrtDteDsrDtrEnable   INTEGER,
	  modmPrtDteSignaling      OCTET STRING,
      modmPrtDteLoops		   INTEGER,
      modmPrtDteTests		   Integer32,
	  modmPrtDteClearAllTests  INTEGER,
	  modmPrtDteBertResult     DisplayString,
	  modmPrtDteErrCorrect     INTEGER,
	  modmPrtDteV54DigitalTest	   		INTEGER,	
	  modmPrtDteV54DigitalTestStatus  	INTEGER,	
	  modmPrtDteTestTimeOut	   Integer32,
	  modmPrtDteAlarmForwarding	 INTEGER	
      }

modmPrtDteIndex OBJECT-TYPE
      SYNTAX Integer32
      MAX-ACCESS read-only
      STATUS current
      DESCRIPTION
      "The DTE port index." 
      ::= { modmPrtDteEntry 1}

modmPrtDteProtocol OBJECT-TYPE
      SYNTAX INTEGER {
                sync  (2),
                async (3)
		            }
      MAX-ACCESS read-write
      STATUS current
      DESCRIPTION
      "The DTE port Protocol." 
      ::= { modmPrtDteEntry 2}

modmPrtDteDataBits OBJECT-TYPE
      SYNTAX INTEGER {
        dataBits6  (1),
        dataBits7  (2),
        dataBits8  (3),
        dataBits9  (4),
        dataBits10 (5),
        dataBits11 (6),
        dataBits5  (7)
		}
      MAX-ACCESS read-write
      STATUS current
      DESCRIPTION
      "The DTE number of data bits." 
      ::= { modmPrtDteEntry 3}

modmPrtDteStopBits OBJECT-TYPE
      SYNTAX INTEGER {
          stopBits1Bit      (1),
          stopBits1dot5Bits (2),
          stopBits2Bits     (3)
		            }
      MAX-ACCESS read-write
      STATUS current
      DESCRIPTION
      "The DTE minimum number of stop bits in the tx async frame." 
      ::= { modmPrtDteEntry 4}

modmPrtDteRate OBJECT-TYPE
      SYNTAX INTEGER {
        r300bps      (1),
        r600bps      (2),
        r1200bps     (3),
        r2400bps     (4),
        r4800bps     (5),
        r9600bps     (6),
        r14400bps    (7),
	    r16000bps    (8),
        r19200bps    (9),
        r28800bps   (10),
        r32000bps   (11),
        r38400bps   (12),
        r48000bps   (13),
        r56000bps   (14),
	    r57600bps   (15),
        r64000bps   (16),
        r72000bps   (17),
        r96000bps   (18),
        r112000bps  (19),
        r115200bps  (20),
        r128Kbps    (21),
        r144Kbps    (22),
        r192Kbps    (23),
        r256Kbps    (24),
        r320Kbps    (25),
        r384Kbps    (26),
        r448Kbps    (27),
        r512Kbps    (28),
        r576Kbps    (29),
        r640Kbps    (30),
        r704Kbps    (31),
        r768Kbps    (32),
		r1024Kbps   (33),
		r1536Kbps   (34),
		r1544Kbps   (35),
		r2048Kbps   (36),
		e1          (37),
		t1          (38),
		r896Kbps    (39),
		r960Kbps    (40),
		r1152Kbps   (41),
		r1920Kbps   (42),
		r34Mbps     (43),	 -- e3
		r45Mbps     (44),	 -- t3

		r1088Kbps   (45),
		r1216Kbps   (46),
		r1344Kbps   (47),
		r1408Kbps   (48),
		r1472Kbps   (49),
		r1600Kbps   (50),
		r1664Kbps   (51),
		r1728Kbps   (52),
		r1792Kbps   (53),
		r1856Kbps   (54),
		r1984Kbps   (55),

		r1280Kbps   (56),
		r2304Kbps   (57),						   
		r832Kbps	(58),
												   
        r2176Kbps 	(59),						   
												   
        r2432Kbps 	(60),						   
        r2560Kbps 	(61),						   
        r2688Kbps 	(62),						   
        r2816Kbps 	(63),						   
        r2944Kbps 	(64),						   
        r3072Kbps 	(65),						   
        r3200Kbps 	(66),						   
        r3328Kbps 	(67),						   
        r3456Kbps 	(68),						   
        r3584Kbps 	(69),						   
        r3712Kbps 	(70),						   
        r3840Kbps 	(71),
        r3968Kbps 	(72),
        r4096Kbps 	(73),

        r2112Kbps   (74),
        r2240Kbps   (75),

        r4224Kbps   (76),
        r4352Kbps   (77),
        r4480Kbps   (78),
        r4608Kbps   (79),
        
        notApplicable (255) 

		}
      MAX-ACCESS read-write
      STATUS current
      DESCRIPTION
      "The DTE port rate." 
      ::= { modmPrtDteEntry 5}
	
modmPrtDteCtsDelay OBJECT-TYPE
      SYNTAX INTEGER 
          {
        d0       (1),
        d1       (2),
        d7       (3),
		d8       (4),
        d10      (5),
        d70      (6),
		disabled (7),
		enabled  (8),
        notApplicable (255)
                	}
      MAX-ACCESS read-write
      STATUS current
      DESCRIPTION
      "CTS/RTS delay, in msec.
       dxx = xx msec.
       notApplicable - for ASMi-31, ASMi-32." 
      ::= { modmPrtDteEntry 6}

modmPrtDteParity OBJECT-TYPE
      SYNTAX  INTEGER
	      {
          none  (1),
          odd   (2),
          even  (3)
	      }
      MAX-ACCESS  read-write
      STATUS  current
      DESCRIPTION
      "This attribute indicates the parity mode in async frame."
      ::= { modmPrtDteEntry 7}

modmPrtDteIfType OBJECT-TYPE
      SYNTAX  INTEGER
	      {
		  v24      (1),
		  rs530    (2),
		  x21      (3),
		  g703     (4),	  --E1
		  v36      (5),
		  v35      (6),
		  g703r64k (7),
		  hdb3     (8),
		  ethernet (9),	 --UTP
		  g703T1   (10),
		  ethBNC   (11),
          noIR     (15),
		  ipUtp    (16),
		  ethQ     (17),
		  rs530WA  (18),
		  v35WA    (19),
		  g704E1   (20),
		  ethQN	   (21),	
		  g704T1   (22),
		  ethQV    (23),

		  other    (255)
		  }
      MAX-ACCESS  read-only
      STATUS  current
      DESCRIPTION
      "The interface type of the DTE port."
      ::= { modmPrtDteEntry 8}

modmPrtDteRlbEnable OBJECT-TYPE
      SYNTAX INTEGER {
                disable  (2),
                enable   (3)
		            }
      MAX-ACCESS read-write
      STATUS current
      DESCRIPTION
      "Enable/Disable Remote Loop-Back on this modem, externally
       initiated." 
      ::= {modmPrtDteEntry 9}

modmPrtDteAlbEnable OBJECT-TYPE
      SYNTAX INTEGER {
                disable  (2),
                enable   (3)
		            }
      MAX-ACCESS read-write
      STATUS current
      DESCRIPTION
      "Enable/Disable Analog Loop-Back on this modem, externally
       initiated." 
      ::= {modmPrtDteEntry 10}

modmPrtDteRtsDcdEnable OBJECT-TYPE
      SYNTAX INTEGER {
                disable  (2),
                enable   (3)
		            }
      MAX-ACCESS read-write
      STATUS current
      DESCRIPTION
      "Enable/Disable RTS-DCD." 
      ::= {modmPrtDteEntry 11}

modmPrtDteDsrDtrEnable OBJECT-TYPE
      SYNTAX INTEGER {
                disable  (2),
                enable   (3)
		            }
      MAX-ACCESS read-write
      STATUS current
      DESCRIPTION
      "Enable/Disable DSR-DTR." 
      ::= {modmPrtDteEntry 12}

modmPrtDteSignaling OBJECT-TYPE
      SYNTAX OCTET STRING
      MAX-ACCESS read-only
      STATUS current
      DESCRIPTION
      "Each bit represents a specific signal state.
       1 - means : signal is ON , Enabled, Yes (exists)
       0 - means : signal is OFF, Disabled, No .
       For detailed bit assignment see product's spec." 
      ::= {modmPrtDteEntry 13}

modmPrtDteLoops  OBJECT-TYPE
      SYNTAX  INTEGER
	      {
		none        (1),
		ana         (2),
		rem         (3),
		anaAndBert  (4),
		remAndBert  (5),
		bert        (6),
		twoBerts    (7),
		digital     (8),
		dual        (9),
		clb         (10),
		clbAndBert  (11),
		dteLLB      (12),
		lineRLB     (13)
	      }
      MAX-ACCESS  read-write
      STATUS  current
      DESCRIPTION
      "Loops that can be run on the DTE port.
       none - no loop (stop running loop) 
       ana  - Local Analog Line loop
       rem  - Remote Analog Line loop
	   anaAndBert - ana & BERT together
	   remAndBert - rem & BERT together
	   bert - BERT test
	   twoBerts - 2 BERT test
	   digital - A remote loop on the local modem. 
	   dual - Remote loop and ana loop.
	   clb - Local loop on the DTE connection. Must 
	        be set together with modmPrtDteTestTimeOut parameter. 
	        Applicable to asmi51/CQ/CD.
	   clbAndBert - CLB & BERT together. 
	   		Applicable to asmi51/CQ/CD. 
	   dteLLB  - DTE LLB  (Local Loopback on DTE Digital Interface)
	   lineRLB - Line RLB (Remote Loopback on Line Analog Interface)."
      ::= {modmPrtDteEntry 14}

modmPrtDteTests  OBJECT-TYPE
      SYNTAX  Integer32
      MAX-ACCESS  read-write
      STATUS  current
      DESCRIPTION
      "This is a mask which indicates 
       - for Get: which tests are running on the DTE port.
       - for Set: tests the user wishes to start or stop.
       Each test has its specific bit. 
       - '1' means the test runs (Set: should run).
       - '0' means the test does not run (Set: should stop):

         TEST                  BIT
        -----------            ---
        LEDs                    0
		

        e.g : If the return value is 1 the LEDs test is running."
      ::= {modmPrtDteEntry 15}

modmPrtDteClearAllTests  OBJECT-TYPE
      SYNTAX  INTEGER
	      {
		off(2),
		on (3)
	      }
      MAX-ACCESS  read-write
      STATUS  current
      DESCRIPTION
      "Setting this attribute to on, clears all the running loops 
       and tests of the DTE port. Upon completion, the value will 
       automatically change to off(2)."
      ::= {modmPrtDteEntry 16}

modmPrtDteBertResult	 OBJECT-TYPE
	  SYNTAX  DisplayString 
      MAX-ACCESS  read-only
      STATUS  current
      DESCRIPTION
	  "Result of BERT for the selected DTE port. 
	   Applicable only if BERT is running on the DTE port."
	  ::= {modmPrtDteEntry 17}

modmPrtDteErrCorrect  OBJECT-TYPE
      SYNTAX  INTEGER
	      {
		notApplicable (1),
		off     (2),
		on      (3),
		onBurst (4)
	      }
      MAX-ACCESS  read-write
      STATUS  current
      DESCRIPTION
      "notApplicable - for modems that do not support this object
       on      - will start a random error correction process.
	   onBurst - will start a burst error correction process.
       Setting this object to 'off', will stop any kind of error correction process."
      ::= {modmPrtDteEntry 18}

modmPrtDteV54DigitalTest  OBJECT-TYPE
      SYNTAX  INTEGER
	      {
		notApplicable (1),
		disable(2),
		enable (3)
	      }
      MAX-ACCESS  read-write
      STATUS  current
      DESCRIPTION
      "Enables to start a remote digital loopback upon recognition of a special pattern.
      disable - will not start a digital loopback when a special pattern is 
      recognized.
      enable  - will start a loopback upon recognition of a special pattern."
      ::= {modmPrtDteEntry 19}

modmPrtDteV54DigitalTestStatus  OBJECT-TYPE
      SYNTAX  INTEGER
	      {
		notApplicable (1),
        off  (2),
        on   (3)
	      }
      MAX-ACCESS  read-only
      STATUS  current
      DESCRIPTION
      "Indicates whether a remote digital test was triggered by a pattern
      by the remote modem or not.
      no  - the digital test wasn't triggered by a pattern by the remote modem.
      yes - the digital test was triggered by a pattern by the remote modem."
      ::= {modmPrtDteEntry 20}

modmPrtDteTestTimeOut  OBJECT-TYPE
      SYNTAX  Integer32
      MAX-ACCESS  read-write
      STATUS  current
      DESCRIPTION
      "Indicates the timeout for LLB test.
       0=Forever "
      ::= {modmPrtDteEntry 21}

modmPrtDteAlarmForwarding  OBJECT-TYPE
      SYNTAX  INTEGER
	      {
		notApplicable (1),
        disable   (2),
	 	enable    (3)
	      }
      MAX-ACCESS  read-write
      STATUS  current
      DESCRIPTION
      "This MIB object defines whether to enable or disable Alarm Forwarding for this port.
       It means whether this port will be affected by the failure of its respective Line port."
      ::= {modmPrtDteEntry 22}


-- Line port 

modmLinePort  OBJECT IDENTIFIER  ::=  {modmPrt 5}

modmPrtLineTable  OBJECT-TYPE
      SYNTAX SEQUENCE OF ModmPrtLineEntry
      MAX-ACCESS not-accessible
      STATUS  current
      DESCRIPTION
      "Configuration parameters of the Master and Slave Modem Line 
       Ports. The port and unit (Master/Slave) is identified by 
       its specific modmPrtLineIndex value."
       ::= { modmLinePort 1 }

modmPrtLineEntry OBJECT-TYPE
      SYNTAX ModmPrtLineEntry
      MAX-ACCESS not-accessible
      STATUS current
	DESCRIPTION  "An entry in table."
	INDEX {modmPrtLineIndex}
      ::= { modmPrtLineTable 1}

ModmPrtLineEntry ::=
      SEQUENCE {
	  modmPrtLineIndex		   Integer32,
	  modmPrtLineClkSrc        INTEGER,
	  modmPrtLineTxLevel       INTEGER,
	  modmPrtLineRxLevel       INTEGER,
	  modmPrtLineOutImp        INTEGER,
	  modmPrtLineInImp         INTEGER,
	  modmPrtLineCarrCntrl     INTEGER,
	  modmPrtLineRAP           INTEGER,
	  modmPrtLineWaveLength    INTEGER,
	  modmPrtLineCdSense       INTEGER,
	  modmPrtLineAIS           INTEGER,
	  modmPrtLineCoding        INTEGER,
	  modmPrtLineLength        INTEGER,
	  modmPrtLineClkSrcPort    INTEGER,
	  modmPrtLineDteClkConfig  INTEGER,
	  modmPrtLineMaskAlr	   INTEGER		
      }

modmPrtLineIndex OBJECT-TYPE
      SYNTAX Integer32 
	  MAX-ACCESS read-only
      STATUS current
      DESCRIPTION
      "The Line port index." 
      ::= {modmPrtLineEntry 1}

modmPrtLineClkSrc OBJECT-TYPE
      SYNTAX INTEGER 
	      {
           localExtRemoteRcv     (1),
           localIntRemoteRcv     (2),
           localRcvRemoteInt     (3),
		   localRcvRemoteExt     (4),
		   localExtAutoRemoteRcv (5),
		   localRcvRemoteExtAuto (6),
		   localSysRemoteRcv     (7),
		   localRcvRemoteSys     (8),
		   internal              (9),
		   external              (10),
		   system                (11),
		   receive               (12),
		   
		   notApplicable         (255)
	      }
	  MAX-ACCESS read-write
      STATUS current
      DESCRIPTION
      "The clock source of the Line port. 
       (5),(6) - applicable only for ASMi-24 and ASMi-50.
       (7),(8) - System level Clock Source. Applicable to CQ modems." 
      ::= {modmPrtLineEntry 2}

modmPrtLineTxLevel OBJECT-TYPE
      SYNTAX  INTEGER
          {
           n12    (1),
		   n9     (2),
           n6     (3),
           n3     (4),
           p0     (5),
           p4     (6),
		   p6     (7),
           p10    (8)
          }            
      MAX-ACCESS  read-write
      STATUS  current
      DESCRIPTION
      "Transmit level in dBm.
       pxx = positive xx = +xx
       nxx = negative xx = -xx  "
      ::= {modmPrtLineEntry 3}

modmPrtLineRxLevel OBJECT-TYPE
      SYNTAX  INTEGER       
          {
           n14  (1),
		   n12  (2),
           n10  (3),
           n9   (4),
           n6   (5),
           n3   (6),
           p0   (7),
		   low  (8),
		   high (9)
          }            
      MAX-ACCESS  read-write
      STATUS  current
      DESCRIPTION
      "Rx Sensitivity in dBm.
       pxx = positive xx = +xx
       nxx = negative xx = -xx."
      ::= {modmPrtLineEntry 4}

modmPrtLineOutImp OBJECT-TYPE
      SYNTAX  INTEGER
      {
       infinite  (1),
       i75ohm    (2),
       i100ohm   (3),
       i120ohm   (4),
	   i150ohm   (5),
	   i300ohm   (6),
       i600ohm   (7)
      }            
      MAX-ACCESS  read-write
      STATUS  current
      DESCRIPTION
      "Output impedance in Ohm."
      ::= {modmPrtLineEntry 5}

modmPrtLineInImp OBJECT-TYPE
      SYNTAX  INTEGER
      {
       infinite  (1),
       i75ohm    (2),
       i100ohm   (3),
       i120ohm   (4),
	   i150ohm   (5),
	   i300ohm   (6),
       i600ohm   (7)
      }            
      MAX-ACCESS  read-write
      STATUS  current
      DESCRIPTION
      "Input impedance in Ohm."
      ::= {modmPrtLineEntry 6}

modmPrtLineCarrCntrl OBJECT-TYPE
      SYNTAX  INTEGER           
	      {
          off    (2),
          on     (3)
	      }
      MAX-ACCESS  read-write
      STATUS  current
      DESCRIPTION
      "Carrier control."
      ::= {modmPrtLineEntry 7}

modmPrtLineRAP OBJECT-TYPE
      SYNTAX  INTEGER
      {
       private (1),
       v110    (2),
       v220    (3),
	   privateV110Enable (4),
	   notApplicable (255)
      }            
      MAX-ACCESS  read-write
      STATUS  current
      DESCRIPTION
      "Rate Adapting Protocol.
      privateV110Enable (4)= private but enables return to v110. "
      ::= {modmPrtLineEntry 8}


modmPrtLineWaveLength OBJECT-TYPE
      SYNTAX  INTEGER
      {
       notApplicable (1),
       nm850         (2),
       nm1300        (3),
	   nm780Laser    (4),
	   nm1300Laser   (5),
	   nm1550Laser   (6)
      }            
      MAX-ACCESS  read-only
      STATUS  current
      DESCRIPTION
      "Wave Length of the optical Line.
       notApplicable - when the modem Line is not optical.
       The units are nano-meters [nm]."
      ::= {modmPrtLineEntry 9}

modmPrtLineCdSense OBJECT-TYPE
      SYNTAX  INTEGER
      {
       notApplicable (1),
       high          (2),
       low           (3)
      }            
      MAX-ACCESS  read-write
      STATUS  current
      DESCRIPTION
      "Carrier Detect Sense - Detection Sensitivity of Carrier Wave.
       high - high sensitivity
       low  - low  sensitivity. "
      ::= {modmPrtLineEntry 10}

modmPrtLineAIS OBJECT-TYPE
      SYNTAX  INTEGER
      {
       notApplicable (1),
       disable       (2),
       enable        (3)
      }            
      MAX-ACCESS  read-write
      STATUS  current
      DESCRIPTION
      "AIS enable/disable.
       notApplicable - for modems that do not support this feature."
      ::= {modmPrtLineEntry 11}


modmPrtLineCoding OBJECT-TYPE
      SYNTAX  INTEGER
      {
       notApplicable   	(1),
       ami   			(2),
       hdb3   			(3),
       b8zs 			(4)
      }            
      MAX-ACCESS  read-write
      STATUS  current
      DESCRIPTION
      "Line Coding."
      ::= {modmPrtLineEntry 12}


modmPrtLineLength OBJECT-TYPE
      SYNTAX  INTEGER
       {
		unknown      (1),
        len0p133ft   (2),
        len134p266ft (3),
        len267p399ft (4),
        len400p533ft (5),
        len534p655ft (6),

		notApplicable(255)
	      }
      MAX-ACCESS  read-write
      STATUS  current
      DESCRIPTION
      "This attribute is the line length mask parameter used only 
       for T1/DSU interfaces.
       len400p533ft=length range: 400ft to 533ft."
      ::= {modmPrtLineEntry 13}

modmPrtLineClkSrcPort OBJECT-TYPE
      SYNTAX  INTEGER
       {
		notApplicable(1),
		modem1 (2),
        modem2 (3),
        modem3 (4),
        modem4 (5),
		ds1    (6),
		dte    (7)
	  }
      MAX-ACCESS  read-write
      STATUS  current
      DESCRIPTION
      "Clock Source Port.
      This parameter is relevant for external clock source."
      ::= {modmPrtLineEntry 14}

modmPrtLineDteClkConfig  OBJECT-TYPE
      SYNTAX  INTEGER
	  {
		notApplicable (1),
        dceExternal   (2),
        dce           (3)
	  }
      MAX-ACCESS  read-write
      STATUS  current
      DESCRIPTION
      "Indicates the clock source of the modems, which were not selected to supply
       the external clock."
      ::= {modmPrtLineEntry 15}

modmPrtLineMaskAlr  OBJECT-TYPE
      SYNTAX  INTEGER
	  {
		notApplicable (1),
        dontMask      (2),
        mask          (3)
	  }
      MAX-ACCESS  read-write
      STATUS  current
      DESCRIPTION
      "This parameter determine whether masking or not the alarms for this line."
      ::= {modmPrtLineEntry 16}


-- Traps

--NOTIFICATIONS

modmSaEvents OBJECT-IDENTITY
   STATUS  current
   DESCRIPTION
   "The events for Stand Alone Modems."
   ::= { modmSa 0 }

modmSysEvents OBJECT-IDENTITY
   STATUS  current
   DESCRIPTION
   "The events for General Modems."
   ::= { modmSys 0 }

modmSAlarmTrap NOTIFICATION-TYPE
      OBJECTS  {modmSaStatAlarms}
      STATUS  current
      DESCRIPTION
	  "The trap is sent every 5 seconds in which a change has 
	   occurred in the status of the variables sent. 
	   For modems containing a T1/E1 interface, dsx1LineStatus 
	   will be sent as well in the variables, after modmSaStatAlarms.
	   This trap is applicable for Stand-alone modems or Agents 
	   that are cards of a Hub."
      ::= { modmSaEvents 1 }


modmSLedTrap NOTIFICATION-TYPE
      OBJECTS  {agnLed}
      STATUS  current
      DESCRIPTION
	  "The trap is sent every 5 seconds in which a change has 
	   occurred in the state of one of the LEDs.
	   This trap is applicable for Stand-Alone modems or Agents 
	   that are cards of a Hub.
	   'agnLed' - will include both central and remote modems: 
	              first central, last remote."
      ::= { modmSaEvents 2 }

-- the following traps are for a modems-Hub or IMOD modems

modmHubConfigChange  NOTIFICATION-TYPE
      OBJECTS  {mdlCardType, mdlSPanelType}
      STATUS  current
      DESCRIPTION
	  "The trap is sent when any card of the modems Hub is inserted
	   or removed."
      ::= { modmSysEvents 3 }

modemMasterSlaveComm NOTIFICATION-TYPE
      OBJECTS  {modemMngLink}
      STATUS  current
      DESCRIPTION
	  "This trap is applicable only for IMOD modems .
	   The trap is sent when communication between a Master modem 
	   and its Slave is stopped or resumed.
	   'modemMngLink' includes the modemIdx."
      ::= { modmSysEvents 4 }

modemMasterChange NOTIFICATION-TYPE
      OBJECTS  {modemConfigMode, modemModeTemporary}
      STATUS  current
      DESCRIPTION
	  "This trap is applicable only for IMOD modems .
	   The trap is sent when a modem's permanent or temporary mode 
	   is changed.
	   'modemConfigMode' and 'modemModeTemporary' include the 
	    modemIdx."
      ::= { modmSysEvents 5 }

mngmntControlChange NOTIFICATION-TYPE
      OBJECTS  {modmHubController}
      STATUS  current
      DESCRIPTION
	  "This trap is applicable only for LRS-12.
	   The trap is sent when the Hub management controller is 
	   changed (NMS<->Terminal)."
      ::= { modmSysEvents 6 }

modemInvalidParameter NOTIFICATION-TYPE
      OBJECTS  {modemIdx}
      STATUS  current
      DESCRIPTION
	  "This trap is applicable only for IMOD cards of a Hub.
	   The trap is sent when an invalid parameter was Set to the 
	   modem."
      ::= { modmSysEvents 7 }

modemAlarm NOTIFICATION-TYPE
      OBJECTS  {modemActiveAlarms}
      STATUS  current
      DESCRIPTION
	  "This trap is applicable only for IMOD modems .
	   The trap is sent when the active alarms of an IMOD modem, 
	   change."
      ::= { modmSysEvents 8 }

cardStatusChange NOTIFICATION-TYPE
      OBJECTS  {mdlSLed}
      STATUS  current
      DESCRIPTION
	  "The trap is sent upon any change of the Leds status in the 
	   PS, CL or IMOD cards."
      ::= { modmSysEvents 9 }

modemSignalingChange NOTIFICATION-TYPE
      OBJECTS  {modmPrtDteSignaling}
      STATUS  current
      DESCRIPTION
	  "The trap is sent for any IMOD modem, when an unmasked
	   signal change occured in the attached variable (see
	   modemMaskSignaling object)."
      ::= { modmSysEvents 10 }

modmHubPsFail  NOTIFICATION-TYPE
      OBJECTS  {mdlSLed}
      STATUS  current
      DESCRIPTION
	  "The trap is sent when a PS card of the modems-Hub failed.
	   'mdlSLed' includes the mdlSIdx."
      ::= { modmSysEvents 11 }

modmHubIPModeChange  NOTIFICATION-TYPE
      OBJECTS  {modmHubIpMode}
      STATUS  current
      DESCRIPTION
	  "The trap is sent upon any change of modmHubIpMode parameter."
      ::= { modmSysEvents 12 }

modmInterfaceChange  NOTIFICATION-TYPE
      STATUS  current
      DESCRIPTION
	  "The trap is sent upon any change of interfaces for a modem that
	   is a card of a Hub or part of it.
	   In order to know what changed, for each product, specific variables will 
	   be attached. These variables will be specified in the product's spec.

	   For FOMi-E3/T3 and Optimux-4E1/T1-C : the trap will be sent when
	   the connectors card in LRS is removed/inserted."
      ::= { modmSysEvents 13 }


modmRackAlarms  NOTIFICATION-TYPE
      STATUS  current
      DESCRIPTION
	  "The trap is applicable for LRS-52.
	   The trap is sent when an alarm occurs. 
	   Attached variables are detailed in product specification."
      ::= { modmSysEvents 14 }


-- 
-- file :D:\Synergy\WorkArea\545\mib_rad\txt\kmux.txt
-- 
--                RAD-KMUX MIB    (Kilomux)

--Title:     RAD's Kilomux PRODUCT MIB
--Version:   1.0
--Date:      29.8.96
--By:        Yair Arian, Smadar Tauber and Yaira Gabay
--File:      kmux.txt ver535
--
--Last update: 29-10-2007  by Smadar Tauber


kmux  OBJECT IDENTIFIER  ::=  {radWan 6}


systemKmux  OBJECT IDENTIFIER  ::=  {kmux 1}

generalKmux  OBJECT IDENTIFIER  ::=  {systemKmux 1}

sysGenKmuxTable  OBJECT-TYPE
      SYNTAX SEQUENCE OF SysGenKmuxEntry
      MAX-ACCESS not-accessible
      STATUS  current
      DESCRIPTION
      "A table containing the general Kmux parameters."
       ::= { generalKmux 1 }

sysGenKmuxEntry OBJECT-TYPE
      SYNTAX SysGenKmuxEntry
      MAX-ACCESS not-accessible
      STATUS current
	DESCRIPTION  "An entry in table."
	INDEX {sysGenConfigIdx}
      ::= {sysGenKmuxTable 1}

SysGenKmuxEntry ::=
      SEQUENCE {
   sysGenConfigIdx              Integer32,
   sysGenFlipIntegration        INTEGER,
   sysGenMlMode                 INTEGER,
   sysGenFaType                 INTEGER,
   sysGenLinkRecovery           INTEGER,
   sysGenLinkSourceClock        INTEGER,
   sysGenMngBwA                 Integer32,
   sysGenMngBwB                 Integer32,
   sysGenAutoDialSlot           Integer32,
   sysGenResetBypassEnable      INTEGER,
   sysGenRebuildFrame           INTEGER
   }

sysGenConfigIdx OBJECT-TYPE
      SYNTAX  Integer32 (1..255)
      MAX-ACCESS  read-only
      STATUS  current
      DESCRIPTION
      "This object indicates the Configuration number (1..255) 
       referred.
       Value of  255 specifies the TmpCnfg (Scratch).
       The write operation in this Table is valid only to the 
       TmpCnfg entry."
      ::= { sysGenKmuxEntry 1}

sysGenFlipIntegration OBJECT-TYPE
      SYNTAX INTEGER { notApplicable(1),
                       short        (2),
                       long         (3)
      }
      MAX-ACCESS read-write
      STATUS current
      DESCRIPTION
      "The parameter is relevant only for KM-2100 and only when 
       sysGenMlMode=redundancy, switchBackup, or priorityBumping."
      ::= { sysGenKmuxEntry 2}

sysGenMlMode OBJECT-TYPE
      SYNTAX INTEGER { single         (2),
                       redundancy     (3),
                       dualLink       (4),
                       priorityBumping(5),
                       switchBackup   (6)
      }
      MAX-ACCESS read-write
      STATUS current
      DESCRIPTION
      "The Main Link operation mode. Determines how many links are
       used (one/two) and how they are used."
      ::= { sysGenKmuxEntry 3}

sysGenFaType OBJECT-TYPE
      SYNTAX INTEGER { auto   (2),
                       manual (3)
      }
      MAX-ACCESS read-write
      STATUS current
      DESCRIPTION
      "Frame Allocation type:
       auto - automatic frame allocation (by Kmux)
       manual - manually configured frame allocation (by user)."
      ::= { sysGenKmuxEntry 4}

sysGenLinkRecovery OBJECT-TYPE
      SYNTAX INTEGER { 
                       notApplicable (1),
                       auto          (2),
                       manual        (3)
      }
      MAX-ACCESS read-write
      STATUS current
      DESCRIPTION
      "The parameter determines the Link Recovery mode.
       The parameter is relevant only when the sysGenMlMode is either 
       switchBackup or priorityBumping."
      ::= { sysGenKmuxEntry 5}

sysGenLinkSourceClock OBJECT-TYPE
      SYNTAX INTEGER { none       (1),
                       kmxMlA  (103),
                       kmxMlB  (104)
      }
      MAX-ACCESS read-write
      STATUS current
      DESCRIPTION
      "The source clock for the links. The parameter is relevant 
       only for KM-2100 having a KDI or KDI/CH cards. ML-A or ML-B 
       are selectable only when sysGenMlMode=dual or priorityBumping."
      ::= { sysGenKmuxEntry 6}

sysGenMngBwA OBJECT-TYPE
      SYNTAX Integer32 
      MAX-ACCESS read-write
      STATUS current
      DESCRIPTION
      "The required management rate for ML-A, in bps. It is very important when a remote 
       unit is managed. 
       The selected value must be < ML-A Rate value.
       0 = None or not applicable
       800   bps = minimum value
       19200 bps = maximum value"
      ::= { sysGenKmuxEntry 7}

sysGenMngBwB OBJECT-TYPE
      SYNTAX Integer32 
      MAX-ACCESS read-write
      STATUS current
      DESCRIPTION
      "The required management rate for ML-B, in bps. It is very important when a remote 
       unit is managed. 
       The selected value must be < ML-B Rate value.
       0 = None or not applicable
       800   bps = minimum value
       19200 bps = maximum value"
      ::= { sysGenKmuxEntry 8}
 
sysGenAutoDialSlot OBJECT-TYPE
      SYNTAX Integer32 
      MAX-ACCESS read-write
      STATUS current
      DESCRIPTION
      "This object indicates the IO-SLOTs that can be used to initiate Automatic 
      DialUp.
      This field will be applicable when KML.10 is a ML and its
      prtIsdnSwitchMode=auto.
      Each IO Slot is represented by a bit:   11 .............0
                                        MSB(IO12)       LSB(IO1)
      bit 0 (LSB) kmxIO1: '1'- used
                       '0'- not used
      bit 1       kmxIO2: '1'- used
                      '0'- not used
      bit 2       kmxIO3: '1'- used
      .       '0'- not used
      .
      bit 11(MSB) kmxIO12: '1'- used
                       '0'- not used
      
      The value will be: SUM of [2**n] ; n=bit number." 
      ::= { sysGenKmuxEntry 9}

sysGenResetBypassEnable OBJECT-TYPE
      SYNTAX INTEGER {
       notApplicable(1),
       disabled     (2),
       enabled      (3)
      }
      MAX-ACCESS read-write
      STATUS current
      DESCRIPTION
      "Enable/Disable Reset Bypass operation when a KDI card exists
       and one of its links failed.
       notApplicable - when no KDI card exists in the Hub."
      ::= { sysGenKmuxEntry 10}

sysGenRebuildFrame OBJECT-TYPE
      SYNTAX INTEGER { 
      notApplicable   (1),
      automatically   (2),
      manually        (3)
      }
      MAX-ACCESS read-write
      STATUS current
      DESCRIPTION
      "How to rebuild frame (when a CH is connected/disconnected):
       automatically - immediately, by automatic frame allocation (by Kmux)
       manually - manually configured frame allocation (by user), or Rebuild 
       Frame command to ML card."
      ::= { sysGenKmuxEntry 11}
 
 
sysGenLinkRecoveryCmd OBJECT-TYPE
      SYNTAX INTEGER { 
                       noOp (1),
                       off  (2),
                       on   (3)
      }
      MAX-ACCESS read-write
      STATUS current
      DESCRIPTION
      "Command to recover from ML failure.
       When 'on', the agent will perform manual link recovery and 
       reset the variable to 'off'. 
       The conditions for this action are: 
       sysGenMlMode= priorityBumping or switchBackup and also 
       sysGenLinkRecovery=manual(3)."
      ::= { generalKmux 2}

sysGenFlipMlCmd OBJECT-TYPE
      SYNTAX INTEGER { 
                       noOp (1),
                       off  (2),
                       on   (3)
      }
      MAX-ACCESS read-write
      STATUS current
      DESCRIPTION
      "Command to flip the ML when sysGenMlMode=redundancy.
       When 'on', the agent will flip the ML and reset
       the variable to 'off'."
      ::= { generalKmux 3}
  
sysGenMonitorChannel OBJECT-TYPE
      SYNTAX Integer32
      MAX-ACCESS read-write
      STATUS current
      DESCRIPTION
      "The variable specifies the channel to be monitored and 
       presented on the front panel LEDs. The channel will be 
       specified according to: Slot*100+Ch. 
       0 - no monitoring."
      ::= { generalKmux 4}


statusKmux  OBJECT IDENTIFIER  ::=  {systemKmux 2}
  
sysStatusOnLineML OBJECT-TYPE
      SYNTAX INTEGER { both      (1),
                       kmxMlA  (103),
                       kmxMlB  (104)        
      }
      MAX-ACCESS read-only
      STATUS current
      DESCRIPTION
      "The main links which are online."
      ::= { statusKmux 1}

sysKmuxStatus OBJECT-TYPE
      SYNTAX Integer32
      MAX-ACCESS read-only
      STATUS current
      DESCRIPTION
      "A BIT string indicating the system status as follows
       On - the bit is set to '1':
      Bit 0 (LSB): Alarm Relay. 
   Bit 1: SP param. 
             Off- Configure the SP port from the database
             On - Default parameters (9600bps, 8 data bits, 
                  no parity, one stop bit).
   Bit 2: DBinit. 
             The status of the dip switch in the Common Logic Card.
             Off- Configuration parameters were determined by the 
                  user.
             On - Default configuration parameters are loaded on 
                  mux power-on.
   Bit 3: DownloadBw.
             Off - Disable in-band management.
             On  - Enable in-band management.
   Bit 4 (MSB): Passwd.
             Off - No password is required.
             On  - Password is required.
      Example: 8 (10000) means Passwd.=On and all the others off."
      ::= { statusKmux 2}

sysKmuxOffset OBJECT-TYPE
      SYNTAX INTEGER {
                       notApplicable (1),
                       off           (2),
                       on            (3)
      }
      MAX-ACCESS read-only
      STATUS current
      DESCRIPTION
      "'on' - slots 1..4 of KM-2104 match slots 11..14 of KM-2100.
       'off'- slots 1..4 of KM-2104 match slots  7..10 of KM-2100.
       notApplicable - for KM-2100."
      ::= { statusKmux 3}



backupKmux  OBJECT IDENTIFIER  ::=  {systemKmux 3}

sysBackupTable  OBJECT-TYPE
      SYNTAX SEQUENCE OF SysBackupEntry
      MAX-ACCESS not-accessible
      STATUS  current
      DESCRIPTION
      "A table containing the backup parameters."
       ::= { backupKmux 1 }

sysBackupEntry OBJECT-TYPE
      SYNTAX SysBackupEntry
      MAX-ACCESS not-accessible
      STATUS current
	DESCRIPTION  "An entry in table."
	INDEX {sysBackupConfigIdx}
      ::= {sysBackupTable 1}

SysBackupEntry ::=
      SEQUENCE {
   sysBackupConfigIdx            Integer32,
   sysBackupDatabase             INTEGER,
   sysBackupMode                 INTEGER,
   sysBackupDialTimeout          INTEGER,
   sysBackupOptions              INTEGER
   }

sysBackupConfigIdx OBJECT-TYPE
      SYNTAX  Integer32 (1..255)
      MAX-ACCESS  read-only
      STATUS  current
      DESCRIPTION
      "This object indicates the Configuration number (1..255) 
       referred.
       Value of  255 specifies the TmpCnfg (Scratch)."
      ::= { sysBackupEntry 1}

sysBackupDatabase OBJECT-TYPE
      SYNTAX INTEGER { onLine   (2),
                       alternate(3)
      }
      MAX-ACCESS read-write
      STATUS current
      DESCRIPTION
      "Determines the database to switch to, when ML recovery occurs."
      ::= { sysBackupEntry 2}

sysBackupMode OBJECT-TYPE
      SYNTAX INTEGER { isdn(2),
                       pstn(3)
      }			    
      MAX-ACCESS read-write
      STATUS current
      DESCRIPTION
      "isdn - for connection to ISDN network.
       pstn - for connection to PSTN network."
      ::= { sysBackupEntry 3}

sysBackupDialTimeout OBJECT-TYPE
      SYNTAX INTEGER { sec30 (2),
                       sec45 (3),
                       sec60 (4),
                       sec120(5)
      }
      MAX-ACCESS read-write
      STATUS current
      DESCRIPTION
      "The dial timeout in seconds (when backup is attempted)."
      ::= { sysBackupEntry 4}


sysBackupOptions OBJECT-TYPE
      SYNTAX INTEGER { noBackup (2),
                       line     (3),
                       path     (4)
      }
      MAX-ACCESS read-write
      STATUS current
      DESCRIPTION
      "The Backup options:
       noBackup - No backup is applicable
       line - Line Data backup
       path - Line Mng backup ."
      ::= { sysBackupEntry 5}


sysBackupAgendaTable  OBJECT-TYPE
      SYNTAX SEQUENCE OF SysBackupAgendaEntry
      MAX-ACCESS not-accessible
      STATUS  current
      DESCRIPTION
      "A table containing the backup schedule. It is possible to
       define 4 different time zone schedules per day of the week."
       ::= { backupKmux 2 }

sysBackupAgendaEntry OBJECT-TYPE
      SYNTAX SysBackupAgendaEntry
      MAX-ACCESS not-accessible
      STATUS current
	DESCRIPTION  "An entry in table."
	INDEX {sysBackupCfgIdx,sysBackupDay,sysBackupZone}
      ::= {sysBackupAgendaTable 1}

SysBackupAgendaEntry ::=
      SEQUENCE {
   sysBackupCfgIdx       INTEGER,
   sysBackupDay          INTEGER,
   sysBackupZone         INTEGER, 
   sysBackupEndTime      DisplayString,
   sysBackupStatus       INTEGER 
   }

sysBackupCfgIdx OBJECT-TYPE
      SYNTAX  INTEGER 
           {
            active      (1),
            temporary (255)
           }  
      MAX-ACCESS  read-only
      STATUS  current
      DESCRIPTION
      "This object indicates the Configuration number (1,255) 
       referred.
       Write operation for the table entries is allowed only to
       the temporary configuration (255)."
      ::= { sysBackupAgendaEntry 1}

sysBackupDay OBJECT-TYPE
      SYNTAX INTEGER {sunday   (1),
                      monday   (2),
                      tuesday  (3),
                      wednesday(4),
                      thursday (5),
                      friday   (6),
                      saturday (7)
        }
      MAX-ACCESS read-only
      STATUS current
      DESCRIPTION
      "Day of the week."
      ::= { sysBackupAgendaEntry 2}

sysBackupZone OBJECT-TYPE
      SYNTAX INTEGER {zone1(1),
                      zone2(2),
                      zone3(3),
                      zone4(4),
					  zone5(5)
        }
      MAX-ACCESS read-only
      STATUS current
      DESCRIPTION
      "The time zone."
      ::= { sysBackupAgendaEntry 3}


sysBackupEndTime OBJECT-TYPE
      SYNTAX DisplayString (SIZE(0..255))
      MAX-ACCESS read-write
      STATUS current
      DESCRIPTION
      "The end time for this time zone. The format is HH:MM. For
       example 23:59.
       For Zone 4, End Time = 23:59 (constant)."
      ::= { sysBackupAgendaEntry 4}

sysBackupStatus OBJECT-TYPE
      SYNTAX INTEGER { enable (1),
                       disable(2)
     }
      MAX-ACCESS read-write
      STATUS current
      DESCRIPTION
      "Enable or disable this backup schedule entry."
      ::= { sysBackupAgendaEntry 5}


frameAllocationKmux  OBJECT IDENTIFIER  ::=  {systemKmux 4}


sysFrameAllocationTable  OBJECT-TYPE
      SYNTAX SEQUENCE OF SysFrameAllocationEntry
      MAX-ACCESS not-accessible
      STATUS  current
      DESCRIPTION
      "A table for manually configuring the frame allocation.
       The table will contain always all the programmed cards' 
       ports. sysFaNumOfBits"
       ::= { frameAllocationKmux 1 }

sysFrameAllocationEntry OBJECT-TYPE
      SYNTAX SysFrameAllocationEntry
      MAX-ACCESS not-accessible
      STATUS current
	DESCRIPTION  "An entry in table."
	INDEX {sysFaConfigIdx, sysFaLink, sysFaPrt}
      ::= {sysFrameAllocationTable 1}

SysFrameAllocationEntry ::=
      SEQUENCE {
   sysFaConfigIdx   Integer32,
   sysFaLink        INTEGER, 
   sysFaPrt         Integer32,
   sysFaStartingBit Integer32,
   sysFaNumOfBits   Integer32 
	}

sysFaConfigIdx OBJECT-TYPE
      SYNTAX  Integer32 (1..255)
      MAX-ACCESS  read-only
      STATUS  current
      DESCRIPTION
      "This object indicates the Configuration number (1..255) 
       referred.
       Value of  255 specifies the TmpCnfg (Scratch).
       Write operation for the table entries is allowed only to 
       Config=255."
      ::= { sysFrameAllocationEntry 1}

sysFaLink OBJECT-TYPE
      SYNTAX INTEGER { 
                    kmxMlA  (103),
                    kmxMlB  (104)
      }
      MAX-ACCESS read-only
      STATUS current
      DESCRIPTION
      "The main link on which frame allocation is done."
      ::= { sysFrameAllocationEntry 2}

sysFaPrt OBJECT-TYPE
      SYNTAX Integer32 
      MAX-ACCESS read-only
      STATUS current
      DESCRIPTION
      "The Frame Allocation (FA) port.
       The ports will be specified by:
          Slot*100+Ch.
       - for Bypass  of KDI or KDI/CH the port will be:
          Slot*100+11 (internal-1=non-existent port ; just for use
                       of the same MIB table)
       - for all the programmed cards, there will be an artificial
         port entry that will represent the card, in order to 
         specify  the Control Signal Bits that are at card level:
          Slot*100+0 . "
      ::= { sysFrameAllocationEntry 3}

sysFaStartingBit OBJECT-TYPE
      SYNTAX Integer32 (0..239)
      MAX-ACCESS read-write
      STATUS current
      DESCRIPTION
      "The data starting bit for the channel.
       - for Bypass of KDI or KDI/CH, this will be the Starting Bit 
         of the Bypass Window on the specific sysFaLink.
       - for Control Signals of a card  ( sysFaPrt=Slot*100+0)
         this will be the Starting Bit of the Control Signals of the 
         card."
      ::= { sysFrameAllocationEntry 4}

sysFaNumOfBits OBJECT-TYPE
      SYNTAX Integer32 (0..239)
      MAX-ACCESS read-write
      STATUS current
      DESCRIPTION
      "The data size in number of bits for the channel.
       - for Bypass of KDI or KDI/CH, this will be the Bypass Window 
         size. In this case, this value must be the same  for both 
   MLs.
       - for Control Signals of a card  ( sysFaPrt=Slot*100+0)
         this will be the number of Control Signal Bits of the 
         card."
      ::= { sysFrameAllocationEntry 5}


-- Disconnect Supervision Event Table.
-- This table contains all the Disconnect Supervision Events
-- that occurred on the KVF.6 and KVF.8 cards of the KM.

sysDisconnectSupervisionEventTable  OBJECT-TYPE
      SYNTAX SEQUENCE OF SysDisconnectSupervisionEventEntry
      MAX-ACCESS not-accessible
      STATUS current
	  DESCRIPTION  "Disconnect Supervision Event table."
    ::=  {systemKmux 5}

sysDisconnectSupervisionEventEntry OBJECT-TYPE
      SYNTAX SysDisconnectSupervisionEventEntry
      MAX-ACCESS not-accessible
      STATUS current
	  DESCRIPTION  "An entry in the table."
	  INDEX { sysDsEventIdx }
      ::= { sysDisconnectSupervisionEventTable 1}

SysDisconnectSupervisionEventEntry ::=
      SEQUENCE {
      sysDsEventIdx            Integer32,
      sysDsEventSlot           INTEGER,
	  sysDsEventTS			   Integer32,
	  sysDsEventDescr		   DisplayString,
	  sysDsEventDateAndTime	   DisplayString
        }

sysDsEventIdx OBJECT-TYPE
      SYNTAX  Integer32
      MAX-ACCESS  read-only
      STATUS  current
      DESCRIPTION
      "This object indicates a unique Event Index."
      ::= { sysDisconnectSupervisionEventEntry 1}

sysDsEventSlot OBJECT-TYPE
      SYNTAX  INTEGER
      {
      kmxIO1 (107),
      kmxIO2 (108),
      kmxIO3 (109),
      kmxIO4 (110),
      kmxIO5 (111),
      kmxIO6 (112),
      kmxIO7 (113),
      kmxIO8 (114),
      kmxIO9 (115),
      kmxIO10(116),
      kmxIO11(117),
      kmxIO12(118)
      }
      MAX-ACCESS  read-only
      STATUS  current
      DESCRIPTION
      "This object indicates a unique number of the slot position,
       where the KVF.6 or KVF.8 card is inserted, 
       and the Disconnect Supervision Event occurred."
      ::= { sysDisconnectSupervisionEventEntry 2}

sysDsEventTS OBJECT-TYPE
      SYNTAX  Integer32 (1..31)
      MAX-ACCESS  read-only
      STATUS  current
      DESCRIPTION
      "This object defines the Time Slot number, 
       where the Disconnect Supervision Event occurred."
      ::= { sysDisconnectSupervisionEventEntry 3}

sysDsEventDescr OBJECT-TYPE
      SYNTAX  DisplayString
      MAX-ACCESS  read-only
      STATUS  current
      DESCRIPTION
      "This object defines the Description
       of the Disconnect Supervision Event."
      ::= { sysDisconnectSupervisionEventEntry 4}

sysDsEventDateAndTime OBJECT-TYPE
      SYNTAX  DisplayString
      MAX-ACCESS  read-only
      STATUS  current
      DESCRIPTION
      "This object defines the Date and Time,
       when the Disconnect Supervision Event occurred.
       It will be displayed in the following format: YYYY-MM-DD HH:MM:SS."
      ::= { sysDisconnectSupervisionEventEntry 5}


mdlKmux  OBJECT IDENTIFIER  ::=  {kmux 2}

mdlKmxTable  OBJECT-TYPE
      SYNTAX SEQUENCE OF MdlKmxEntry
      MAX-ACCESS not-accessible
      STATUS current
	DESCRIPTION  "A table."
	::=  { mdlKmux 2 }

mdlKmxEntry OBJECT-TYPE
      SYNTAX MdlKmxEntry
      MAX-ACCESS not-accessible
      STATUS current
	DESCRIPTION  "An entry in table."
	INDEX { mdlKmxConfigIdx, mdlKmxSlotIdx  }
      ::= { mdlKmxTable 1}

MdlKmxEntry ::=
      SEQUENCE {
      mdlKmxConfigIdx         Integer32,
      mdlKmxSlotIdx           INTEGER,
      mdlKmxOperatedMl        INTEGER,
      mdlKmxMlAtoMlBPrio      INTEGER,
      mdlKmxMlBtoMlAPrio      INTEGER,
      mdlKmxOutSrvMethod      INTEGER,
      mdlKmxV54Config         INTEGER,
      mdlKmxTiming            INTEGER,
      mdlKmxIsdnDisconnectCause Unsigned32,
      mdlKmxIsdnCallStatus    INTEGER,
      mdlKmxIsdnLayer1State   INTEGER,
      mdlKmxIsdnLayer2State   INTEGER
      }

mdlKmxConfigIdx OBJECT-TYPE
      SYNTAX  Integer32 (1..255)
      MAX-ACCESS  read-only
      STATUS  current
      DESCRIPTION
      "This object indicates the Configuration number (1..255) 
       referred.
       Value of  255 specifies the TmpCnfg (Scratch).
       Write operation for the table entries is allowed only to 
       Config=255."
      ::= { mdlKmxEntry 1}

mdlKmxSlotIdx OBJECT-TYPE
      SYNTAX  INTEGER
       {
    kmxPsA (101),
    kmxPsB (102),
    kmxMlA (103),
    kmxMlB (104),
    kmxCl  (105),
    kmxOpt (106),
    kmxIO1 (107),
    kmxIO2 (108),
    kmxIO3 (109),
    kmxIO4 (110),
    kmxIO5 (111),
    kmxIO6 (112),
    kmxIO7 (113),
    kmxIO8 (114),
    kmxIO9 (115),
    kmxIO10(116),
    kmxIO11(117),
    kmxIO12(118)
       }
      MAX-ACCESS  read-only
      STATUS  current
      DESCRIPTION
      "This object indicates a unique number of the slot position 
       in which the module is inserted."
      ::= { mdlKmxEntry 2}

mdlKmxOperatedMl OBJECT-TYPE
      SYNTAX  INTEGER {
                      notApplicable(1),
                      kmxMlA       (103),
                      kmxMlB       (104),
					  kmxMlAandMlB (119)    -- for KVF.6 and KMBE/NEW
        }
      MAX-ACCESS  read-write
      STATUS  current
      DESCRIPTION
      "The main link for this card.
       The field is relevant only for ML modes of Dual, Priority 
       Bumping and Switched Backup."
      ::= { mdlKmxEntry 3}

mdlKmxMlAtoMlBPrio OBJECT-TYPE
      SYNTAX  INTEGER {notApplicable(1),
                       low          (2),
                       high         (3)
        }
      MAX-ACCESS  read-write
      STATUS  current
      DESCRIPTION
      "ML-A to ML-B Priority.
       The field is relevant only for ML modes of Priority Bumping
       and Switched Backup."
      ::= { mdlKmxEntry 4}

mdlKmxMlBtoMlAPrio OBJECT-TYPE
      SYNTAX  INTEGER  {notApplicable(1),
                        low          (2),
                        high         (3)
        }
      MAX-ACCESS  read-write
      STATUS  current
      DESCRIPTION
      "ML-B to ML-A Priority.
       The field is relevant only for ML modes of Priority Bumping."
      ::= { mdlKmxEntry 5}

mdlKmxOutSrvMethod OBJECT-TYPE
      SYNTAX  INTEGER {notApplicable(1),
                    idleBusy     (2),
        forcedIdle   (3),
        busyIdle     (4),
        forcedBusy   (5)
        }
      MAX-ACCESS  read-write
      STATUS  current
      DESCRIPTION
      "Out of service method. For KVC.1 and KVC.1M all values are 
       applicable.
       For KVC.2, KVC.3, KVF.1, KVF.3, KVF.4: only forcedIdle and 
       forcedBusy are applicable."
      ::= { mdlKmxEntry 6}

mdlKmxV54Config OBJECT-TYPE
      SYNTAX  INTEGER {notApplicable(1),
                       dceDce       (2),
                       dceDte       (3),
                       dteDce       (4),
                       dteDte       (5)
                       } 
      MAX-ACCESS  read-write
      STATUS  current
      DESCRIPTION
      "Relevant only for KLS.1/New card."
      ::= { mdlKmxEntry 7}

mdlKmxTiming OBJECT-TYPE
      SYNTAX  INTEGER {notApplicable(1),
                       lt           (2),
                       nt           (3),
                       te           (4)
                       } 
      MAX-ACCESS  read-only
      STATUS  current
      DESCRIPTION
      "Applicable only for KHSU.1, KHSU.2, KVF.4/S0, KVC.3/S0 cards.
       lt - local timing
       nt - network timing
       te - terminal equipment "
      ::= { mdlKmxEntry 8}

mdlKmxIsdnDisconnectCause  OBJECT-TYPE
     SYNTAX  Unsigned32 
     MAX-ACCESS  read-only
     STATUS  current
     DESCRIPTION
	 "This attribute indicates the cause of the ISDN Disconnection for 
     the card installed in the specific slot position. The value can be
     0..255. The numeric values have a well known meaning for ISDN experts."
	 ::= { mdlKmxEntry 9 }

mdlKmxIsdnCallStatus OBJECT-TYPE
      SYNTAX  INTEGER 
              {noCallIndicator(1),
               dialing        (2),
               connected      (3),
			   disconnecting  (4),
			   disconnected   (5)
              } 
      MAX-ACCESS  read-only
      STATUS  current
      DESCRIPTION
      "This attribute indicates the current ISDN Call Status for 
       the card installed in the specific slot position."
      ::= { mdlKmxEntry 10}

mdlKmxIsdnLayer1State OBJECT-TYPE
      SYNTAX  INTEGER 
              {disconnected   (2),
               connected      (3)
              } 
      MAX-ACCESS  read-only
      STATUS  current
      DESCRIPTION
      "This attribute indicates the ISDN Layer 1 State for 
       the card installed in the specific slot position."
      ::= { mdlKmxEntry 11}

mdlKmxIsdnLayer2State OBJECT-TYPE
      SYNTAX  INTEGER 
              {disconnected   (2),
               connected      (3)
              } 
      MAX-ACCESS  read-only
      STATUS  current
      DESCRIPTION
      "This attribute indicates the ISDN Layer 2 State for 
       the card installed in the specific slot position."
      ::= { mdlKmxEntry 12}
					   

mdlKvf5PbxTable  OBJECT-TYPE
      SYNTAX SEQUENCE OF MdlKvf5PbxEntry
      MAX-ACCESS not-accessible
      STATUS  current
      DESCRIPTION
      "Parameters specific to KVF.5, KVF.6 and KVF.8 PBX cards."
      ::= { mdlKmux 3 }

mdlKvf5PbxEntry OBJECT-TYPE
      SYNTAX MdlKvf5PbxEntry
      MAX-ACCESS not-accessible
      STATUS current
	DESCRIPTION  "An entry in table."
	INDEX { mdlKvf5PbxConfigIdx, mdlKvf5PbxSlotIdx  }
      ::= { mdlKvf5PbxTable 1}

MdlKvf5PbxEntry ::=
      SEQUENCE {
      mdlKvf5PbxConfigIdx         Integer32,
      mdlKvf5PbxSlotIdx           INTEGER,
      mdlKvf5PbxSig               INTEGER,
      mdlKvf5PbxSigMode           INTEGER,
      mdlKvf5PbxTsAssign          INTEGER,
      mdlKvf5PbxCcsTs             Integer32,
      mdlKvf5PbxOos               INTEGER,
      mdlKvf5PbxSigTxPbx          INTEGER,
      mdlKvf5PbxSigRxPbx          INTEGER,
      mdlKvf5PbxDefABCD           OCTET STRING,
      mdlKvf5PbxFramerSlot        INTEGER,
	  mdlKvf5PbxCcsRate           INTEGER,
	  mdlKvf5PbxTxAbcdBit         OCTET STRING,
      mdlKvf5PbxHdlcCrc           INTEGER			
     }

mdlKvf5PbxConfigIdx OBJECT-TYPE
      SYNTAX  Integer32 (1..255)
      MAX-ACCESS  read-only
      STATUS  current
      DESCRIPTION
      "This object indicates the Configuration number (1..255) 
       referred.
       Value of  255 specifies the TmpCnfg (Scratch).
       Write operation for the table entries is allowed only to 
       Config=255."
      ::= { mdlKvf5PbxEntry 1}

mdlKvf5PbxSlotIdx OBJECT-TYPE
      SYNTAX  INTEGER
       {
    kmxIO1 (107),
    kmxIO2 (108),
    kmxIO3 (109),
    kmxIO4 (110),
    kmxIO5 (111),
    kmxIO6 (112),
    kmxIO7 (113),
    kmxIO8 (114),
    kmxIO9 (115),
    kmxIO10(116),
    kmxIO11(117),
    kmxIO12(118)
       }
      MAX-ACCESS  read-only
      STATUS  current
      DESCRIPTION
      "This object indicates a unique number of the slot position 
       in which the module is inserted."
      ::= { mdlKvf5PbxEntry 2}

mdlKvf5PbxSig OBJECT-TYPE
      SYNTAX  INTEGER { 
        notApplicable(1),      
        a    (2),
        aANDb(3),
        b    (4),
        ccs  (5),
		cas  (6)
        }
      MAX-ACCESS  read-write
      STATUS  current
      DESCRIPTION
      "Signaling  type.
       When 'mdlKvf5PbxSig' is valid, 'mdlKvf5PbxSigTxPbx' and 'mdlKvf5PbxSigRxPbx' 
       are not valid.
       mdlKvf5PbxSig  - is supported by KVF.5 OLD SW ver and KVF.6 card.
       mdlKvf5PbxSigTxPbx and mdlKvf5PbxSigRxPbx - are supported by KVF.5 NEW SW ver
       and KVF.6."
      ::= { mdlKvf5PbxEntry 3}

mdlKvf5PbxSigMode OBJECT-TYPE
      SYNTAX  INTEGER {
        notApplicable(1),      
        direct (2),
        inverse(3)
        }
      MAX-ACCESS  read-write
      STATUS  current
      DESCRIPTION
      "Signaling Mode."
	  ::= { mdlKvf5PbxEntry 4}

mdlKvf5PbxTsAssign OBJECT-TYPE
      SYNTAX  INTEGER {
        s1s2s3s4     (2),
        s5s6s7s8     (3),
        s9s10s11s12  (4),
        s13s14s15s16 (5),
        s17s18s19s20 (6),
        s21s22s23s24 (7),

        s13s14s15s17 (8),
        s18s19s20s21 (9),
        s22s23s24s25(10),
        s26s27s28s29(11),
        s30s31      (12)
        }
      MAX-ACCESS  read-write
      STATUS  current
      DESCRIPTION
      "Ts Assignment group. Each KVF.5 card of the Mux should have 
       a different value.
       For KVF.5/E1 values: 2,3,4,8,9,10,11,12 are applicable.
       For KVF.5/T1 values: 2,3,4,5,6,7  are applicable."
      ::= { mdlKvf5PbxEntry 5}

mdlKvf5PbxCcsTs  OBJECT-TYPE
      SYNTAX  Integer32
      MAX-ACCESS  read-write
      STATUS  current
      DESCRIPTION
      "CCS TS of the KVF.5/T1/E1 and KVF.6/T1/E1 card.
       It is applicable for Kmux KVF.5 Framer cards and KVF.6 cards
       when mdlKvf5PbxSig=ccs.
       Valid values:
       1..24 - CCS TS of T1
       1..31 - CCS TS of E1
       255   - notApplicable (for agents that do not support this 
               feature or for irrelevant cards)
    Other values are invalid.
    The value selected should not be the same as one of the TSs assigned for
    any card of the same group via mdlKvf5PbxTsAssign."
      ::= { mdlKvf5PbxEntry 6}

mdlKvf5PbxOos  OBJECT-TYPE
      SYNTAX  INTEGER
       {
        notSupported  (2),
        forcedIdle    (3),
        forcedBusy    (4)
       }
      MAX-ACCESS  read-write
      STATUS  current
      DESCRIPTION
      "'idle' = '0' = on-hook, idle state
       'busy' = '1' = off-hook, busy state
       'forcedIdle' = SP = both A and B signaling bits are forced
                      to '0' during out-of-service periods.
       'forcedBusy' = MK = both A and B signaling bits are forced
                      to '1' during out-of-service periods.
       - for T1:    '0'=0   ;  '1'=1                         
       - for E1:    '0'=1   ;  '1'=0   "
   ::= { mdlKvf5PbxEntry 7}

mdlKvf5PbxSigTxPbx  OBJECT-TYPE
      SYNTAX  INTEGER
       {
        notApplicable(1),      
        a            (2), 
        b            (3),
        aANDb        (4),
        crossAandB   (5),
        ccs          (6),
		aEqualsB     (7) 
       }
      MAX-ACCESS  read-write
      STATUS  current
      DESCRIPTION
      "TxPbx signaling means transmit signaling from KM to PBX (KM-->PBX)
       When 'mdlKvf5PbxSigTxPbx' is valid, 'mdlKvf5PbxSig' field is not valid. 
       mdlKvf5PbxSig  - is supported by KVF.5 OLD SW ver.
       mdlKvf5PbxSigTxPbx and mdlKvf5PbxSigRxPbx - are supported by KVF.5 NEW SW ver."
   ::= { mdlKvf5PbxEntry 8}

mdlKvf5PbxSigRxPbx  OBJECT-TYPE
      SYNTAX  INTEGER
       {
        notApplicable(1),      
        a            (2), 
        b            (3),
        aANDb        (4),
        ccs          (6)
       }
      MAX-ACCESS  read-write
      STATUS  current
      DESCRIPTION
      "RxPbx signaling means receive signaling from PBX to KM (PBX-->KM-->KM)
       When 'mdlKvf5PbxSigRxPbx' is valid, 'mdlKvf5PbxSig' field is not valid. 
       mdlKvf5PbxSig - is supported by KVF.5 OLD SW ver.
       mdlKvf5PbxSigTxPbx and mdlKvf5PbxSigRxPbx - are supported by KVF.5 NEW SW ver."
   ::= { mdlKvf5PbxEntry 9}

mdlKvf5PbxDefABCD  OBJECT-TYPE
      SYNTAX  OCTET STRING (SIZE (0..1))
      MAX-ACCESS  read-write
      STATUS  current
      DESCRIPTION
      "This object determines what KM will send for the ABCD Bits that
       are not 'filled' by the dynamic signaling. This field is applicable
       only for  signaling transmit to PBX ('mdlKvf5PbxSigTxPbx'). 
       For KVF.5 cards: valid range (00 - 0F HEX) - ABCD Bits."
   ::= { mdlKvf5PbxEntry 10}

mdlKvf5PbxFramerSlot  OBJECT-TYPE
      SYNTAX  INTEGER
       { 
        kmxIO1 (107),
        kmxIO2 (108),                        
        kmxIO3 (109),
        kmxIO4 (110),
        kmxIO5 (111),
        kmxIO6 (112),
        kmxIO7 (113),
        kmxIO8 (114),
        kmxIO9 (115),
        kmxIO10(116),
        kmxIO11(117),
        kmxIO12(118),
        notApplicable (255)
       }
      MAX-ACCESS  read-write
      STATUS  current
      DESCRIPTION
      "This object indicates the Framer's slot number this card belongs to.
       Several cards having the same mdlKvf5PbxFramerSlot value, work together
       as a group."
   ::= { mdlKvf5PbxEntry 11}

mdlKvf5PbxCcsRate  OBJECT-TYPE
      SYNTAX  INTEGER
       {
	   notConnected(1),
       bps4800(2),
	   bps6400(3),
       bps9600(4),
	   bps12800(5),
       bps16000(6),
	   bps19200(7),
       bps32000(8),
       bps64000(9)
       }
      MAX-ACCESS  read-write
      STATUS  current
      DESCRIPTION
      "Determines the Ccs speed - for KVF.6 and KVF.5 cards."
   ::= { mdlKvf5PbxEntry 12}

mdlKvf5PbxTxAbcdBit OBJECT-TYPE
      SYNTAX  OCTET STRING
      MAX-ACCESS  read-write
      STATUS  current
      DESCRIPTION
      "This object is applicable only for KVF.6 and KVF.8 cards, when mdlKvf5PbxSig=cas(6).
       It represents 4 parameters, by 2 Octets :
       D Bit Code-MSB nibble,
       C Bit Code-    nibble,
       B Bit Code-    nibble,
       A Bit Code-LSB nibble.

       Each of A,B,C,D Bit Code nibble represents:
    0 hex = 0000 = 0
    1 hex = 0001 = 1
    2 hex = 0010 = A bit
    3 hex = 0011 = B bit
    4 hex = 0100 = C bit
    5 hex = 0101 = D bit
    6 hex = 0110 = A bit inverse
    7 hex = 0111 = B bit inverse
    8 hex = 1000 = C bit inverse
    9 hex = 1001 = D bit inverse
    A-E hex - not used (invalid values)
    
    When the object is not applicable, 0 Octets will be sent."
      ::= { mdlKvf5PbxEntry 13}

mdlKvf5PbxHdlcCrc  OBJECT-TYPE
      SYNTAX  INTEGER
       {
	   notApplicable(1),
       crc16(2),
	   crc32(3)
       }
      MAX-ACCESS  read-write
      STATUS  current
      DESCRIPTION
      "Determines the CRC type of HDLC protocol, that CCS signaling 
       is working with. Applicable for KVF.6 cards when Signaling
       is CCS (only)."
   ::= { mdlKvf5PbxEntry 14}



-- Disconnect Supervision (Ds) Table.
-- Applicable for KVF.6 and KVF.8 cards.

mdlDisconnectSupervisionTable  OBJECT-TYPE
      SYNTAX SEQUENCE OF MdlDisconnectSupervisionEntry
      MAX-ACCESS not-accessible
      STATUS current
	  DESCRIPTION  "Disconnect Supervision table."
	::=  { mdlKmux 4 }

mdlDisconnectSupervisionEntry OBJECT-TYPE
      SYNTAX MdlDisconnectSupervisionEntry
      MAX-ACCESS not-accessible
      STATUS current
	  DESCRIPTION  "An entry in the table."
	  INDEX { mdlDsConfigIdx, mdlDsSlotIdx  }
    ::= { mdlDisconnectSupervisionTable 1}

MdlDisconnectSupervisionEntry ::=
      SEQUENCE {
      mdlDsConfigIdx           Integer32,
      mdlDsSlotIdx             INTEGER,
      mdlDs                    INTEGER,
	  mdlDsUserLoc             INTEGER,
	  mdlDsMode                INTEGER,
	  mdlDsSilence             Integer32,
	  mdlDsClrFwSig            OCTET STRING,
	  mdlDsAnswerSig           OCTET STRING,
	  mdlDsClrBwSig            OCTET STRING,
	  mdlDsFbtLowFreq          Integer32,
	  mdlDsFbtHighFreq         Integer32,
	  mdlDsFbtTimeOn1          Integer32,
	  mdlDsFbtTimeOff1         Integer32,
	  mdlDsFbtTimeOn2          Integer32,
	  mdlDsFbtTimeOff2         Integer32,
	  mdlDsFbtLowFreqLevel     Integer32,
	  mdlDsFbtHighFreqLevel    Integer32
     }

mdlDsConfigIdx OBJECT-TYPE
      SYNTAX  Integer32 (1..255)
      MAX-ACCESS  read-only
      STATUS  current
      DESCRIPTION
      "This object indicates the Configuration number (1..255) 
       referred.
       Value of 255 specifies the TmpCnfg (Scratch).
       Write operation for the table entries is allowed only to 
       Config=255."
      ::= { mdlDisconnectSupervisionEntry 1}

mdlDsSlotIdx OBJECT-TYPE
      SYNTAX  INTEGER
      {
      kmxIO1 (107),
      kmxIO2 (108),
      kmxIO3 (109),
      kmxIO4 (110),
      kmxIO5 (111),
      kmxIO6 (112),
      kmxIO7 (113),
      kmxIO8 (114),
      kmxIO9 (115),
      kmxIO10(116),
      kmxIO11(117),
      kmxIO12(118)
      }
      MAX-ACCESS  read-only
      STATUS  current
      DESCRIPTION
      "This object indicates a unique number of the slot position 
       in which the module is inserted."
      ::= { mdlDisconnectSupervisionEntry 2}

mdlDs OBJECT-TYPE
      SYNTAX  INTEGER
      {
      disable                    (1),
      remoteDisconnect           (2),
      remoteDisconnectAndSilence (3),
      silenceOnly                (4),
      fastBusyOnly               (5),
      silenceOrFastBusy          (6)
      }
      MAX-ACCESS  read-write
      STATUS  current
      DESCRIPTION
      "This object defines which terms will cause disconnection of call.
       disable = the Disconnect Supervision feature is disabled. In this case,
       all other objects of this table are irrelevant.

       Remote Sanity - 
       If mdlDsUserLoc = Remote Location , the valid values are :
       disable(1), silenceOnly(4), fastBusyOnly(5), silenceOrFastBusy(6).
       If mdlDsUserLoc = Local , the valid values are 
       disable(1), remoteDisconnect(2), remoteDisconnectAndSilence (3)."

      ::= { mdlDisconnectSupervisionEntry 3}

mdlDsUserLoc OBJECT-TYPE
      SYNTAX  INTEGER
      {
      notApplicable (1),
      remote        (2),
      local         (3)
      }
      MAX-ACCESS  read-write
      STATUS  current
      DESCRIPTION
      "User located in local or remote station.
	   Local station will disconnect the call actually if needed.
	   Applicable only if Disconnect Supervision (mdlDs) is different from disable.
	   Should be a Sanity check between the mdlDs and the mdlDsUserLoc parameters (see mdlDs)."
      ::= { mdlDisconnectSupervisionEntry 4}

mdlDsMode OBJECT-TYPE
      SYNTAX  INTEGER
      {
      notApplicable (1),
      reportOnly    (2),
      disconnect    (3)
      }
      MAX-ACCESS  read-write
      STATUS  current
      DESCRIPTION
      "This object defines the action, which will be done after remote disconnect occurred.
	   This object is relevant only when mdlDsUserLoc = local(3).
       Applicable only if Disconnect Supervision (mdlDs) is different from disable 
       AND User Location (mdlDsUserLoc) = local(3)."
      ::= { mdlDisconnectSupervisionEntry 5}

mdlDsSilence OBJECT-TYPE
      SYNTAX  Integer32
      MAX-ACCESS  read-write
      STATUS  current
      DESCRIPTION 
      "This object defines the silence period needed for an indication (seconds).
       Applicable only if Disconnect Supervision (mdlDs) is different from disable
	   AND includes 'Silence', i.e. is one of the following:
	   remoteDisconnectAndSilence(3), silenceOnly(4), silenceOrFastBusy(6).
       Valid values: 0,20,40..(every 20 seconds)..300, 0 = notApplicable.
       notApplicable = silence disabled when mdlDs doesn't include 'silence'."
      ::= { mdlDisconnectSupervisionEntry 6}

mdlDsClrFwSig OBJECT-TYPE
      SYNTAX  OCTET STRING
      MAX-ACCESS  read-write
      STATUS  current
      DESCRIPTION
      "This object defines the Clear FWD Signal (A,B,C,D bits) for KVF.6 cards.
       This object is an indication of Near PBX to the Far PBX, 
       that it wants to disconnect the call.
       Applicable only if Disconnect Supervision (mdlDs) is different from disable.
       Applicable only for KVF.6 cards.
       
       It represents 4 parameters, by an Octet:
	   ( Bit 7 = MSB, Bit 0 = LSB )
       D Bit - bits 6,7 of the MSB nibble,
	   C Bit - bits 4,5 of the MSB nibble,
	   B Bit - bits 2,3 of the LSB nibble,
	   A Bit - bits 0,1 of the LSB nibble.     
       
       For each of A,B,C,D Bits:
       00 = 0,
       01 = 1,
       10 = reserved,
       11 = x.

	   For A,B Bits - only one of them can be 'x' (not both at the same time).
	   For C,D Bits - 'x' won't be in use.
       
       When the object is not applicable, a 0 Octet will be sent."
      ::= { mdlDisconnectSupervisionEntry 7}

mdlDsAnswerSig OBJECT-TYPE
      SYNTAX  OCTET STRING
      MAX-ACCESS  read-write
      STATUS  current
      DESCRIPTION
      "This object defines the Clear FWD Signal (A,B,C,D bits) for KVF.6 cards.
       This object is an indication of Near PBX to the Far PBX,
	   taht a call is present now on the line.
       Applicable only if Disconnect Supervision (mdlDs) is different from disable.
       Applicable only for KVF.6 cards.
       
       It represents 4 parameters, by an Octet:
	   ( Bit 7 = MSB, Bit 0 = LSB )
       D Bit - bits 6,7 of the MSB nibble,
	   C Bit - bits 4,5 of the MSB nibble,
	   B Bit - bits 2,3 of the LSB nibble,
	   A Bit - bits 0,1 of the LSB nibble.     
       
       For each of A,B,C,D Bits:
       00 = 0,
       01 = 1,
       10 = reserved,
       11 = x.

	   For A,B Bits - only one of them can be 'x' (not both at the same time).
	   For C,D Bits - 'x' won't be in use.
       
       When the object is not applicable, a 0 Octet will be sent."
      ::= { mdlDisconnectSupervisionEntry 8}

mdlDsClrBwSig OBJECT-TYPE
      SYNTAX  OCTET STRING
      MAX-ACCESS  read-write
      STATUS  current
      DESCRIPTION
      "This object defines the Clear FWD Signal (A,B,C,D bits) for KVF.6 cards.
       This object is an indication of Far PBX to the Near PBX,
	   that the call was disconnected (on the Far side).
       Applicable only if Disconnect Supervision (mdlDs) is different from disable.
       Applicable only for KVF.6 cards.
       
       It represents 4 parameters, by an Octet:
	   ( Bit 7 = MSB, Bit 0 = LSB )
       D Bit - bits 6,7 of the MSB nibble,
	   C Bit - bits 4,5 of the MSB nibble,
	   B Bit - bits 2,3 of the LSB nibble,
	   A Bit - bits 0,1 of the LSB nibble.     
       
       For each of A,B,C,D Bits:
       00 = 0,
       01 = 1,
       10 = reserved,
       11 = x.

	   For A,B,C,D Bits - 'x' won't be in use.
       
       When the object is not applicable, a 0 Octet will be sent."
      ::= { mdlDisconnectSupervisionEntry 9}

mdlDsFbtLowFreq OBJECT-TYPE
      SYNTAX  Integer32
      MAX-ACCESS  read-write
      STATUS  current
      DESCRIPTION
      "First frequency in Fast Busy Tone (Fbt) combination (Hz).
       Valid values: 0..4000,4095. 4095 = notApplicable.
       Available only if Disconnect Supervision (mdlDs) is different from disable
	   AND includes 'Tones' (Fast Busy), i.e. is one of the following:
	   fastBusyOnly(5), silenceOrFastBusy(6)."
      ::= { mdlDisconnectSupervisionEntry 10}

mdlDsFbtHighFreq OBJECT-TYPE
      SYNTAX  Integer32
      MAX-ACCESS  read-write
      STATUS  current
      DESCRIPTION
      "Second frequency in Fast Busy Tone (Fbt) combination (Hz).
       Valid values: 0..4000,4095. 4095 = notApplicable.
       Available only if Disconnect Supervision (mdlDs) is different from disable
	   AND includes 'Tones' (Fast Busy), i.e. is one of the following:
	   fastBusyOnly(5), silenceOrFastBusy(6)."
      ::= { mdlDisconnectSupervisionEntry 11}

mdlDsFbtTimeOn1 OBJECT-TYPE
      SYNTAX  Integer32
      MAX-ACCESS  read-write
      STATUS  current
      DESCRIPTION
      "This object defines the Time On 1 cadence (in msec).
       Valid values: 0,10,20..(every 10 msec)..10000,10230. 
       0 = disable, 10230 = notApplicable.
       Available only if Disconnect Supervision (mdlDs) is different from disable
	   AND includes 'Tones' (Fast Busy), i.e. is one of the following:
	   fastBusyOnly(5), silenceOrFastBusy(6)."
      ::= { mdlDisconnectSupervisionEntry 12}

mdlDsFbtTimeOff1 OBJECT-TYPE
      SYNTAX  Integer32
      MAX-ACCESS  read-write
      STATUS  current
      DESCRIPTION
      "This object defines the Time Off 1 cadence (in msec).
       Valid values: 0,10,20..(every 10 msec)..10000,10230.
	   0 = disable, 10230 = notApplicable.
	   Available only if Disconnect Supervision (mdlDs) is different from disable
	   AND includes 'Tones' (Fast Busy), i.e. is one of the following:
	   fastBusyOnly(5), silenceOrFastBusy(6)."
      ::= { mdlDisconnectSupervisionEntry 13}

mdlDsFbtTimeOn2 OBJECT-TYPE
      SYNTAX  Integer32
      MAX-ACCESS  read-write
      STATUS  current
      DESCRIPTION
      "This object defines the Time On 2 cadence (in msec).
       Valid values: 0,10,20..(every 10 msec)..10000,10230.
	   0 = disable, 10230 = notApplicable.
	   Available only if Disconnect Supervision (mdlDs) is different from disable
	   AND includes 'Tones' (Fast Busy), i.e. is one of the following:
	   fastBusyOnly(5), silenceOrFastBusy(6)."
      ::= { mdlDisconnectSupervisionEntry 14}

mdlDsFbtTimeOff2 OBJECT-TYPE
      SYNTAX  Integer32
      MAX-ACCESS  read-write
      STATUS  current
      DESCRIPTION
      "This object defines the Time Off 2 cadence (in msec).
       Valid values: 0,10,20..(every 10 msec)..10000,10230.
	   0 = disable, 10230 = notApplicable.
	   Available only if Disconnect Supervision (mdlDs) is different from disable
	   AND includes 'Tones' (Fast Busy), i.e. is one of the following:
	   fastBusyOnly(5), silenceOrFastBusy(6)."
      ::= { mdlDisconnectSupervisionEntry 15}

mdlDsFbtLowFreqLevel OBJECT-TYPE
      SYNTAX  Integer32
      MAX-ACCESS  read-write
      STATUS  current
      DESCRIPTION
      "First frequency level for Fast Busy Tone (Fbt) in dBm units.
       Valid values: -32..31.
       Available only if Disconnect Supervision (mdlDs) is different from disable
	   AND includes 'Tones' (Fast Busy), i.e. is one of the following:
	   fastBusyOnly(5), silenceOrFastBusy(6)."
      ::= { mdlDisconnectSupervisionEntry 16}

mdlDsFbtHighFreqLevel OBJECT-TYPE
      SYNTAX  Integer32
      MAX-ACCESS  read-write
      STATUS  current
      DESCRIPTION
      "Second frequency level for Fast Busy Tone (Fbt) in dBm units.
       Valid values: -32..31.
       Available only if Disconnect Supervision (mdlDs) is different from disable
	   AND includes 'Tones' (Fast Busy), i.e. is one of the following:
	   fastBusyOnly(5), silenceOrFastBusy(6)."
      ::= { mdlDisconnectSupervisionEntry 17}


prtKmux  OBJECT IDENTIFIER  ::=  {kmux 3}

prtMainLink  OBJECT IDENTIFIER  ::=  {prtKmux 1}

prtMlFrameStatsTable  OBJECT-TYPE
      SYNTAX SEQUENCE OF PrtMlFrameStatsEntry
      MAX-ACCESS not-accessible
      STATUS  current
      DESCRIPTION
      "Frame diagnostics for the main links."
      ::= { prtMainLink 1 }

prtMlFrameStatsEntry OBJECT-TYPE
      SYNTAX PrtMlFrameStatsEntry
      MAX-ACCESS not-accessible
      STATUS current
	DESCRIPTION  "An entry in table."
	INDEX { prtMlFrameIdx }
      ::= { prtMlFrameStatsTable 1}

PrtMlFrameStatsEntry ::=
     SEQUENCE {
  prtMlFrameIdx           Integer32,
  prtMlFrameSlt           INTEGER,
  prtMlBitWeight          INTEGER,
  prtMlDataUsage          Integer32,
  prtMlControlSig         Integer32,
  prtMlDownload           Integer32,
  prtMlSync               Integer32,
  prtMlTotalUsage         Integer32,
  prtMlTotalFree          Integer32 
	}

prtMlFrameIdx OBJECT-TYPE
      SYNTAX  Integer32
      MAX-ACCESS  read-only
      STATUS  current
      DESCRIPTION
      "The prtGenPrtIdx index of this link.
       Slot*100+1."
      ::= { prtMlFrameStatsEntry 1}

prtMlFrameSlt     OBJECT-TYPE
      SYNTAX  INTEGER
       {
       kmxMlA  (103),
       kmxMlB  (104)
       }
      MAX-ACCESS  read-only
      STATUS  current
      DESCRIPTION
      "This attribute indicates a unique number to identify the slot 
       where the ML card is inserted."
      ::= { prtMlFrameStatsEntry 2}

prtMlBitWeight     OBJECT-TYPE
      SYNTAX  INTEGER
       {
       bps400  (1),
       bps800  (2),
       bps1600 (3),
       bps3200 (4),
	   bps6400 (5)
       }
      MAX-ACCESS  read-only
      STATUS  current
      DESCRIPTION
      "This attribute indicates the Bit Weight [bps/bit] used for
       the selected prtMlFrameSlt. The Bit Weight is according to 
       the ML Speed."
      ::= { prtMlFrameStatsEntry 3}

prtMlDataUsage OBJECT-TYPE
      SYNTAX  Integer32
      MAX-ACCESS  read-only
      STATUS  current
      DESCRIPTION
      "Data usage in [bits].
       In order to convert it to 'bps' units, the 'bits' should be multiplied
       by prtMlBitWeight value."
      ::= { prtMlFrameStatsEntry 4}

prtMlControlSig OBJECT-TYPE
      SYNTAX  Integer32
      MAX-ACCESS  read-only
      STATUS  current
      DESCRIPTION
      "Control Signals usage of the ML in [bits].
       In order to convert it to 'bps' units, the 'bits' should be multiplied
       by prtMlBitWeight value."
      ::= { prtMlFrameStatsEntry 5}

prtMlDownload OBJECT-TYPE
      SYNTAX  Integer32
      MAX-ACCESS  read-only
      STATUS  current
      DESCRIPTION
      "Download bandwidth usage of the ML in [bits].
       In order to convert it to 'bps' units, the 'bits' should be multiplied
       by prtMlBitWeight value."
      ::= { prtMlFrameStatsEntry 6}

prtMlSync OBJECT-TYPE
      SYNTAX  Integer32
      MAX-ACCESS  read-only
      STATUS  current
      DESCRIPTION
      "Sync bandwidth usage of the ML in [bits].
       In order to convert it to 'bps' units, the 'bits' should be multiplied
       by prtMlBitWeight value."
      ::= { prtMlFrameStatsEntry 7}

prtMlTotalUsage OBJECT-TYPE
      SYNTAX  Integer32
      MAX-ACCESS  read-only
      STATUS  current
      DESCRIPTION
      "Total bandwidth usage of the ML in [bits].
       In order to convert it to 'bps' units, the 'bits' should be multiplied
       by prtMlBitWeight value."
      ::= { prtMlFrameStatsEntry 8}

prtMlTotalFree OBJECT-TYPE
      SYNTAX  Integer32
      MAX-ACCESS  read-only
      STATUS  current
      DESCRIPTION
      "Free bandwidth of the ML in [bits].
       In order to convert it to 'bps' units, the 'bits' should be multiplied
       by prtMlBitWeight value."
      ::= { prtMlFrameStatsEntry 9}


prtMlTable  OBJECT-TYPE
      SYNTAX SEQUENCE OF PrtMlEntry
      MAX-ACCESS not-accessible
      STATUS  current
      DESCRIPTION
      "Parameters for the main links. 
       KML.1 - KML.6, KML.7(T1), KML.8(E1), KML.10(ISDN) and 
       KML.F(KML.11 Fiber-optic)."
      ::= { prtMainLink 2 }

prtMlEntry OBJECT-TYPE
      SYNTAX PrtMlEntry
      MAX-ACCESS not-accessible
      STATUS current
	DESCRIPTION  "An entry in table."
	INDEX { prtMlCnfgIdx, prtMlIdx }
      ::= { prtMlTable 1}

PrtMlEntry ::=
     SEQUENCE {
  prtMlCnfgIdx  Integer32,
  prtMlIdx           Integer32,
  prtMlSlt           INTEGER,
  prtMlTiming        INTEGER,
  prtMlBufferSize    INTEGER,
  prtMlDsrCts        INTEGER,
  prtMlSpeed         INTEGER,
  prtMlStartTS       Integer32,
  prtMlBypassTs16    INTEGER,
  prtMlCallMode      INTEGER,
  prtMlBondingEnable INTEGER
  }

prtMlCnfgIdx OBJECT-TYPE
      SYNTAX  Integer32 (1..255)
      MAX-ACCESS  read-only
      STATUS  current
      DESCRIPTION
      "This attribute indicates the Idx of the Config being accessed.
       Idx of 255 relates to the Temporary (Scratch) Config.
       Write operation for the table entries is allowed only to 
       Config=255. "
      ::= { prtMlEntry 1}

prtMlIdx OBJECT-TYPE
      SYNTAX  Integer32
      MAX-ACCESS  read-only
      STATUS  current
      DESCRIPTION
   "The prtGenPrtIdx index of this link.
    Slot*100+1 ."
      ::= { prtMlEntry 2}

prtMlSlt     OBJECT-TYPE
      SYNTAX  INTEGER
       {
     kmxMlA  (103),
     kmxMlB  (104)
       }
      MAX-ACCESS  read-only
      STATUS  current
      DESCRIPTION
      "This attribute indicates a unique number to identify the slot where
       the ML card is inserted in."
      ::= { prtMlEntry 3}

prtMlTiming     OBJECT-TYPE
      SYNTAX  INTEGER
       {
    notApplicable(1),
       dte   (2),
       dce   (3),
       eDce  (4),
       int   (5),
       lbt   (6),
	   adaptive (7)
       }
      MAX-ACCESS  read-write
      STATUS  current
      DESCRIPTION
      "The clock source for this link.
       For KML.1-KML.4, valid values: dte, eDce, or dce. 
       For KML.5-KML.8, valid values: int or lbt.
       notApplicable - for KML.10 and KML.F."
      ::= { prtMlEntry 4}

prtMlBufferSize     OBJECT-TYPE
      SYNTAX  INTEGER
       {
       notApplicable(1),
       bits8        (2),
       bits256      (3)
       }
      MAX-ACCESS  read-write
      STATUS  current
      DESCRIPTION
      "The buffer size in bits for absorbing timing jitters."
      ::= { prtMlEntry 5}

prtMlDsrCts     OBJECT-TYPE
      SYNTAX  INTEGER
       {
       notApplicable(1),
       internal     (2),
       external     (3)
       }
      MAX-ACCESS  read-write
      STATUS  current
      DESCRIPTION
      "Determines the DSR and CTS signal handling.
       notApplicable - for KML.4-KML.6."
      ::= { prtMlEntry 6}

prtMlSpeed     OBJECT-TYPE
      SYNTAX  INTEGER
       {
       bps9600(2),
       bps14400(3),
       bps19200(4),
       bps28800(5),
       bps32000(6),
       bps48000(7),
       bps56000(8),
       bps64000(9),
       bps128000(10),
       bps192000(11),
       bps256000(12),
       bps384000(13),
       bps512000(14),
       bps768000(15),
	   bps1024000(16),
	   bps1536000(17)
       }
      MAX-ACCESS  read-write
      STATUS  current
      DESCRIPTION
      "Determines the Main Link port speed.
       KML.1, KML.3, KML.4 support (Kbps): 9.6, 14.4, 19.2, 28.8, 32, 48, 56,
                                          64, 128, 192, 256, 384, 512, 768, 1024, 1536.
	   KML.2 supports (Kbps): 9.6, 14.4, 19.2, 28.8, 32, 48, 56, 64, 128
	   KML.5 supports (Kbps): 64, 128.
       KML.6 supports (Kbps): 9.6, 19.2, 56.
    KML.7-KML.8 support (Kbps): 56, 64, 128, 192, 256, 384, 512, 
                                768, 1024, 1536.
    KML.10 supports (Kbps): 64, 128.
    KML.F  supports (Kbps): 128, 256, 384, 512, 768, 1024, 1536."
      ::= { prtMlEntry 7}

prtMlStartTS     OBJECT-TYPE
      SYNTAX  Integer32  (0..31)
      MAX-ACCESS  read-write
      STATUS  current
      DESCRIPTION
      "0=notApplicable - for all cards except  KML.7, KML.8
       For KML.7 - valid values: 1..24
       For KML.8 - valid values: 1..31."
      ::= { prtMlEntry 8}

prtMlBypassTs16     OBJECT-TYPE
      SYNTAX  INTEGER  { 
                 notApplicable(1), 
                 no           (2), 
                 yes          (3) 
                 }
      MAX-ACCESS  read-write
      STATUS  current
      DESCRIPTION
      "notApplicable - for all cards except KML.8."
      ::= { prtMlEntry 9}

prtMlCallMode     OBJECT-TYPE
      SYNTAX  INTEGER  { 
                 notApplicable(1), 
                 initiate     (2), 
                 listen       (3) 
                 }
      MAX-ACCESS  read-write
      STATUS  current
      DESCRIPTION
      "This object will be used when using an external modem linked to the 
       KML.1-KML.4 or KML.10 cards.
       Initiate - KML card can initiate calls to the modem
       Listen   - KML card listens only ; cannot initiate a call."
      ::= { prtMlEntry 10}

prtMlBondingEnable     OBJECT-TYPE
      SYNTAX  INTEGER  { 
                 notApplicable(1), 
                 disabled     (2), 
                 enabled      (3) 
                 }
      MAX-ACCESS  read-write
      STATUS  current
      DESCRIPTION
      "Disable/Enable applying the Bonding process, for KML.10 cards.
       notApplicable - for all cards except KML.10."
      ::= { prtMlEntry 11}

 
prtMlIsdnTable  OBJECT-TYPE
      SYNTAX SEQUENCE OF PrtMlIsdnEntry
      MAX-ACCESS not-accessible
      STATUS  current
      DESCRIPTION
      "Parameters for ISDN main links: KML.10."
      ::= { prtMainLink 3 }

prtMlIsdnEntry OBJECT-TYPE
      SYNTAX PrtMlIsdnEntry
      MAX-ACCESS not-accessible
      STATUS current
	DESCRIPTION  "An entry in table."
	INDEX { prtMlIsdnCnfgIdx, prtMlIsdnIdx }
      ::= { prtMlIsdnTable 1}

PrtMlIsdnEntry ::=
     SEQUENCE {
  prtMlIsdnCnfgIdx       Integer32,
  prtMlIsdnIdx           Integer32,
  prtMlIsdnSlt           INTEGER,
  prtMlIsdnMode          INTEGER,
  prtMlIsdnStandard       INTEGER,
  prtMlIsdnLocSubNum      DisplayString,
  prtMlIsdnLocNum         DisplayString,
  prtMlIsdnOutSubNum      DisplayString,
  prtMlIsdnBackupCallNum  DisplayString,
  prtMlIsdnInNumMode      INTEGER
  }

prtMlIsdnCnfgIdx OBJECT-TYPE
      SYNTAX  Integer32 (1..255)
      MAX-ACCESS  read-only
      STATUS  current
      DESCRIPTION
      "This attribute indicates the Idx of the Config being accessed.
       Idx of 255 relates to the Temporary (Scratch) Config. 
       Write operation for the table entries is allowed only to 
       Config=255. "
      ::= { prtMlIsdnEntry 1}

prtMlIsdnIdx OBJECT-TYPE
      SYNTAX  Integer32
      MAX-ACCESS  read-only
      STATUS  current
      DESCRIPTION
   "The prtGenPrtIdx index of this link.
    Slot*100+1 ."
      ::= { prtMlIsdnEntry 2}

prtMlIsdnSlt     OBJECT-TYPE
      SYNTAX  INTEGER
       {
           kmxMlA  (103),
           kmxMlB  (104)
       }
      MAX-ACCESS  read-only
      STATUS  current
      DESCRIPTION
      "This attribute indicates a unique number to identify the slot where
       the ML card is inserted in."
      ::= { prtMlIsdnEntry 3}

prtMlIsdnMode OBJECT-TYPE
      SYNTAX  INTEGER  { 
                 leased  (2), 
                 switched(3)
                       }
      MAX-ACCESS  read-write
      STATUS  current
      DESCRIPTION
   "ISDN Mode.
    switched - when ML Mode is Switched Backup.
    leased   - in all other cases."
      ::= { prtMlIsdnEntry 4}

prtMlIsdnStandard OBJECT-TYPE
      SYNTAX  INTEGER  { european      (2),
                         israeli       (3),
                         ess5Multipoint(4),
                         ess5Ptp       (5),
                         dms100        (6),
                         ntt           (7),
                         nationalIsdn1 (8)
                       }
      MAX-ACCESS  read-write
      STATUS  current
      DESCRIPTION
   "The ISDN standard."
      ::= { prtMlIsdnEntry 5}

prtMlIsdnLocSubNum OBJECT-TYPE
      SYNTAX  DisplayString (SIZE(0..25))
      MAX-ACCESS  read-write
      STATUS  current
      DESCRIPTION
   "Local sub-number. 4 chars (digits 0..9)."
      ::= { prtMlIsdnEntry 6}

prtMlIsdnLocNum OBJECT-TYPE
      SYNTAX  DisplayString (SIZE(0..25))
      MAX-ACCESS  read-write
      STATUS  current
      DESCRIPTION
   "Local number. 20 chars (digits: 0..9)."
      ::= { prtMlIsdnEntry 7}

prtMlIsdnOutSubNum OBJECT-TYPE
      SYNTAX  DisplayString (SIZE(0..25))
      MAX-ACCESS  read-write
      STATUS  current
      DESCRIPTION
   "Out sub-number. 4 chars (digits 0..9)."
      ::= { prtMlIsdnEntry 8}

prtMlIsdnBackupCallNum OBJECT-TYPE
      SYNTAX  DisplayString (SIZE(0..25))
      MAX-ACCESS  read-write
      STATUS  current
      DESCRIPTION
   "Backup call number. 20 chars (digits: 0..9)."
      ::= { prtMlIsdnEntry 9}

prtMlIsdnInNumMode OBJECT-TYPE
      SYNTAX  INTEGER  { none (2), 
                         all  (3),
                         local(4)
                       }
      MAX-ACCESS  read-write
      STATUS  current
      DESCRIPTION
   "In number mode."
      ::= { prtMlIsdnEntry 10}



prtHsLs  OBJECT IDENTIFIER  ::=  {prtKmux 2}

prtHsLsTable  OBJECT-TYPE
      SYNTAX SEQUENCE OF PrtHsLsEntry
      MAX-ACCESS not-accessible
      STATUS  current
      DESCRIPTION
      "Parameters for the High and Low speed channels. 
       Cards: KLS.1,KLS.2, KHS.1, KHS.2, KDI/CH, KHSU.1, KHSU.2, KHS.703."
      ::= { prtHsLs 1 }

prtHsLsEntry OBJECT-TYPE
      SYNTAX PrtHsLsEntry
      MAX-ACCESS not-accessible
      STATUS current
	DESCRIPTION  "An entry in table."
	INDEX { prtHsLsCnfgIdx, prtHsLsIdx }
      ::= { prtHsLsTable 1}

PrtHsLsEntry ::=
     SEQUENCE {
  prtHsLsCnfgIdx       Integer32,
  prtHsLsIdx           Integer32,
  prtHsLsSlt           INTEGER,
  prtHsLsCommProtocol  INTEGER,
  prtHsLsAsyncDataLen  INTEGER,
  prtHsLsTiming        INTEGER,
  prtHsLsCtrlSignal    INTEGER,
  prtHsLsCts           INTEGER,
  prtHsLsRtsCtsDelay   INTEGER,
  prtHsLsDsrMode       INTEGER,
  prtHsLsSpeed         INTEGER,
  prtHsLsUType         INTEGER 
  }

prtHsLsCnfgIdx OBJECT-TYPE
      SYNTAX  Integer32 (1..255)
      MAX-ACCESS  read-only
      STATUS  current
      DESCRIPTION
      "This attribute indicates the Idx of the Config being accessed.
       Idx of 255 relates to the Temporary (Scratch) Config.
       Write operation for the table entries is allowed only to 
       Config=255. "
      ::= { prtHsLsEntry 1}

prtHsLsIdx OBJECT-TYPE
      SYNTAX  Integer32
      MAX-ACCESS  read-only
      STATUS  current
      DESCRIPTION
   "The prtGenPrtIdx index of this channel.
    In KHSU.1 and KHSU.2 there are three ISDN sub-channels on 
    each port (2B+D).The sub-channels are numbered:  
    Slot*100+11 ; Slot*100+12 ; Slot*100+13 (First Port), 
    Slot*100+14 ; Slot*100+15 ; Slot*100+16 (Second Port)."
      ::= { prtHsLsEntry 2}

prtHsLsSlt     OBJECT-TYPE
      SYNTAX  INTEGER
       {
	kmxOpt (106),	-- For KDI/CH card type
    kmxIO1 (107),
    kmxIO2 (108),
    kmxIO3 (109),
    kmxIO4 (110),
    kmxIO5 (111),
    kmxIO6 (112),
    kmxIO7 (113),
    kmxIO8 (114),
    kmxIO9 (115),
    kmxIO10(116),
    kmxIO11(117),
    kmxIO12(118)
       }
      MAX-ACCESS  read-only
      STATUS  current
      DESCRIPTION
      "This attribute indicates a unique number to identify the slot where
       the card is inserted in.
       In the 2104 Unit the entries kmxIO5(111)..kmxIO12(118) are not valid.
       The entry kmxOpt(106) is valid only for KDI/CH card."
      ::= { prtHsLsEntry 3}

prtHsLsCommProtocol OBJECT-TYPE
      SYNTAX  INTEGER  { notApplicable(1),
                         async        (2),
                      sync         (3)
        }
      MAX-ACCESS  read-write
      STATUS  current
      DESCRIPTION
   "The communication protocol."
      ::= { prtHsLsEntry 4}

prtHsLsAsyncDataLen OBJECT-TYPE
      SYNTAX  INTEGER   
        { notApplicable(1),
          bit6         (2),
          bit7         (3),
          bit8         (4),
          bit9         (5)
        } 
      MAX-ACCESS  read-write
      STATUS  current
      DESCRIPTION
   "Async Data Length in Bits.
    notApplicable - when prtHsLsCommProtocol=sync or 
                    notApplicable."
      ::= { prtHsLsEntry 5}

prtHsLsTiming OBJECT-TYPE
      SYNTAX  INTEGER  {
      notApplicable(1),
      dce   (2),
      dte1  (3),
      dte2  (4)
              }
      MAX-ACCESS  read-write
      STATUS  current
      DESCRIPTION
   "The variable is RW only if the communications protocol is 
    sync. 
    When the comm protocol is async, the variable is RO and its 
    value is DCE."
      ::= { prtHsLsEntry 6}

prtHsLsCtrlSignal OBJECT-TYPE
      SYNTAX  INTEGER  { notApplicable(1),
                         local        (2),
                         dtrAndRts    (3),
                         rts          (4)
        }
      MAX-ACCESS  read-write
      STATUS  current
      DESCRIPTION
   "Control signals."
      ::= { prtHsLsEntry 7}

prtHsLsCts OBJECT-TYPE
      SYNTAX  INTEGER { notApplicable(1),
                        equalRts     (2),
                        on           (3)
       }
      MAX-ACCESS  read-write
      STATUS  current
      DESCRIPTION
   "CTS Signal."
      ::= { prtHsLsEntry 8}

prtHsLsRtsCtsDelay OBJECT-TYPE
      SYNTAX  INTEGER  {
       notApplicable(1),
       min  (2),
       ms10 (3),
       ms50 (4),
       ms100(5),
       ms200(6)
        }
      MAX-ACCESS  read-write
      STATUS  current
      DESCRIPTION
   "RTS-CTS delay in ms.
    notApplicable - when prtHsLsCts=on."
      ::= { prtHsLsEntry 9}

prtHsLsDsrMode OBJECT-TYPE
      SYNTAX  INTEGER { notApplicable(1),
                        permanentOn  (2),
                        sync         (3)
       }
      MAX-ACCESS  read-write
      STATUS  current
      DESCRIPTION
   "DSR Mode."
      ::= { prtHsLsEntry 10}

prtHsLsSpeed OBJECT-TYPE
      SYNTAX  INTEGER {
      notConnected(1),
      bps300   (2),
      bps600   (3),
      bps1200  (4),
      bps2400  (5),
      bps4800  (6),
      bps7200  (7),
      bps8000  (8),
      bps9600  (9),
      bps12000(10),
      bps14400(11),
      bps16000(12),
      bps16800(13),
      bps19200(14),
      bps21600(15),
      bps24000(16),
      bps26400(17),
      bps28800(18),
      bps31200(19),
      bps32000(20),
      bps33600(21),
      bps36000(22),
      bps38400(23),
      bps40800(24),
      bps43200(25),
      bps45600(26),
      bps48000(27),
      bps50400(28),
      bps52800(29),
      bps55200(30),
      bps56000(31),
      bps57600(32),
      bps60000(33),
      bps62400(34),
      bps64000(35),
      bps64800(36),
      bps67200(37),
      bps69600(38),
      bps72000(39),
      bps74400(40),
      bps76800(41),
      bps79200(42),
      bps81600(43),
      bps84000(44),
      bps86400(45),
      bps88800(46),
      bps91200(47),
      bps93600(48),
      bps96000(49),
      bps98400(50),
      bps100800(51),
      bps103200(52),
      bps105600(53),
      bps108000(54),
      bps110400(55),
      bps112800(56),
      bps115200(57),
      bps117600(58),
      bps120000(59),
      bps122400(60),
      bps124800(61),
      bps127200(62),
      bps128000(63),
      bps129600(64),
      bps134400(65),
      bps139200(66),
      bps144000(67),
      bps148800(68),
      bps153600(69),
      bps158400(70),
      bps163200(71),
      bps168000(72),
      bps172800(73),
      bps177600(74),
      bps182400(75),
      bps187200(76),
      bps192000(77),
      bps196800(78),
      bps201600(79),
      bps206400(80),
      bps211200(81),
      bps216000(82),
      bps220800(83),
      bps225600(84),
      bps230400(85),
      bps235200(86),
      bps240000(87),
      bps244800(88),
      bps249600(89),
      bps254400(90),
      bps256000(91),
      bps259200(92),
      bps264000(93),
      bps268800(94),
      bps273600(95),
      bps278400(96),
      bps283200(97),
      bps288000(98),
      bps292800(99),
      bps297600(100),
      bps302400(101),
      bps307200(102),
      bps316800(103),
      bps326400(104),
      bps336000(105),
      bps345600(106),
      bps355200(107),
      bps364800(108),
      bps374400(109),
      bps384000(110),
      bps393600(111),
      bps403200(112),
      bps412800(113),
      bps422400(114),
      bps432000(115),
      bps441600(116),
      bps451200(117),
      bps460800(118),
      bps470400(119),
      bps480000(120),
      bps489600(121),
      bps499200(122),
      bps508800(123),
      bps518400(124),
      bps528000(125),
      bps537600(126),
      bps547200(127),
      bps556800(128),
      bps566400(129),
      bps576000(130),
      bps585600(131),
      bps595200(132),
      bps604800(133),
      bps614400(134)
       }
      MAX-ACCESS  read-write
      STATUS  current
      DESCRIPTION
   "KLS.1 supports (Kbps): 0.3, 0.6, 1.2, 2.4, 4.8, 9.6, 19.2, 38.4.
    KLS.1/New, KDI/CH support (Kbps): 
                               Group 1: 0.3, 0.6, 1.2, 2.4, 4.8, 9.6, 
                                       19.2, 38.4
                               Group 2: 7.2, 14.4, 28.8, 57.6
                               Group 3: 8, 16, 24, 32, 48, 56, 64 
    KLS.2 supports (Kbps): 2.4, 4.8, 9.6, 19.2.
    KHS.1 supports (Kbps): 32, 48, 56, 64, 128, 192, 256, 384
    KHS.2 supports (Kbps): ...
    KHSU.1/2 support (Kbps): 16, 32, 64.
    KHS.703 support (Kbps): 64."
      ::= { prtHsLsEntry 11}

prtHsLsUType OBJECT-TYPE
      SYNTAX  INTEGER {
      notApplicable(1), 
      regular(2),
      type1  (3)
       }
      MAX-ACCESS  read-write
      STATUS  current
      DESCRIPTION
      "U Interface Type. Applicable for KHSU.1/2 cards.
       The value will be the same for B1 and B2 pair; B3 and B4."
      ::= { prtHsLsEntry 12}



prtTreMbe  OBJECT IDENTIFIER  ::=  {prtKmux 3}

prtTreMbeTable OBJECT-TYPE
      SYNTAX SEQUENCE OF PrtTreMbeEntry
      MAX-ACCESS not-accessible
      STATUS  current
      DESCRIPTION
       "The write operation into the Table Objects is valid only
        to the TmpCnfg entry. Parameters for the channels of the
        TRE and MBE cards: KTRE, KMBE, KMBE/NEW."
      ::= {prtTreMbe 2}

prtTreMbeEntry OBJECT-TYPE
      SYNTAX PrtTreMbeEntry
      MAX-ACCESS not-accessible
      STATUS current
	DESCRIPTION  "An entry in table."
	INDEX {prtTreMbeCnfgIdx, prtTreMbeIdx }
      ::= { prtTreMbeTable 1}

PrtTreMbeEntry ::=
      SEQUENCE {
        prtTreMbeCnfgIdx     Integer32,
        prtTreMbeIdx         Integer32,
        prtTreMbeSlt         INTEGER,
        prtTreMbeLan         INTEGER,
        prtTreMbeLanRate     INTEGER,
        prtTreMbeLinkSpeed   INTEGER
      }

prtTreMbeCnfgIdx OBJECT-TYPE
      SYNTAX  Integer32  (1..255)
      MAX-ACCESS  read-only
      STATUS  current
      DESCRIPTION
      "This attribute indicates the Idx of the Cnfg (1..100) being
       accessed.
       Idx 255 relates to the TmpCnfg."
      ::= {prtTreMbeEntry 1}

prtTreMbeIdx OBJECT-TYPE
      SYNTAX  Integer32
      MAX-ACCESS  read-only
      STATUS  current
      DESCRIPTION
      "A unique port identifier within the card.
       Slot*100+11 ."
      ::= {prtTreMbeEntry 2}

prtTreMbeSlt OBJECT-TYPE
      SYNTAX  INTEGER
     {
    kmxIO1 (107),
    kmxIO2 (108),
    kmxIO3 (109),
    kmxIO4 (110),
    kmxIO5 (111),
    kmxIO6 (112),
    kmxIO7 (113),
    kmxIO8 (114),
    kmxIO9 (115),
    kmxIO10(116),
    kmxIO11(117),
    kmxIO12(118)
       }
      MAX-ACCESS  read-only
      STATUS  current
      DESCRIPTION
      "This attribute indicates a unique number to identify the slot where
       the card is inserted in.
       In the 2104 Unit the entries kmxIO5(111)..kmxIO12(118) are not valid."
      ::= {prtTreMbeEntry 3}

prtTreMbeLan OBJECT-TYPE
      SYNTAX  INTEGER
       {
        notApplicable(1),
        main         (2),
        remote       (3)
		
       }
      MAX-ACCESS  read-write
      STATUS  current
      DESCRIPTION
      "This attribute indicates whether the TRE/MBE port is operated 
       as main or remote bridge.
       Default=remote."
      ::= {prtTreMbeEntry 4}

prtTreMbeLanRate OBJECT-TYPE
      SYNTAX  INTEGER
       {
        notApplicable(1),
        r4M  (2),
        r16M (3)
       }
      MAX-ACCESS  read-write
      STATUS  current
      DESCRIPTION
      "This attribute indicates the Rate of the TRE port 
       in Mbit/sec. Default-r4M."
      ::= {prtTreMbeEntry 5}

prtTreMbeLinkSpeed OBJECT-TYPE
      SYNTAX  INTEGER
       {
  notConnected(1),
  bps9600   (2),
  bps19200  (3),
  bps28800  (4),
  bps38400  (5),
  bps48000  (6),
  bps57600  (7),
  bps67200  (8),
  bps76800  (9),
  bps86400 (10),
  bps96000 (11),
  bps105600(12),
  bps115200(13),
  bps124800(14),
  bps128000(15),
  bps160000(16),
  bps192000(17),
  bps224000(18),
  bps240000(19),
  bps272000(20),
  bps304000(21),
  bps336000(22),
  bps368000(23)
       }
      MAX-ACCESS  read-write
      STATUS  current
      DESCRIPTION
      "The Link Speed."
      ::= {prtTreMbeEntry 6}


prtVoiceFax  OBJECT IDENTIFIER  ::=  {prtKmux 4}

prtVoiceFaxTable OBJECT-TYPE
      SYNTAX SEQUENCE OF PrtVoiceFaxEntry
      MAX-ACCESS not-accessible
      STATUS  current
      DESCRIPTION
       "The write operation into the Table Objects is valid only
        to the TmpCnfg entry. Parameters for the channels of the
        Voice and Fax channels. 
        Cards: KVC.1/E&M,  KVC.1/FXO,  KVC.1/FXS,
               KVC.1M/E&M, KVC.1M/FXO, KVC.1M/FXS, KVC.1M/FXSW, 
               KVC.2/E&M,  KVC.2/FXO,  KVC.2/FXS, 
               KVC.2/1/E&M,KVC.2/1/FXO,KVC.2/1/FXS, 
               KVC.3/E&M,  KVC.3/FXO,  KVC.3/FXS, KVC.3/S0
               KVF.1/E&M,  KVF.1/FXO,  KVF.1/FXS, 
               KVF.3/E&M,  KVF.3/FXO,  KVF.3/FXS, 
               KVF.4/E&M,  KVF.4/FXO,  KVF.4/FXS, KVF.4/FXSW, KVF.4/S0,
               KVF.4/FXO3, KVF.4/FXS3, KVF.4/NS0     
               KVF.5 family, KVF.6 family, KVF.8 family."
      ::= { prtVoiceFax 1}

prtVoiceFaxEntry OBJECT-TYPE
      SYNTAX PrtVoiceFaxEntry
      MAX-ACCESS not-accessible
      STATUS current
	DESCRIPTION  "An entry in table."
	INDEX {prtVoiceFaxCnfgIdx, prtVoiceFaxIdx }
      ::= { prtVoiceFaxTable 1}

PrtVoiceFaxEntry ::=
      SEQUENCE {
        prtVoiceFaxCnfgIdx         Integer32,
        prtVoiceFaxIdx             Integer32,
        prtVoiceFaxSlt             INTEGER,
        prtVoiceFaxTransGain       Integer32,
        prtVoiceFaxReceiveGain     Integer32,
        prtVoiceFaxWire            INTEGER,
        prtVoiceFaxTimeOut         INTEGER,
        prtVoiceFaxEchoCanceler    INTEGER,
        prtVoiceFaxSpeed           INTEGER,
        prtVoiceFaxMeterRate       INTEGER,
        prtVoiceFaxCodingLaw       INTEGER,
		prtVoiceFaxOperMode	       INTEGER,
		prtVoiceFaxSigInOutband    OCTET STRING,
		prtVoiceFaxTsGroup         INTEGER,
		prtVoiceFaxRxFaxGain       Integer32,
		prtVoiceFaxSigHold         INTEGER,
		prtVoiceFaxIfSignaling     INTEGER,
		prtVoiceFaxEMTypes         INTEGER,
		prtVoiceFaxRingFrequency   INTEGER,
		prtVoiceFaxSignalingStatus OCTET STRING

      }

prtVoiceFaxCnfgIdx OBJECT-TYPE
      SYNTAX  Integer32  (1..255)
      MAX-ACCESS  read-only
      STATUS  current
      DESCRIPTION
      "This attribute indicates the Idx of the Cnfg (1..100) being 
       accessed.
       Idx  255 relates to the TmpCnfg."
      ::= {prtVoiceFaxEntry 1}

prtVoiceFaxIdx OBJECT-TYPE
      SYNTAX  Integer32
      MAX-ACCESS  read-only
      STATUS  current
      DESCRIPTION
      "A unique identifier of the port, within the card.
       Slot*100+Ch
       external ports:  Ch=1..10
       internal ports (sub-channels): Ch=11..20."
      ::= {prtVoiceFaxEntry 2}

prtVoiceFaxSlt OBJECT-TYPE
      SYNTAX  INTEGER
 {
    kmxIO1 (107),
    kmxIO2 (108),
    kmxIO3 (109),
    kmxIO4 (110),
    kmxIO5 (111),
    kmxIO6 (112),
    kmxIO7 (113),
    kmxIO8 (114),
    kmxIO9 (115),
    kmxIO10(116),
    kmxIO11(117),
    kmxIO12(118)
       }
      MAX-ACCESS  read-only
      STATUS  current
      DESCRIPTION
      "This attribute indicates a unique number to identify the slot where
       the card is inserted in.
       In the 2104 Unit the entries kmxIO5(111)..kmxIO12(118) are not valid."
      ::= {prtVoiceFaxEntry 3}

prtVoiceFaxTransGain OBJECT-TYPE
      SYNTAX  Integer32          
      MAX-ACCESS  read-write
      STATUS  current
      DESCRIPTION
      "Transmit gain in dBm. A value of 255 is for notApplicable.
       The value will be:  real value+50dBm (in order to avoid
       negative values)."
      ::= {prtVoiceFaxEntry 4}

prtVoiceFaxReceiveGain OBJECT-TYPE
      SYNTAX  Integer32       
      MAX-ACCESS  read-write
      STATUS  current
      DESCRIPTION
      "Receive gain in dBm. A value of 255 is for notApplicable.
       The value will be:  real value+50dBm (in order to avoid
       negative values)."
      ::= {prtVoiceFaxEntry 5}

prtVoiceFaxWire OBJECT-TYPE
      SYNTAX  INTEGER
       {notApplicable(1),
           w2wire   (2),
           w4wire   (3)
       }
      MAX-ACCESS  read-write
      STATUS  current
      DESCRIPTION
      "Applicable only for E&M cards."
      ::= {prtVoiceFaxEntry 6}

prtVoiceFaxTimeOut OBJECT-TYPE
      SYNTAX  INTEGER
       {notApplicable(1),
     manual(2),
     sec30 (3),
     sec60 (4),
     sec90 (5)
       }
      MAX-ACCESS  read-write
      STATUS  current
      DESCRIPTION
      "Fax timeout in seconds."
      ::= {prtVoiceFaxEntry 7}

prtVoiceFaxEchoCanceler OBJECT-TYPE
      SYNTAX  INTEGER
       {notApplicable(1),
           off    (2),
           on     (3)
       }
      MAX-ACCESS  read-write
      STATUS  current
      DESCRIPTION
      "Echo canceler activation."
      ::= {prtVoiceFaxEntry 8}

prtVoiceFaxSpeed OBJECT-TYPE
      SYNTAX  INTEGER
      {notConnected(1),
    bps4800(2),
    bps6400(3),
    bps7200(4),
    bps8000(5),
    bps9600(6),
    bps12800(7),
    bps16000(8),
    bps24000(9),
    bps32000(10),
    bps64000(11),
	bps11200(12)
      }
      MAX-ACCESS  read-write
      STATUS  current
      DESCRIPTION
      "The channel speed.
       For KVF.6 and KVF.8 cards, each value will represent [4 x value], since each
       channel (Internal or External) is comprised of 4 sub-channels having the selected value."
      ::= {prtVoiceFaxEntry 9}

prtVoiceFaxMeterRate OBJECT-TYPE
      SYNTAX  INTEGER
      {
        notApplicable(1),
        r16Khz (2),
        r12Khz (3)
      }
      MAX-ACCESS  read-write
      STATUS  current
      DESCRIPTION
      "This entry is valid to KVF.4/FXO3 and KVF.4/FXS3.
       Meter Rate means rate of Call Meter in Public Phones, in KHz units.
       Must be equal for both channels."
      ::= {prtVoiceFaxEntry 10}

prtVoiceFaxCodingLaw OBJECT-TYPE
      SYNTAX  INTEGER
      {
        notApplicable(1),
        aLaw         (2),
        uLaw         (3)
      }
      MAX-ACCESS  read-write
      STATUS  current
      DESCRIPTION
      "Coding Law. This entry is valid for KVF.4/NS0 external channel and 
       KVF.6 internal channels."
      ::= {prtVoiceFaxEntry 11}

prtVoiceFaxOperMode OBJECT-TYPE
      SYNTAX  INTEGER
      {
        notApplicable      (1),
        voiceANDfax        (2),
        voice              (3),
		voiceAndFaxAndData (4)
      }
      MAX-ACCESS  read-write
      STATUS  current
      DESCRIPTION
      "Operation Mode. This parameter is valid for KVF.6 and KVF.8 family."
      ::= {prtVoiceFaxEntry 12}

prtVoiceFaxSigInOutband OBJECT-TYPE
      SYNTAX  OCTET STRING	 (SIZE(2))
      MAX-ACCESS  read-write
      STATUS  current
      DESCRIPTION
      "This object is applicable for KVF.4/FXO3, KVF.4/FXS3, KVF.8 family cards.

	   For KVF.4/FXO3, KVF.4/FXS3:
	   Octet 1 for Receive parameters.
	   Octet 2 for Transmit parameters. 
       It represents 4 parameters, in each Octet :
	   Bit 7     6     5     4     3     2     1     0
	       |_____|     |_____|     |_____|     |_____|
	   MSB  Spare    On/Off Hook   Metering    Polarity LSB   

       Each parameter's bits represent:
       00 = NC
       01 = Inband(A/B)
       10 = Outband(A)	
       11 = Outband(B)
    

	  For KVF.8 family:
	   It represents 4 parameters, by 2 Octets :
       General Bit Code-    MSB nibble,
       On/Off Hook Bit Code-    nibble,
       Metering Bit Code-       nibble,
       Polarity Bit Code-   LSB nibble.

       Each of General, On/Off Hook, Metering, Polarity Bit Code nibble represents:
       0 hex = 0000 = 0
       1 hex = 0001 = 1
       2 hex = 0010 = A bit
       3 hex = 0011 = B bit
       4 hex = 0100 = C bit
       5 hex = 0101 = D bit
       6 hex = 0110 = A bit inverse
       7 hex = 0111 = B bit inverse
       8 hex = 1000 = C bit inverse
       9 hex = 1001 = D bit inverse
       A-E hex - not used (invalid values)


       When the object is not applicable, 0 Octets will be sent."
      ::= {prtVoiceFaxEntry 13}

prtVoiceFaxTsGroup OBJECT-TYPE
      SYNTAX  INTEGER
      {
		notApplicable(1),
        s1s2s3s4     (2),
        s5s6s7s8     (3),
        s9s10s11s12  (4),
        s13s14s15s16 (5),
        s17s18s19s20 (6),
        s21s22s23s24 (7),
        s25s26s27s28 (8),
        s29s30s31    (9)
        }
      MAX-ACCESS  read-write
      STATUS  current
      DESCRIPTION
      "Ts Assignment group. Each KVF.6 internal channel should have 
       a different value.
	   's21s22s23s24' = TSs: 21, 22, 23, 24
   	   For KVF.6/E1/16, KVF.6/E1/31 values: 2..9 are applicable.
       For KVF.6/T1/12, KVF.6/T1/24 values: 2..7 are applicable."
      ::= {prtVoiceFaxEntry 14}

prtVoiceFaxRxFaxGain OBJECT-TYPE
      SYNTAX  Integer32       
      MAX-ACCESS  read-write
      STATUS  current
      DESCRIPTION
      "FAX Receive gain in dBm. 
       The value will be:  (real value*10)+500dBm (in order to avoid
       negative and fractional values)."
      ::= {prtVoiceFaxEntry 15}
    
prtVoiceFaxSigHold  OBJECT-TYPE
      SYNTAX  INTEGER
       {
	   notApplicable(1),
       sec0(2),
       sec10(3)
       }
      MAX-ACCESS  read-write
      STATUS  current
      DESCRIPTION
      "Signal Hold in [sec]. Applicable for all KVF.4 cards except S0/NS0.
       When a ML fails, instead of interrupting immediately a 
       conversation and connecting it again when ML operation is resumed, 
       user can select to Hold the signal a few seconds before interruption (ML 
       operation may return during this time).
       sec0 = No Hold = 0 sec
       sec10= 10 sec hold."
   ::= {prtVoiceFaxEntry 16}

															 
prtVoiceFaxIfSignaling OBJECT-TYPE
      SYNTAX  INTEGER
       {notApplicable   (1),
           loopStart    (2),
           groundStart  (3),
		   winkStart    (4)
       }
      MAX-ACCESS  read-write
      STATUS  current
      DESCRIPTION
      "Applicable only for KVF.8/FXO, KVF.8/FXS cards.
       Interface Analog Signaling."
      ::= {prtVoiceFaxEntry 17}


prtVoiceFaxEMTypes OBJECT-TYPE
      SYNTAX  INTEGER
       {notApplicable   (1),
           em1          (2),
           em2          (3),
		   em3          (4),
		   ssdc5   	    (5)
       }
      MAX-ACCESS  read-write
      STATUS  current
      DESCRIPTION
      "Applicable only for KVF.8/E&M card."
      ::= {prtVoiceFaxEntry 18}
      


prtVoiceFaxRingFrequency OBJECT-TYPE
      SYNTAX  INTEGER
	  {
        notApplicable (1),
        f16dot7Hz     (2),
        f20Hz         (3),
		f25Hz         (4),
		f50Hz         (5)
      }
      MAX-ACCESS  read-write
      STATUS  current
      DESCRIPTION
      "Applicable only for KVF.8/E&M card.
       The Ringing Frequency units will be in Hz."
      ::= {prtVoiceFaxEntry 19}

prtVoiceFaxSignalingStatus OBJECT-TYPE	      
      SYNTAX  OCTET STRING	 (SIZE(0..2))
      MAX-ACCESS  read-write
      STATUS  current
      DESCRIPTION
      "For KM-2100 this parameter should be Read Only.
       This object is applicable for KVF.6 and KVF.5 family cards.
	   It shows the status (0 or 1) of each Signaling Bit (A, B, C, D), 
	   for each TS of a TS Group (according to it's position in the group).
       Each nibble represent a TS from the 'TS Group' selected 
       for the channel (two Octets represents 4 TSs of each group):
      
       Bit 7  6  5  4  3  2  1  0  7  6  5  4  3  2  1  0
	       |________|  |________|  |________|  |________|
	   MSB   TS i+3      TS i+2      TS i+1      TS i    LSB   

       It represents 4 parameters for each TS:
		 TS-i          TS-i+1     ..
       0 - A bit       4 - A bit
	   1 - B bit	   5 - B bit
	   2 - C bit	   6 - C bit
	   3 - D bit	   7 - D bit

  	   When the object is not applicable, 0 Octets will be sent."
      ::= {prtVoiceFaxEntry 20}
-- 
-- file :D:\Synergy\WorkArea\545\mib_rad\txt\imx.txt
-- 
--RAD-IMX-MIB

--                RAD-IMX MIB    (Inverse Multiplexer)

--Title:     RAD's IMX-64 PRODUCT MIB
--Version:   1.0
--Date:      1.8.96
--By:        Yair Arian
--File:      imx.mib
--
--Update: 16.09.99 by Smadar (corrected conflicts with existing RAD MIB).
--Last Update : 06.01.00 by Smadar (added comments for Traps)


imx  OBJECT IDENTIFIER  ::=  {radWan 7}


systemImx  OBJECT IDENTIFIER  ::=  {imx 1}

generalImx  OBJECT IDENTIFIER  ::=  {systemImx 1}

sysGenClearAlarm OBJECT-TYPE
      SYNTAX INTEGER { on(1),
	                   off(2)
					 }
      MAX-ACCESS read-write
      STATUS current
      DESCRIPTION
      "Clear the alarm buffer. The agent resets the variable automatically
       to off."
      ::= { generalImx 1}

sysGenAlarmBuffTable  OBJECT-TYPE
      SYNTAX SEQUENCE OF SysGenAlarmBuffEntry
      MAX-ACCESS not-accessible
      STATUS  current
      DESCRIPTION
      "The alarm buffer of the imx."
       ::= { generalImx 2 }

sysGenAlarmBuffEntry OBJECT-TYPE
      SYNTAX SysGenAlarmBuffEntry
      MAX-ACCESS not-accessible
      STATUS current
      DESCRIPTION
	  "An entry in table sysGenAlarmBuffTable."
      INDEX {sysGenAlarmBuffIndex}
      ::= { sysGenAlarmBuffTable 1}

SysGenAlarmBuffEntry ::=
      SEQUENCE {
	  sysGenAlarmBuffIndex Integer32,
	  sysGenAlarmDescr     DisplayString
      }

sysGenAlarmBuffIndex OBJECT-TYPE
      SYNTAX Integer32 (1..100)
      MAX-ACCESS read-only
      STATUS current
      DESCRIPTION
      "The index of the alarm buffer Table."
      ::= { sysGenAlarmBuffEntry 1}

sysGenAlarmDescr OBJECT-TYPE
      SYNTAX DisplayString
      MAX-ACCESS read-only
      STATUS current
      DESCRIPTION
      "The description of the alarm. Up to 80 chars."
      ::= { sysGenAlarmBuffEntry 2}

sysGenClearLog OBJECT-TYPE
      SYNTAX INTEGER { on(1),
	                   off(2)
					 }
      MAX-ACCESS read-write
      STATUS current
      DESCRIPTION
      "Clear the log buffer. The agent resets the variable automatically
       to off."
      ::= { generalImx 3}

sysGenLogTable  OBJECT-TYPE
      SYNTAX SEQUENCE OF SysGenLogEntry
      MAX-ACCESS not-accessible
      STATUS  current
      DESCRIPTION
      "The call log buffer of the imx."
       ::= { generalImx 4 }

sysGenLogEntry OBJECT-TYPE
      SYNTAX SysGenLogEntry
      MAX-ACCESS not-accessible
      STATUS current
      DESCRIPTION
	  "An entry in table sysGenLogTable."
      INDEX {sysGenLogIndex}
      ::= { sysGenLogTable 1}

SysGenLogEntry ::=
      SEQUENCE {
	  sysGenLogIndex     Integer32,
	  sysGenLogDescr     DisplayString
      }

sysGenLogIndex OBJECT-TYPE
      SYNTAX Integer32 (1..100)
      MAX-ACCESS read-only
      STATUS current
      DESCRIPTION
      "The index of the log Table."
      ::= { sysGenLogEntry 1}

sysGenLogDescr OBJECT-TYPE
      SYNTAX DisplayString
      MAX-ACCESS read-only
      STATUS current
      DESCRIPTION
      "The description of the entry in the log buffer. Up to 80 chars."
      ::= { sysGenLogEntry 2}


profilesImx  OBJECT IDENTIFIER  ::=  {systemImx 2}

callProfileImx  OBJECT IDENTIFIER  ::=  {profilesImx 1}

sysCallProfileTable  OBJECT-TYPE
      SYNTAX SEQUENCE OF SysCallProfileEntry
      MAX-ACCESS not-accessible
      STATUS  current
      DESCRIPTION
      "A table containing call profile parameters. There are 40 call
       profiles."
       ::= { callProfileImx 1 }

sysCallProfileEntry OBJECT-TYPE
      SYNTAX SysCallProfileEntry
      MAX-ACCESS not-accessible
      STATUS current
      DESCRIPTION
	  "An entry in table sysCallProfileTable."
      INDEX {sysCallProfileIndex}
      ::= {sysCallProfileTable 1}

SysCallProfileEntry ::=
      SEQUENCE {
	  sysCallProfileIndex                  Integer32,
	  sysCallProfileConnectCmd             INTEGER,
	  sysCallProfileDisconnectCmd          INTEGER,
	  sysCallProfileIncrBwCmd              Integer32,
	  sysCallProfileDecrBwCmd              Integer32
      }

sysCallProfileIndex OBJECT-TYPE
      SYNTAX Integer32 (1..40)
      MAX-ACCESS read-only
      STATUS current
      DESCRIPTION
      "A running index for the table."
      ::= { sysCallProfileEntry 1}

sysCallProfileConnectCmd OBJECT-TYPE
      SYNTAX INTEGER { off(1),
	                   on(2)
					}
      MAX-ACCESS read-write
      STATUS current
      DESCRIPTION
      "On(2) - Connect the call profile. The agent will automatically
       reset the variable to off(1) ."
      ::= { sysCallProfileEntry 2}

sysCallProfileDisconnectCmd OBJECT-TYPE
      SYNTAX INTEGER { off(1),
	                   on(2)
					}
      MAX-ACCESS read-write
      STATUS current
      DESCRIPTION
      "On(2) - Disconnect the call profile. The agent will automatically
       reset the variable to off(1)."
      ::= { sysCallProfileEntry 3}

sysCallProfileIncrBwCmd OBJECT-TYPE
      SYNTAX Integer32 (0..6)
      MAX-ACCESS read-write
      STATUS current
      DESCRIPTION
      "Increment bandwidth of a call.
       The number of channels to increment 1..6. The agent will automatically
       reset the variable to 0."
      ::= { sysCallProfileEntry 4}

sysCallProfileDecrBwCmd OBJECT-TYPE
      SYNTAX Integer32 (0..6)
      MAX-ACCESS read-write
      STATUS current
      DESCRIPTION
      "Decrement bandwidth of a call.
       The number of channels to decrement 1..6. The agent will automatically
       reset the variable to 0."
      ::= { sysCallProfileEntry 5}


portImx  OBJECT IDENTIFIER  ::=  {imx 2}

userPortImx  OBJECT IDENTIFIER  ::=  {portImx 1}

prtCnfgTable  OBJECT-TYPE
      SYNTAX SEQUENCE OF PrtCnfgEntry
      MAX-ACCESS not-accessible
      STATUS  current
      DESCRIPTION
      "A table containing configuration parameters for the user ports."
       ::= { userPortImx 1 }

prtCnfgEntry OBJECT-TYPE
      SYNTAX PrtCnfgEntry
      MAX-ACCESS not-accessible
      STATUS current
      DESCRIPTION
	  "An entry in table prtCnfgTable."
      INDEX {prtIndex}
      ::= {prtCnfgTable 1}

PrtCnfgEntry ::=
      SEQUENCE {
	  prtIndex                Integer32,
	  prtCnfgDecrBwChNum      Integer32,	
	  prtCnfgIncrBwChNum      Integer32,	
	  prtCnfgDisconnect       INTEGER,
	  prtCnfgActivateLoop     INTEGER,
	  prtCnfgClearLoop        INTEGER,
	  prtCnfgLoopStatus       Integer32
	  }

prtIndex OBJECT-TYPE
      SYNTAX Integer32 (1..2)
      MAX-ACCESS read-only
      STATUS current
      DESCRIPTION
      "The user port index."
      ::= { prtCnfgEntry 1}

prtCnfgDecrBwChNum OBJECT-TYPE
      SYNTAX Integer32 (0..6)
      MAX-ACCESS read-write
      STATUS current
      DESCRIPTION
      "Decrement the port bandwidth by the specified number of channels.
       The agent resets the variable to 0."
      ::= { prtCnfgEntry 2}

prtCnfgIncrBwChNum OBJECT-TYPE
      SYNTAX Integer32 (0..6)
      MAX-ACCESS read-write
      STATUS current
      DESCRIPTION
      "Increment the port bandwidth by the specified number of channels.
       The agent resets the variable to 0."
      ::= { prtCnfgEntry 3}

prtCnfgDisconnect OBJECT-TYPE
      SYNTAX INTEGER { on(1),
	                   off(2)
					 }
      MAX-ACCESS read-write
      STATUS current
      DESCRIPTION
      "Disconnect the port (on(1)). The agent resets the variable to off(2)."
      ::= { prtCnfgEntry 4}

prtCnfgActivateLoop OBJECT-TYPE
      SYNTAX INTEGER { none(1),
                       local(2),
	                   remote(3),
					   bonding(4)
					 }
      MAX-ACCESS read-write
      STATUS current
      DESCRIPTION
      "Activate the desired loop on the port. 
       The agent will reset the variable to none(1)."
      ::= { prtCnfgEntry 5}

prtCnfgClearLoop OBJECT-TYPE
      SYNTAX INTEGER { none(1),
                       local(2),
	                   remote(3),
					   bonding(4),
					   all(5)
					 }
      MAX-ACCESS read-write
      STATUS current
      DESCRIPTION
      "Clear the desired loop from the port. The agent will
       reset the variable to none(1)"
      ::= { prtCnfgEntry 6}

prtCnfgLoopStatus OBJECT-TYPE
      SYNTAX Integer32 
      MAX-ACCESS read-only
      STATUS current
      DESCRIPTION
      "The loop status at this port. The variable is a sum of 2**n where
       n is as follows:
       0 - Local Loop is on.
       1 - Remote Loop is on.
       2 - BONDING Loop is on.
       If the variable is 0, there is no active loop."
      ::= { prtCnfgEntry 7}


supervisoryPortImx  OBJECT IDENTIFIER  ::=  {portImx 2}

prtSpUsageImx OBJECT-TYPE
      SYNTAX INTEGER { nmsSlip(2),
	                   terminal(3)
					 }
     MAX-ACCESS read-write
      STATUS current
      DESCRIPTION
      "The supervisory port terminal usage definition."
      ::= { supervisoryPortImx 1}


channelImx  OBJECT IDENTIFIER  ::=  {imx 4}

channelCnfgTable  OBJECT-TYPE
      SYNTAX SEQUENCE OF ChannelCnfgEntry
      MAX-ACCESS not-accessible
      STATUS  current
      DESCRIPTION
      "A table containing configuration parameters for the channels."
       ::= { channelImx 1 }

channelCnfgEntry OBJECT-TYPE
      SYNTAX ChannelCnfgEntry
      MAX-ACCESS not-accessible
      STATUS current
      DESCRIPTION
	  "An entry in table channelCnfgTable."
      INDEX {chIndex}
      ::= {channelCnfgTable 1}

ChannelCnfgEntry ::=
      SEQUENCE {
	  chIndex                 Integer32,
	  chCnfgUnlock           INTEGER,
	  chCnfgPing             INTEGER
	  }

chIndex OBJECT-TYPE
      SYNTAX Integer32 (1..6)
      MAX-ACCESS read-only
      STATUS current
      DESCRIPTION
      "The channel index."
      ::= { channelCnfgEntry 1}

chCnfgUnlock OBJECT-TYPE
      SYNTAX INTEGER { on(1),
	                   off(2)
					 }
      MAX-ACCESS read-write
      STATUS current
      DESCRIPTION
      "Unlock the channel (on). The agent resets the variable to off."
      ::= { channelCnfgEntry 2}

chCnfgPing OBJECT-TYPE
      SYNTAX INTEGER  { on(1),
	                   off(2)
					 }
      MAX-ACCESS read-write
      STATUS current
      DESCRIPTION
      "Ping the channel (on). The agent resets the variable to off."
      ::= { channelCnfgEntry 3}


channelStatTable  OBJECT-TYPE
      SYNTAX SEQUENCE OF ChannelStatEntry
      MAX-ACCESS not-accessible
      STATUS  current
      DESCRIPTION
      "A table containing status and statistics information for the channels."
       ::= { channelImx 2 }

channelStatEntry OBJECT-TYPE
      SYNTAX ChannelStatEntry
      MAX-ACCESS not-accessible
      STATUS current
      DESCRIPTION
	  "An entry in table channelStatTable."
      INDEX {chIndex}
      ::= {channelStatTable 1}

ChannelStatEntry ::=
      SEQUENCE {
	  chStatOperStatus		  INTEGER
	  }

chStatOperStatus OBJECT-TYPE
      SYNTAX INTEGER { up(1),
	                   down(2),
					   engaged(3),
					   notDedicated(4)
					 }
      MAX-ACCESS read-only
      STATUS current
      DESCRIPTION
      "The operational state of the channel based on a ping operation."
      ::= { channelStatEntry 1}

-- Traps

imxAlarmTrap NOTIFICATION-TYPE
      STATUS  current
      DESCRIPTION
	  "The trap is sent every time a new alarm is logged into the alarm
	   buffer. The trap may not be sent more than once in a five second
	   interval."
      ::= { radSysWanEvents 2 }

imxCallLogTrap NOTIFICATION-TYPE
      STATUS  current
      DESCRIPTION
	  "The trap is sent every time a new call log entry is logged into the
	   log buffer. The trap may not be sent more than once in a five second
	   interval."
      ::= { radSysWanEvents 3 }

imxPingTrap NOTIFICATION-TYPE
      OBJECTS  {chStatOperStatus}
      STATUS  current
      DESCRIPTION
	  "The trap is sent every time a ping operation is performed on a
	   channel."
      ::= { radSysWanEvents 4 }

-- Traps 5-7 having the same enterprise, are used by ipmux.txt.


-- 
-- file :D:\Synergy\WorkArea\545\mib_rad\txt\ntePrtCo.txt
-- 
-- *************************
-- file  : NtePrtConfg.txt
--
--Version:   1.0
--Date:      12.11.97
--By:        Ilana Schvetz
--File:      v:\doc\rdv\mib\ver530\atm\NtePrtConfg.txt 

--Last Update: 8-Mar-07 by Shay Harari 
-- Copyright 1997 RAD Data Communications, Ltd.
-- All Rights Reserved.

atmNte              OBJECT IDENTIFIER ::= { radAtm 3 }
atmNtePrt		    OBJECT IDENTIFIER ::= { atmNte 2 }
atmNtePrtConfig		OBJECT IDENTIFIER ::= { atmNtePrt 1 }

atmNteEvents OBJECT-IDENTITY
     STATUS  current
     DESCRIPTION
     "The events for RAD ATM products."
     ::= { atmNte 0 }

atmNteConfIfTable OBJECT-TYPE
              SYNTAX  SEQUENCE OF AtmNteConfIfEntry
              MAX-ACCESS  not-accessible
              STATUS  current
              DESCRIPTION
              "The Physical interface configuration table."
              ::= { atmNtePrtConfig 1 }

          atmNteConfIfEntry OBJECT-TYPE
              SYNTAX  AtmNteConfIfEntry
              MAX-ACCESS  not-accessible
              STATUS  current
              DESCRIPTION
              "An entry in the Physical interface configuration table.
               The ifIndex is of the lowest physical layer."
              INDEX   { ifIndex}
              ::= { atmNteConfIfTable 1 }

          AtmNteConfIfEntry ::=
              SEQUENCE {
				atmConfIfTransmitClk
				      INTEGER,
				atmConfIfLoopback
				      INTEGER,
				atmConfIfFrameType
				      INTEGER,
				atmConfIfCardType
				      INTEGER,
				atmConfAtmIfVpiVciLimit
				      INTEGER,
				atmConfIfHwFeatures
				      INTEGER,
				atmConfIfOutputRate
				      Integer32,
				atmConfIfInputRate
				      Integer32,
				atmConfAlarmForwarding
				      INTEGER,
				atmConfIfAllocatedBw
					  Integer32,
				atmConfIfLowerVpi
					  Integer32,
				atmConfIfOamMode
					  INTEGER,
				atmConfIfOamFailureInd
					  INTEGER
                 }

          atmConfIfTransmitClk OBJECT-TYPE
              SYNTAX  INTEGER { internal(2), external(3), loopback(4), adaptive(5) }
              MAX-ACCESS  read-write
              STATUS  current
              DESCRIPTION
              "The transmit clock of the port."
              ::= { atmNteConfIfEntry 1 }

          atmConfIfLoopback OBJECT-TYPE
              SYNTAX  INTEGER { internal(2), external(3), disable(4) }
              MAX-ACCESS  read-write
              STATUS  current
              DESCRIPTION
              "Interface Loopback."
              ::= { atmNteConfIfEntry 2 }

          atmConfIfFrameType OBJECT-TYPE
              SYNTAX  INTEGER {  
              other        (1),
              sonet        (2),
			  sdh          (3),
			  direct       (4),
			  plcpInternal (5),
			  plcpExternal (6),
			  e3           (7),
			  ethCrcTrans  (8),	
			  ethCrcNotTrans          (9),
	          directNoScrmbling       (10),
	          plcpInternalNoScrmbling (11),
	          plcpExternalNoScrmbling (12)
	          }
              MAX-ACCESS  read-write
              STATUS  current
              DESCRIPTION
              "The frame type. Valid values for a 155M interface:
               sonet(2), sdh(3). Valid values for a T3 interface:
               direct(4), plcpInternal(5), plcpExternal(6), 
               directNoScrmbling(10), plcpInternalNoScrmbling(11),
               plcpExternalNoScrmbling(12). Valid values for Ethernet 
               interface: ethCrcTrans (8), ethCrcNotTrans(9). 
               (DS1 interfaces frame type is specified in the DSX1 mib)."
              ::= { atmNteConfIfEntry 3 }

          atmConfIfCardType OBJECT-TYPE
              SYNTAX  INTEGER {
		      notApplicable(1), 
		      sc13m-155(2),
		      st13s-155(3),
		      st13l-155(4),
		      utp-155(5),
		      cx-bnc-155(6),
		      e3(7),
		      t3(8),
			  e1(9),
		      e1-ltu(10),
		      fc13l-155(11),
		      fc13lh-155(12),
		      fc15lh-155(13),
		      fc13l-e3(14),
	          fc13lh-e3(15),
		      fc15lh-e3(16),
		      fc13l-t3(17),
		      fc13lh-t3(18),
		      fc15lh-t3(19)
              }			
         	  MAX-ACCESS  read-only
         	  STATUS  deprecated
         	  DESCRIPTION
         	          "The card type."
         	  ::= { atmNteConfIfEntry 4 }
				
         	  atmConfAtmIfVpiVciLimit OBJECT-TYPE
         	  SYNTAX  INTEGER { 
         	  bits15(2),
			  bits17(3)
			   }
         	  MAX-ACCESS  read-only
         	  STATUS  current
         	  DESCRIPTION
         	  "The limit on the sum of the VPI+VCI bits for this interface."
         	  ::= { atmNteConfIfEntry 5 }
				
              atmConfIfHwFeatures  OBJECT-TYPE
              SYNTAX  INTEGER { 
              disable(1),
			  enable(2)
			  }
              MAX-ACCESS  read-write
              STATUS  current
              DESCRIPTION
              "HW features command."
              ::= { atmNteConfIfEntry 6 }

              atmConfIfOutputRate  OBJECT-TYPE
              SYNTAX  Integer32
              MAX-ACCESS  read-write
              STATUS  current
              DESCRIPTION
              "This parameter indicates the output rate in cells/sec, which is 
              supported per port. Successfully setting this parameter 
              is dependent on all other ports values calculations, 
              which are described in the NMS SRS."
              ::= { atmNteConfIfEntry 7 }

              atmConfIfInputRate  OBJECT-TYPE
              SYNTAX  Integer32
              MAX-ACCESS  read-write
              STATUS  current
              DESCRIPTION
              "This parameter indicates the input rate in cells/sec, which is 
              supported per port. Successfully setting this parameter 
              is dependent on all other ports values calculations, 
              which are described in the NMS SRS."
              ::= { atmNteConfIfEntry 8 }

          atmConfAlarmForwarding OBJECT-TYPE
              SYNTAX  INTEGER { disable(2), enable(3) }
              MAX-ACCESS  read-write
              STATUS  current
              DESCRIPTION
              "Enables Path AIS Alarm forwarding upon a failure detection. The
			  following might be considered as a failure: LOS, LOF, LOC, SLM, 
			  LOP, Path AIS and Line AIS. 
              
              disable(2) -  will not forward an alarm upon a failure on this port.  
              
              enable(3) - will forward an alarm upon a failure on this port."
              ::= { atmNteConfIfEntry 9 }

		  atmConfIfAllocatedBw OBJECT-TYPE
			  SYNTAX  Integer32 
    		  MAX-ACCESS read-only
			  STATUS current
			  DESCRIPTION
			  	"Total VC Bandwidth Allocation."
			  ::= { atmNteConfIfEntry 10 }

		  atmConfIfLowerVpi OBJECT-TYPE
    		  SYNTAX  Integer32
 		      MAX-ACCESS  read-write
		      STATUS  current
		      DESCRIPTION
			    "The Lower possible VPI."
			  ::= { atmNteConfIfEntry 11 }
		  
		  atmConfIfOamMode OBJECT-TYPE
    		  SYNTAX  INTEGER {
              		--	intermediate(1),
              		segmentTermination(2),
              		endToEndTermination(3)
			  		-- vpEndToEndVcSegment(4)
              	}
 		      MAX-ACCESS  read-write
		      STATUS  current
		      DESCRIPTION
			    "OAM support Mode, which determines the
			     interface's location in a segment wise."
			  ::= { atmNteConfIfEntry 12 }

	atmConfIfOamFailureInd OBJECT-TYPE
             SYNTAX INTEGER { 
             		disabled  (2), 
             		ais       (3),
             		rdi       (4),
             		aisAndRdi (5)
             		} 
             MAX-ACCESS read-write
             STATUS     current
             DESCRIPTION
             "This object allows user to define the type of indication
               (if any) that will be created upon a LB cell failure, 
               for all VCs on which OAM loopback traffic is activated.
                    disabled(2) - no indication will be created.
                    ais(3) - will cause Tx of AIS.
                    rdi(4) - will cause Tx of RDI.
                    aisAndRdi(5) - will cause Tx of AIS & RDI.
    	  For LA-110, indication will be sent only 
    	  for VCs with atmConfVcLoopbackFailureInd <> disabled"               
             ::= {atmNteConfIfEntry 13}
		  

atmNteAlarmIfTable OBJECT-TYPE
              SYNTAX  SEQUENCE OF AtmNteAlarmIfEntry
              MAX-ACCESS  not-accessible
              STATUS  current
              DESCRIPTION
                      "The interface Alarm table."
              ::= { atmNtePrtConfig 2 }

          atmNteAlarmIfEntry OBJECT-TYPE
              SYNTAX  AtmNteAlarmIfEntry
              MAX-ACCESS  not-accessible
              STATUS  current
              DESCRIPTION
                      "An entry in the interface Alarm table."
              INDEX   { ifIndex}
              ::= { atmNteAlarmIfTable 1 }

          AtmNteAlarmIfEntry ::=
              SEQUENCE {
				atmInterfaceActiveAlarms
				      Integer32,
				atmThresholdSectionBIP
				      Integer32,
				atmThresholdLineBIP
				      Integer32,
				atmThresholdLineFEBE
				      Integer32,
				atmThresholdPathBIP
				      Integer32,
				atmThresholdPathFEBE
				      Integer32,
				atmThresholdErroredCells
				      Integer32,
				atmThresholdLostCells
				      Integer32,
				atmThresholdMisinsertedCells
				      Integer32,
			    atmInterfaceAlarmStatus
				      INTEGER,
                atmInterfaceMaskAlarms
				      Integer32
              }

          atmInterfaceActiveAlarms OBJECT-TYPE
              SYNTAX  Integer32 
              MAX-ACCESS  read-only
              STATUS  current
              DESCRIPTION
                      "A Bit String of the active alarms on this interface.
					   An up bit (1) means there is an active alarm of this
					   type. A down bit (0) means there is no such alarm.
                       The meaning of the bits is as follows:
                       1 - LOS
                       2 - LOF
                       3 - Line AIS (SONET)/ PLCP LOF (DS3)
                       4 - LOP
                       5 - Path AIS
                       6 - SLM
                       7 - LCD
                       8 - Line RDI  (SONET)/ PLCP Yellow (DS3)
                       9 - Path RDI  (SONET)/ RDI (DS3)
					   10 - Section BIP (SONET)/ P1/P2 (DS3) > Threshold
					   11 -	Line BIP (SONET)/ PLCP BIP (DS3) > Threshold
					   12 - Line FEBE (SONET)/ PLCP FEBE (DS3) > Threshold
					   13 - Path BIP > Threshold
					   14 - Path FEBE > Threshold
					   15 - HW Failure
                       "
              ::= { atmNteAlarmIfEntry 1 }

          atmThresholdSectionBIP OBJECT-TYPE
              SYNTAX  Integer32 
              MAX-ACCESS  read-write
              STATUS  current
              DESCRIPTION
                      "When Section BIPs are greater than this threshold,
	an active alarm is raised. N/A for ds3/e3 interface."
              ::= { atmNteAlarmIfEntry 2 }

          atmThresholdLineBIP OBJECT-TYPE
              SYNTAX  Integer32 
              MAX-ACCESS  read-write
              STATUS  current
              DESCRIPTION
                      "When Line BIPs are greater than this threshold,
	an active alarm is raised. N/A for ds3/e3 interface."
              ::= { atmNteAlarmIfEntry 3 }

          atmThresholdLineFEBE OBJECT-TYPE
              SYNTAX  Integer32 
              MAX-ACCESS  read-write
              STATUS  current
              DESCRIPTION
                      "When Line FEBEs are greater than this threshold,
	an active alarm is raised. N/A for ds3/e3 interface."
              ::= { atmNteAlarmIfEntry 4 }

          atmThresholdPathBIP OBJECT-TYPE
              SYNTAX  Integer32 
              MAX-ACCESS  read-write
              STATUS  current
              DESCRIPTION
                      "When Path BIPs are greater than this threshold,
					   an active alarm is raised."
              ::= { atmNteAlarmIfEntry 5 }

          atmThresholdPathFEBE OBJECT-TYPE
              SYNTAX  Integer32 
              MAX-ACCESS  read-write
              STATUS  current
              DESCRIPTION
                      "When Path FEBEs are greater than this threshold,
					   an active alarm is raised."
              ::= { atmNteAlarmIfEntry 6 }

          atmThresholdErroredCells OBJECT-TYPE
              SYNTAX  Integer32 
              MAX-ACCESS  read-write
              STATUS  current
              DESCRIPTION
                      "When Errored Cells are greater than this threshold,
					   an active alarm is raised."
              ::= { atmNteAlarmIfEntry 7 }

          atmThresholdLostCells OBJECT-TYPE
              SYNTAX  Integer32 
              MAX-ACCESS  read-write
              STATUS  current
              DESCRIPTION
                      "When Lost Cells are greater than this threshold,
					   an active alarm is raised."
              ::= { atmNteAlarmIfEntry 8 }

          atmThresholdMisinsertedCells OBJECT-TYPE
              SYNTAX  Integer32 
              MAX-ACCESS  read-write
              STATUS  current
              DESCRIPTION
                      "When Misinserted Cells are greater than this threshold,
					   an active alarm is raised."
              ::= { atmNteAlarmIfEntry 9 }

 

          atmInterfaceAlarmStatus OBJECT-TYPE
              SYNTAX  INTEGER { off(2),
			                    on(3) }
              MAX-ACCESS  read-only
              STATUS  current
              DESCRIPTION
                      "The variable is on(3) when there is any active alarm
                       on this interface."
              ::= { atmNteAlarmIfEntry 10 }

          atmInterfaceMaskAlarms OBJECT-TYPE
              SYNTAX  Integer32 
              MAX-ACCESS  read-write
              STATUS  current
              DESCRIPTION
                      "A Bit String of alarms mask on this interface.
					   An up bit (1) means that the respective alarm is masked.
					   A down bit (0) means no mask.
                       The mask is supported for the following alarms:
                       1 - LOS
                       "
              ::= { atmNteAlarmIfEntry 11 }


          atmNteConfVpTable OBJECT-TYPE
              SYNTAX  SEQUENCE OF AtmNteConfVpEntry
              MAX-ACCESS  not-accessible
              STATUS  current
              DESCRIPTION
                      "The ATM VP configuration table.
                       The table is an extension to the atmVplTable of
                       RFC-1695."
              ::= { atmNtePrtConfig 3 }

          atmNteConfVpEntry OBJECT-TYPE
              SYNTAX  AtmNteConfVpEntry
              MAX-ACCESS  not-accessible
              STATUS  current
              DESCRIPTION
                      "An entry in the ATM VP configuration table.
                       ifIndex of the ATM layer."
              INDEX   { ifIndex, atmVplVpi }
              ::= { atmNteConfVpTable 1 }

          AtmNteConfVpEntry ::=
              SEQUENCE {
			atmConfVpPolicing            		INTEGER,
			atmConfVpCCAdminStatus       		INTEGER,
			atmConfVpLoopbackAdminStatus 		INTEGER,
			atmConfVpLoopbackSinkAddress 		OCTET STRING,
			atmConfVpCongestionControl   		OCTET STRING,
			atmConfVpCCDirection         		INTEGER,
            atmConfVpCreationTime        		DateAndTime,
            atmConfVpOamSupport          		INTEGER,
            atmConfVpCCOperStatus        		INTEGER,
			atmConfVpLoopbackTraffic     		INTEGER,
            atmConfVpLoopbackFailureInd	 		INTEGER,
            atmConfVpLoopbackFailureThreshold	Integer32,
			atmConfVpOamDirection        		INTEGER,
			atmConfVpOamDescrIndex	 	 		Integer32,
			atmConfVpConnected			 		INTEGER
           }

 atmConfVpPolicing OBJECT-TYPE
              SYNTAX  INTEGER { 
                 none(1), 
                 police(2), 
                 monitor(3), 
                 shaping(4), 
                 policingAndShaping(5) 
              }
              MAX-ACCESS  read-write
              STATUS  current
              DESCRIPTION
                      "Policing method desired for this VPL."
              ::= { atmNteConfVpEntry 1 }

        atmConfVpCCAdminStatus OBJECT-TYPE
             SYNTAX INTEGER {
		            up    (2), 
            		down  (3), 
		            source(4),      -- agent send Oam CC cells 
		            sink  (5),      -- agent check received Oam CC cells
                    listenToActivationCells (6),
                    originateActivationCells(7)     
                            } 
             MAX-ACCESS read-write
             STATUS current
             DESCRIPTION
                     	"up(2) - Activate Continuity Check (CC).
                      	down(3) - Deactivate CC.
		                source(4)      - Activate OAM CC(Continuity Check) of local agent
                        			( start sending Oam cells to the remote side ).
      		            sink(5)          - Activate CC of remote agent ( start receiving Oam cells from
      		             				remote 	side ).
                     listenToActivationCells (6) - Passive listener till gets an activation request
                     originateActivationCells(7) - Sands Activation cell according to atmConfVcCCDirection."
             ::= {atmNteConfVpEntry 2}

	atmConfVpLoopbackAdminStatus OBJECT-TYPE
                    SYNTAX INTEGER {
		            up(2),
		            down(3),
		            llid(4),
		            segment(5),
		            endToEnd(6),
		            segmentLlid(7),
		            endToEndLlid(8)
	                } 
             		MAX-ACCESS read-write
             		STATUS current
             		DESCRIPTION
                        "up(2) - Start loopback OAM cells.
                         down(3) - Stop sending loopback OAM cells.
                   
                         For ace2002:
                         up(2)   - Transmitting LB cells with llid all ones 
                                   (i.e. FFFF..FF)
                         down(3) - Not transmitting LB cells. 
                         llid(4) - Transmitting LB cells with llid indicated 
                                    in the address field.
                         segment(5) - Transmitting Segment LB cells with llid
                                       all ones. 
                         endToEnd(6) - Transmitting End to End LB cells with llid
                                        all ones. 
                         segmentLlid(7) - Transmitting Segment LB cells with
                                           llid indicated in the address field.  
                         endToEndLlid(8) - Transmitting LB cells with llid
                                            indicated in the address field.  
                   
                         This parameter value might be in conflict with 
                         atmConfVpOamSupport value, since this parameter is for LB, 
                         while atmConfVpOamSupport is for any other OAM cells."                   
             ::= {atmNteConfVpEntry 3}

	atmConfVpLoopbackSinkAddress OBJECT-TYPE
             		SYNTAX OCTET STRING  (SIZE(0..20))
             		MAX-ACCESS read-write
             		STATUS current
             		DESCRIPTION
                    	 "Destination address.
                    	 For ace101: 2 bytes are used.
                    	 For ace2002: 16 bytes are used."
             ::= {atmNteConfVpEntry 4}

	atmConfVpCongestionControl OBJECT-TYPE
             		SYNTAX OCTET STRING
             		MAX-ACCESS read-write
             		STATUS current
             		DESCRIPTION
                    	 "Each bit indicates a selection of one option 
                               as the following description.  All combinations 
                               are possible and legal.
                               The codes are: 
                               1 - EPD
                               2 - CLP
                               4 - EFCI"
             ::= {atmNteConfVpEntry 5}

     atmConfVpCCDirection OBJECT-TYPE
             SYNTAX  INTEGER {
		            both  (2), 
		            source(4),      
		            sink  (5)     
                            } 
             MAX-ACCESS read-write
             STATUS current
             DESCRIPTION
                     	"both(2) - Agent send OAM CC cells and check received OAM CC cells
                        source(4)- Agent send OAM CC cells.
      		            sink(5)  - Agent checks received OAM CC cells."    
             ::= {atmNteConfVpEntry 6}

     atmConfVpCreationTime OBJECT-TYPE
         SYNTAX   DateAndTime
         MAX-ACCESS   read-only
         STATUS   current
         DESCRIPTION
            "A date-time in which the VP was created."
         ::= { atmNteConfVpEntry 7 }

     atmConfVpOamSupport OBJECT-TYPE
               SYNTAX  INTEGER {
                          intermediate(1),
                          segmentTermination(2),
                          endToEndTermination(3)
                      }
               MAX-ACCESS  read-write
               STATUS  current
               DESCRIPTION
               "OAM support  mode, which determines the device location
                in a segment wise."
               ::= { atmNteConfVpEntry 8 }


	atmConfVpCCOperStatus OBJECT-TYPE
             SYNTAX INTEGER {
		             initial (1),
		             source(4),       
		             sink  (5),
					 both  (8),
		 			 timeout (9), 
				     denied (10),
					 conflict (11),
					 manual (12)
                            } 
             MAX-ACCESS read-only
             STATUS current
             DESCRIPTION
                     	"
		                initial(1) - The CC activation process is not started.
		                source(4) - Agent sends OAM CC cells.
      		            sink(5)   - Agent checks received OAM CC cells.
						both (8) - OAM CC of local and remote agents activation.
		                timeout (9) - Timeout occured on receiving answer from
                                      the remote agent.
		                denied  (10) - CC activation process rejected by remote agent.
		                conflict (11) - local and remote sides requested activation
                                      simultaneously.
				        manual (12) - OAM CC of local agent activated manually.
                        "
             ::= {atmNteConfVpEntry 9}

	atmConfVpLoopbackTraffic OBJECT-TYPE
             		SYNTAX INTEGER { off(2), on(3) } 
             		MAX-ACCESS read-write
             		STATUS current
             		DESCRIPTION
                    	 "This parameter has both command and status meanings: 
                    	 off(2) - Set to 'Off' will Stop traffic loop. Getting this
                    	          value means that the loop is not running.
                      	 on (3) - Set to 'On' will start traffic loop. Getting 
                      	          this value means that the loop is currently running."
             ::= {atmNteConfVpEntry 10}

	atmConfVpLoopbackFailureInd OBJECT-TYPE
             		SYNTAX INTEGER { 
             		disabled(2), 
             		segmentAis(3),
             		segmentRdi(4),
             		segmentAisAndRdi(5),
             		endToEndAis(6),
             		endToEndRdi(7),
             		endToEndAisAndRdi(8)
             		} 
             		MAX-ACCESS read-write
             		STATUS current
             		DESCRIPTION
    "This object allows user to define the Indication that will be created upon 
     a LB cell failure.
     disabled(2) - no indication will be created.
     segmentAis(3) - will cause Tx of a segment AIS.
     segmentRdi(4) - will cause Tx of a segment RDI.
     segmentAisAndRdi(5) - will cause Tx of a segment AIS & RDI. 
     endToEndAis(6) - will cause Tx of an End to End AIS.
     endToEndRdi(7)	- will cause Tx of an End to End RDI.
     endToEndAisAndRdi(8) - will cause Tx of an End to End AIS & RDI.
     Default: disabled(2)."
             ::= {atmNteConfVpEntry 11}

	atmConfVpLoopbackFailureThreshold OBJECT-TYPE
             		SYNTAX Integer32  
             		MAX-ACCESS read-write
             		STATUS current
             		DESCRIPTION
    "The number of the LB failures before starting transmission of the 
    Indication defined by atmConfVcLoopbackFailureInd.
    Range: 1..16. Default: 1."
             ::= {atmNteConfVpEntry 12}

     atmConfVpOamDirection OBJECT-TYPE
             SYNTAX  INTEGER {
		            notApplicable  (1), 
		            downStream     (2),      
		            upStream       (3)     
                            } 
             MAX-ACCESS read-write
             STATUS current
             DESCRIPTION
     "The direction of OAM cell insertion.
	 downStream(2) - The OAM cell will be inserted in downStream.     
	 upStream(3)   - The OAM cell will be inserted in upStream."    
             ::= {atmNteConfVpEntry 13}

atmConfVpOamDescrIndex OBJECT-TYPE
	SYNTAX  Integer32 
	MAX-ACCESS read-write
	STATUS current
	DESCRIPTION
	"This parameter indicates the VPL's OAM Descriptor index,
	 according to the OAM Descriptor Configuration Table."    
			::= {atmNteConfVpEntry 14}

atmConfVpConnected OBJECT-TYPE
	SYNTAX  INTEGER {
		notConnected	(1), 
		mng				(2),      
		bridgePort		(3),
		ds0Bundle		(4),
		atm				(5),
		pw				(6)     
        } 
	MAX-ACCESS read-write
	STATUS current
	DESCRIPTION
	"This object indicates whether this VP is connected
	and if connected, what is it connected to."    
			::= {atmNteConfVpEntry 15}


--Alarm Table
          atmNteAlarmVpTable OBJECT-TYPE
              SYNTAX  SEQUENCE OF AtmNteAlarmVpEntry
              MAX-ACCESS  not-accessible
              STATUS  current
              DESCRIPTION
                      "The ATM VP Alarm table."
              ::= { atmNtePrtConfig 5 }

          atmNteAlarmVpEntry OBJECT-TYPE
              SYNTAX  AtmNteAlarmVpEntry
              MAX-ACCESS  not-accessible
              STATUS  current
              DESCRIPTION
                      "An entry in the ATM VP Alarm table.
                       ifIndex of the ATM layer."
              INDEX   { ifIndex, atmNteVpAlarmVpi}
              ::= { atmNteAlarmVpTable 1 }

          AtmNteAlarmVpEntry ::=
              SEQUENCE {
			    atmNteVpAlarmVpi
				      Integer32,
			    atmNteVpActiveAlarms
				      Integer32
              }

          atmNteVpAlarmVpi OBJECT-TYPE
              SYNTAX  Integer32 
              MAX-ACCESS  read-only
              STATUS  current
              DESCRIPTION
                      "The VPI on which there is an active alarm."
              ::= { atmNteAlarmVpEntry 1 }

          atmNteVpActiveAlarms OBJECT-TYPE
              SYNTAX  Integer32 
              MAX-ACCESS  read-only
              STATUS  current
              DESCRIPTION
                      "A Bit String of the active alarms on this VP.
					   An up bit (1) means there is an active alarm of this
					   type. A down bit (0) means there is no such alarm.
                       The meaning of the bits is as follows:
                       1 -	VP AIS
                       2 -	VP Loss Of Continuity
					   3 -  VP RDI Reception
					   4 -	VP Errored Cells > Threshold 
					   5 -	VP Lost Cells > Threshold 
					   6 -	VP Misinserted Cells > Threshold
					   9 -  VP Loopback Failure
                       "
              ::= { atmNteAlarmVpEntry 2 }

          atmNteAlarmVcTable OBJECT-TYPE
              SYNTAX  SEQUENCE OF AtmNteAlarmVcEntry
              MAX-ACCESS  not-accessible
              STATUS  current
              DESCRIPTION
                      "The ATM VC Alarm table."
              ::= { atmNtePrtConfig 6 }

          atmNteAlarmVcEntry OBJECT-TYPE
              SYNTAX  AtmNteAlarmVcEntry
              MAX-ACCESS  not-accessible
              STATUS  current
              DESCRIPTION
                      "An entry in the ATM VC Alarm table.
                       ifIndex of the ATM layer."
              INDEX   { ifIndex, atmNteVcAlarmVpi, atmNteVcAlarmVci}
              ::= { atmNteAlarmVcTable 1 }

          AtmNteAlarmVcEntry ::=
              SEQUENCE {
			    atmNteVcAlarmVpi
				      Integer32,
			    atmNteVcAlarmVci
				      Integer32,
			    atmNteVcActiveAlarms
				      Integer32
              }

          atmNteVcAlarmVpi OBJECT-TYPE
              SYNTAX  Integer32 
              MAX-ACCESS  read-only
              STATUS  current
              DESCRIPTION
                      "The VPI of the VC on which there is an active alarm."
              ::= { atmNteAlarmVcEntry 1 }

          atmNteVcAlarmVci OBJECT-TYPE
              SYNTAX  Integer32 
              MAX-ACCESS  read-only
              STATUS  current
              DESCRIPTION
                      "The VCI of the VC on which there is an active alarm."
              ::= { atmNteAlarmVcEntry 2 }

atmNteVcActiveAlarms OBJECT-TYPE
              SYNTAX  Integer32 
              MAX-ACCESS  read-only
              STATUS  current
              DESCRIPTION
                      "A Bit String of the active alarms on this VC.
					   An up bit (1) means there is an active alarm of this
					   type. A down bit (0) means there is no such alarm.
                       The meaning of the bits is as follows:
                       1 -	VC AIS
                       2 -	VC Loss Of Continuity
					   3 -  VC RDI
					   4 -	VC Errored Cells > Threshold 
					   5 -	VC Lost Cells > Threshold 
					   6 -	VC Misinserted Cells > Threshold
					   7 - 	Tx VC AIS
					   8 - 	Tx VC RDI
					   9 -  VC Loopback Failure
                       "
              ::= { atmNteAlarmVcEntry 3 }

-- 
-- file :D:\Synergy\WorkArea\545\mib_rad\txt\ace101.txt
-- 
-- 
-- file Ace101.txt
--

atmGen  OBJECT IDENTIFIER  ::=  {radAtm 2}

atmPerfHistory  OBJECT IDENTIFIER  ::=  {atmGen 1}

atmIfPerformance  OBJECT IDENTIFIER  ::=  {atmPerfHistory 1}
-- aal5VccXTable  ::= { atmIfPerformance 4 }  in aal5.txt


          atmIfDataTable OBJECT-TYPE
              SYNTAX  SEQUENCE OF AtmIfDataEntry
              MAX-ACCESS  not-accessible
              STATUS  current
              DESCRIPTION
                      "The ATM interface Data table."
              ::= { atmIfPerformance 1 }

          atmIfDataEntry OBJECT-TYPE
              SYNTAX  AtmIfDataEntry
              MAX-ACCESS  not-accessible
              STATUS  current
              DESCRIPTION
                      "An entry in the ATM interface Data table."
              INDEX   { ifIndex }
              ::= { atmIfDataTable 1 }

          AtmIfDataEntry ::=
              SEQUENCE {
                  atmIfTimeElapsed
                      Integer32,
                  atmIfValidIntervals
                      Integer32,
				  atmIfTxCells
				       Counter32,
				  atmIfRxCells
				       Counter32,
				  atmIfUncorrectedHecs
				       Counter32 	
              }

           atmIfTimeElapsed OBJECT-TYPE
               SYNTAX  Integer32 (0..899)
               MAX-ACCESS  read-only
               STATUS  current
               DESCRIPTION
                       "The number of seconds that have elapsed since
                       the beginning of the near end current error-
                       measurement period."
              ::= { atmIfDataEntry 1 }

          atmIfValidIntervals OBJECT-TYPE
              SYNTAX  Integer32 (0..96)
              MAX-ACCESS  read-only
              STATUS  current
              DESCRIPTION
                      "The number of previous near end intervals for
                      which valid data was collected.  The value will be
                      96 unless the interface was brought online within
                      the last 24 hours, in which case the value will be
                      the number of complete 15 minute near end
                      intervals since the interface has been online."
              ::= { atmIfDataEntry 2 }

          atmIfTxCells OBJECT-TYPE
              SYNTAX  Counter32 
              MAX-ACCESS  read-only
              STATUS  current
              DESCRIPTION
                      "The counter associated with the total number of transmitted
                      cells, encountered by an ATM interface."
              ::= { atmIfDataEntry 3 }

		  atmIfRxCells OBJECT-TYPE
              SYNTAX  Counter32 
              MAX-ACCESS  read-only
              STATUS  current
              DESCRIPTION
                      "The counter associated with the total number of received
                      cells, encountered by an ATM
                      interface."
              ::= { atmIfDataEntry 4 }
		  
		  atmIfUncorrectedHecs OBJECT-TYPE
              SYNTAX  Counter32 
              MAX-ACCESS  read-only
              STATUS  current
              DESCRIPTION
                      "The counter associated with the total number of cells with
                      uncorrected HEC errors, encountered by an ATM
                      interface."
              ::= { atmIfDataEntry 5 }

				   
          -- the ATM interface Current

          -- The ATM interface current table contains various statistics being
          -- collected for the current 15 minute interval.

          atmIfCurrentTable OBJECT-TYPE
              SYNTAX  SEQUENCE OF AtmIfCurrentEntry
              MAX-ACCESS  not-accessible
              STATUS  current
              DESCRIPTION
                      "The ATM interface Current table."
              ::= { atmIfPerformance 2 }

          atmIfCurrentEntry OBJECT-TYPE
              SYNTAX  AtmIfCurrentEntry
              MAX-ACCESS  not-accessible
              STATUS  current
              DESCRIPTION
                      "An entry in the ATM interface Current table."
              INDEX   { ifIndex }
              ::= { atmIfCurrentTable 1 }

          AtmIfCurrentEntry ::=
              SEQUENCE {
                  atmIfCurrentTxCells
                      Gauge32,
                  atmIfCurrentRxCells
                      Gauge32,
                  atmIfCurrentCorrectedHecs
                      Gauge32,
                  atmIfCurrentUncorrectedHecs
                      Gauge32,
				  atmIfCurrentHecErrorSeconds
                      Gauge32
              }

          atmIfCurrentTxCells OBJECT-TYPE
              SYNTAX  Gauge32
              MAX-ACCESS  read-only
              STATUS  current
              DESCRIPTION
                      "The counter associated with the number of transmitted
                      cells, encountered by an ATM interface in
                      the current 15 minute interval."
              ::= { atmIfCurrentEntry 1 }

          atmIfCurrentRxCells OBJECT-TYPE
              SYNTAX  Gauge32
              MAX-ACCESS  read-only
              STATUS  current
              DESCRIPTION
                      "The counter associated with the number of received
                      cells, encountered by an ATM
                      interface in the current 15 minute interval."
              ::= { atmIfCurrentEntry 2 }

          atmIfCurrentCorrectedHecs OBJECT-TYPE
              SYNTAX  Gauge32
              MAX-ACCESS  read-only
              STATUS  current
              DESCRIPTION
                      "The counter associated with the number of cells with
                      corrected HEC errors, encountered by an
                      ATM interface in the current 15 minute
                      interval."
              ::= { atmIfCurrentEntry 3 }

          atmIfCurrentUncorrectedHecs OBJECT-TYPE
              SYNTAX  Gauge32
              MAX-ACCESS  read-only
              STATUS  current
              DESCRIPTION
                      "The counter associated with the number of cells with
                      uncorrected HEC errors, encountered by an ATM
                      interface in the current 15 minute interval."
              ::= { atmIfCurrentEntry 4 }

          atmIfCurrentHecErrorSeconds OBJECT-TYPE
              SYNTAX  Gauge32
              MAX-ACCESS  read-only
              STATUS  current
              DESCRIPTION
                      "The counter associated with the number of seconds with
                      HEC errors, encountered by an ATM	interface in 
                      the current 15 minute interval."
              ::= { atmIfCurrentEntry 5 }


          -- the ATM interface Interval

          -- The ATM interface Interval Table contains various statistics
          -- collected by each ATM Interface over the previous 24
          -- hours of operation.  The past 24 hours are broken into 96
          -- completed 15 minute intervals.

          atmIfIntervalTable OBJECT-TYPE
              SYNTAX  SEQUENCE OF AtmIfIntervalEntry
              MAX-ACCESS  not-accessible
              STATUS  current
              DESCRIPTION
                      "The ATM interface Interval table."
              ::= { atmIfPerformance 3 }

          atmIfIntervalEntry OBJECT-TYPE
              SYNTAX  AtmIfIntervalEntry
              MAX-ACCESS  not-accessible
              STATUS  current
              DESCRIPTION
                      "An entry in the ATM interface Interval table."
              INDEX   { ifIndex, atmIfIntervalNumber }
              ::= { atmIfIntervalTable 1 }

          AtmIfIntervalEntry ::=
              SEQUENCE {
                  atmIfIntervalNumber
                      Integer32,
                  atmIfIntervalTxCells
                      Gauge32,
                  atmIfIntervalRxCells
                      Gauge32,
                  atmIfIntervalCorrectedHecs
                      Gauge32,
                  atmIfIntervalUncorrectedHecs
                      Gauge32,
                  atmIfIntervalHecErrorSeconds
                      Gauge32
              }

          atmIfIntervalNumber OBJECT-TYPE
              SYNTAX  Integer32 (1..96)
              MAX-ACCESS  read-only
              STATUS  current
              DESCRIPTION
                      "A number between 1 and 96, where 1 is the most
                      recently completed 15 minute interval and 96 is
                      the least recently completed 15 minutes interval
                      (assuming that all 96 intervals are valid)."
              ::= { atmIfIntervalEntry 1 }

          atmIfIntervalTxCells OBJECT-TYPE
              SYNTAX  Gauge32
              MAX-ACCESS  read-only
              STATUS  current
              DESCRIPTION
                      "The counter associated with the number of transmitted 
                      cells , encountered by an ATM interface in
                      one of the previous 96, individual 15 minute,
                      intervals."
              ::= { atmIfIntervalEntry 2 }

          atmIfIntervalRxCells OBJECT-TYPE
              SYNTAX  Gauge32
              MAX-ACCESS  read-only
              STATUS  current
              DESCRIPTION
                      "The counter associated with the number of received
                      cells, encountered by an ATM
                      interface in one of the previous 96, individual 15
                      minute, intervals."
              ::= { atmIfIntervalEntry 3 }

          atmIfIntervalCorrectedHecs OBJECT-TYPE
              SYNTAX  Gauge32
              MAX-ACCESS  read-only
              STATUS  current
              DESCRIPTION
                      "The counter associated with the number of cells with
                      corrected HEC errors, encountered by an
                      ATM interface in one of the previous 96,
                      individual 15 minute, intervals."
              ::= { atmIfIntervalEntry 4 }

          atmIfIntervalUncorrectedHecs OBJECT-TYPE
              SYNTAX  Gauge32
              MAX-ACCESS  read-only
              STATUS  current
              DESCRIPTION
                      "The counter associated with the number of cells with
                      uncorrected HEC errors, encountered by an ATM
                      interface in one of the previous 96, individual 15
                      minute, intervals."
              ::= { atmIfIntervalEntry 5 }

          atmIfIntervalHecErrorSeconds OBJECT-TYPE
              SYNTAX  Gauge32
              MAX-ACCESS  read-only
              STATUS  current
              DESCRIPTION
                      "The counter associated with the number of seconds with
                      HEC errors, encountered by an ATM	interface in one of 
                      the previous 96, individual 15 minute, intervals."
              ::= { atmIfIntervalEntry 6 }


atmPvcPerformance  OBJECT IDENTIFIER  ::=  {atmPerfHistory 2}

atmVpPerformance  OBJECT IDENTIFIER  ::=  {atmPvcPerformance 1}

          -- the ATM VP Current

          -- The ATM VP current table contains various statistics being
          -- collected for the current 15 minute interval.

          atmVpCurrentTable OBJECT-TYPE
              SYNTAX  SEQUENCE OF AtmVpCurrentEntry
              MAX-ACCESS  not-accessible
              STATUS  current
              DESCRIPTION
                      "The ATM VP Current table."
              ::= { atmVpPerformance 1 }

          atmVpCurrentEntry OBJECT-TYPE
              SYNTAX  AtmVpCurrentEntry
              MAX-ACCESS  not-accessible
              STATUS  current
              DESCRIPTION
                      "An entry in the ATM VP Current table."
              INDEX   { ifIndex, atmVpCurrentVpi }
              ::= { atmVpCurrentTable 1 }

          AtmVpCurrentEntry ::=
              SEQUENCE {
	     atmVpCurrentVpi
                      Integer32,
                  atmVpCurrentRxCellsClp01
                      Gauge32,
                  atmVpCurrentRxCellsClp0
                      Gauge32,
                  atmVpCurrentGcra0Violations
                      Gauge32,
                  atmVpCurrentGcra1Violations
                      Gauge32,
                  atmVpCurrentRxAIS
                      Gauge32,
                  atmVpCurrentTxAIS
                      Gauge32,
                  atmVpCurrentRxRDI
                      Gauge32,
                  atmVpCurrentTxRDI
                      Gauge32,
                  atmVpCurrentContinuityLoss
                      Gauge32,
                  atmVpCurrentUAS
                      Gauge32,
	              atmVpCurrentSES 
	                  Gauge32,
	              atmVpCurrentCDC
	                  Gauge32,
                  atmVpCurrentTotalDiscards     
                      Gauge32,
                  atmVpCurrentClp0Discards      
                      Gauge32,
                  atmVpCurrentTotalCellOuts     
                      Gauge32,
                  atmVpCurrentClp0CellOuts      
                      Gauge32,
                  atmVpCurrentTaggedOuts        
                      Gauge32,
	              atmVpCurrentPCR
	                  Gauge32,
	              atmVpCurrentSCR
	                  Gauge32,
	              atmVpCurrentMCR
	                  Gauge32,
                  atmVpCurrentShaperTotalDiscards     
                      Gauge32,
                  atmVpCurrentShaperClp0Discards      
                      Gauge32,
                  atmVpCurrentShaperClp1Discards      
                      Gauge32
          }

          atmVpCurrentVpi OBJECT-TYPE
              SYNTAX  Integer32
              MAX-ACCESS  read-only
              STATUS  current
              DESCRIPTION
                      "The VPI of the VPL."
              ::= { atmVpCurrentEntry 1 }

          atmVpCurrentRxCellsClp01 OBJECT-TYPE
              SYNTAX  Gauge32
              MAX-ACCESS  read-only
              STATUS  current
              DESCRIPTION
                      "The counter associated with the number of transmitted
                      cells, encountered by the VPL of this ATM interface in
                      the current 15 minute interval."
              ::= { atmVpCurrentEntry 2 }

          atmVpCurrentRxCellsClp0 OBJECT-TYPE
              SYNTAX  Gauge32
              MAX-ACCESS  read-only
              STATUS  current
              DESCRIPTION
                      "The counter associated with the number of received
                      cells, encountered by the VPL of this ATM
                      interface in the current 15 minute interval."
              ::= { atmVpCurrentEntry 3 }

          atmVpCurrentGcra0Violations OBJECT-TYPE
              SYNTAX  Gauge32
              MAX-ACCESS  read-only
              STATUS  current
              DESCRIPTION
                      "The counter associated with the number of cells 
                      violating GCRA0, encountered by the VPL of this
                      ATM interface in the current 15 minute
                      interval."
              ::= { atmVpCurrentEntry 4 }

          atmVpCurrentGcra1Violations OBJECT-TYPE
              SYNTAX  Gauge32
              MAX-ACCESS  read-only
              STATUS  current
              DESCRIPTION
                      "The counter associated with the number of cells 
                      violating GCRA1, encountered by the VPL of this ATM
                      interface in the current 15 minute interval."
              ::= { atmVpCurrentEntry 5 }

          atmVpCurrentRxAIS OBJECT-TYPE
              SYNTAX  Gauge32
              MAX-ACCESS  read-only
              STATUS  current
              DESCRIPTION
                      "The counter associated with the number of received
                      AIS cells, encountered by the VPL of this ATM
                      interface in the current 15 minute interval."
              ::= { atmVpCurrentEntry 6 }

          atmVpCurrentTxAIS OBJECT-TYPE
              SYNTAX  Gauge32
              MAX-ACCESS  read-only
              STATUS  current
              DESCRIPTION
                      "The counter associated with the number of transmitted
                      AIS cells, encountered by the VPL of this ATM
                      interface in the current 15 minute interval. Not Supported
	        in the first phase."
              ::= { atmVpCurrentEntry 7 }

          atmVpCurrentRxRDI OBJECT-TYPE
              SYNTAX  Gauge32
              MAX-ACCESS  read-only
              STATUS  current
              DESCRIPTION
                      "The counter associated with the number of received
                      RDI cells, encountered by the VPL of this ATM
                      interface in the current 15 minute interval."
              ::= { atmVpCurrentEntry 8 }

          atmVpCurrentTxRDI OBJECT-TYPE
              SYNTAX  Gauge32
              MAX-ACCESS  read-only
              STATUS  current
              DESCRIPTION
                      "The counter associated with the number of transmitted
                      RDI cells, encountered by the VPL of this ATM
                      interface in the current 15 minute interval."
              ::= { atmVpCurrentEntry 9 }

          atmVpCurrentContinuityLoss OBJECT-TYPE
              SYNTAX  Gauge32
              MAX-ACCESS  read-only
              STATUS  current
              DESCRIPTION
                      "The counter associated with the number of loss of
                      continuity cells, encountered by the VPL of this ATM
                      interface in the current 15 minute interval."
              ::= { atmVpCurrentEntry 10 }

          atmVpCurrentUAS OBJECT-TYPE
              SYNTAX  Gauge32
              MAX-ACCESS  read-only
              STATUS  current
              DESCRIPTION
                      "The counter associated with the number of Unavailable
                      Seconds, encountered by the VPL of this ATM
                      interface in the current 15 minute interval."
              ::= { atmVpCurrentEntry 11 }

	atmVpCurrentSES OBJECT-TYPE
              SYNTAX  Gauge32
              MAX-ACCESS  read-only
              STATUS  current
              DESCRIPTION
                      "The counter associated with the number of Severerly Errored
                      Seconds, encountered by the VPL of this ATM
                      interface in the current 15 minute interval."
              ::= { atmVpCurrentEntry 12 }

 	atmVpCurrentCDC OBJECT-TYPE
              SYNTAX  Gauge32
              MAX-ACCESS  read-only
              STATUS  current
              DESCRIPTION
                      "Amount of cells dropped in the current 15 minute interval 
                       of the VP connection."
              ::= { atmVpCurrentEntry 13 }
                        
    atmVpCurrentTotalDiscards OBJECT-TYPE
              SYNTAX       Gauge32
              MAX-ACCESS       read-only
              STATUS       current
              DESCRIPTION
                      "The total number of valid ATM cells discarded by
                      the traffic policing entity.  This includes cells
                      originally received with CLP=0 and CLP=1."
              ::= { atmVpCurrentEntry 14 }

    atmVpCurrentClp0Discards OBJECT-TYPE
              SYNTAX       Gauge32
              MAX-ACCESS       read-only
              STATUS       current
              DESCRIPTION
                      "The total number of valid ATM cells received with
                      CLP=0 and discarded by the traffic policing
                      entity."
              ::= { atmVpCurrentEntry 15 }

    atmVpCurrentTotalCellOuts OBJECT-TYPE
              SYNTAX       Gauge32
              MAX-ACCESS       read-only
              STATUS       current
              DESCRIPTION
                      "The total number of valid ATM cells transmitted
                      by this VPL. This includes both CLP=0 and CLP=1
                      cells."
              ::= { atmVpCurrentEntry 16 }
                       
    atmVpCurrentClp0CellOuts OBJECT-TYPE
              SYNTAX       Gauge32
              MAX-ACCESS       read-only
              STATUS       current
              DESCRIPTION
                      "The total number of valid ATM cells transmitted
                      with CLP=0 by this VPL."
              ::= { atmVpCurrentEntry 17 }

    atmVpCurrentTaggedOuts OBJECT-TYPE
              SYNTAX       Gauge32
              MAX-ACCESS       read-only
              STATUS       current
              DESCRIPTION
                      "The total number of valid ATM cells tagged by the
                      traffic policing entity from CLP=0 to CLP=1 and
                      transmitted by this VPL."
              ::= { atmVpCurrentEntry 18 }
                        
	atmVpCurrentPCR OBJECT-TYPE
              SYNTAX  Gauge32
              MAX-ACCESS  read-only
              STATUS  current
              DESCRIPTION
                      "The maximum traffic rate encountered in the 
                      last interval of the VP connection (monitored once a second)."
              ::= { atmVpCurrentEntry 19 }

	atmVpCurrentSCR OBJECT-TYPE
              SYNTAX  Gauge32
              MAX-ACCESS  read-only
              STATUS  current
              DESCRIPTION
                      "The average traffic rate during the last interval of the VP 
                      connection."
              ::= { atmVpCurrentEntry 20 }

	atmVpCurrentMCR OBJECT-TYPE
              SYNTAX  Gauge32
              MAX-ACCESS  read-only
              STATUS  current
              DESCRIPTION
                      "MCR - The minimum traffic rate encountered in the last 
                      interval of the VP connection (monitored once a second)."
              ::= { atmVpCurrentEntry 21 }

    atmVpCurrentShaperTotalDiscards OBJECT-TYPE
              SYNTAX       Gauge32
              MAX-ACCESS       read-only
              STATUS       current
              DESCRIPTION
                      "The total number of cells (CLP0 and CLP1) discarded
                       due to congestion by the traffic shaper."
              ::= { atmVpCurrentEntry 22 }

    atmVpCurrentShaperClp0Discards OBJECT-TYPE
              SYNTAX       Gauge32
              MAX-ACCESS       read-only
              STATUS       current
              DESCRIPTION
                      "The total number of CLP0 cells discarded
                       due to congestion by the traffic shaper."
              ::= { atmVpCurrentEntry 23 }
    
    atmVpCurrentShaperClp1Discards OBJECT-TYPE
              SYNTAX       Gauge32
              MAX-ACCESS       read-only
              STATUS       current
              DESCRIPTION
                      "The total number of CLP1 cells discarded
                       due to congestion by the traffic shaper."
              ::= { atmVpCurrentEntry 24 }


          -- The ATM VP current table for Performance Management
          -- which contains various statistics being
          -- collected for the current 15 minute interval.

          atmVpPMCurrentTable OBJECT-TYPE
              SYNTAX  SEQUENCE OF AtmVpPMCurrentEntry
              MAX-ACCESS  not-accessible
              STATUS  current
              DESCRIPTION
                      "The ATM VP Current table for Performance Management."
              ::= { atmVpPerformance 2 }

          atmVpPMCurrentEntry OBJECT-TYPE
              SYNTAX  AtmVpPMCurrentEntry
              MAX-ACCESS  not-accessible
              STATUS  current
              DESCRIPTION
                      "An entry in the ATM VP Current table for Performance
                       Management."
              INDEX   { ifIndex, atmVpPMCurrentVpi, atmVpPMCurrentDir }
              ::= { atmVpPMCurrentTable 1 }

          AtmVpPMCurrentEntry ::=
              SEQUENCE {
	atmVpPMCurrentDir			 
                      INTEGER,
	atmVpPMCurrentVpi			 
	        Integer32,
                  atmVpPMCurrentTxClp01
                      Gauge32,
                  atmVpPMCurrentTxClp0
                      Gauge32,
                  atmVpPMCurrentRxClp01
                      Gauge32,
                  atmVpPMCurrentRxClp0
                      Gauge32,
                  atmVpPMCurrentErroredCells
                      Gauge32,
                  atmVpPMCurrentLostCells
                      Gauge32,
                  atmVpPMCurrentMisinsertedCells
                      Gauge32,
                  atmVpPMCurrentECB
                      Gauge32,
                  atmVpPMCurrentSECB
                      Gauge32,
                  atmVpPMCurrentES
                      Gauge32,
                  atmVpPMCurrentSES
                      Gauge32,
                  atmVpPMCurrentUAS
                      Gauge32,
	              atmVpPMCurrentIntervalQuality
	                  INTEGER,
	              atmVpPMCurrentLastDayQuality
	                  INTEGER
              }

 	atmVpPMCurrentVpi OBJECT-TYPE
              SYNTAX  Integer32
              MAX-ACCESS  read-only
              STATUS  current
              DESCRIPTION
                      "The VPI of the VPL."
	::= { atmVpPMCurrentEntry 1 }

	atmVpPMCurrentDir OBJECT-TYPE
              SYNTAX  INTEGER {forward(2), backward(3) }
              MAX-ACCESS  read-only
              STATUS  current
              DESCRIPTION
                      "The direction of performance management."	
	::= { atmVpPMCurrentEntry 2 }

          atmVpPMCurrentTxClp01 OBJECT-TYPE
              SYNTAX  Gauge32
              MAX-ACCESS  read-only
              STATUS  current
              DESCRIPTION
                      "The counter associated with the number of transmitted 
                      CLP 0+1 cells, encountered by the VPL of this ATM
                      interface in the current 15 minute interval."
              ::= { atmVpPMCurrentEntry 3 }

          atmVpPMCurrentTxClp0 OBJECT-TYPE
              SYNTAX  Gauge32
              MAX-ACCESS  read-only
              STATUS  current
              DESCRIPTION
                      "The counter associated with the number of transmitted
                      CLP 0	cells, encountered by the VPL of this ATM
                      interface in the current 15 minute interval."
              ::= { atmVpPMCurrentEntry 4 }

          atmVpPMCurrentRxClp01 OBJECT-TYPE
              SYNTAX  Gauge32
              MAX-ACCESS  read-only
              STATUS  current
              DESCRIPTION
                      "The counter associated with the number of received
                      CLP 0+1 cells, encountered by the VPL of this ATM
                      interface in the current 15 minute interval."
              ::= { atmVpPMCurrentEntry 5 }

          atmVpPMCurrentRxClp0 OBJECT-TYPE
              SYNTAX  Gauge32
              MAX-ACCESS  read-only
              STATUS  current
              DESCRIPTION
                      "The counter associated with the number of received
                      CLP 0 cells, encountered by the VPL of this ATM
                      interface in the current 15 minute interval."
              ::= { atmVpPMCurrentEntry 6 }

          atmVpPMCurrentErroredCells OBJECT-TYPE
              SYNTAX  Gauge32
              MAX-ACCESS  read-only
              STATUS  current
              DESCRIPTION
                      "The counter associated with the number of errored
                      cells, encountered by the VPL of this ATM
                      interface in the current 15 minute interval."
              ::= { atmVpPMCurrentEntry 7 }

          atmVpPMCurrentLostCells OBJECT-TYPE
              SYNTAX  Gauge32
              MAX-ACCESS  read-only
              STATUS  current
              DESCRIPTION
                      "The counter associated with the number of lost
                      cells, encountered by the VPL of this ATM
                      interface in the current 15 minute interval."
              ::= { atmVpPMCurrentEntry 8 }

          atmVpPMCurrentMisinsertedCells OBJECT-TYPE
              SYNTAX  Gauge32
              MAX-ACCESS  read-only
              STATUS  current
              DESCRIPTION
                      "The counter associated with the number of misinserted
                      cells, encountered by the VPL of this ATM
                      interface in the current 15 minute interval."
              ::= { atmVpPMCurrentEntry 9 }

          atmVpPMCurrentECB OBJECT-TYPE
              SYNTAX  Gauge32
              MAX-ACCESS  read-only
              STATUS  current
              DESCRIPTION
                      "The counter associated with the number of ECB,
                      encountered by the VPL of this ATM
                      interface in the current 15 minute interval."
              ::= { atmVpPMCurrentEntry 10 }

          atmVpPMCurrentSECB OBJECT-TYPE
              SYNTAX  Gauge32
              MAX-ACCESS  read-only
              STATUS  current
              DESCRIPTION
                      "The counter associated with the number of SECB,
                      encountered by the VPL of this ATM
                      interface in the current 15 minute interval."
              ::= { atmVpPMCurrentEntry 11 }

          atmVpPMCurrentES OBJECT-TYPE
              SYNTAX  Gauge32
              MAX-ACCESS  read-only
              STATUS  current
              DESCRIPTION
                      "The counter associated with the number of 
                      Errored Seconds, encountered by the VPL of this ATM
                      interface in the current 15 minute interval."
              ::= { atmVpPMCurrentEntry 12 }

          atmVpPMCurrentSES OBJECT-TYPE
              SYNTAX  Gauge32
              MAX-ACCESS  read-only
              STATUS  current
              DESCRIPTION
                      "The counter associated with the number of Severely
                      Errored Seconds, encountered by the VPL of this ATM
                      interface in the current 15 minute interval."
              ::= { atmVpPMCurrentEntry 13 }

          atmVpPMCurrentUAS OBJECT-TYPE
              SYNTAX  Gauge32
              MAX-ACCESS  read-only
              STATUS  current
              DESCRIPTION
                      "The counter associated with the number of Unavailable
                      Seconds, encountered by the VPL of this ATM
                      interface in the current 15 minute interval."
              ::= { atmVpPMCurrentEntry 14 }

	atmVpPMCurrentIntervalQuality OBJECT-TYPE
              SYNTAX  INTEGER { normal(2), unacceptable(3) }
	MAX-ACCESS read-only
	STATUS current
	DESCRIPTION
		" If the number of errors per interval is superior to
		the atmNteUPLTCR value, the quality of service of
		the interval is declared as unacceptable."
	DEFVAL { normal }
	::= { atmVpPMCurrentEntry 15 }

	    atmVpPMCurrentLastDayQuality OBJECT-TYPE
              SYNTAX  INTEGER { normal(2), degraded(4) }
	MAX-ACCESS read-only
	STATUS current
	DESCRIPTION
		" If the number of errors per 24 hours is superior to
		the atmNteDPLTCR value, the quality of service of
		the day is declared as degraded."
	DEFVAL { normal }
	::= { atmVpPMCurrentEntry 16 }


          -- the ATM VP Interval

          -- The ATM VP Interval Table contains various statistics
          -- collected by each ATM Interface/VP over the previous 24
          -- hours of operation.  The past 24 hours are broken into 96
          -- completed 15 minute intervals.

          atmVpIntervalTable OBJECT-TYPE
              SYNTAX  SEQUENCE OF AtmVpIntervalEntry
              MAX-ACCESS  not-accessible
              STATUS  current
              DESCRIPTION
                      "The ATM Vp Interval table."
              ::= { atmVpPerformance 3 }

          atmVpIntervalEntry OBJECT-TYPE
              SYNTAX  AtmVpIntervalEntry
              MAX-ACCESS  not-accessible
              STATUS  current
              DESCRIPTION
                      "An entry in the ATM Vp Interval table."
              INDEX   { ifIndex, atmVpIntervalVpi, 
                        atmVpIntervalNumber }
              ::= { atmVpIntervalTable 1 }

          AtmVpIntervalEntry ::=
              SEQUENCE {
			      atmVpIntervalVpi
				      Integer32,
                  atmVpIntervalNumber
                      Integer32,
                  atmVpIntervalRxCellsClp01
                      Gauge32,
                  atmVpIntervalRxCellsClp0
                      Gauge32,
                  atmVpIntervalGcra0Violations
                      Gauge32,
                  atmVpIntervalGcra1Violations
                      Gauge32,
                  atmVpIntervalRxAIS
                      Gauge32,
                  atmVpIntervalTxAIS
                      Gauge32,
                  atmVpIntervalRxRDI
                      Gauge32,
                  atmVpIntervalTxRDI
                      Gauge32,
                  atmVpIntervalContinuityLoss
                      Gauge32,
                  atmVpIntervalUAS
                      Gauge32,
	              atmVpIntervalSES
	                  Gauge32,
	              atmVpIntervalCDC
	                  Gauge32,
                  atmVpIntervalTotalDiscards     
                      Gauge32,
                  atmVpIntervalClp0Discards      
                      Gauge32,
                  atmVpIntervalTotalCellOuts     
                      Gauge32,
                  atmVpIntervalClp0CellOuts      
                      Gauge32,
                  atmVpIntervalTaggedOuts        
                      Gauge32,
	              atmVpIntervalPCR
	                  Gauge32,
	              atmVpIntervalSCR
	                  Gauge32,
	              atmVpIntervalMCR
	                  Gauge32,
                  atmVpIntervalShaperTotalDiscards     
                      Gauge32,
                  atmVpIntervalShaperClp0Discards      
                      Gauge32,
                  atmVpIntervalShaperClp1Discards      
                      Gauge32
              }

          atmVpIntervalVpi OBJECT-TYPE
              SYNTAX  Integer32
              MAX-ACCESS  read-only
              STATUS  current
              DESCRIPTION
                      "The VPI of the VPL."
              ::= { atmVpIntervalEntry 1 }

          atmVpIntervalNumber OBJECT-TYPE
              SYNTAX  Integer32 (1..96)
              MAX-ACCESS  read-only
              STATUS  current
              DESCRIPTION
                      "A number between 1 and 96, where 1 is the most
                      recently completed 15 minute interval and 96 is
                      the least recently completed 15 minutes interval
                      (assuming that all 96 intervals are valid)."
              ::= { atmVpIntervalEntry 2 }

          atmVpIntervalRxCellsClp01 OBJECT-TYPE
              SYNTAX  Gauge32
              MAX-ACCESS  read-only
              STATUS  current
              DESCRIPTION
                      "The counter associated with the number of transmitted 
                      cells , encountered by an ATM interface/VP in
                      one of the previous 96, individual 15 minute,
                      intervals."
              ::= { atmVpIntervalEntry 3 }

          atmVpIntervalRxCellsClp0 OBJECT-TYPE
              SYNTAX  Gauge32
              MAX-ACCESS  read-only
              STATUS  current
              DESCRIPTION
                      "The counter associated with the number of received
                      cells, encountered by an ATM
                      interface/VP in one of the previous 96, individual 15
                      minute, intervals."
              ::= { atmVpIntervalEntry 4 }

          atmVpIntervalGcra0Violations OBJECT-TYPE
              SYNTAX  Gauge32
              MAX-ACCESS  read-only
              STATUS  current
              DESCRIPTION
                      "The counter associated with the number of
                      cells violating GCRA0, encountered by an ATM
                      interface/VP in one of the previous 96, individual 15
                      minute, intervals."
              ::= { atmVpIntervalEntry 5 }

          atmVpIntervalGcra1Violations OBJECT-TYPE
              SYNTAX  Gauge32
              MAX-ACCESS  read-only
              STATUS  current
              DESCRIPTION
                      "The counter associated with the number of
                      cells violating GCRA1, encountered by an ATM
                      interface/VP in one of the previous 96, individual 15
                      minute, intervals."
              ::= { atmVpIntervalEntry 6 }

          atmVpIntervalRxAIS OBJECT-TYPE
              SYNTAX  Gauge32
              MAX-ACCESS  read-only
              STATUS  current
              DESCRIPTION
                      "The counter associated with the number of received
                      AIS cells, encountered by an ATM
                      interface/VP in one of the previous 96, individual 15
                      minute, intervals."
              ::= { atmVpIntervalEntry 7 }

          atmVpIntervalTxAIS OBJECT-TYPE
              SYNTAX  Gauge32
              MAX-ACCESS  read-only
              STATUS  current
              DESCRIPTION
                      "The counter associated with the number of transmitted
                      AIS cells, encountered by an ATM
                      interface/VP in one of the previous 96, individual 15
                      minute, intervals. Not supported in the first phase."
              ::= { atmVpIntervalEntry 8 }

          atmVpIntervalRxRDI OBJECT-TYPE
              SYNTAX  Gauge32
              MAX-ACCESS  read-only
              STATUS  current
              DESCRIPTION
                      "The counter associated with the number of received
                      RDI cells, encountered by an ATM
                      interface/VP in one of the previous 96, individual 15
                      minute, intervals."
              ::= { atmVpIntervalEntry 9 }

          atmVpIntervalTxRDI OBJECT-TYPE
              SYNTAX  Gauge32
              MAX-ACCESS  read-only
              STATUS  current
              DESCRIPTION
                      "The counter associated with the number of transmitted
                      RDI cells, encountered by an ATM
                      interface/VP in one of the previous 96, individual 15
                      minute, intervals."
              ::= { atmVpIntervalEntry 10 }

          atmVpIntervalContinuityLoss OBJECT-TYPE
              SYNTAX  Gauge32
              MAX-ACCESS  read-only
              STATUS  current
              DESCRIPTION
                      "The counter associated with the number of Continuity
                      Loss cells, encountered by an ATM
                      interface/VP in one of the previous 96, individual 15
                      minute, intervals."
              ::= { atmVpIntervalEntry 11 }

          atmVpIntervalUAS OBJECT-TYPE
              SYNTAX  Gauge32
              MAX-ACCESS  read-only
              STATUS  current
              DESCRIPTION
                      "The counter associated with the number of Unavailable
                      Seconds, encountered by an ATM
                      interface/VP in one of the previous 96, individual 15
                      minute, intervals."
              ::= { atmVpIntervalEntry 12 }

	atmVpIntervalSES OBJECT-TYPE
              SYNTAX  Gauge32
              MAX-ACCESS  read-only
              STATUS  current
              DESCRIPTION
                      "The counter associated with the number of Severerly Errored
                      Seconds, encountered by an ATM
                      interface/VP in one of the previous 96, individual 15
                      minute, intervals."
              ::= { atmVpIntervalEntry 13 }

	atmVpIntervalCDC OBJECT-TYPE
              SYNTAX  Gauge32
              MAX-ACCESS  read-only
              STATUS  current
              DESCRIPTION
                      "Amount of cells dropped in the 15 minute interval 
                       of the VP connection."
              ::= { atmVpIntervalEntry 14 }

    atmVpIntervalTotalDiscards OBJECT-TYPE
              SYNTAX       Gauge32
              MAX-ACCESS       read-only
              STATUS       current
              DESCRIPTION
                      "The total number of valid ATM cells discarded by
                      the traffic policing entity.  This includes cells
                      originally received with CLP=0 and CLP=1."
              ::= { atmVpIntervalEntry 15 }

    atmVpIntervalClp0Discards OBJECT-TYPE
              SYNTAX       Gauge32
              MAX-ACCESS       read-only
              STATUS       current
              DESCRIPTION
                      "The total number of valid ATM cells received with
                      CLP=0 an  discarded by the traffic policing
                      entity."
              ::= { atmVpIntervalEntry 16 }

    atmVpIntervalTotalCellOuts OBJECT-TYPE
              SYNTAX       Gauge32
              MAX-ACCESS       read-only
              STATUS       current
              DESCRIPTION
                      "The total number of valid ATM cells transmitted
                      by this VPL.  This includes both CLP=0 and CLP=1
                      cells."
              ::= { atmVpIntervalEntry 17 }
                        
                       
    atmVpIntervalClp0CellOuts OBJECT-TYPE
              SYNTAX       Gauge32
              MAX-ACCESS       read-only
              STATUS       current
              DESCRIPTION
                      "The total number of valid ATM cells transmitted
                      with CLP=0 by this VPL."
              ::= { atmVpIntervalEntry 18 }

    atmVpIntervalTaggedOuts OBJECT-TYPE
              SYNTAX       Gauge32
              MAX-ACCESS       read-only
              STATUS       current
              DESCRIPTION
                      "The total number of valid ATM cells tagged by the
                      traffic policing entity from CLP=0 to CLP=1 and
                      transmitted by this VPL."
              ::= { atmVpIntervalEntry 19 }
                        
	atmVpIntervalPCR OBJECT-TYPE
              SYNTAX  Gauge32
              MAX-ACCESS  read-only
              STATUS  current
              DESCRIPTION
                     "The maximum traffic rate encountered in the last 
                     interval of the VP connection (monitored once a second)  
                     encountered by an ATM interface/VP in one of the previous 
                     96, individual 15 minute, intervals."
              ::= { atmVpIntervalEntry 20 }

	atmVpIntervalSCR OBJECT-TYPE
              SYNTAX  Gauge32
              MAX-ACCESS  read-only
              STATUS  current
              DESCRIPTION
                     "The average traffic rate during the last interval of the 
                     VP connection , encountered by an ATM interface/VP in one 
                     of the previous 96, individual 15 minute, intervals."
              ::= { atmVpIntervalEntry 21 }

	atmVpIntervalMCR OBJECT-TYPE
              SYNTAX  Gauge32
              MAX-ACCESS  read-only
              STATUS  current
              DESCRIPTION
                     "MCR - The minimum traffic rate encountered in the last 
                     interval of the VP connection (monitored once a second)  
                     encountered by an ATM interface/VP in one of the previous 
                     96, individual 15 minute, intervals."
              ::= { atmVpIntervalEntry 22 }

    atmVpIntervalShaperTotalDiscards OBJECT-TYPE
              SYNTAX       Gauge32
              MAX-ACCESS       read-only
              STATUS       current
              DESCRIPTION
                      "The total number of cells (CLP0 and CLP1) discarded
                       due to congestion by the traffic shaper."
              ::= { atmVpIntervalEntry 23 }

    atmVpIntervalShaperClp0Discards OBJECT-TYPE
              SYNTAX       Gauge32
              MAX-ACCESS       read-only
              STATUS       current
              DESCRIPTION
                      "The total number of CLP0 cells discarded
                       due to congestion by the traffic shaper."
              ::= { atmVpIntervalEntry 24 }
    
    atmVpIntervalShaperClp1Discards OBJECT-TYPE
              SYNTAX       Gauge32
              MAX-ACCESS       read-only
              STATUS       current
              DESCRIPTION
                      "The total number of CLP1 cells discarded
                       due to congestion by the traffic shaper."
              ::= { atmVpIntervalEntry 25 }


          -- The ATM VP Interval Table for Performance Management
          -- contains various statistics
          -- collected by each ATM Interface/VP over the previous 24
          -- hours of operation.  The past 24 hours are broken into 96
          -- completed 15 minute intervals.

          atmVpPMIntervalTable OBJECT-TYPE
              SYNTAX  SEQUENCE OF AtmVpPMIntervalEntry
              MAX-ACCESS  not-accessible
              STATUS  current
              DESCRIPTION
                      "The ATM Vp Interval table for Performance Management."
              ::= { atmVpPerformance 4 }

          atmVpPMIntervalEntry OBJECT-TYPE
              SYNTAX  AtmVpPMIntervalEntry
              MAX-ACCESS  not-accessible
              STATUS  current
              DESCRIPTION
                      "An entry in the ATM Vp Interval table for Performance
                       Management."
              INDEX   { ifIndex, atmVpPMIntervalVpi, atmVpPMIntervalDir, atmVpPMIntervalNumber }
              ::= { atmVpPMIntervalTable 1 }

          AtmVpPMIntervalEntry ::=
              SEQUENCE {
	              atmVpPMIntervalVpi
	                  Integer32,
	              atmVpPMIntervalDir 
	                  INTEGER,
 	              atmVpPMIntervalNumber 
 	                  Integer32,
                  atmVpPMIntervalTxClp01
                      Gauge32,
                  atmVpPMIntervalTxClp0
                      Gauge32,
                  atmVpPMIntervalRxClp01
                      Gauge32,
                  atmVpPMIntervalRxClp0
                      Gauge32,
                  atmVpPMIntervalErroredCells
                      Gauge32,
                  atmVpPMIntervalLostCells
                      Gauge32,
                  atmVpPMIntervalMisinsertedCells
                      Gauge32,
                  atmVpPMIntervalECB
                      Gauge32,
                  atmVpPMIntervalSECB
                      Gauge32,
                  atmVpPMIntervalES
                      Gauge32,
                  atmVpPMIntervalSES
                      Gauge32,
                  atmVpPMIntervalUAS
                      Gauge32,
	              atmVpPMIntervalQuality
		              INTEGER,
	              atmVpPMIntervalLastDayQuality
		              INTEGER
              }

          atmVpPMIntervalVpi OBJECT-TYPE
              SYNTAX  Integer32
              MAX-ACCESS  read-only
              STATUS  current
              DESCRIPTION
                      "The VPI of the VPL."
              ::= { atmVpPMIntervalEntry 1 }

          atmVpPMIntervalDir OBJECT-TYPE
              SYNTAX  INTEGER {forward(2),
			                   backward(3) }
              MAX-ACCESS  read-only
              STATUS  current
              DESCRIPTION
                      "The direction of performance management."
              ::= { atmVpPMIntervalEntry 2 }

          atmVpPMIntervalNumber OBJECT-TYPE
              SYNTAX  Integer32 (1..96)
              MAX-ACCESS  read-only
              STATUS  current
              DESCRIPTION
                      "A number between 1 and 96, where 1 is the most
                      recently completed 15 minute interval and 96 is
                      the least recently completed 15 minutes interval
                      (assuming that all 96 intervals are valid)."
              ::= { atmVpPMIntervalEntry 3 }

          atmVpPMIntervalTxClp01 OBJECT-TYPE
              SYNTAX  Gauge32
              MAX-ACCESS  read-only
              STATUS  current
              DESCRIPTION
                      "The counter associated with the number of transmitted
                      CLP 0+1 cells, encountered by an ATM
                      interface/VP in one of the previous 96, individual 15
                      minute, intervals."
              ::= { atmVpPMIntervalEntry 4 }

          atmVpPMIntervalTxClp0 OBJECT-TYPE
              SYNTAX  Gauge32
              MAX-ACCESS  read-only
              STATUS  current
              DESCRIPTION
                      "The counter associated with the number of transmitted
                      CLP 0 cells, encountered by an ATM
                      interface/VP in one of the previous 96, individual 15
                      minute, intervals."
              ::= { atmVpPMIntervalEntry 5 }

          atmVpPMIntervalRxClp01 OBJECT-TYPE
              SYNTAX  Gauge32
              MAX-ACCESS  read-only
              STATUS  current
              DESCRIPTION
                      "The counter associated with the number of received
                      CLP 0+1 cells, encountered by an ATM
                      interface/VP in one of the previous 96, individual 15
                      minute, intervals."
              ::= { atmVpPMIntervalEntry 6 }

          atmVpPMIntervalRxClp0 OBJECT-TYPE
              SYNTAX  Gauge32
              MAX-ACCESS  read-only
              STATUS  current
              DESCRIPTION
                      "The counter associated with the number of received
                      CLP 0 cells, encountered by an ATM
                      interface/VP in one of the previous 96, individual 15
                      minute, intervals."
              ::= { atmVpPMIntervalEntry 7 }

          atmVpPMIntervalErroredCells OBJECT-TYPE
              SYNTAX  Gauge32
              MAX-ACCESS  read-only
              STATUS  current
              DESCRIPTION
                      "The counter associated with the number of Errored
                      cells, encountered by an ATM
                      interface/VP in one of the previous 96, individual 15
                      minute, intervals."
              ::= { atmVpPMIntervalEntry 8 }

          atmVpPMIntervalLostCells OBJECT-TYPE
              SYNTAX  Gauge32
              MAX-ACCESS  read-only
              STATUS  current
              DESCRIPTION
                      "The counter associated with the number of Lost
                      cells, encountered by an ATM
                      interface/VP in one of the previous 96, individual 15
                      minute, intervals."
              ::= { atmVpPMIntervalEntry 9 }

          atmVpPMIntervalMisinsertedCells OBJECT-TYPE
              SYNTAX  Gauge32
              MAX-ACCESS  read-only
              STATUS  current
              DESCRIPTION
                      "The counter associated with the number of Misinserted
                      cells, encountered by an ATM
                      interface/VP in one of the previous 96, individual 15
                      minute, intervals."
              ::= { atmVpPMIntervalEntry 10 }

          atmVpPMIntervalECB OBJECT-TYPE
              SYNTAX  Gauge32
              MAX-ACCESS  read-only
              STATUS  current
              DESCRIPTION
                      "The counter associated with the number of ECBs
                      encountered by an ATM
                      interface/VP in one of the previous 96, individual 15
                      minute, intervals."
              ::= { atmVpPMIntervalEntry 11 }

          atmVpPMIntervalSECB OBJECT-TYPE
              SYNTAX  Gauge32
              MAX-ACCESS  read-only
              STATUS  current
              DESCRIPTION
                      "The counter associated with the number of SECBs
                      encountered by an ATM
                      interface/VP in one of the previous 96, individual 15
                      minute, intervals."
              ::= { atmVpPMIntervalEntry 12 }

          atmVpPMIntervalES OBJECT-TYPE
              SYNTAX  Gauge32
              MAX-ACCESS  read-only
              STATUS  current
              DESCRIPTION
                      "The counter associated with the number of Errored
                      Seconds, encountered by an ATM
                      interface/VP in one of the previous 96, individual 15
                      minute, intervals."
              ::= { atmVpPMIntervalEntry 13 }

          atmVpPMIntervalSES OBJECT-TYPE
              SYNTAX  Gauge32
              MAX-ACCESS  read-only
              STATUS  current
              DESCRIPTION
                      "The counter associated with the number of Severely
                      Errored Seconds, encountered by an ATM
                      interface/VP in one of the previous 96, individual 15
                      minute, intervals."
              ::= { atmVpPMIntervalEntry 14 }

          atmVpPMIntervalUAS OBJECT-TYPE
              SYNTAX  Gauge32
              MAX-ACCESS  read-only
              STATUS  current
              DESCRIPTION
                      "The counter associated with the number of Unavailable
                      Seconds, encountered by an ATM
                      interface/VP in one of the previous 96, individual 15
                      minute, intervals."
              ::= { atmVpPMIntervalEntry 15 }

	atmVpPMIntervalQuality OBJECT-TYPE
              		SYNTAX  INTEGER { normal(2), unacceptable(3) }
		MAX-ACCESS read-only
		STATUS current
		DESCRIPTION
		" If the number of errors per interval is superior to
		the atmNteUPLTCR value, the quality of service of
		the interval is declared as unacceptable."
		DEFVAL { normal }
	::= { atmVpPMIntervalEntry 16}

	    atmVpPMIntervalLastDayQuality OBJECT-TYPE
              		SYNTAX  INTEGER { normal(2), degraded(4) }
		MAX-ACCESS read-only
		STATUS current
		DESCRIPTION
		" If the number of errors per 24 hours is superior to
		the atmNteDPLTCR value, the quality of service of
		the day is declared as degraded."
		DEFVAL { normal }
	::= { atmVpPMIntervalEntry 17}

-- VP QoS Table

atmVpQoSTable OBJECT-TYPE
    SYNTAX  SEQUENCE OF AtmVpQoSEntry
    MAX-ACCESS  not-accessible
    STATUS  current
    DESCRIPTION
        "The VP QoS table."
    ::= { atmVpPerformance 5 }

atmVpQoSEntry OBJECT-TYPE
    SYNTAX  AtmVpQoSEntry
    MAX-ACCESS  not-accessible
    STATUS  current
    DESCRIPTION
        "."
    INDEX   { ifIndex, atmVplVpi, atmVpQoSPeriodRef }
    ::= { atmVpQoSTable 1 }

AtmVpQoSEntry ::=
    SEQUENCE {
	          atmVpQoSPeriodRef     INTEGER,
	          atmVpQoSElapsedTime	Integer32,
	          atmVpQoSUAS		    Gauge32
             }

atmVpQoSPeriodRef OBJECT-TYPE
	SYNTAX  INTEGER { 
	                 currentPeriod (1), 
	                 lastPeriod    (2) 
                 	} 
	MAX-ACCESS  read-only
	STATUS  current
	DESCRIPTION
	    "This object is an index that specifies which period of time, the next 
	     2 objects refer to.
	     currentPeriod - the period since last systemResetAllStatsCmd received or
	                     since Start-up (if no systemResetAllStatsCmd was received since
	                     Start-up) until now.
	     lastPeriod    - the period between last two commands of systemResetAllStatsCmd.
	                     - If only one command occurred since Start-up: the period between 
	                       Start-up and last command.
	                     - If no command occurred since Start-up: this period will not 
	                       actually exist. In this case, he following 5 objects will be 0."
	::= { atmVpQoSEntry 1 }

atmVpQoSElapsedTime OBJECT-TYPE
	SYNTAX  Integer32 
	MAX-ACCESS  read-only
	STATUS  current
	DESCRIPTION
	    "Elapsed Time in seconds.
	     - for atmVpQoSPeriodRef = currentPeriod:
	       The period since last systemResetAllStatsCmd received or	since Start-up 
	       (if no systemResetAllStatsCmd was received since	Start-up) until now.
	     - for atmVpQoSPeriodRef = lastPeriod:
	       The value of atmVpQoSElapsedTime when last systemResetAllStatsCmd
	       was received."
	::= { atmVpQoSEntry 2 }

atmVpQoSUAS OBJECT-TYPE
	SYNTAX  Gauge32 
	MAX-ACCESS  read-only
	STATUS  current
	DESCRIPTION
	    "Number of Unavailable Seconds for the reference period (atmVpQoSPeriodRef)."
	::= { atmVpQoSEntry 3 }

-- VP PM QoS Table

atmVpPMQoSTable OBJECT-TYPE
     SYNTAX  SEQUENCE OF AtmVpPMQoSEntry
     MAX-ACCESS  not-accessible
     STATUS  current
     DESCRIPTION
         "The PM VP QoS table."
     ::= { atmVpPerformance 6 }

atmVpPMQoSEntry OBJECT-TYPE
     SYNTAX  AtmVpPMQoSEntry
     MAX-ACCESS  not-accessible
     STATUS  current
     DESCRIPTION
         "."
     INDEX   { ifIndex, atmVplVpi, atmVpPMQoSDirection ,atmVpPMQoSPeriodRef }
     ::= { atmVpPMQoSTable 1 }

AtmVpPMQoSEntry ::=
     SEQUENCE {
               atmVpPMQoSDirection	   INTEGER,
	           atmVpPMQoSPeriodRef	   INTEGER,
	           atmVpPMQoSCLR		   Gauge32,
	           atmVpPMQoSCER           Gauge32,
	           atmVpPMQoSCMR           Gauge32
              }

atmVpPMQoSDirection OBJECT-TYPE
     SYNTAX  INTEGER 
           {
            forward  (2),
			backward (3) 
		   }
     MAX-ACCESS  read-only
     STATUS  current
     DESCRIPTION
          "The direction of performance management."
      ::= { atmVpPMQoSEntry 1 }

atmVpPMQoSPeriodRef OBJECT-TYPE
	 SYNTAX  INTEGER 
	      {
           currentPeriod  (1),
           lastPeriod     (2)
	      }
	 MAX-ACCESS  read-only
	 STATUS  current
	 DESCRIPTION
	     "This object is an index that specifies which period of time, the next
	      5 objects refer to.
	      currentPeriod - the period since last systemResetAllStatsCmd received or
	                      since Start-up (if no systemResetAllStatsCmd was received since
	                      Start-up) until now.
	      lastPeriod    - the period between last two commands of systemResetAllStatsCmd.
	                      - If only one command occurred since Start-up: the period between 
	                        Start-up and last command.
	                      - If no command occurred since Start-up: this period will not 
	                        actually exist. In this case, he following 5 objects will be 0."
	::= { atmVpPMQoSEntry 2 }


atmVpPMQoSCLR OBJECT-TYPE
	SYNTAX  Gauge32 
	MAX-ACCESS  read-only
	STATUS  current
	DESCRIPTION
	"Cell Loss Ratio counter for the reference period (atmVpPMQoSPeriodRef)- 
	defined in accordance with I.356 , in %.
	The value will be multipuled by 100."
	::= { atmVpPMQoSEntry 3 }

atmVpPMQoSCER OBJECT-TYPE
	SYNTAX  Gauge32 
	MAX-ACCESS  read-only
	STATUS  current
	DESCRIPTION
	"Cell Error Ratio counter for the reference period (atmVpPMQoSPeriodRef) 
	defined in accordance with I.356 , in %.
	The value will be multipuled by 100."
	::= { atmVpPMQoSEntry 4 }

atmVpPMQoSCMR OBJECT-TYPE
	SYNTAX  Gauge32 
	MAX-ACCESS  read-only
	STATUS  current
	DESCRIPTION
	"Cell Misinsertion Ratio counter for the reference period (atmVpPMQoSPeriodRef) 
	defined in accordance with I.356 , cells/sec ."
	::= { atmVpPMQoSEntry 5 }

--VP Shaper Statistics Table
atmVpShaperStatTable OBJECT-TYPE
              SYNTAX  SEQUENCE OF AtmVpShaperStatEntry
              MAX-ACCESS  not-accessible
              STATUS  current
              DESCRIPTION
                      "The ATM VP shaper statistics table."
              ::= { atmVpPerformance 7 }

          atmVpShaperStatEntry OBJECT-TYPE
              SYNTAX  AtmVpShaperStatEntry
              MAX-ACCESS  not-accessible
              STATUS  current
              DESCRIPTION
                      "An entry in the ATM VP shaper statistics table."
              INDEX   { ifIndex, atmVplVpi }
              ::= { atmVpShaperStatTable 1 }

AtmVpShaperStatEntry ::=
     SEQUENCE {
	           atmVpShaperDiscarded          Counter32,
               atmVpShaperOccupation         Integer32,
               atmVpShaperMaxOccupation 	 Integer32,
               atmVpShaperLevel 			 INTEGER,
               atmVpShaperEpdDropped 		 Counter32,
               atmVpShaperTotalEpdDropped 	 Counter32
              }


atmVpShaperDiscarded OBJECT-TYPE
              SYNTAX  Counter32
              MAX-ACCESS  read-only
              STATUS  current
              DESCRIPTION
                   "The number of Cells that were discarded in the shaper on that VPC due 
                    to buffer overflow. 
                    This counter counts till it reaches its MAX value (20 bits) and then 
                    rolls over."
              ::= { atmVpShaperStatEntry 1 }

atmVpShaperOccupation OBJECT-TYPE
              SYNTAX  Integer32
              MAX-ACCESS  read-only
              STATUS  current
              DESCRIPTION
                   "The number of Cells that are currently stored in the buffer.
                   This parameter is limited to 20 bits."
              ::= { atmVpShaperStatEntry 2}

atmVpShaperMaxOccupation OBJECT-TYPE
              SYNTAX  Integer32
              MAX-ACCESS  read-only
              STATUS  current
              DESCRIPTION
                   "The Maximum number of Cells that were stored in the buffer, 
                   since this VP was activated.	This parameter is limited to 20 bits." 
              ::= { atmVpShaperStatEntry 3}

atmVpShaperLevel OBJECT-TYPE
	          SYNTAX  INTEGER { 
	                 empty   (1), 
	                 full    (2), 
	                 below   (3),
	                 above   (4)
                 	} 
              MAX-ACCESS  read-only
              STATUS  current
              DESCRIPTION
                   "The occupation of the buffer according to a predefined threshold.
                   empty - buffer is Empty
                   full  - buffer is Full 
                   below - buffer is Below the threshold
                   above - buffer is Above the threshold. This is also the trigger to 
                   start EPD\PPD mechanism, if set for the VPC."
              ::= { atmVpShaperStatEntry 4}

atmVpShaperEpdDropped OBJECT-TYPE
              SYNTAX  Counter32
              MAX-ACCESS  read-only
              STATUS  current
              DESCRIPTION
                   "The number of Cells that were dropped in the shaper on that VPC 
                   due to EPD\PPD mechanism in the last second.
                   This parameter is limited to 24 bits.
                   Applicable for a EPD/PPD VP only."
              ::= { atmVpShaperStatEntry 5}

atmVpShaperTotalEpdDropped OBJECT-TYPE
              SYNTAX  Counter32
              MAX-ACCESS  read-only
              STATUS  current
              DESCRIPTION
                   "The Total number of Cells that were dropped in the shaper on that 
                   VPC due to EPD\PPD mechanism in the last 15 minutes. This counter 
                   automatically reset itself every 15 minutes.
                   Applicable for a EPD/PPD VP only."
              ::= { atmVpShaperStatEntry 6}


atmVcPerformance  OBJECT IDENTIFIER  ::=  {atmPvcPerformance 2}

          -- the ATM VC Current

          -- The ATM VC current table contains various statistics being
          -- collected for the current 15 minute interval.

          atmVcCurrentTable OBJECT-TYPE
              SYNTAX  SEQUENCE OF AtmVcCurrentEntry
              MAX-ACCESS  not-accessible
              STATUS  current
              DESCRIPTION
                      "The ATM VC Current table."
              ::= { atmVcPerformance 1 }

          atmVcCurrentEntry OBJECT-TYPE
              SYNTAX  AtmVcCurrentEntry
              MAX-ACCESS  not-accessible
              STATUS  current
              DESCRIPTION
                      "An entry in the ATM VC Current table."
              INDEX   { ifIndex, atmVcCurrentVpi, atmVcCurrentVci }
              ::= { atmVcCurrentTable 1 }

          AtmVcCurrentEntry ::=
              SEQUENCE {
				  atmVcCurrentVpi
                      Integer32,
				  atmVcCurrentVci
				      Integer32,
                  atmVcCurrentRxCellsClp01
                      Gauge32,
                  atmVcCurrentRxCellsClp0
                      Gauge32,
                  atmVcCurrentGcra0Violations
                      Gauge32,
                  atmVcCurrentGcra1Violations
                      Gauge32,
                  atmVcCurrentRxAIS
                      Gauge32,
                  atmVcCurrentTxAIS
                      Gauge32,
                  atmVcCurrentRxRDI
                      Gauge32,
                  atmVcCurrentTxRDI
                      Gauge32,
                  atmVcCurrentContinuityLoss
                      Gauge32,
                  atmVcCurrentUAS
                      Gauge32,
	              atmVcCurrentSES     
	                  Gauge32,
	              atmVcCurrentCDC
	                  Gauge32,
                  atmVcCurrentTotalDiscards     
                      Gauge32,
                  atmVcCurrentClp0Discards      
                      Gauge32,
                  atmVcCurrentTotalCellOuts     
                      Gauge32,
                  atmVcCurrentClp0CellOuts      
                      Gauge32,
                  atmVcCurrentTaggedOuts        
                      Gauge32,
	              atmVcCurrentPCR
	                  Gauge32,
	              atmVcCurrentSCR
	                  Gauge32,
	              atmVcCurrentMCR
	                  Gauge32,
                  atmVcCurrentShaperTotalDiscards     
                      Gauge32,
                  atmVcCurrentShaperClp0Discards      
                      Gauge32,
                  atmVcCurrentShaperClp1Discards      
                      Gauge32
              }

          atmVcCurrentVpi OBJECT-TYPE
              SYNTAX  Integer32
              MAX-ACCESS  read-only
              STATUS  current
              DESCRIPTION
                      "The VPI of the VCL."
              ::= { atmVcCurrentEntry 1 }

          atmVcCurrentVci OBJECT-TYPE
              SYNTAX  Integer32
              MAX-ACCESS  read-only
              STATUS  current
              DESCRIPTION
                      "The VCI of the VCL."
              ::= { atmVcCurrentEntry 2 }

          atmVcCurrentRxCellsClp01 OBJECT-TYPE
              SYNTAX  Gauge32
              MAX-ACCESS  read-only
              STATUS  current
              DESCRIPTION
                      "The counter associated with the number of transmitted
                      cells, encountered by the VCL of this ATM interface in
                      the current 15 minute interval."
              ::= { atmVcCurrentEntry 3 }

          atmVcCurrentRxCellsClp0 OBJECT-TYPE
              SYNTAX  Gauge32
              MAX-ACCESS  read-only
              STATUS  current
              DESCRIPTION
                      "The counter associated with the number of received
                      cells, encountered by the VCL of this ATM
                      interface in the current 15 minute interval."
              ::= { atmVcCurrentEntry 4 }

          atmVcCurrentGcra0Violations OBJECT-TYPE
              SYNTAX  Gauge32
              MAX-ACCESS  read-only
              STATUS  current
              DESCRIPTION
                      "The counter associated with the number of cells 
                      violating GCRA0, encountered by the VCL of this
                      ATM interface in the current 15 minute
                      interval."
              ::= { atmVcCurrentEntry 5 }

          atmVcCurrentGcra1Violations OBJECT-TYPE
              SYNTAX  Gauge32
              MAX-ACCESS  read-only
              STATUS  current
              DESCRIPTION
                      "The counter associated with the number of cells 
                      violating GCRA1, encountered by the VCL of this ATM
                      interface in the current 15 minute interval."
              ::= { atmVcCurrentEntry 6 }

          atmVcCurrentRxAIS OBJECT-TYPE
              SYNTAX  Gauge32
              MAX-ACCESS  read-only
              STATUS  current
              DESCRIPTION
                      "The counter associated with the number of received
                      AIS cells, encountered by the VCL of this ATM
                      interface in the current 15 minute interval."
              ::= { atmVcCurrentEntry 7 }

          atmVcCurrentTxAIS OBJECT-TYPE
              SYNTAX  Gauge32
              MAX-ACCESS  read-only
              STATUS  current
              DESCRIPTION
                      "The counter associated with the number of transmitted
                      AIS cells, encountered by the VCL of this ATM
                      interface in the current 15 minute interval. Not Supported
	        in the first phase."
              ::= { atmVcCurrentEntry 8 }

          atmVcCurrentRxRDI OBJECT-TYPE
              SYNTAX  Gauge32
              MAX-ACCESS  read-only
              STATUS  current
              DESCRIPTION
                      "The counter associated with the number of received
                      RDI cells, encountered by the VCL of this ATM
                      interface in the current 15 minute interval."
              ::= { atmVcCurrentEntry 9 }

          atmVcCurrentTxRDI OBJECT-TYPE
              SYNTAX  Gauge32
              MAX-ACCESS  read-only
              STATUS  current
              DESCRIPTION
                      "The counter associated with the number of transmitted
                      RDI cells, encountered by the VCL of this ATM
                      interface in the current 15 minute interval."
              ::= { atmVcCurrentEntry 10 }

          atmVcCurrentContinuityLoss OBJECT-TYPE
              SYNTAX  Gauge32
              MAX-ACCESS  read-only
              STATUS  current
              DESCRIPTION
                      "The counter associated with the number of loss of
                      continuity cells, encountered by the VCL of this ATM
                      interface in the current 15 minute interval."
              ::= { atmVcCurrentEntry 11 }

          atmVcCurrentUAS OBJECT-TYPE
              SYNTAX  Gauge32
              MAX-ACCESS  read-only
              STATUS  current
              DESCRIPTION
                      "The counter associated with the number of Unavailable
                      Seconds, encountered by the VCL of this ATM
                      interface in the current 15 minute interval."
              ::= { atmVcCurrentEntry 12 }


 	atmVcCurrentSES OBJECT-TYPE
              SYNTAX  Gauge32
              MAX-ACCESS  read-only
              STATUS  current
              DESCRIPTION
                      "The counter associated with the number of Severerly Errored
                      Seconds, encountered by the VCL of this ATM
                      interface in the current 15 minute interval."
              ::= { atmVcCurrentEntry 13 }

	atmVcCurrentCDC OBJECT-TYPE
              SYNTAX  Gauge32
              MAX-ACCESS  read-only
              STATUS  current
              DESCRIPTION
                      "Amount of cells dropped in the current 15 minute interval 
                       of the VC connection."
              ::= { atmVcCurrentEntry 14 }

    atmVcCurrentTotalDiscards OBJECT-TYPE
              SYNTAX       Gauge32
              MAX-ACCESS       read-only
              STATUS       current
              DESCRIPTION
                      "The total number of valid ATM cells discarded by
                      the traffic policing entity.  This includes cells
                      originally received with CLP=0 and CLP=1."
              ::= { atmVcCurrentEntry 15 }

    atmVcCurrentClp0Discards OBJECT-TYPE
              SYNTAX       Gauge32
              MAX-ACCESS       read-only
              STATUS       current
              DESCRIPTION
                      "The total number of valid ATM cells received with
                      CLP=0 an  discarded by the traffic policing
                      entity."
              ::= { atmVcCurrentEntry 16 }

    atmVcCurrentTotalCellOuts OBJECT-TYPE
              SYNTAX       Gauge32
              MAX-ACCESS       read-only
              STATUS       current
              DESCRIPTION
                      "The total number of valid ATM cells transmitted
                      by this VPL.  This includes both CLP=0 and CLP=1
                      cells."
              ::= { atmVcCurrentEntry 17 }
                       
    atmVcCurrentClp0CellOuts OBJECT-TYPE
              SYNTAX       Gauge32
              MAX-ACCESS       read-only
              STATUS       current
              DESCRIPTION
                      "The total number of valid ATM cells transmitted
                      with CLP=0 by this VPL."
              ::= { atmVcCurrentEntry 18 }

    atmVcCurrentTaggedOuts OBJECT-TYPE
              SYNTAX       Gauge32
              MAX-ACCESS       read-only
              STATUS       current
              DESCRIPTION
                      "The total number of valid ATM cells tagged by the
                      traffic policing entity from CLP=0 to CLP=1 and
                      transmitted by this VPL."
              ::= { atmVcCurrentEntry 19 }
                        
	atmVcCurrentPCR OBJECT-TYPE
              SYNTAX  Gauge32
              MAX-ACCESS  read-only
              STATUS  current
              DESCRIPTION
                      "The maximum traffic rate encountered in the last 
                      interval of the VC connection (monitored once a second)."
              ::= { atmVcCurrentEntry 20 }

	atmVcCurrentSCR OBJECT-TYPE
              SYNTAX  Gauge32
              MAX-ACCESS  read-only
              STATUS  current
              DESCRIPTION
                      "The average traffic rate during the last interval 
                      of the VC connection."
              ::= { atmVcCurrentEntry 21 }

	atmVcCurrentMCR OBJECT-TYPE
              SYNTAX  Gauge32
              MAX-ACCESS  read-only
              STATUS  current
              DESCRIPTION
                      "MCR - The minimum traffic rate encountered in the last 
                      interval of the VC connection (monitored once a second)."
              ::= { atmVcCurrentEntry 22 }

    atmVcCurrentShaperTotalDiscards OBJECT-TYPE
              SYNTAX       Gauge32
              MAX-ACCESS       read-only
              STATUS       current
              DESCRIPTION
                      "The total number of cells (CLP0 and CLP1) discarded
                       due to congestion by the traffic shaper."
              ::= { atmVcCurrentEntry 23 }

    atmVcCurrentShaperClp0Discards OBJECT-TYPE
              SYNTAX       Gauge32
              MAX-ACCESS       read-only
              STATUS       current
              DESCRIPTION
                      "The total number of CLP0 cells discarded
                       due to congestion by the traffic shaper."
              ::= { atmVcCurrentEntry 24 }
    
    atmVcCurrentShaperClp1Discards OBJECT-TYPE
              SYNTAX       Gauge32
              MAX-ACCESS       read-only
              STATUS       current
              DESCRIPTION
                      "The total number of CLP1 cells discarded
                       due to congestion by the traffic shaper."
              ::= { atmVcCurrentEntry 25 }


          -- The ATM VC current table for Performance Management
          -- which contains various statistics being
          -- collected for the current 15 minute interval.

          atmVcPMCurrentTable OBJECT-TYPE
              SYNTAX  SEQUENCE OF AtmVcPMCurrentEntry
              MAX-ACCESS  not-accessible
              STATUS  current
              DESCRIPTION
                      "The ATM VC Current table for Performance Management."
              ::= { atmVcPerformance 2 }

          atmVcPMCurrentEntry OBJECT-TYPE
              SYNTAX  AtmVcPMCurrentEntry
              MAX-ACCESS  not-accessible
              STATUS  current
              DESCRIPTION
                      "An entry in the ATM VC Current table for Performance
                       Management."
              INDEX   { ifIndex, atmVcPMCurrentVpi, 
                        atmVcPMCurrentVci, atmVcPMCurrentDir }
              ::= { atmVcPMCurrentTable 1 }

          AtmVcPMCurrentEntry ::=
              SEQUENCE {
	              atmVcPMCurrentVpi
                      Integer32,
	              atmVcPMCurrentVci
	                  Integer32,
	              atmVcPMCurrentDir
	                  Integer32,
                  atmVcPMCurrentTxClp01
                      Gauge32,
                  atmVcPMCurrentTxClp0
                      Gauge32,
                  atmVcPMCurrentRxClp01
                      Gauge32,
                  atmVcPMCurrentRxClp0
                      Gauge32,
                  atmVcPMCurrentErroredCells
                      Gauge32,
                  atmVcPMCurrentLostCells
                      Gauge32,
                  atmVcPMCurrentMisinsertedCells
                      Gauge32,
                  atmVcPMCurrentECB
                      Gauge32,
                  atmVcPMCurrentSECB
                      Gauge32,
                  atmVcPMCurrentES
                      Gauge32,
                  atmVcPMCurrentSES
                      Gauge32,
                  atmVcPMCurrentUAS
                      Gauge32,
	              atmVcPMCurrentIntervalQuality
	                  INTEGER,
	              atmVcPMCurrentLastDayQuality
	                  INTEGER
                  }

          atmVcPMCurrentVpi OBJECT-TYPE
              SYNTAX  Integer32
              MAX-ACCESS  read-only
              STATUS  current
              DESCRIPTION
                      "The VPI of the VCL."
              ::= { atmVcPMCurrentEntry 1 }

          atmVcPMCurrentVci OBJECT-TYPE
              SYNTAX  Integer32
              MAX-ACCESS  read-only
              STATUS  current
              DESCRIPTION
                      "The VCI of the VCL."
              ::= { atmVcPMCurrentEntry 2 }

          atmVcPMCurrentDir OBJECT-TYPE
              SYNTAX  Integer32
              MAX-ACCESS  read-only
              STATUS  current
              DESCRIPTION
                      "The direction of Performance Management."
              ::= { atmVcPMCurrentEntry 3 }

          atmVcPMCurrentTxClp01 OBJECT-TYPE
              SYNTAX  Gauge32
              MAX-ACCESS  read-only
              STATUS  current
              DESCRIPTION
                      "The counter associated with the number of transmitted 
                      CLP 0+1 cells, encountered by the VCL of this ATM
                      interface in the current 15 minute interval."
              ::= { atmVcPMCurrentEntry 4 }

          atmVcPMCurrentTxClp0 OBJECT-TYPE
              SYNTAX  Gauge32
              MAX-ACCESS  read-only
              STATUS  current
              DESCRIPTION
                      "The counter associated with the number of transmitted
                      CLP 0	cells, encountered by the VCL of this ATM
                      interface in the current 15 minute interval."
              ::= { atmVcPMCurrentEntry 5 }

          atmVcPMCurrentRxClp01 OBJECT-TYPE
              SYNTAX  Gauge32
              MAX-ACCESS  read-only
              STATUS  current
              DESCRIPTION
                      "The counter associated with the number of received
                      CLP 0+1 cells, encountered by the VCL of this ATM
                      interface in the current 15 minute interval."
              ::= { atmVcPMCurrentEntry 6 }

          atmVcPMCurrentRxClp0 OBJECT-TYPE
              SYNTAX  Gauge32
              MAX-ACCESS  read-only
              STATUS  current
              DESCRIPTION
                      "The counter associated with the number of received
                      CLP 0 cells, encountered by the VCL of this ATM
                      interface in the current 15 minute interval."
              ::= { atmVcPMCurrentEntry 7 }

          atmVcPMCurrentErroredCells OBJECT-TYPE
              SYNTAX  Gauge32
              MAX-ACCESS  read-only
              STATUS  current
              DESCRIPTION
                      "The counter associated with the number of errored
                      cells, encountered by the VCL of this ATM
                      interface in the current 15 minute interval."
              ::= { atmVcPMCurrentEntry 8 }

          atmVcPMCurrentLostCells OBJECT-TYPE
              SYNTAX  Gauge32
              MAX-ACCESS  read-only
              STATUS  current
              DESCRIPTION
                      "The counter associated with the number of lost
                      cells, encountered by the VCL of this ATM
                      interface in the current 15 minute interval."
              ::= { atmVcPMCurrentEntry 9 }

          atmVcPMCurrentMisinsertedCells OBJECT-TYPE
              SYNTAX  Gauge32
              MAX-ACCESS  read-only
              STATUS  current
              DESCRIPTION
                      "The counter associated with the number of misinserted
                      cells, encountered by the VCL of this ATM
                      interface in the current 15 minute interval."
              ::= { atmVcPMCurrentEntry 10 }

          atmVcPMCurrentECB OBJECT-TYPE
              SYNTAX  Gauge32
              MAX-ACCESS  read-only
              STATUS  current
              DESCRIPTION
                      "The counter associated with the number of ECBs
                      encountered by the VCL of this ATM
                      interface in the current 15 minute interval."
              ::= { atmVcPMCurrentEntry 11 }

          atmVcPMCurrentSECB OBJECT-TYPE
              SYNTAX  Gauge32
              MAX-ACCESS  read-only
              STATUS  current
              DESCRIPTION
                      "The counter associated with the number of SECBs
                      encountered by the VCL of this ATM
                      interface in the current 15 minute interval."
              ::= { atmVcPMCurrentEntry 12 }

          atmVcPMCurrentES OBJECT-TYPE
              SYNTAX  Gauge32
              MAX-ACCESS  read-only
              STATUS  current
              DESCRIPTION
                      "The counter associated with the number of 
                      Errored Seconds, encountered by the VCL of this ATM
                      interface in the current 15 minute interval."
              ::= { atmVcPMCurrentEntry 13 }

          atmVcPMCurrentSES OBJECT-TYPE
              SYNTAX  Gauge32
              MAX-ACCESS  read-only
              STATUS  current
              DESCRIPTION
                      "The counter associated with the number of Severely
                      Errored Seconds, encountered by the VCL of this ATM
                      interface in the current 15 minute interval."
              ::= { atmVcPMCurrentEntry 14 }

          atmVcPMCurrentUAS OBJECT-TYPE
              SYNTAX  Gauge32
              MAX-ACCESS  read-only
              STATUS  current
              DESCRIPTION
                      "The counter associated with the number of Severely
                      Errored Seconds, encountered by the VCL of this ATM
                      interface in the current 15 minute interval."
              ::= { atmVcPMCurrentEntry 15 }

atmVcPMCurrentIntervalQuality OBJECT-TYPE
              SYNTAX  INTEGER { normal(2), unacceptable(3) }
	MAX-ACCESS read-only
	STATUS current
	DESCRIPTION
		" If the number of errors per interval is superior to
		the atmNteUPLTCR value, the quality of service of
		the interval is declared as unacceptable."
	DEFVAL { normal }
	::= { atmVcPMCurrentEntry 16 }

	    atmVcPMCurrentLastDayQuality OBJECT-TYPE
              SYNTAX  INTEGER { normal(2), degraded(4) }
	MAX-ACCESS read-only
	STATUS current
	DESCRIPTION
		" If the number of errors per 24 hours is superior to
		the atmNteDPLTCR value, the quality of service of
		the day is declared as degraded."
	DEFVAL { normal }
	::= { atmVcPMCurrentEntry 17 }


          -- the ATM VC Interval

          -- The ATM VC Interval Table contains various statistics
          -- collected by each ATM Interface/VC over the previous 24
          -- hours of operation.  The past 24 hours are broken into 96
          -- completed 15 minute intervals.

          atmVcIntervalTable OBJECT-TYPE
              SYNTAX  SEQUENCE OF AtmVcIntervalEntry
              MAX-ACCESS  not-accessible
              STATUS  current
              DESCRIPTION
                      "The ATM Vc Interval table."
              ::= { atmVcPerformance 3 }

          atmVcIntervalEntry OBJECT-TYPE
              SYNTAX  AtmVcIntervalEntry
              MAX-ACCESS  not-accessible
              STATUS  current
              DESCRIPTION
                      "An entry in the ATM Vc Interval table."
              INDEX   { ifIndex, atmVcIntervalVpi, 
                        atmVcIntervalVci, atmVcIntervalNumber }
              ::= { atmVcIntervalTable 1 }

          AtmVcIntervalEntry ::=
              SEQUENCE {
	    atmVcIntervalVpi
	      Integer32,
	    atmVcIntervalVci
	      Integer32,
                  atmVcIntervalNumber
                      Integer32,
                  atmVcIntervalRxCellsClp01
                      Gauge32,
                  atmVcIntervalRxCellsClp0
                      Gauge32,
                  atmVcIntervalGcra0Violations
                      Gauge32,
                  atmVcIntervalGcra1Violations
                      Gauge32,
                  atmVcIntervalRxAIS
                      Gauge32,
                  atmVcIntervalTxAIS
                      Gauge32,
                  atmVcIntervalRxRDI
                      Gauge32,
                  atmVcIntervalTxRDI
                      Gauge32,
                  atmVcIntervalContinuityLoss
                      Gauge32,
                  atmVcIntervalUAS
                      Gauge32,
	              atmVcIntervalSES 
	                  Gauge32,
	              atmVcIntervalCDC
	                  Gauge32,
                  atmVcIntervalTotalDiscards     
                      Gauge32,
                  atmVcIntervalClp0Discards      
                      Gauge32,
                  atmVcIntervalTotalCellOuts     
                      Gauge32,
                  atmVcIntervalClp0CellOuts      
                      Gauge32,
                  atmVcIntervalTaggedOuts        
                      Gauge32,
	              atmVcIntervalPCR
	                  Gauge32,
	              atmVcIntervalSCR
	                  Gauge32,
	              atmVcIntervalMCR
	                  Gauge32,
                  atmVcIntervalShaperTotalDiscards     
                      Gauge32,
                  atmVcIntervalShaperClp0Discards      
                      Gauge32,
                  atmVcIntervalShaperClp1Discards      
                      Gauge32
          }

          atmVcIntervalVpi OBJECT-TYPE
              SYNTAX  Integer32
              MAX-ACCESS  read-only
              STATUS  current
              DESCRIPTION
                      "The VPI of the VCL."
              ::= { atmVcIntervalEntry 1 }

          atmVcIntervalVci OBJECT-TYPE
              SYNTAX  Integer32
              MAX-ACCESS  read-only
              STATUS  current
              DESCRIPTION
                      "The VCI of the VCL."
              ::= { atmVcIntervalEntry 2 }

          atmVcIntervalNumber OBJECT-TYPE
              SYNTAX  Integer32 (1..96)
              MAX-ACCESS  read-only
              STATUS  current
              DESCRIPTION
                      "A number between 1 and 96, where 1 is the most
                      recently completed 15 minute interval and 96 is
                      the least recently completed 15 minutes interval
                      (assuming that all 96 intervals are valid)."
              ::= { atmVcIntervalEntry 3 }

          atmVcIntervalRxCellsClp01 OBJECT-TYPE
              SYNTAX  Gauge32
              MAX-ACCESS  read-only
              STATUS  current
              DESCRIPTION
                      "The counter associated with the number of transmitted 
                      cells , encountered by an ATM interface/VC in
                      one of the previous 96, individual 15 minute,
                      intervals."
              ::= { atmVcIntervalEntry 4 }

          atmVcIntervalRxCellsClp0 OBJECT-TYPE
              SYNTAX  Gauge32
              MAX-ACCESS  read-only
              STATUS  current
              DESCRIPTION
                      "The counter associated with the number of received
                      cells, encountered by an ATM
                      interface/VC in one of the previous 96, individual 15
                      minute, intervals."
              ::= { atmVcIntervalEntry 5 }

          atmVcIntervalGcra0Violations OBJECT-TYPE
              SYNTAX  Gauge32
              MAX-ACCESS  read-only
              STATUS  current
              DESCRIPTION
                      "The counter associated with the number of
                      cells violating GCRA0, encountered by an ATM
                      interface/VC in one of the previous 96, individual 15
                      minute, intervals."
              ::= { atmVcIntervalEntry 6 }

          atmVcIntervalGcra1Violations OBJECT-TYPE
              SYNTAX  Gauge32
              MAX-ACCESS  read-only
              STATUS  current
              DESCRIPTION
                      "The counter associated with the number of
                      cells violating GCRA1, encountered by an ATM
                      interface/VC in one of the previous 96, individual 15
                      minute, intervals."
              ::= { atmVcIntervalEntry 7 }

          atmVcIntervalRxAIS OBJECT-TYPE
              SYNTAX  Gauge32
              MAX-ACCESS  read-only
              STATUS  current
              DESCRIPTION
                      "The counter associated with the number of received
                      AIS cells, encountered by an ATM
                      interface/VC in one of the previous 96, individual 15
                      minute, intervals."
              ::= { atmVcIntervalEntry 8 }

          atmVcIntervalTxAIS OBJECT-TYPE
              SYNTAX  Gauge32
              MAX-ACCESS  read-only
              STATUS  current
              DESCRIPTION
                      "The counter associated with the number of transmitted
                      AIS cells, encountered by an ATM
                      interface/VC in one of the previous 96, individual 15
                      minute, intervals. Not supported  in the first phase."
              ::= { atmVcIntervalEntry 9 }

          atmVcIntervalRxRDI OBJECT-TYPE
              SYNTAX  Gauge32
              MAX-ACCESS  read-only
              STATUS  current
              DESCRIPTION
                      "The counter associated with the number of received
                      RDI cells, encountered by an ATM
                      interface/VC in one of the previous 96, individual 15
                      minute, intervals."
              ::= { atmVcIntervalEntry 10 }

          atmVcIntervalTxRDI OBJECT-TYPE
              SYNTAX  Gauge32
              MAX-ACCESS  read-only
              STATUS  current
              DESCRIPTION
                      "The counter associated with the number of transmitted
                      RDI cells, encountered by an ATM
                      interface/VC in one of the previous 96, individual 15
                      minute, intervals."
              ::= { atmVcIntervalEntry 11 }

          atmVcIntervalContinuityLoss OBJECT-TYPE
              SYNTAX  Gauge32
              MAX-ACCESS  read-only
              STATUS  current
              DESCRIPTION
                      "The counter associated with the number of Continuity
                      Loss cells, encountered by an ATM
                      interface/VC in one of the previous 96, individual 15
                      minute, intervals."
              ::= { atmVcIntervalEntry 12 }

          atmVcIntervalUAS OBJECT-TYPE
              SYNTAX  Gauge32
              MAX-ACCESS  read-only
              STATUS  current
              DESCRIPTION
                      "The counter associated with the number of Unavailable
                      Seconds, encountered by an ATM
                      interface/VC in one of the previous 96, individual 15
                      minute, intervals."
              ::= { atmVcIntervalEntry 13 }

          atmVcIntervalSES OBJECT-TYPE
              SYNTAX  Gauge32
              MAX-ACCESS  read-only
              STATUS  current
              DESCRIPTION
                      "The counter associated with the number of Severerly Errored
                      Seconds, encountered by an ATM
                      interface/VC in one of the previous 96, individual 15
                      minute, intervals."
              ::= { atmVcIntervalEntry 14 }

	atmVcIntervalCDC OBJECT-TYPE
              SYNTAX  Gauge32
              MAX-ACCESS  read-only
              STATUS  current
              DESCRIPTION
                      "Amount of cells dropped in the 15 minute interval 
                       of the VC connection."
              ::= { atmVcIntervalEntry 15 }

    atmVcIntervalTotalDiscards OBJECT-TYPE
              SYNTAX       Gauge32
              MAX-ACCESS       read-only
              STATUS       current
              DESCRIPTION
                      "The total number of valid ATM cells discarded by
                      the traffic policing entity.  This includes cells
                      originally received with CLP=0 and CLP=1."
              ::= { atmVcIntervalEntry 16 }

    atmVcIntervalClp0Discards OBJECT-TYPE
              SYNTAX       Gauge32
              MAX-ACCESS       read-only
              STATUS       current
              DESCRIPTION
                      "The total number of valid ATM cells received with
                      CLP=0 an  discarded by the traffic policing
                      entity."
              ::= { atmVcIntervalEntry 17 }

    atmVcIntervalTotalCellOuts OBJECT-TYPE
              SYNTAX       Gauge32
              MAX-ACCESS       read-only
              STATUS       current
              DESCRIPTION
                      "The total number of valid ATM cells transmitted
                      by this VPL.  This includes both CLP=0 and CLP=1
                      cells."
              ::= { atmVcIntervalEntry 18 }
                        
                       
    atmVcIntervalClp0CellOuts OBJECT-TYPE
              SYNTAX       Gauge32
              MAX-ACCESS       read-only
              STATUS       current
              DESCRIPTION
                      "The total number of valid ATM cells transmitted
                      with CLP=0 by this VPL."
              ::= { atmVcIntervalEntry 19 }

    atmVcIntervalTaggedOuts OBJECT-TYPE
              SYNTAX       Gauge32
              MAX-ACCESS       read-only
              STATUS       current
              DESCRIPTION
                      "The total number of valid ATM cells tagged by the
                      traffic policing entity from CLP=0 to CLP=1 and
                      transmitted by this VPL."
              ::= { atmVcIntervalEntry 20 }
                        
	atmVcIntervalPCR OBJECT-TYPE
              SYNTAX  Gauge32
              MAX-ACCESS  read-only
              STATUS  current
              DESCRIPTION
                      "The maximum traffic rate encountered in the 
                      last interval of the VC connection (monitored once a second)  
                      encountered by an ATM interface/VC in one of the previous 96, 
                      individual 15  minute, intervals."
              ::= { atmVcIntervalEntry 21 }

	atmVcIntervalSCR OBJECT-TYPE
              SYNTAX  Gauge32
              MAX-ACCESS  read-only
              STATUS  current
              DESCRIPTION
                      "The average traffic rate during the last interval 
                      of the VC connection, encountered by an ATM interface/VC 
                      in one of the previous 96, individual 15 minute, intervals."
              ::= { atmVcIntervalEntry 22 }

	atmVcIntervalMCR OBJECT-TYPE
              SYNTAX  Gauge32
              MAX-ACCESS  read-only
              STATUS  current
              DESCRIPTION
                      "MCR - The minimum traffic rate encountered in the last 
                      interval of the VC connection (monitored once a second)  
                      encountered by an ATM interface/VC in one of the previous 96, 
                      individual 15 minute, intervals."
              ::= { atmVcIntervalEntry 23 }

    atmVcIntervalShaperTotalDiscards OBJECT-TYPE
              SYNTAX       Gauge32
              MAX-ACCESS       read-only
              STATUS       current
              DESCRIPTION
                      "The total number of cells (CLP0 and CLP1) discarded
                       due to congestion by the traffic shaper."
              ::= { atmVcIntervalEntry 24 }

    atmVcIntervalShaperClp0Discards OBJECT-TYPE
              SYNTAX       Gauge32
              MAX-ACCESS       read-only
              STATUS       current
              DESCRIPTION
                      "The total number of CLP0 cells discarded
                       due to congestion by the traffic shaper."
              ::= { atmVcIntervalEntry 25 }
    
    atmVcIntervalShaperClp1Discards OBJECT-TYPE
              SYNTAX       Gauge32
              MAX-ACCESS       read-only
              STATUS       current
              DESCRIPTION
                      "The total number of CLP1 cells discarded
                       due to congestion by the traffic shaper."
              ::= { atmVcIntervalEntry 26 }


          -- The ATM VC Interval Table for Performance Management
          -- which contains various statistics
          -- collected by each ATM Interface/VC over the previous 24
          -- hours of operation.  The past 24 hours are broken into 96
          -- completed 15 minute intervals.

          atmVcPMIntervalTable OBJECT-TYPE
              SYNTAX  SEQUENCE OF AtmVcPMIntervalEntry
              MAX-ACCESS  not-accessible
              STATUS  current
              DESCRIPTION
                      "The ATM Vc Interval table for Performance Management."
              ::= { atmVcPerformance 4 }

--atmCESAAL1StatsTable OBJECT IDENTIFIER ::= {atmVcPerformance 5} (see hybCES.txt)

          atmVcPMIntervalEntry OBJECT-TYPE
              SYNTAX  AtmVcPMIntervalEntry
              MAX-ACCESS  not-accessible
              STATUS  current
              DESCRIPTION
                      "An entry in the ATM Vc Interval table for Performance
                       Management."
              INDEX   { ifIndex, atmVcPMIntervalVpi, 
                        atmVcPMIntervalVci, atmVcPMIntervalDir, atmVcPMIntervalNumber }
              ::= { atmVcPMIntervalTable 1 }

          AtmVcPMIntervalEntry ::=
              SEQUENCE {
	              atmVcPMIntervalVpi
	                  Integer32,
	              atmVcPMIntervalVci
	                  Integer32,
	              atmVcPMIntervalDir 
	                  INTEGER,
 	              atmVcPMIntervalNumber 
                      Integer32,
                  atmVcPMIntervalTxClp01
                      Gauge32,
                  atmVcPMIntervalTxClp0
                      Gauge32,
                  atmVcPMIntervalRxClp01
                      Gauge32,
                  atmVcPMIntervalRxClp0
                      Gauge32,
                  atmVcPMIntervalErroredCells
                      Gauge32,
                  atmVcPMIntervalLostCells
                      Gauge32,
                  atmVcPMIntervalMisinsertedCells
                      Gauge32,
                  atmVcPMIntervalECB
                      Gauge32,
                  atmVcPMIntervalSECB
                      Gauge32,
                  atmVcPMIntervalES
                      Gauge32,
                  atmVcPMIntervalSES
                      Gauge32,
                  atmVcPMIntervalUAS
                      Gauge32,
	    atmVcPMIntervalQuality
	        INTEGER,
	    atmVcPMIntervalLastDayQuality
	        INTEGER
              }

          atmVcPMIntervalVpi OBJECT-TYPE
              SYNTAX  Integer32
              MAX-ACCESS  read-only
              STATUS  current
              DESCRIPTION
                      "The VPI of the VCL."
              ::= { atmVcPMIntervalEntry 1 }

          atmVcPMIntervalVci OBJECT-TYPE
              SYNTAX  Integer32
              MAX-ACCESS  read-only
              STATUS  current
              DESCRIPTION
                      "The VCI of the VCL."
              ::= { atmVcPMIntervalEntry 2 }

          atmVcPMIntervalDir OBJECT-TYPE
              SYNTAX  INTEGER {forward(2),
			                   backward(3) }
              MAX-ACCESS  read-only
              STATUS  current
              DESCRIPTION
                      "The direction of Performance Management."
              ::= { atmVcPMIntervalEntry 3 }

          atmVcPMIntervalNumber OBJECT-TYPE
              SYNTAX  Integer32 (1..96)
              MAX-ACCESS  read-only
              STATUS  current
              DESCRIPTION
                      "A number between 1 and 96, where 1 is the most
                      recently completed 15 minute interval and 96 is
                      the least recently completed 15 minutes interval
                      (assuming that all 96 intervals are valid)."
              ::= { atmVcPMIntervalEntry 4 }

          atmVcPMIntervalTxClp01 OBJECT-TYPE
              SYNTAX  Gauge32
              MAX-ACCESS  read-only
              STATUS  current
              DESCRIPTION
                      "The counter associated with the number of transmitted
                      CLP 0+1 cells, encountered by an ATM
                      interface/VC in one of the previous 96, individual 15
                      minute, intervals."
              ::= { atmVcPMIntervalEntry 5 }

          atmVcPMIntervalTxClp0 OBJECT-TYPE
              SYNTAX  Gauge32
              MAX-ACCESS  read-only
              STATUS  current
              DESCRIPTION
                      "The counter associated with the number of transmitted
                      CLP 0 cells, encountered by an ATM
                      interface/VC in one of the previous 96, individual 15
                      minute, intervals."
              ::= { atmVcPMIntervalEntry 6 }

          atmVcPMIntervalRxClp01 OBJECT-TYPE
              SYNTAX  Gauge32
              MAX-ACCESS  read-only
              STATUS  current
              DESCRIPTION
                      "The counter associated with the number of received
                      CLP 0+1 cells, encountered by an ATM
                      interface/VC in one of the previous 96, individual 15
                      minute, intervals."
              ::= { atmVcPMIntervalEntry 7 }

          atmVcPMIntervalRxClp0 OBJECT-TYPE
              SYNTAX  Gauge32
              MAX-ACCESS  read-only
              STATUS  current
              DESCRIPTION
                      "The counter associated with the number of received
                      CLP 0 cells, encountered by an ATM
                      interface/VC in one of the previous 96, individual 15
                      minute, intervals."
              ::= { atmVcPMIntervalEntry 8 }

          atmVcPMIntervalErroredCells OBJECT-TYPE
              SYNTAX  Gauge32
              MAX-ACCESS  read-only
              STATUS  current
              DESCRIPTION
                      "The counter associated with the number of Errored
                      cells, encountered by an ATM
                      interface/VC in one of the previous 96, individual 15
                      minute, intervals."
              ::= { atmVcPMIntervalEntry 9 }

          atmVcPMIntervalLostCells OBJECT-TYPE
              SYNTAX  Gauge32
              MAX-ACCESS  read-only
              STATUS  current
              DESCRIPTION
                      "The counter associated with the number of Lost
                      cells, encountered by an ATM
                      interface/VC in one of the previous 96, individual 15
                      minute, intervals."
              ::= { atmVcPMIntervalEntry 10 }

          atmVcPMIntervalMisinsertedCells OBJECT-TYPE
              SYNTAX  Gauge32
              MAX-ACCESS  read-only
              STATUS  current
              DESCRIPTION
                      "The counter associated with the number of Misinserted
                      cells, encountered by an ATM
                      interface/VC in one of the previous 96, individual 15
                      minute, intervals."
              ::= { atmVcPMIntervalEntry 11 }

          atmVcPMIntervalECB OBJECT-TYPE
              SYNTAX  Gauge32
              MAX-ACCESS  read-only
              STATUS  current
              DESCRIPTION
                      "The counter associated with the number of ECBs
                      encountered by an ATM
                      interface/VC in one of the previous 96, individual 15
                      minute, intervals."
              ::= { atmVcPMIntervalEntry 12 }

          atmVcPMIntervalSECB OBJECT-TYPE
              SYNTAX  Gauge32
              MAX-ACCESS  read-only
              STATUS  current
              DESCRIPTION
                      "The counter associated with the number of SECBs
                      encountered by an ATM
                      interface/VC in one of the previous 96, individual 15
                      minute, intervals."
              ::= { atmVcPMIntervalEntry 13 }

          atmVcPMIntervalES OBJECT-TYPE
              SYNTAX  Gauge32
              MAX-ACCESS  read-only
              STATUS  current
              DESCRIPTION
                      "The counter associated with the number of Errored
                      Seconds, encountered by an ATM
                      interface/VC in one of the previous 96, individual 15
                      minute, intervals."
              ::= { atmVcPMIntervalEntry 14 }

          atmVcPMIntervalSES OBJECT-TYPE
              SYNTAX  Gauge32
              MAX-ACCESS  read-only
              STATUS  current
              DESCRIPTION
                      "The counter associated with the number of Severely
                       Errored Seconds, encountered by an ATM
                       interface/VC in one of the previous 96, individual 15
                       minute, intervals."
              ::= { atmVcPMIntervalEntry 15 }

          atmVcPMIntervalUAS OBJECT-TYPE
              SYNTAX  Gauge32
              MAX-ACCESS  read-only
              STATUS  current
              DESCRIPTION
                      "The counter associated with the number of Unavailable
                       Seconds, encountered by an ATM
                       interface/VC in one of the previous 96, individual 15
                       minute, intervals."
              ::= { atmVcPMIntervalEntry 16 }

atmVcPMIntervalQuality OBJECT-TYPE
              		SYNTAX  INTEGER { normal(2), unacceptable(3) }
		MAX-ACCESS read-only
		STATUS current
		DESCRIPTION
		" If the number of errors per interval is superior to
		the atmNteUPLTCR value, the quality of service of
		the interval is declared as unacceptable."
		DEFVAL { normal }
	::= { atmVcPMIntervalEntry 17}

	    atmVcPMIntervalLastDayQuality OBJECT-TYPE
              		SYNTAX  INTEGER { normal(2), degraded(4) }
		MAX-ACCESS read-only
		STATUS current
		DESCRIPTION
		" If the number of errors per 24 hours is superior to
		the atmNteDPLTCR value, the quality of service of
		the day is declared as degraded."
		DEFVAL { normal }
	::= { atmVcPMIntervalEntry 18}




-- VC QoS Table

atmVcQoSTable OBJECT-TYPE
    SYNTAX  SEQUENCE OF AtmVcQoSEntry
    MAX-ACCESS  not-accessible
    STATUS  current
    DESCRIPTION
        "The ATM VP QoS table."
    ::= { atmVcPerformance 6 }

atmVcQoSEntry OBJECT-TYPE
    SYNTAX  AtmVcQoSEntry
    MAX-ACCESS  not-accessible
    STATUS  current
    DESCRIPTION
        "An entry in the ATM VP table."
    INDEX   { ifIndex, atmVclVpi, atmVclVci, atmVcQoSPeriodRef }
    ::= { atmVcQoSTable 1 }

AtmVcQoSEntry ::=
    SEQUENCE {
	          atmVcQoSPeriodRef     INTEGER,
	          atmVcQoSElapsedTime	Integer32,
	          atmVcQoSUAS		    Gauge32
             }


atmVcQoSPeriodRef OBJECT-TYPE
	SYNTAX  INTEGER 
	      {
           currentPeriod  (1),
           lastPeriod     (2)
	      }
	MAX-ACCESS  read-only
	STATUS  current
	DESCRIPTION
	    "This object is an index that specifies which period of time, the next 
	     2 objects refer to.
	     currentPeriod  - the period since last systemResetAllStatsCmd received or
	                      since Start-up (if no systemResetAllStatsCmd was received since
	                      Start-up) until now.
	     lastPeriod    - the period between last two commands of systemResetAllStatsCmd.
	                     - If only one command occurred since Start-up: the period between 
	                       Start-up and last command.
	                     - If no command occurred since Start-up: this period will not 
	                       actually exist. In this case, he following 5 objects will be 0."
	::= { atmVcQoSEntry 1 }

atmVcQoSElapsedTime OBJECT-TYPE
	SYNTAX  Integer32 
	MAX-ACCESS  read-only
	STATUS  current
	DESCRIPTION
	    "Elapsed Time in seconds.
	     - for atmVcQoSPeriodRef = currentPeriod:
	       The period since last systemResetAllStatsCmd received or	since Start-up 
	       (if no systemResetAllStatsCmd was received since	Start-up) until now.
	     - for atmVcQoSPeriodRef = lastPeriod:
	       The value of atmVcQoSElapsedTime when last systemResetAllStatsCmd
	       was received."
	::= { atmVcQoSEntry 2 }

atmVcQoSUAS OBJECT-TYPE
	SYNTAX  Gauge32 
	MAX-ACCESS  read-only
	STATUS  current
	DESCRIPTION
	    "Number of Unavailable Seconds for the reference period (atmVcQoSPeriodRef)."
	::= { atmVcQoSEntry 3 }

-- VC PM QoS Table

atmVcPMQoSTable OBJECT-TYPE
     SYNTAX  SEQUENCE OF AtmVcPMQoSEntry
     MAX-ACCESS  not-accessible
     STATUS  current
     DESCRIPTION
         "The PM VC QoS table."
     ::= { atmVcPerformance 7 }

atmVcPMQoSEntry OBJECT-TYPE
     SYNTAX  AtmVcPMQoSEntry
     MAX-ACCESS  not-accessible
     STATUS  current
     DESCRIPTION
         "An entry in the VC PM QoS table."
     INDEX   { ifIndex, atmVclVpi, atmVclVci, atmVcPMQoSDirection ,atmVcPMQoSPeriodRef }
     ::= { atmVcPMQoSTable 1 }

AtmVcPMQoSEntry ::=
     SEQUENCE {
               atmVcPMQoSDirection	   INTEGER,
	           atmVcPMQoSPeriodRef	   INTEGER,
	           atmVcPMQoSCLR		   Gauge32,
	           atmVcPMQoSCER           Gauge32,
	           atmVcPMQoSCMR           Gauge32
              }

atmVcPMQoSDirection OBJECT-TYPE
     SYNTAX  INTEGER 
         {
          forward(2),
		  backward(3) 
		 }
      MAX-ACCESS  read-only
      STATUS  current
      DESCRIPTION
          "The direction of performance management."
      ::= { atmVcPMQoSEntry 1 }

atmVcPMQoSPeriodRef OBJECT-TYPE
	SYNTAX  INTEGER 
	      {
           currentPeriod  (1),
           lastPeriod     (2)
	      }
	MAX-ACCESS  read-only
	STATUS  current
	DESCRIPTION
	"This object is an index that specifies which period of time, the next
	 5 objects refer to.
	 currentPeriod - the period since last systemResetAllStatsCmd received or
	                 since Start-up (if no systemResetAllStatsCmd was received since
	                 Start-up) until now.
	 lastPeriod    - the period between last two commands of systemResetAllStatsCmd.
	                 - If only one command occurred since Start-up: the period between 
	                   Start-up and last command.
	                 - If no command occurred since Start-up: this period will not 
	                   actually exist. In this case, he following 5 objects will be 0."
	::= { atmVcPMQoSEntry 2 }


atmVcPMQoSCLR OBJECT-TYPE
	SYNTAX  Gauge32 
	MAX-ACCESS  read-only
	STATUS  current
	DESCRIPTION
	"Cell Loss Ratio counter for the reference period (atmVcPMQoSPeriodRef)- 
	defined in accordance with I.356 , in %.
	The value will be multipuled by 100."
	::= { atmVcPMQoSEntry 3 }

atmVcPMQoSCER OBJECT-TYPE
	SYNTAX  Gauge32 
	MAX-ACCESS  read-only
	STATUS  current
	DESCRIPTION
	"Cell Error Ratio counter for the reference period (atmVcPMQoSPeriodRef) 
	defined in accordance with I.356 , in %.
	The value will be multipuled by 100."
	::= { atmVcPMQoSEntry 4 }

atmVcPMQoSCMR OBJECT-TYPE
	SYNTAX  Gauge32 
	MAX-ACCESS  read-only
	STATUS  current
	DESCRIPTION
	"Cell Miss-insertion Ratio counter for the reference period (atmVcPMQoSPeriodRef) 
	defined in accordance with I.356 , cells/sec ."
	::= { atmVcPMQoSEntry 5 }

--VC Shaper Statistics Table
atmVcShaperStatTable OBJECT-TYPE
              SYNTAX  SEQUENCE OF AtmVcShaperStatEntry
              MAX-ACCESS  not-accessible
              STATUS  current
              DESCRIPTION
                      "The ATM VC shaper statistics table."
              ::= { atmVcPerformance 8 }

          atmVcShaperStatEntry OBJECT-TYPE
              SYNTAX  AtmVcShaperStatEntry
              MAX-ACCESS  not-accessible
              STATUS  current
              DESCRIPTION
                      "An entry in the ATM VC shaper statistics table."
              INDEX   { ifIndex, atmVclVpi, atmVclVci }
              ::= { atmVcShaperStatTable 1 }

AtmVcShaperStatEntry ::=
     SEQUENCE {
	           atmVcShaperDiscarded          Counter32,
               atmVcShaperOccupation 		 Integer32,
               atmVcShaperMaxOccupation 	 Integer32,
               atmVcShaperLevel 			 INTEGER,
               atmVcShaperEpdDropped 		 Counter32,
               atmVcShaperTotalEpdDropped 	 Counter32
              }

atmVcShaperDiscarded  OBJECT-TYPE
              SYNTAX  Counter32
              MAX-ACCESS  read-only
              STATUS  current
              DESCRIPTION
                   "The number of Cells that were discarded in the shaper on that VCC due 
                    to buffer overflow. This counter counts till it reaches its MAX value 
                    (20 bits) and then rolls over."
              ::= { atmVcShaperStatEntry 1 }

atmVcShaperOccupation OBJECT-TYPE
              SYNTAX  Integer32
              MAX-ACCESS  read-only
              STATUS  current
              DESCRIPTION
                   "The number of Cells that are currently stored in the buffer.
                   This parameter is limited to 20 bits."
              ::= { atmVcShaperStatEntry 2}

atmVcShaperMaxOccupation OBJECT-TYPE
              SYNTAX  Integer32
              MAX-ACCESS  read-only
              STATUS  current
              DESCRIPTION
                   "The Maximum number of Cells that were stored in the buffer, 
                   since this VC was activated.	This parameter is limited to 20 bits."
              ::= { atmVcShaperStatEntry 3}

atmVcShaperLevel OBJECT-TYPE
	          SYNTAX  INTEGER { 
	                 empty   (1), 
	                 full    (2), 
	                 below   (3),
	                 above   (4)
                 	} 
              MAX-ACCESS  read-only
              STATUS  current
              DESCRIPTION
                   "The occupation of the buffer according to a predefined threshold.
                   empty - buffer is Empty
                   full  - buffer is Full 
                   below - buffer is Below the threshold
                   above - buffer is Above the threshold. This is also the trigger to 
                   start EPD\PPD mechanism, if set for the VCC."
              ::= { atmVcShaperStatEntry 4}

atmVcShaperEpdDropped OBJECT-TYPE
              SYNTAX  Counter32
              MAX-ACCESS  read-only
              STATUS  current
              DESCRIPTION
                   "The number of Cells that were dropped in the shaper on that VCC 
                   due to EPD\PPD mechanism in the last second.
                   This parameter is limited to 24 bits.
                   Applicable for a EPD/PPD VC only."
              ::= { atmVcShaperStatEntry 5}

atmVcShaperTotalEpdDropped OBJECT-TYPE
              SYNTAX  Counter32
              MAX-ACCESS  read-only
              STATUS  current
              DESCRIPTION
                   "The Total number of Cells that were dropped in the shaper on that 
                   VPC due to EPD\PPD mechanism in the last 15 minutes. This counter 
                   automatically reset itself every 15 minutes.
                   Applicable for a EPD/PPD VC only."
              ::= { atmVcShaperStatEntry 6}



-- New
-- The agent will keep in this group the date & time corresponding to each interval.
atmIntervalDateTable OBJECT-TYPE
	SYNTAX  SEQUENCE OF AtmIntervalDateEntry
	MAX-ACCESS  not-accessible
              STATUS  current
              DESCRIPTION
	"The agent will keep in this group the date & time
	 corresponding to each interval."
             ::=  {atmPerfHistory 3}

 atmIntervalDateEntry OBJECT-TYPE
              SYNTAX AtmIntervalDateEntry 
              MAX-ACCESS  not-accessible
              STATUS  current
              DESCRIPTION
                      "The date & time for the given interval."
              INDEX   { atmIntervalDateInterval } 
              ::= { atmIntervalDateTable 1 }

         AtmIntervalDateEntry ::=
              SEQUENCE {
 		atmIntervalDateInterval 
                      		Integer32,
		atmIntervalDateDate
			DisplayString,
                  	atmIntervalDateTime
                      		DisplayString
	}

	atmIntervalDateInterval  OBJECT-TYPE
              		SYNTAX  Integer32 (1..96)
		MAX-ACCESS read-only
		STATUS current
		DESCRIPTION
		" The interval number defining this entry."
	::= { atmIntervalDateEntry 1}

	atmIntervalDateDate OBJECT-TYPE
              		SYNTAX DisplayString
		MAX-ACCESS read-only
		STATUS current
		DESCRIPTION
		"The date corresponding to this interval."
	::= { atmIntervalDateEntry 2}

	atmIntervalDateTime OBJECT-TYPE
              		SYNTAX DisplayString
		MAX-ACCESS read-only
		STATUS current
		DESCRIPTION
		"The time corresponding to this interval."
	::= { atmIntervalDateEntry 3}



--atmNte  OBJECT IDENTIFIER  ::=  {radAtm 3}

atmNteSys  OBJECT IDENTIFIER  ::=  {atmNte 1}

atmNteSysConfig  OBJECT IDENTIFIER  ::=  {atmNteSys 1}

          atmNteManagerTable OBJECT-TYPE
              SYNTAX  SEQUENCE OF AtmNteManagerEntry
              MAX-ACCESS  not-accessible
              STATUS  current
              DESCRIPTION
                      "The Manager Table includes all the NMSs that
                       receive traps from this agent. A single manager
                       can receive traps on more than one PVC. The agent 
                       will set	implicitly the correct ifIndex, VPI, VCI 
                       values to all relevant entries in the table when 
                       the user changes	them for one of the PVCs."
              ::= { atmNteSysConfig 1 }

          atmNteManagerEntry OBJECT-TYPE
              SYNTAX  AtmNteManagerEntry
              MAX-ACCESS  not-accessible
              STATUS  current
              DESCRIPTION
                      "A single manager and the PVC for receiving traps."
              INDEX   { atmNteManagerIP, atmNteManagerPvc} 
              ::= { atmNteManagerTable 1 }

          AtmNteManagerEntry ::=
              SEQUENCE {
                  atmNteManagerIP
                      IpAddress,
				  atmNteManagerPvc
				      Integer32,
                  atmNteManagerIfIndex
                      Integer32,
                  atmNteManagerVpi
                      Integer32,
                  atmNteManagerVci
                      Integer32,
                  atmNteManagerTrapMask
                      Integer32,
                  atmNteManagerRowStatus
                      RowStatus,
                  atmNteManagerNextHop
                      IpAddress,
				  atmNteManagerVlanSupport
					  INTEGER,
				  atmNteManagerVlanIdentifier
					  Integer32,
				  atmNteManagerVlanFramePriority
					  Integer32,
				  atmNteManagerAlarmTrapMask
				  	  OCTET STRING,
				  atmNteManagerConfigPorts
					  Integer32
              }

          atmNteManagerIP OBJECT-TYPE
              SYNTAX  IpAddress 
              MAX-ACCESS  read-only
              STATUS  current
              DESCRIPTION
                      "The IP address of the NMS."
              ::= { atmNteManagerEntry 1 }

          atmNteManagerPvc OBJECT-TYPE
              SYNTAX  Integer32 
              MAX-ACCESS  read-only
              STATUS  current
              DESCRIPTION
                      "A PVC index. The range is 1..8. There are four PVCs
                       on the User Port and four PVCs on the Network Port.
                       The default VPI, VCI values are specified below." 
              ::= { atmNteManagerEntry 2 }

          atmNteManagerIfIndex OBJECT-TYPE
              SYNTAX  Integer32 
              MAX-ACCESS  read-create
              STATUS  current
              DESCRIPTION
                      "The ATM interface index of the management port."
              ::= { atmNteManagerEntry 3 }

          atmNteManagerVpi OBJECT-TYPE
              SYNTAX  Integer32 
              MAX-ACCESS  read-create
              STATUS  current
              DESCRIPTION
                      "The VPI of the management VCL. Default: 0."
              ::= { atmNteManagerEntry 4 }

          atmNteManagerVci OBJECT-TYPE
              SYNTAX  Integer32 
              MAX-ACCESS  read-create
              STATUS  current
              DESCRIPTION
                      "The VCI of the management VCL. Defaults: 32,33,34,35."
              ::= { atmNteManagerEntry 5 }

          atmNteManagerTrapMask OBJECT-TYPE
         	SYNTAX  Integer32 
        	MAX-ACCESS  read-create
        	STATUS current
        	DESCRIPTION
               "The value of this attribute determines the type of traps the 
                agent should mask and not send to this NMS. The 
                value is differently determined for different products. There are 
                mainly two methods:
              - an integer number, specifying the traps' severity.
              - a sum of 2**n, where n is a bit assigned to a certain 
                masked trap group.
                User should consult the product specification, to find out 
                the method employed."
        	::= { atmNteManagerEntry 6 }

    atmNteManagerRowStatus OBJECT-TYPE
              SYNTAX RowStatus 
              MAX-ACCESS read-create
              STATUS current
              DESCRIPTION
                 "Creation/Deletion of rows in the table."
              ::= {atmNteManagerEntry 7}

    atmNteManagerNextHop OBJECT-TYPE
              SYNTAX  IpAddress 
              MAX-ACCESS  read-create
              STATUS  current
              DESCRIPTION
                      "This parameter is relevant to Ethernet out of band 
                      host only (PVC=10).
                      The Next Hop IP address of the entry route."
              ::= { atmNteManagerEntry 8 }

    atmNteManagerVlanSupport OBJECT-TYPE
    		SYNTAX       INTEGER {
		    no		(2),
		    yes	    (3)
		    }
		    MAX-ACCESS  read-create
		    STATUS  current
		    DESCRIPTION
		    "VLAN support (Tagging).
		     no - No support to VLAN.
		     yes - 4 VLAN bytes will be added to the frame."
	    ::= { atmNteManagerEntry 9}

    atmNteManagerVlanIdentifier OBJECT-TYPE
 		  SYNTAX  Integer32 
 	      MAX-ACCESS  read-create
    	  STATUS  current
	      DESCRIPTION
    	  "VLAN ID. Range is 0..4095."
     	::= { atmNteManagerEntry 10 }
  
    atmNteManagerVlanFramePriority OBJECT-TYPE
	     SYNTAX  Integer32 
	     MAX-ACCESS  read-create
	     STATUS  current
	     DESCRIPTION
	     "VLAN Frame priority.Range is 0..7."
	     ::= { atmNteManagerEntry 11 }

    atmNteManagerAlarmTrapMask OBJECT-TYPE
       	 SYNTAX  OCTET STRING
         MAX-ACCESS  read-create
         STATUS current
         DESCRIPTION
         "The value of this object determines the alarm traps that the 
          agent should mask and not send to this NMS.
           
          The value is an Octet String, where each bit is assigned to a certain
          trap.
          If the bit = 1, the trap will be masked.
          If the bit = 0, the trap will not be masked.
          More details on the masked traps exist in the product specification.
		  
		  For products that do not mask specific traps, the value of the bits will be 0."
       	::= { atmNteManagerEntry 12 }

    atmNteManagerConfigPorts OBJECT-TYPE
	     SYNTAX  Integer32 
	     MAX-ACCESS  read-create
	     STATUS  current
	     DESCRIPTION
	     "This variable defines from which port/s this manager can configure the device.
		  For IPmux 11 the value of this variable will be according to the ports 
		  combination:
	      Network =1
	      User1=2
		  User2=4
		  (For Example: All ports = 7)."
	     ::= { atmNteManagerEntry 13 }



atmNteUPLTCR OBJECT-TYPE
              SYNTAX Integer32 
              MAX-ACCESS read-write
              STATUS current
              DESCRIPTION
                 "The Unacceptable ES Limit threshold for Performance Management."
              ::= {atmNteSysConfig 2}

atmNteDPLTCR OBJECT-TYPE
              SYNTAX Integer32 
              MAX-ACCESS read-write
              STATUS current
              DESCRIPTION
                 "The Degraded ES Limit threshold for Performance Management."
              ::= {atmNteSysConfig 3}

atmNteSysLogClearAll OBJECT-TYPE
              SYNTAX INTEGER { off(2), clear(3) }
              MAX-ACCESS read-write
              STATUS current
              DESCRIPTION
                 "Setting the variable to clear(3) removes all entries in the
	              Log Buffer of the agent. The agent will immediately reset 
	              the variable to off(2)."
              ::= {atmNteSysConfig 4}

atmNteUSESLTCR OBJECT-TYPE
              SYNTAX Integer32 
              MAX-ACCESS read-write
              STATUS current
              DESCRIPTION
	             "The Unacceptable SES Limit threshold for Performance Management."
              ::= {atmNteSysConfig 5}

atmNteDSESLTCR OBJECT-TYPE
              SYNTAX Integer32 
              MAX-ACCESS read-write
              STATUS current
              DESCRIPTION
                 "The Degraded ES Limit threshold for Performance Management."
              ::= {atmNteSysConfig 6}


atmNteProtection OBJECT IDENTIFIER  ::= { atmNteSysConfig  8 }

atmNteProtectionMode OBJECT-TYPE
               SYNTAX  INTEGER {
                          off       (1),
                          mspOn     (2),
						  pathOn    (3),
						  mspUniOn  (4),
						  mspOneToN (5)
                      }
               MAX-ACCESS  read-write
               STATUS  current
               DESCRIPTION
               "Protection  Mode.
               MspOn - Multiplex section protection. 
               pathOn - High order path protection.
               mspUniOn - Multiplex section Uni-directional protection.
               mspOneToN - Multiplex section protection."
               ::= { atmNteProtection 1 }

atmNteProtectionWorkingLink OBJECT-TYPE
               SYNTAX  INTEGER {
                          trunk1(2),
                          trunk2(3)
                      }
               MAX-ACCESS  read-write
               STATUS  current
               DESCRIPTION
               "Selects the working link when atmNteProtectionMode is off."
               ::= { atmNteProtection 2 }

atmNteProtectionSwitchLink OBJECT-TYPE
               SYNTAX  INTEGER {
                          off(1),
                          forceSwitch(2)
                      }
               MAX-ACCESS  read-write
               STATUS  current
               DESCRIPTION
               "ForceSwitch - will force Switching from the working link to the backup link. 
                Afterwards the agent will set atmNteProtectionSwitchLink back to off(1).
                atmNteProtectionMode must be either mspOn or pathOn."
               ::= { atmNteProtection 3 }

atmNteConfOam OBJECT IDENTIFIER  ::= { atmNteSysConfig  9 }

atmNteConfOamSupport OBJECT-TYPE
               SYNTAX  INTEGER {
                          intermediate(1),
                          segmentTermination(2),
                          endToEndTermination(3),
						  vpEndToEndVcSegment(4)
                      }
               MAX-ACCESS  read-write
               STATUS  current
               DESCRIPTION
               "OAM support  mode, which determines the device location
                in a segment wise."
               ::= { atmNteConfOam 1 }

atmNteConfOamTransmission OBJECT IDENTIFIER  ::= { atmNteConfOam  2 }

atmNteConfOamAIS OBJECT-TYPE
               SYNTAX  INTEGER {
                          none(1),
                          user(2),
                          network(3),
                          both(4)
                      }
               MAX-ACCESS  read-write
               STATUS  current
               DESCRIPTION
               "Defines if a F4 segment OAM cell is transmitted due 
                to problems in the other port, i.e. physical layer 
                alarm or F4 defect. This is valid only when the ACE101
                has ATM UNI interfaces in both sides and is configured
                for 'Non-Intrusive' mode.
                none - AIS is not sent to any of the ports.
                user - F4 AIS will be sent toward the user when defect 
                       is detected in the network port.
                network - F4 AIS will be sent toward the network when 
                          defect is detected in the user port.
                both - F4 AIS will be sent toward the network when defect
                       is detected in the user port and toward the user 
                       when defect is detected in the network port."
               ::= { atmNteConfOamTransmission 1 }

atmNteConfOamRDI OBJECT-TYPE
               SYNTAX  INTEGER {
                          none(1),
                          user(2),
                          network(3),
                          both(4)
                      }
               MAX-ACCESS  read-write
               STATUS  current
               DESCRIPTION
               "Defines if an F4 OAM RDI cell is transmitted due to
                physical layer problems in the port (in addition to 
                F4 RDI cells transmitted due to ATM layer problems).
                The type of F4 RDI (Segment or End-to-End) is according
                to the ACE-101 OAM mode.
                For example, If it is enabled for Network port, then 
                physical layer defect will initiate the transmission 
                of F4 RDI cell back to the trunk."
               ::= { atmNteConfOamTransmission 2 }

atmNteConfOamAddressing OBJECT IDENTIFIER  ::= { atmNteConfOam  3 }

atmNteConfLoopbackAddMode OBJECT-TYPE
             		SYNTAX INTEGER{
                          off(1),
                          on(2)
                      }
            	    MAX-ACCESS read-write
             		STATUS current
             		DESCRIPTION
                    	 "Loopback addressing mode.
                    	  on  - will enable  loopback addressing.
                    	  off - will disable loopback addressing."
             ::= { atmNteConfOamAddressing  1 }

atmNteConfLoopbackSourceAdd OBJECT-TYPE
             		SYNTAX OCTET STRING  (SIZE(2..20))
             		MAX-ACCESS read-write
             		STATUS current
             		DESCRIPTION
                    	 " Loopback source address. This field is relevant when 
                                atmNteConfOamAddMode is on."
             ::= { atmNteConfOamAddressing  2 }

--OAM Table
atmNteConfOamIfTable OBJECT-TYPE
              SYNTAX  SEQUENCE OF AtmNteConfOamIfEntry
              MAX-ACCESS  not-accessible
              STATUS  current
              DESCRIPTION
                      "OAM support per ATM interface."
               ::= { atmNteConfOam 4 }

atmNteConfOamIfEntry OBJECT-TYPE
              SYNTAX  AtmNteConfOamIfEntry
              MAX-ACCESS  not-accessible
              STATUS  current
              DESCRIPTION
                      "."
              INDEX   { ifIndex } 
              ::= { atmNteConfOamIfTable 1 }

AtmNteConfOamIfEntry ::=
            SEQUENCE {
                atmNteConfOamIfAisRdi   INTEGER
			    }

     atmNteConfOamIfAisRdi OBJECT-TYPE
                SYNTAX  INTEGER {
                           off(1),
                           on (2)
                }
                MAX-ACCESS  read-write
                STATUS  current
                DESCRIPTION
                "This parameter controls the generation of F4/F5 
                AIS and RDI due to lower order problems such as physical
                layer problems.
                 
                For AIS: Defines if F4/F5 AIS cell is transmitted due
                 to problems such as physical layer alarm or F4/F5 defect. 
                 This is applicable for all  ports .
                 off - Problems in this port  will not trigger F4/F5 AIS
                       transmition to the ajacent port (e.g. from USER to 
                       NETWORK) of a VPC/VCC.
                 on  - Problems in this port will trigger F4/F5 AIS 
                       transmition to the ajacent port (e.g. from USER 
                       to NETWORK) of a VPC/VCC.                 
                 
                For RDI: Defines if F4/F5 RDI cell will be transmitted due to
                 physical layer problems in that port (in addition to
                 F4/F5 RDI cells transmitted due to ATM layer problems).
                 For example, If it is enabled for Network port, then
                 physical layer defect will initiate the transmission
                 of F4/F5 RDI cell back to the trunk.

                 The type of F4/F5 (Segment or End-to-End) is according
                 to the configuration of the VPC/VCC."
                 ::= { atmNteConfOamIfEntry 1 }


atmNteConfCAC OBJECT IDENTIFIER  ::= { atmNteSysConfig  10 }

atmNteConfCACMode OBJECT-TYPE
               SYNTAX  INTEGER {
 		disable(1),
		enable(2)
                }
               MAX-ACCESS  read-write
               STATUS  current
               DESCRIPTION
               "CAC support  mode. 

               For ACE2002, the following are the applicable values:
               disable(1), enable(2), 10 - 1000."
               ::= { atmNteConfCAC 1 }

atmNteHostIfTable OBJECT-TYPE
              SYNTAX  SEQUENCE OF AtmNteHostIfEntry
              MAX-ACCESS  not-accessible
              STATUS  current
              DESCRIPTION
                      "Host IP interface table."
              ::= { atmNteSysConfig 11 }

atmNteHostIfEntry OBJECT-TYPE
              SYNTAX  AtmNteHostIfEntry
              MAX-ACCESS  not-accessible
              STATUS  current
              DESCRIPTION
                      "."
              INDEX   { atmNteHostPvcIndex } 
              ::= { atmNteHostIfTable 1 }

AtmNteHostIfEntry ::=
            SEQUENCE {
              atmNteHostPvcIndex
                    Integer32,
              atmNteHostIP
                    IpAddress,
              atmNteHostMask
                    IpAddress,
              atmNteHostAtmIfIndex
                    Integer32,
              atmNteHostVpi
                    Integer32,
              atmNteHostVci
                    Integer32,
              atmNteHostRowStatus
                    RowStatus,	
              atmNteHostRdnVpi
                    Integer32,
              atmNteHostRdnVci
                    Integer32,
			  atmNteHostDefaultNextHop
                    IpAddress,
			  atmNteHostVlanTagging
                    INTEGER,
			  atmNteHostDefaultVlanID
			  		Integer32,
			  atmNteHostDefaultVlanPriority
			  		Integer32
              }


atmNteHostPvcIndex OBJECT-TYPE
              SYNTAX  Integer32 
              MAX-ACCESS  read-only
              STATUS  current
              DESCRIPTION
                      "A PVC index. The range is 1..10."
              ::= { atmNteHostIfEntry 1 }

atmNteHostIP OBJECT-TYPE
              SYNTAX  IpAddress 
              MAX-ACCESS  read-create
              STATUS  current
              DESCRIPTION
                      "The host interface IP address."
              ::= { atmNteHostIfEntry 2 }

atmNteHostMask OBJECT-TYPE
              SYNTAX  IpAddress 
              MAX-ACCESS  read-create
              STATUS  current
              DESCRIPTION
                      "The host interface subnet mask."
              ::= { atmNteHostIfEntry 3 }

atmNteHostAtmIfIndex OBJECT-TYPE
              SYNTAX  Integer32 
              MAX-ACCESS  read-create
              STATUS  current
              DESCRIPTION
                      "ATM interface index. Will be 1 
                       for user port, and 2 for network port."
              ::= { atmNteHostIfEntry 4 }

atmNteHostVpi OBJECT-TYPE
              SYNTAX  Integer32 
              MAX-ACCESS  read-create
              STATUS  current
              DESCRIPTION
                      "VPI of the PVC connected to that host interface."
              ::= { atmNteHostIfEntry 5 }

atmNteHostVci OBJECT-TYPE
              SYNTAX  Integer32 
              MAX-ACCESS  read-create
              STATUS  current
              DESCRIPTION
                      "VCI of the PVC connected to that host interface."
              ::= { atmNteHostIfEntry 6 }

atmNteHostRowStatus OBJECT-TYPE
              SYNTAX  RowStatus 
              MAX-ACCESS  read-create
              STATUS  current
              DESCRIPTION
                 "Creation/Deletion of rows in the table."
              ::= { atmNteHostIfEntry 7 }

atmNteHostRdnVpi OBJECT-TYPE
              SYNTAX  Integer32 
              MAX-ACCESS  read-create
              STATUS  current
              DESCRIPTION
                      "The VPI of the redundant management VCL.
                      This parameter is applicable only if atmNteRdnManagement=enable(3). "
              ::= { atmNteHostIfEntry 8 }

atmNteHostRdnVci OBJECT-TYPE
              SYNTAX  Integer32 
              MAX-ACCESS  read-create
              STATUS  current
              DESCRIPTION
                      "The VCI of the redundant management VCL.
                      This parameter is applicable only if atmNteRdnManagement=enable(3). "
              ::= { atmNteHostIfEntry 9 }

atmNteHostDefaultNextHop OBJECT-TYPE
              SYNTAX  IpAddress 
              MAX-ACCESS  read-create
              STATUS  current
              DESCRIPTION
                      "The host interface Default Next Hop address.
                       This address will be used as default next hop for 
                       every Bundle mapped to this Host."
              ::= { atmNteHostIfEntry 10 }

atmNteHostVlanTagging OBJECT-TYPE
              SYNTAX  INTEGER {
 			       		no		(2),
			       		yes		(3)
			       		}
 
              MAX-ACCESS  read-create
              STATUS  current
              DESCRIPTION
                      "VLAN Tag support.
       				   no - No support to VLAN.
       				   yes - 4 VLAN bytes will be added 
       				   to each frame connected to this Host."
              ::= { atmNteHostIfEntry 11 }

atmNteHostDefaultVlanID OBJECT-TYPE
       SYNTAX  Integer32 
       MAX-ACCESS  read-create
       STATUS  current
       DESCRIPTION
       "Default VLAN ID of this Host."
       ::= { atmNteHostIfEntry 12 }
  
atmNteHostDefaultVlanPriority OBJECT-TYPE
       SYNTAX  Integer32 
       MAX-ACCESS  read-create
       STATUS  current
       DESCRIPTION
       "Default VLAN priority for this Host."
       ::= { atmNteHostIfEntry 13 }


atmNteShaperMode OBJECT-TYPE
               SYNTAX  INTEGER {
 		         normal		(1),
		         group		(2),
		         aggregate	(3),
				 vpInbandMng (4)
                }
               MAX-ACCESS  read-write
               STATUS  current
               DESCRIPTION
               "Shaper Mode.
               vpInbandMng - Vcc within a Vp for management."
               ::= { atmNteSysConfig 12 }


atmNteOutputRate OBJECT-TYPE
               SYNTAX  Integer32
               MAX-ACCESS  read-write
               STATUS  current
               DESCRIPTION
               "Aggregate shaping output rate in Cells per Seconds units.
               Default value is the Network port rate."
               ::= { atmNteSysConfig 13 }

atmNteTosMode OBJECT-TYPE
               SYNTAX  INTEGER {
 		         notApplicable   (1),
		         disable		 (2),
		         enable	         (3)
                }
               MAX-ACCESS  read-write
               STATUS  current
               DESCRIPTION
               "TOS Mode."
               ::= { atmNteSysConfig 14 }

atmNteTosMask OBJECT-TYPE
               SYNTAX  OCTET STRING	(SIZE(1))
               MAX-ACCESS  read-write
               STATUS  current
               DESCRIPTION
               "This parameter determines the seqence of bits that will be used for TOS.
               For ACE101 this parameter is applicable only if atmNteTosMode = enable.
               Valid only for IP-TOS process."
               ::= { atmNteSysConfig 15 }

atmNteTosHighPriority OBJECT-TYPE
               SYNTAX  OCTET STRING (SIZE(8))
               MAX-ACCESS  read-write
               STATUS  current
               DESCRIPTION
               "Priorities options are High or Low.
			   High priority will be represented by bit = 1.
			   Low  priority will be represented by bit = 0.
			   Each TOS value will be represented by the bit location.
			   For example, the string for TOS 2, 9, 15 with High priority,
			   will be:
			   
			   |0000 0000|... ...|0000 0000|1000 0010|0000 0100| 
												...98 7654 3210	  (Bit  #)
																  
					8	   ...		  3			2		  1		  (Byte #)."
               ::= { atmNteSysConfig 16 }

atmNtePlugAndPlayActivity OBJECT-TYPE
               SYNTAX  INTEGER {
 		         disable   (1),
		         offline   (2),
		         online	   (3)
                }
               MAX-ACCESS  read-write
               STATUS  current
               DESCRIPTION
               "Activity control for Manager Plug And Play.
               disable - disable the feature.
               offline - Automatic learn IP address into offline memory.
               online  - Automatic learn IP address into online memory. "
               ::= { atmNteSysConfig 17 }

atmNteSlotUsage OBJECT-TYPE
               SYNTAX  INTEGER {
 		         notApplicable   (1),
		         user		     (2),
		         network	     (3)
                }
               MAX-ACCESS  read-write
               STATUS  current
               DESCRIPTION
               "Applicable to ace2002. Slot 2 might be configured
               as user slot or as network slot."
               ::= { atmNteSysConfig 18 }

atmNteConnectionsMaxNumber OBJECT-TYPE
               SYNTAX  INTEGER {
                       notApplicable(1),
                       max1024      (2),
                       max2048      (3)
               }
              MAX-ACCESS  read-write
              STATUS  current
              DESCRIPTION
                      "The MAX number of connections supported by system.
                       Setting this parameter will affect the number of MAX intervals supported.
                       This parameter will affect the system only after reset.
					   Changing this parameter from high value to a low value, will be accepted by agent
					   only if the actual used connection <= the desired connection Max number.
                       Applicable to ace2002. "
              ::= { atmNteSysConfig 19 }

atmNteDefaultVpi OBJECT-TYPE
               SYNTAX  Integer32
               MAX-ACCESS  read-write
               STATUS  current
               DESCRIPTION
                       "Default Vpi for management."
              ::= { atmNteSysConfig 20 }

atmNteDefaultVci OBJECT-TYPE
               SYNTAX  Integer32 
               MAX-ACCESS  read-write
               STATUS  current
               DESCRIPTION
               "Default Vci for management."
               ::= { atmNteSysConfig 21 }

atmNteReservedVpi    OBJECT-TYPE
              SYNTAX    Integer32  (0..255)
              MAX-ACCESS    read-write
              STATUS    current
              DESCRIPTION
                   "Internal use VPI, where shaperMode=vpInbandMng."
              ::= { atmNteSysConfig 22 }

atmNteRdnManagement OBJECT-TYPE
                SYNTAX  INTEGER {
                      disabled (2),
                      enabled  (3)
                 }
                MAX-ACCESS  read-only
                STATUS  current
                DESCRIPTION
                "The redundancy management status."
              ::= { atmNteSysConfig 23 }

atmNtePlugAndPlayIfIndex OBJECT-TYPE
                SYNTAX  InterfaceIndex
                MAX-ACCESS  read-write
                STATUS  current
                DESCRIPTION
                "The ifIndex of the Plug and Play VCC."
              ::= { atmNteSysConfig 24 }

atmNteLoopbackTimeout OBJECT-TYPE
                SYNTAX  Integer32
                MAX-ACCESS  read-write
                STATUS  current
                DESCRIPTION
                "The Loopback state timeout in minutes. A value of 
                zero means no timeout (for ever). Default is 5 min."
              ::= { atmNteSysConfig 25 }

atmNteOamTable OBJECT-TYPE
    SYNTAX  SEQUENCE OF AtmNteOamEntry
    MAX-ACCESS  not-accessible
    STATUS  current
    DESCRIPTION
    "This table is a static table, which is created by agent once
	upon initialization. The created entries are actually, only the
	supported OAM features. 
	This table enables addition of new features by adding new entries
	rather than adding scalar parameters.
    An OAM feature is defined by the indexes values combination."
              ::= { atmNteSysConfig 26 }

atmNteOamEntry OBJECT-TYPE
    SYNTAX  AtmNteOamEntry
    MAX-ACCESS  not-accessible
    STATUS  current
    DESCRIPTION
    "An entry in the OAM table.
     Each entry in this table will indicate a special OAM." 
    INDEX {atmNteOamMode, atmNteOamCellType, atmNteOamLevel}
    ::= { atmNteOamTable 1 }

AtmNteOamEntry ::=
    SEQUENCE {
    atmNteOamMode
    INTEGER,
    atmNteOamCellType
    INTEGER,
	atmNteOamLevel
	INTEGER,
	atmNteOamEnable
	INTEGER
    }

atmNteOamMode OBJECT-TYPE
    SYNTAX  INTEGER
    {
     endToEnd  (1)
    }
    MAX-ACCESS  read-only
    STATUS  current
    DESCRIPTION
    "The OAM cell path.
    endToEnd(1) - the entire path."
    ::= { atmNteOamEntry 1 }

atmNteOamCellType OBJECT-TYPE
    SYNTAX  INTEGER
    {
     aisAndRdi (1),
	 loopback  (2)
    }
    MAX-ACCESS  read-only
    STATUS  current
    DESCRIPTION
    "This object indicates a unique Indication Signal.
     aisAndRdi(1) - Alarm Indication Signal (AIS) and 
                     Remote Defect Indication (RDI) cell.
     loopback(2) - Loopback cell."
    ::= { atmNteOamEntry 2 }

atmNteOamLevel OBJECT-TYPE
    SYNTAX  INTEGER
    {
--	 f4 (2),
	 f5 (3)
    }
    MAX-ACCESS  read-only
    STATUS  current
    DESCRIPTION
    "The level of the OAM cell.
--    	 f4 (2) - VP level,
	     f5 (3)	- VC level."
    ::= { atmNteOamEntry 3 }

atmNteOamEnable OBJECT-TYPE
    SYNTAX  INTEGER
    {
     disable      (2),
	 enable       (3)
    }
    MAX-ACCESS  read-write
    STATUS  current
    DESCRIPTION
    "This parameter determines if the specified OAM cells 
    will be enabled."
    ::= { atmNteOamEntry 4 }


atmNteDefaultLoopbackThreshold OBJECT-TYPE
                SYNTAX  Integer32
                MAX-ACCESS  read-write
                STATUS  current
                DESCRIPTION
                "The Default OAM Loopback Failure Threshold value 
                that will be used for configuration."
              ::= { atmNteSysConfig 27 }

atmNteMaxBurstSize OBJECT-TYPE
                SYNTAX  Integer32
                MAX-ACCESS  read-write
                STATUS  current
                DESCRIPTION
                "The Maximum allowed burst size (cell units).
                This object is applicable for each Physical port."
              ::= { atmNteSysConfig 28 }

atmNteGranularityFactor OBJECT-TYPE
                SYNTAX  Integer32
                MAX-ACCESS  read-write
                STATUS  current
                DESCRIPTION
                "This parameter affects the granularity of the guaranteed 
                Rate (SCR+MCR) in spaced connection (cell/sec units). 
                It is also defines the minimum guaranteed rate in spaced 
                connection."
              ::= { atmNteSysConfig 29 }


atmNteTotalInputRate OBJECT-TYPE
                SYNTAX  Integer32
                MAX-ACCESS  read-only
                STATUS  current
                DESCRIPTION
                "This parameter indicates the total input rate of the 
                device in cells/sec."
              ::= { atmNteSysConfig 30 }

atmNteTotalOutputRate OBJECT-TYPE
                SYNTAX  Integer32
                MAX-ACCESS  read-only
                STATUS  current
                DESCRIPTION
                "This parameter indicates the total output rate of the 
                device in cells/sec."
              ::= { atmNteSysConfig 31 }

atmAlarmForwardingTable OBJECT-TYPE
              SYNTAX  SEQUENCE OF AtmAlarmForwardingEntry
              MAX-ACCESS  not-accessible
              STATUS  current
              DESCRIPTION
                      "The Alarm Forwarding Mechanism will be operated 
                      for this table entries."
              ::= { atmNteSysConfig 32 }

          atmAlarmForwardingEntry OBJECT-TYPE
              SYNTAX  AtmAlarmForwardingEntry
              MAX-ACCESS  not-accessible
              STATUS  current
              DESCRIPTION
                      "Each entry in this table is a pair of ports that
                      the Alarm Forwarding Mechanism is determined for."
              INDEX   { atmAlarmForwardingFailPort, atmAlarmForwardingToPort }
              ::= { atmAlarmForwardingTable 1 }

          AtmAlarmForwardingEntry ::=
              SEQUENCE {
	              atmAlarmForwardingFailPort
	                  Integer32,
                  atmAlarmForwardingToPort
                      Integer32,
                  atmAlarmForwardingRowStatus
                      RowStatus,
                  atmAlarmForwardingFailureLevel
                      BITS, 
                  atmAlarmForwardingRecoveryMode
                      INTEGER, 
                  atmAlarmForwardingRecoveryCommand
                      INTEGER,
                  atmAlarmForwardingTimeFilterWindow
                  	  Unsigned32 
              }

          atmAlarmForwardingFailPort OBJECT-TYPE
              SYNTAX  Integer32 
              MAX-ACCESS  not-accessible
              STATUS  current
              DESCRIPTION
                      "An Index of the port on which a fail occurs."
              ::= { atmAlarmForwardingEntry 1 }

          atmAlarmForwardingToPort OBJECT-TYPE
              SYNTAX  Integer32 
              MAX-ACCESS  not-accessible
              STATUS  current
              DESCRIPTION
                      "An Index of the port that will be affected 
                      upon the failure of the atmAlarmForwardingFailPort."
              ::= { atmAlarmForwardingEntry 2 }

          atmAlarmForwardingRowStatus OBJECT-TYPE
              SYNTAX  RowStatus 
              MAX-ACCESS  read-create
              STATUS  current
              DESCRIPTION
                      "Creation/Deletion of rows in the table."
              ::= { atmAlarmForwardingEntry 3 }

          atmAlarmForwardingFailureLevel OBJECT-TYPE
              SYNTAX  BITS{
			  physical (0),
			  atm      (1)
              } 
              MAX-ACCESS  read-create
              STATUS  current
              DESCRIPTION
                      "This parameter determines the level of failure 
                      that will operate the Alarm Forwarding Mechanism."
              ::= { atmAlarmForwardingEntry 4 }

          atmAlarmForwardingRecoveryMode OBJECT-TYPE
              SYNTAX  INTEGER {
			  manual     (1),
			  automatic  (2)
              } 
              MAX-ACCESS  read-create
              STATUS  current
              DESCRIPTION
                      "This parameter determines the Recovery Mode. 
                      manual - The user should stop the RDI transmission 
                               by using the atmAlarmForwardingRecoveryCommand.
                      automatic - The RDI transmission will be automatically 
                                  stopped upon atmAlarmForwardingFailPort
                                  recovery."
              ::= { atmAlarmForwardingEntry 5 }

          atmAlarmForwardingRecoveryCommand OBJECT-TYPE
              SYNTAX  INTEGER {
			  off   (2),
			  on    (3)
              } 
              MAX-ACCESS  read-create
              STATUS  current
              DESCRIPTION
                      "This parameter is a command. It is applicable when 
                      atmAlarmForwardingRecoveryMode = manual.
                      
                      on - Will stop the RDI transmission. After setting to 'On'
                           the agent will set this parameter back to 'Off'."
              ::= { atmAlarmForwardingEntry 6 }

          atmAlarmForwardingTimeFilterWindow OBJECT-TYPE
              SYNTAX  Unsigned32 
              MAX-ACCESS  read-create
              STATUS  current
              DESCRIPTION
                      "This parameter determines the Time Filter Window, meaning:
                       how much time (in seconds) should the alarm exist
                       in order to start the Alarm Forwarding operation."
              ::= { atmAlarmForwardingEntry 7 }


atmSysConfigCellTest OBJECT IDENTIFIER  ::= { atmNteSysConfig 33 }

          atmSysConfigCellTestPort OBJECT-TYPE
              SYNTAX  InterfaceIndex 
              MAX-ACCESS  read-write
              STATUS  current
              DESCRIPTION
                      "An Index of the port on which the cell test
                      will be sent."
              ::= { atmSysConfigCellTest 1 }

          atmSysConfigCellTestVpi OBJECT-TYPE
              SYNTAX  Integer32 
              MAX-ACCESS  read-write
              STATUS  current
              DESCRIPTION
                      "The VPI on which the cell test will be sent."
              ::= { atmSysConfigCellTest 2 }

          atmSysConfigCellTestVci OBJECT-TYPE
              SYNTAX  Integer32 
              MAX-ACCESS  read-write
              STATUS  current
              DESCRIPTION
                      "The VCI on which the cell test will be sent."
              ::= { atmSysConfigCellTest 3 }
 
          atmSysConfigCellTestPti OBJECT-TYPE
              SYNTAX  INTEGER {
		              user	(1), 
		              oamSegment		(2),
		              oamEndToEnd		(3)
					  }
              MAX-ACCESS  read-write
              STATUS  current
              DESCRIPTION
                      "The cell type."
              ::= { atmSysConfigCellTest 4 }

          atmSysConfigCellTestClp OBJECT-TYPE
              SYNTAX  INTEGER {
		              clp0	(1), 
		              clp1	(2)
					  }
              MAX-ACCESS  read-write
              STATUS  current
              DESCRIPTION
                      "The type of the Cell."
              ::= { atmSysConfigCellTest 5 }

          atmSysConfigCellTestOamType OBJECT-TYPE
              SYNTAX  INTEGER {
		              ais	(1), 
		              rdi	(2),
		              cc	(3),
					  lb    (4)
					  }
              MAX-ACCESS  read-write
              STATUS  current
              DESCRIPTION
                      "The OAM type of the Cell. This object is applicable 
                      if atmSysConfigCellTestPti = oamSegment/oamEndToEnd ."
              ::= { atmSysConfigCellTest 6 }

          atmSysConfigCellTestPayload OBJECT-TYPE
              SYNTAX  OCTET STRING (SIZE(1)) 
              MAX-ACCESS  read-write
              STATUS  current
              DESCRIPTION
                      "The payload of the cell. For OAM cell the payload
                      is set automatically to 6A."
              ::= { atmSysConfigCellTest 7 }
 
          atmSysConfigCellTestQuantity OBJECT-TYPE
              SYNTAX  Integer32 (1..10000) 
              MAX-ACCESS  read-write
              STATUS  current
              DESCRIPTION
                      "Quantity of cells to send."
              ::= { atmSysConfigCellTest 8 }

          atmSysConfigCellTestSendCmd OBJECT-TYPE
              SYNTAX  INTEGER {
		              off	(2), 
		              send	(3)
					  }
              MAX-ACCESS  read-write
              STATUS  current
              DESCRIPTION
                      "Setting the variable to send(3) perfroms cell test.
                       The agent will immediately reset the variable to off(2)."
              ::= { atmSysConfigCellTest 9 }



--  The ATM VP Cross Connect Extension Table

atmVpCrossConnectExtenTable OBJECT-TYPE
	SYNTAX         SEQUENCE OF AtmVpCrossConnectExtenEntry
	MAX-ACCESS     not-accessible
	STATUS         current
	DESCRIPTION
		"An extension to the ATM VP Cross Connect table
		 (RFC2515 - atmVpCrossConnectTable)."
	::= { atmNteSysConfig 34 }

atmVpCrossConnectExtenEntry OBJECT-TYPE
	SYNTAX         AtmVpCrossConnectExtenEntry
	MAX-ACCESS     not-accessible
	STATUS         current
	DESCRIPTION
		"An entry in the table."
	AUGMENTS    { atmVpCrossConnectEntry }  
	::= { atmVpCrossConnectExtenTable 1 }

AtmVpCrossConnectExtenEntry ::= SEQUENCE {
	atmVpCrossConnectName          SnmpAdminString
	}

atmVpCrossConnectName OBJECT-TYPE
	SYNTAX         SnmpAdminString (SIZE (1..64))
	MAX-ACCESS     read-create
	STATUS         current
	DESCRIPTION
		"The Connection's name."
	::= { atmVpCrossConnectExtenEntry 1 }

  
--  The ATM VC Cross Connect Extension Table

atmVcCrossConnectExtenTable OBJECT-TYPE
	SYNTAX         SEQUENCE OF AtmVcCrossConnectExtenEntry
	MAX-ACCESS     not-accessible
	STATUS         current
	DESCRIPTION
		"An extension to the ATM VC Cross Connect table
		 (RFC2515 - atmVcCrossConnectTable)."
	::= { atmNteSysConfig 35 }

atmVcCrossConnectExtenEntry OBJECT-TYPE
	SYNTAX         AtmVcCrossConnectExtenEntry
	MAX-ACCESS     not-accessible
	STATUS         current
	DESCRIPTION
		"An entry in the table."
	AUGMENTS    { atmVcCrossConnectEntry }  
	::= { atmVcCrossConnectExtenTable 1 }

AtmVcCrossConnectExtenEntry ::= SEQUENCE {
	atmVcCrossConnectName          SnmpAdminString
	}

atmVcCrossConnectName OBJECT-TYPE
	SYNTAX         SnmpAdminString (SIZE (1..64))
	MAX-ACCESS     read-create
	STATUS         current
	DESCRIPTION
		"The Connection's name."
	::= { atmVcCrossConnectExtenEntry 1 }


--  Reserved for atmCongestionThresholdTable ::= { atmNteSysConfig 36 }


atmNteQosMode OBJECT-TYPE
    SYNTAX  INTEGER {
		disable		(1),
		multipleVc	(2),
		singleVc	(3)		 
            }
    MAX-ACCESS  read-write
    STATUS  current
    DESCRIPTION
	"This variable defines the QoS Mode.
	 disable(1)		- QoS is disabled.
	 multipleVc(2)	- QoS is enabled and
	 				  multiple VCs can be bound per bridge port.
	 singleVc(3)	- QoS is enabled and
	 				  only single VC can be bound per bridge port."
   ::= { atmNteSysConfig 37 }


atmTrafficDescrParamXTable OBJECT-TYPE
	SYNTAX  	SEQUENCE OF AtmTrafficDescrParamXEntry
    MAX-ACCESS  not-accessible
    STATUS  	current
    DESCRIPTION
		"An Augment to ATM Traffic Descriptor Parameter Table
		 (atmTrafficDescrParamTable in ATM-MIB; RFC-2515)."
     ::= { atmNteSysConfig 38 }

atmTrafficDescrParamXEntry OBJECT-TYPE
	SYNTAX  	AtmTrafficDescrParamXEntry
    MAX-ACCESS	not-accessible
    STATUS  	current
    DESCRIPTION
       "An entry in the table."
    AUGMENTS { atmTrafficDescrParamEntry }
     ::= { atmTrafficDescrParamXTable 1 }

AtmTrafficDescrParamXEntry ::=
    SEQUENCE {
		atmTrafficDescrParamMode		INTEGER
		}

atmTrafficDescrParamMode OBJECT-TYPE
	SYNTAX		INTEGER {
		scheduling				(1),
		schedulingAndShaping	(2),
		policing				(3)
	}
	MAX-ACCESS  read-create
	STATUS  	current
	DESCRIPTION
		"The Mode of the Traffic Descriptor."
	::= { atmTrafficDescrParamXEntry 1 }

      
atmNteSysInfo  OBJECT IDENTIFIER  ::=  {atmNteSys 2}

          atmNteIdTable OBJECT-TYPE
              SYNTAX  SEQUENCE OF AtmNteIdEntry
              MAX-ACCESS  not-accessible
              STATUS  current
              DESCRIPTION
                      "The IDs of the cards and of the system."
              ::= { atmNteSysInfo 1 }

          atmNteIdEntry OBJECT-TYPE
              SYNTAX  AtmNteIdEntry
              MAX-ACCESS  not-accessible
              STATUS  current
              DESCRIPTION
                      "."
              INDEX   { atmNteIdIndex}
              ::= { atmNteIdTable 1 }

          AtmNteIdEntry ::=
              SEQUENCE {
	              atmNteIdIndex
	                  Integer32,
                  atmNteUnitId
                      Integer32,
                  atmNteUnitVersion
                      DisplayString,
                  atmNteCardType
                      INTEGER, 
                  atmNteCardStatus
                      INTEGER, 
                  atmNteCardCmd
                      INTEGER,
                  atmNteProgCardType
                      INTEGER 
              }

          atmNteIdIndex OBJECT-TYPE
              SYNTAX  Integer32 
              MAX-ACCESS  read-only
              STATUS  current
              DESCRIPTION
                      "An Index of the Unit ID table.
                       The following units have IDs in this table:
                       1 - System
                       2 - ATM Board
                       3 - User Card
                       4 - Trunk 1 card
                       5 - Trunk 2 card
	                   6 - Shaper
                       7 - Clock Unit
                       8 -  Slot 1 card
                       9 -  Slot 2 card
                       10 - Slot 3 card
                       11 - Slot 4 card
                       12 - Fan1
                       13 - Fan2
                       14 - Control Unit."
              ::= { atmNteIdEntry 1 }

          atmNteUnitId OBJECT-TYPE
              SYNTAX  Integer32 
              MAX-ACCESS  read-only
              STATUS  current
              DESCRIPTION
                      "The ID of the Unit. 
                      For index = 6, the id will describe the validity
                       of a shaper in the system: 0 - Shaper Not exist
                                                  1 - Shaper exist.
                      For index = 7, the id will describe the validity
                       of a clock in the system: 0 - Clock Not exist
                                                  1 - Clock exist.
												  2- Clock exist but failed.
                      For index = 12,13 the id will describe the functionality
                       of a FAN1 : 0 - OK
                                  1 - Failed."
              ::= { atmNteIdEntry 2 }

         atmNteUnitVersion OBJECT-TYPE
              SYNTAX DisplayString 
              MAX-ACCESS  read-only
              STATUS  current
              DESCRIPTION
                      "Hardware and Software version
                       of the module."
              ::= { atmNteIdEntry 3 }

       atmNteCardType OBJECT-TYPE
              SYNTAX  INTEGER {
		notApplicable	(1), 
		sc13mR155		(2),
		st13sR155		(3),
		st13lR155		(4),
		utpR155			(5),
		cxBncR155		(6),
		e3				(7),
		t3				(8),
		e1				(9),
		e1Ltu			(10),
		fc13lR155		(11),
		fc13lhR155		(12),
		fc15lhR155		(13),
		fc13lE3		    (14),
		fc13lhE3		(15),
		fc15lhE3		(16),
		fc13lT3		    (17),
		fc13lhT3		(18),
		fc15lhT3		(19),
		t1				(20),
		eth				(21),
		ethE1CesBnc	    (22),
		ethE1CesRj45    (23),
		ethT1CesRj45	(24),
		e1CesRj45		(25),
		e1CesBnc		(26),
		t1CesRj45		(27),
		e14Ces			(28),
 		e14CesRj45  	(29),
		t14CesRj45  	(30),

		hdlc4port		(31),
		hdlcE14CesBnc   (32),
		hdlcE14CesRj45  (33),
		hdlcT14CesRj45  (34),
		e1Rj45	  		(35),
		e1Bnc			(36),

		ethE14CesBnc	(37),
		ethE14CesRj45   (38),
		ethT14CesRj45   (39),

		hdlc1portHssi	   (40),
		hdlcHssiE14CesBnc  (41),
		hdlcHssiE14CesRj45 (42),
		hdlcHssiT14CesRj45 (43),

		e14ImaRj45	    (44),
		e14ImaBnc		(45),
		t14ImaRj45	    (46),

		ethE3CesBnc     (47),
		ethT3CesBnc	    (48),

		smSf1R155		(49),
		smSf2R155		(50),

        sc13sR155		(51),
        sc13lR155		(52),

		utp25			(53),

        sc13lhR155		(54),
        sc15lhR155		(55),

        sc13ljR155		(56),
        sc13lhjR155  	(57),
        sc15lhjR155  	(58),

		e18Ces 	        (59),
		e18CesRj45      (60),
		t18CesRj45      (61),

        sc13mR622       (62),
--        st13sR622       (63),
--        st13lR622       (64),
--        utpR622         (65),
--        cxBncR622       (66),
--        fc13lR622       (67),
--        fc13lhR622      (68),
--        fc15lhR622      (69),
--        smSf1R622       (70),
--        smSf2R622       (71),
--        sc13sR622       (72),
        sc13lR622       (73),
        sc13lhR622      (74),
        sc15lhR622      (75),
        
        fr4Port         (76),
		t3j				(77),
        fr1Port         (78),
        hdlc1Port       (79),

		sc13mR155D		(80),
        sc13lR155D		(81),
		fc13lR155D		(82),
		st13lR155D		(83),
        sc13lhR155D  	(84),
		fc13lhR155D		(85),
		st13lhR155D		(86),

		e18ImaBnc		(87),
		e18ImaRj45	    (88),
		t18ImaRj45	    (89),

		lanUtpE		    (90),
		lanLc13lE	    (91),
		lanLc13mE	    (92),

		e14ImaRj45CfgMode  (93),
		e14ImaBncCfgMode   (94),
		t14ImaRj45CfgMode  (95),

		sc13mR155R		(96),  --Dual for Redundancy
        sc13lR155R		(97),  --Dual for Redundancy
		fc13lR155R		(98),  --Dual for Redundancy
		st13lR155R		(99),  --Dual for Redundancy
        sc13lhR155R  	(100), --Dual for Redundancy
		fc13lhR155R		(101), --Dual for Redundancy
		st13lhR155R		(102), --Dual for Redundancy

		fEthUtpD		(103),
		fEthSmD	        (104),
		fEthMmD	        (105),

 		e14CesRj45Unbal (106),

		sc13mR155n		(107),
		sc13lR155n		(108),
		sc13lhR155n		(109),
		sc15lhR155n		(110),
		fc13lR155n		(111),
		fc13lhR155n		(112),
		fc15lhR155n		(113),
		st13lR155n		(114),

		lanUtp		    (115),
		lanLc13l	    (116),
		lanLc13m	    (117),

		e1FrHdlc		(118),
		e1FrHdlcUnbal	(119),
		t1FrHdlc	    (120),

	    channelizedT3   (121),	--for IP-MUX16

		fc15lhR155D		(122), --Dual STM-1
        sc15lhR155D		(123), --Dual STM-1
		smSf1R155D		(124), --Dual STM-1
		smSf2R155D		(125), --Dual STM-1
		smSf3R155D		(126), --Dual STM-1

		fc15lhR155R		(127), --Dual for Redundancy
		sc15lhR155R		(128), --Dual for Redundancy
        smSf1R155R  	(129), --Dual for Redundancy
		smSf2R155R		(130), --Dual for Redundancy
		smSf3R155R		(131), --Dual for Redundancy

		st13lhR155n		(132), --New STM-1
		smSf1R155n		(133), --New STM-1
		smSf2R155n		(134), --New STM-1
		smSf3R155n		(135), --New STM-1

		t18CesNg		(136), 
		e18CesUnbalNg	(137), 
		e18CesBalNg	    (138), 
		t14CesNg		(139), 
		e14CesUnbalNg	(140), 
		e14CesBalNg	    (141), 

		t18ImaUniNg		(142), 
		e18ImaUniUnbalNg(143), 
		e18ImaUniBalNg  (144), 
		t14ImaUniNg		(145), 
		e14ImaUniUnbalNg(146), 
		e14ImaUniBalNg  (147), 

        t1Ces           (148),
		e1CesUnbal      (149),
		e1CesBal        (150),

		switchedLan		(151), --LAN card with ETH switch (usually 4 ports)
		channelizedSts1  (152),	--Channelized STS1 card (for IP-MUX16)
		
		st13mR155		(153),
		st13lhR155		(154),
		st15lhR155		(155),

		gigabitEthUtp	(156),
		gigabitEthSfp	(157),
		fastEthUtp		(158),
		
		fourStm1oc3SingleGbe	(159),
		
		adsl2Plus1p		(160), -- ADSL2+ 1 port
		shdsl			(161),
		gigabitEthCombo	(162),
		adsl2Plus2p		(163), -- ADSL2+ 2 ports

		main8Atm155TwoEth		(249),
		mainChannelized155		(250),
		main			(251),
		control			(252),
		fan				(253),
		unknown			(254),
		empty			(255)

		-- values 1000 and up are reserved
		-- (used by atmNteProgCardType)
	}

              MAX-ACCESS  read-only
              STATUS current 
              DESCRIPTION
                      "The card type."
              ::= { atmNteIdEntry 4 }

         atmNteCardStatus OBJECT-TYPE
              SYNTAX  INTEGER {
                notApplicable       (1),
                notActive           (2),
				active				(3),
				inProgress		    (4),
				empty               (5)
	          }
              MAX-ACCESS  read-only
              STATUS  current
              DESCRIPTION
                      "Status of the card in the selected slot.
                       
                       notActive   -  Connections are in NotReady state. No configuration is 
                                      available for the card. The access to the card HW is blocked.
                                      This state is relevant for an extracted card,	and for a case 
                                      in which the card was deactivated.
				       active	   -  The module installed and functions. A card that in this state 
				                      can be configured.
				       inProgress  -  The status during proccessing of a command from atmNteCardCmd.
				       empty       -  No information is valid for the selected slot. This status is 
				                      relevant to a case in which the card configaration was deleted,
				                      or in case in which a slot was empty since the device startup."
              ::= { atmNteIdEntry 5 }

         atmNteCardCmd OBJECT-TYPE
              SYNTAX  INTEGER {
                notApplicable   (1),
                deleteConfig    (2),
				deactivate      (3),
				activate        (4)
	          }
              MAX-ACCESS  read-write
              STATUS  current
              DESCRIPTION
                      "Command on the card that is installed in the selected slot.
					  The commands are applicable according to the value of atmNteCardStatus.
					  See the specification document for details.
                      
                      deleteConfig - Deletes the card configuration. 
                      deactivate   - All the connections state will be changed to NotReady. The card 
                                     configuration will be blocked.
                      activate     - Does the same as done upon card insertion: Initiates the relevant 
                                     parameters, activates the physical layer, ATM layer and logical 
                                     layer."
              ::= { atmNteIdEntry 6 }

atmNteProgCardType OBJECT-TYPE
		SYNTAX  INTEGER {
			-- values 1...1000 (if needed) should be used
			-- the same as in atmNteCardType
			fourStm1oc3SingleGbe	(159),
			adsl2Plus1p				(160), -- ADSL2+ 1 port
			shdsl					(161),

			adsl2Plus2p				(163), -- ADSL2+ 2 ports
			
			main8Atm155TwoEth		(249),
			mainChannelized155		(250),			
			main					(251),
			control					(252),
			fan						(253),
			empty					(255),

			atm155					(1001),
			eth						(1002),
			channelized155			(1003)
		}
		MAX-ACCESS  read-write
		STATUS current 
		DESCRIPTION
			"The programmed card type."
            ::= { atmNteIdEntry 7 }


         atmSysPSunits OBJECT-TYPE
              SYNTAX  Integer32 
              MAX-ACCESS  read-only
              STATUS  current
              DESCRIPTION
                      "The number of power supply units."
              ::= { atmNteSysInfo 2 }

          atmSysPSunitsInUse OBJECT-TYPE
              SYNTAX  INTEGER { ps1(2), ps2(3) }
              MAX-ACCESS  read-only
              STATUS  current
              DESCRIPTION
              "The main power supply in this unit."
              ::= { atmNteSysInfo 3 }

          atmSysFanUnits OBJECT-TYPE
              SYNTAX  Integer32 
              MAX-ACCESS  read-only
              STATUS  current
              DESCRIPTION
                      "The number of fan units."
              ::= { atmNteSysInfo 4 }

          atmSysNetPrts OBJECT-TYPE
              SYNTAX  Integer32 
              MAX-ACCESS  read-only
              STATUS  current
              DESCRIPTION
                      "The number of network ports."
              ::= { atmNteSysInfo 5 }

          atmSysNetPrtInUse OBJECT-TYPE
              SYNTAX  INTEGER { 
                      trunk1(2),
			          trunk2(3)
			  }
              MAX-ACCESS  read-only
              STATUS  current
              DESCRIPTION
                      "The network port in use."
              ::= { atmNteSysInfo 6 }

          atmNteBridgingMode OBJECT-TYPE
               SYNTAX  INTEGER {
                       accessOnly(1),
                       accessAndSwitching (2)
               }
 	           MAX-ACCESS  read-write
               STATUS  current
               DESCRIPTION
               "Bridging mode can be one of the following: 
	            ATM <> Ethernet - Bridging is between the Ethernet 
	            port and the ATM port (there is no bridging between VCs).
	            ATM <> Ethernet + ATM - Bridging is done both between 
	            the Ethernet port and the ATM port and also between VCs."
               ::= { atmNteSysInfo 7}

          atmSysStats OBJECT IDENTIFIER ::= { atmNteSysInfo 8 }

          atmSysCurrentCdc  OBJECT-TYPE
                SYNTAX  Gauge32
                MAX-ACCESS  read-only
                STATUS  current
                DESCRIPTION
                        "Seconds in which cells dropped was occured in
                        the current 15 minutes interval."
                ::= { atmSysStats 1 }

          atmSysIntervalTable OBJECT-TYPE
              SYNTAX  SEQUENCE OF AtmSysIntervalEntry
              MAX-ACCESS  not-accessible
              STATUS  current
              DESCRIPTION
                      "The system level Interval table."
              ::= { atmSysStats 2 }

          atmSysIntervalEntry OBJECT-TYPE
              SYNTAX  AtmSysIntervalEntry
              MAX-ACCESS  not-accessible
              STATUS  current
              DESCRIPTION
                      "."
              INDEX   { atmSysIntervalNumber }
              ::= { atmSysIntervalTable 1 }

          AtmSysIntervalEntry ::=
              SEQUENCE {
                  atmSysIntervalNumber
					  Integer32,
                  atmSysIntervalCdc
                      Gauge32
              }

          atmSysIntervalNumber OBJECT-TYPE
              SYNTAX  Integer32 (1..96)
              MAX-ACCESS  read-only
              STATUS  current
              DESCRIPTION
                      "A number between 1 and 96, where 1 is the most
                      recently completed 15 minute interval and 96 is
                      the least recently completed 15 minutes interval
                      (assuming that all 96 intervals are valid)."
              ::= { atmSysIntervalEntry 1 }

          atmSysIntervalCdc  OBJECT-TYPE
                SYNTAX  Gauge32
                MAX-ACCESS  read-only
                STATUS  current
                DESCRIPTION
                        "Seconds in which cells dropped was occured in
                        15 minutes interval."
                ::= { atmSysIntervalEntry 2 }

          atmNteEventType OBJECT-TYPE
               SYNTAX  INTEGER {
					ps1NotActive	(3),
					ps1Active		(4),
					ps2NotActive	(5),
					ps2Active		(6),
					heatAlarmOff	(7),
					heatAlarmOn		(8),
					inputAlarm1Off	(9),
					inputAlarm1On	(10),
					inputAlarm2Off	(11),
					inputAlarm2On	(12),
					inputAlarm3Off	(13),
					inputAlarm3On	(14),
					inputAlarm4Off	(15),
					inputAlarm4On	(16),
					fan1Ok	        (17),
					fan1Fail	    (18),
					fan2Ok	        (19),
					fan2Fail	    (20),
                    invalidLogin    (21),
                    validLogin      (22),
					powerFailure 	(23),
					writeToFlashFailure (24)
               }
 	           MAX-ACCESS  read-only
               STATUS  current
               DESCRIPTION
               "This parameter identifies the event.
               On  - the problem exist.
               Off - the problem not exist.
               InvalidLogin - Invalid login on local console.
               CorrectLogin - Successful login operation."
               ::= { atmNteSysInfo 9 }

         atmNteIntervalMaxNumber OBJECT-TYPE
              SYNTAX  Integer32 (1..96)
              MAX-ACCESS  read-only
              STATUS  current
              DESCRIPTION
                      "The MAX number of connections intervals supported by system.
					  This parameter value is a function of atmNteConnectionsMaxNumber 
					  parameter.
					  This parameter should affect the threshold values selected by user.
                      Applicable to ace2002."
              ::= { atmNteSysInfo 10 }

        atmNteAlarmType OBJECT-TYPE
              SYNTAX INTEGER 
              {
		          notApplicable(1),
		          ais(2),
                  rdi(3),
		          continuityLoss(4),
		          loopback(5)
              } 
              MAX-ACCESS read-only
              STATUS  current
              DESCRIPTION
                "This object specifies the type of the alarm."
              ::= { atmNteSysInfo 11 }

        atmNteLevel OBJECT-TYPE
              SYNTAX INTEGER 
              {
		          vp(2),
		          vc(3)
              } 
              MAX-ACCESS read-only
              STATUS  current
              DESCRIPTION
                "This object specifies the ATM level."
              ::= { atmNteSysInfo 12 }

        atmNteConnectionsNumber OBJECT-TYPE
              SYNTAX Integer32 
              MAX-ACCESS read-only
              STATUS  current
              DESCRIPTION
                "This object specifies a quantity of connections."
              ::= { atmNteSysInfo 13 }

        atmNteTotalLb OBJECT-TYPE
              SYNTAX Integer32 
              MAX-ACCESS read-only
              STATUS  current
              DESCRIPTION
                "This parameter counts the total number of end-points
                that were configured with Loopback (LB)."
              ::= { atmNteSysInfo 14 }

        atmNteTotalCc OBJECT-TYPE
              SYNTAX Integer32 
              MAX-ACCESS read-only
              STATUS  current
              DESCRIPTION
                "This parameter counts the total number of end-points
                that were configured with Continuity Check (CC)."
              ::= { atmNteSysInfo 15 }

        atmNteTotalPm OBJECT-TYPE
              SYNTAX Integer32 
              MAX-ACCESS read-only
              STATUS  current
              DESCRIPTION
                "This parameter counts the total number of end-points
                that were configured with PM."
              ::= { atmNteSysInfo 16 }


--atmNtePrt  OBJECT IDENTIFIER  ::=  {atmNte 2}

-- Changed
atmNteLoopback  OBJECT IDENTIFIER  ::=  {atmNtePrt 2}
-- The loopback test consists of inserting special OAM cells. This test is started and stopped
-- upon operator request (by using MIB item atmVpConfLoopbackAdminStatus).
-- There are two tables per VP and two tables per VC: the measurements of the current 15 minutes,
-- and the measurement of the last 96 periods of 15 minutes.
atmLoopbackVpTable  OBJECT-TYPE
      SYNTAX SEQUENCE OF AtmLoopbackVpEntry
      MAX-ACCESS not-accessible
      STATUS  current
      DESCRIPTION
      "This table contains parameters for an OAM VP loopback test."
       ::= {atmNteLoopback 1 }

atmLoopbackVpEntry OBJECT-TYPE
      SYNTAX AtmLoopbackVpEntry
      MAX-ACCESS not-accessible
      STATUS current
	  DESCRIPTION "An entry in table atmLoopbackVpTable."
	  INDEX {atmLoopbackVpIfIndex,atmLoopbackVpVpi}
      ::= {atmLoopbackVpTable 1}

AtmLoopbackVpEntry ::=
      SEQUENCE {
	atmLoopbackVpIfIndex               Integer32,
	atmLoopbackVpVpi                   Integer32,
	atmLoopbackVpOperStatus            INTEGER,
	atmLoopbackVpCDV 		           Integer32,
	atmLoopbackVpAverageDelay          Integer32,
	atmLoopbackVpMaxDelay              Integer32,
	atmLoopbackVpMinDelay              Integer32,
	atmLoopbackVpErrSessions	       Integer32 
	}

atmLoopbackVpIfIndex OBJECT-TYPE
      SYNTAX Integer32 
      MAX-ACCESS read-only
      STATUS current
      DESCRIPTION
      "The interface index of the ATM layer."
      ::= {atmLoopbackVpEntry 1}

atmLoopbackVpVpi OBJECT-TYPE
      SYNTAX Integer32 
      MAX-ACCESS read-only
      STATUS current
      DESCRIPTION
      "The VPI of the OAM VPL."
      ::= {atmLoopbackVpEntry 2}


atmLoopbackVpOperStatus OBJECT-TYPE
      SYNTAX INTEGER {
	noActive(1),
	inProgress(2),
              failed(3),
	endSuccessfully(4)
                     } 
      MAX-ACCESS read-only
      STATUS current
      DESCRIPTION
      "-noActive(1) means that the loopback test has not been activated for this VP.
        -inProgress(2) means that the test has been activated and there is currently no problem.
        -failed(3) means there was problem during the test or after having stopped it
        -endSuccessfully(4) means that the test was stopped and all was OK."
      ::= {atmLoopbackVpEntry 3}

atmLoopbackVpCDV OBJECT-TYPE
      SYNTAX Integer32 
      MAX-ACCESS read-only
      STATUS current
      DESCRIPTION
      "Cell Delay Variation for this sampling."
      ::= {atmLoopbackVpEntry 4}

atmLoopbackVpAverageDelay OBJECT-TYPE
      SYNTAX Integer32 
      MAX-ACCESS read-only
      STATUS current
      DESCRIPTION
      " Average delay without including lost cells."
      ::= {atmLoopbackVpEntry 5}

atmLoopbackVpMaxDelay OBJECT-TYPE
      SYNTAX Integer32 
      MAX-ACCESS read-only
      STATUS current
      DESCRIPTION
      "Maximum delay without including lost cells."
      ::= {atmLoopbackVpEntry 6}

atmLoopbackVpMinDelay OBJECT-TYPE
      SYNTAX Integer32 
      MAX-ACCESS read-only
      STATUS current
      DESCRIPTION
      "Minimum delay."
      ::= {atmLoopbackVpEntry 7}

atmLoopbackVpErrSessions OBJECT-TYPE
      SYNTAX Integer32 
      MAX-ACCESS read-only
      STATUS current
      DESCRIPTION
      "Errored Sessions. Will be updated once in 5 seconds."
      ::= {atmLoopbackVpEntry 8}

atmLoopbackVcTable  OBJECT-TYPE
      SYNTAX SEQUENCE OF AtmLoopbackVcEntry
      MAX-ACCESS not-accessible
      STATUS  current
      DESCRIPTION
      "This table contains parameters for an OAM VC loopback test."
       ::= {atmNteLoopback 2 }

atmLoopbackVcEntry OBJECT-TYPE
      SYNTAX AtmLoopbackVcEntry
      MAX-ACCESS not-accessible
      STATUS current
      DESCRIPTION  "An entry in table."
      INDEX {atmLoopbackVcIfIndex,atmLoopbackVcVpi,atmLoopbackVcVci}
      ::= {atmLoopbackVcTable 1}

AtmLoopbackVcEntry ::=
      SEQUENCE {
	atmLoopbackVcIfIndex               Integer32,
	atmLoopbackVcVpi                   Integer32,
	atmLoopbackVcVci                   Integer32,
	atmLoopbackVcOperStatus            INTEGER,
	atmLoopbackVcCDV	               Integer32,
	atmLoopbackVcAverageDelay          Integer32,
	atmLoopbackVcMaxDelay              Integer32,
	atmLoopbackVcMinDelay              Integer32,
	atmLoopbackVcErrSessions           Integer32 
	}

atmLoopbackVcIfIndex OBJECT-TYPE
      SYNTAX Integer32 
      MAX-ACCESS read-only
      STATUS current
      DESCRIPTION
      "The interface index of the ATM layer."
      ::= {atmLoopbackVcEntry 1}

atmLoopbackVcVpi OBJECT-TYPE
      SYNTAX Integer32 
      MAX-ACCESS read-only
      STATUS current
      DESCRIPTION
      "The VPI of the OAM VCL."
      ::= {atmLoopbackVcEntry 2}

atmLoopbackVcVci OBJECT-TYPE
      SYNTAX Integer32 
      MAX-ACCESS read-only
      STATUS current
      DESCRIPTION
      "The VCI of the OAM VCL."
      ::= {atmLoopbackVcEntry 3}


atmLoopbackVcOperStatus OBJECT-TYPE
      SYNTAX INTEGER {
	noActive(1),
	inProgress(2),
               failed(3),
	endSuccessfully(4)
                     } 
      MAX-ACCESS read-only
      STATUS current
      DESCRIPTION
      "-noActive(1) means that the loopback test has not been activated for this VP.
        -inProgress(2) means that the test has been activated and there is currently no problem.
        -failed(3) means there was problem during the test or after having stopped it
        -endSuccessfully(4) means that the test was stopped and all was OK."
      ::= {atmLoopbackVcEntry 4}

atmLoopbackVcCDV OBJECT-TYPE
      SYNTAX Integer32 
      MAX-ACCESS read-only
      STATUS current
      DESCRIPTION
      "Cell Delay Variation for this sampling."
      ::= {atmLoopbackVcEntry 5}


atmLoopbackVcAverageDelay OBJECT-TYPE
      SYNTAX Integer32 
      MAX-ACCESS read-only
      STATUS current
      DESCRIPTION
      " Average delay without including lost cells."
      ::= {atmLoopbackVcEntry 6}

atmLoopbackVcMaxDelay OBJECT-TYPE
      SYNTAX Integer32 
      MAX-ACCESS read-only
      STATUS current
      DESCRIPTION
      "The maximum delay without including lost cells."
      ::= {atmLoopbackVcEntry 7}

atmLoopbackVcMinDelay OBJECT-TYPE
      SYNTAX Integer32 
      MAX-ACCESS read-only
      STATUS current
      DESCRIPTION
      "The minimum delay."
      ::= {atmLoopbackVcEntry 8}

atmLoopbackVcErrSessions OBJECT-TYPE
      SYNTAX Integer32 
      MAX-ACCESS read-only
      STATUS current
      DESCRIPTION
      "Errored Sessions. Will be updated once in 5 seconds."
      ::= {atmLoopbackVcEntry 9}


-- Entirely New
atmLoopbackVpIvlTable  OBJECT-TYPE
      SYNTAX SEQUENCE OF AtmLoopbackVpIvlEntry 
      MAX-ACCESS not-accessible
      STATUS  current
      DESCRIPTION
      "This table contains parameters for an OAM VP loopback test,
	according interval number."
       ::= {atmNteLoopback 3 }

atmLoopbackVpIvlEntry OBJECT-TYPE
      SYNTAX AtmLoopbackVpIvlEntry 
      MAX-ACCESS not-accessible
      STATUS current
	DESCRIPTION  "An entry in table."
	INDEX { atmLoopbackVpIvlIfIndex, atmLoopbackVpIvlVpi, atmLoopbackVpIvlIvl }
      ::= { atmLoopbackVpIvlTable 1}

AtmLoopbackVpIvlEntry ::=
      SEQUENCE {
	atmLoopbackVpIvlIfIndex               Integer32,
	atmLoopbackVpIvlVpi                   Integer32,
	atmLoopbackVpIvlIvl 		          Integer32,
	atmLoopbackVpIvlOperStatus            INTEGER,
	atmLoopbackVpIvlCDV	                  Integer32,
	atmLoopbackVpIvlAverageDelay          Integer32,
	atmLoopbackVpIvlMaxDelay              Integer32,
	atmLoopbackVpIvlMinDelay              Integer32,
	atmLoopbackVpIvlErrSessions           Integer32 
	}
 
atmLoopbackVpIvlIfIndex OBJECT-TYPE
      SYNTAX Integer32 
      MAX-ACCESS read-only
      STATUS current
      DESCRIPTION
      "The interface index of the ATM layer."
      ::= { atmLoopbackVpIvlEntry 1}

atmLoopbackVpIvlVpi OBJECT-TYPE
      SYNTAX Integer32 
      MAX-ACCESS read-only
      STATUS current
      DESCRIPTION
      "The VPI of the OAM VPL."
      ::= { atmLoopbackVpIvlEntry 2}


atmLoopbackVpIvlIvl OBJECT-TYPE
      SYNTAX Integer32(1..96)
      MAX-ACCESS read-only
      STATUS current
      DESCRIPTION
      "The relevant interval number."
      ::= { atmLoopbackVpIvlEntry 3}

atmLoopbackVpIvlOperStatus OBJECT-TYPE
      SYNTAX INTEGER {
	noActive(1),
	inProgress(2),
               failed(3),
	endSuccessfully(4)
                     } 
      MAX-ACCESS read-only
      STATUS current
      DESCRIPTION
      "-noActive(1) means that the loopback test has not been activated for this VP during this interval.
        -inProgress(2) has no meaning for an ended interval.
        -failed(3) means there was problem during the test or after having stopped it
        -endSuccessfully(4) means that the test was OK."
      ::= { atmLoopbackVpIvlEntry 4}

atmLoopbackVpIvlCDV OBJECT-TYPE
      SYNTAX Integer32 
      MAX-ACCESS read-only
      STATUS current
      DESCRIPTION
      "Cell Delay Variation for this interval."
      ::= { atmLoopbackVpIvlEntry 5}


atmLoopbackVpIvlAverageDelay OBJECT-TYPE
      SYNTAX Integer32 
      MAX-ACCESS read-only
      STATUS current
      DESCRIPTION
      " Average delay without including lost cells for this interval."
      ::= { atmLoopbackVpIvlEntry 6}

atmLoopbackVpIvlMaxDelay OBJECT-TYPE
      SYNTAX Integer32 
      MAX-ACCESS read-only
      STATUS current
      DESCRIPTION
      "The maximum delay without including lost cells for this interval."
      ::= { atmLoopbackVpIvlEntry 7}

atmLoopbackVpIvlMinDelay OBJECT-TYPE
      SYNTAX Integer32 
      MAX-ACCESS read-only
      STATUS current
      DESCRIPTION
      "The minimum delay for this interval."
      ::= {atmLoopbackVpIvlEntry 8}

atmLoopbackVpIvlErrSessions OBJECT-TYPE
      SYNTAX Integer32 
      MAX-ACCESS read-only
      STATUS current
      DESCRIPTION
      "Errored Sessions. Will be updated once in 5 seconds."
      ::= {atmLoopbackVpIvlEntry 9}


atmLoopbackVcIvlTable  OBJECT-TYPE
      SYNTAX SEQUENCE OF AtmLoopbackVcIvlEntry
      MAX-ACCESS not-accessible
      STATUS  current
      DESCRIPTION
      "This table contains parameters for an OAM VC loopback test."
       ::= {atmNteLoopback 4 }

atmLoopbackVcIvlEntry OBJECT-TYPE
      SYNTAX AtmLoopbackVcIvlEntry
      MAX-ACCESS not-accessible
      STATUS current
	DESCRIPTION  "An entry in table."
	INDEX {atmLoopbackVcIvlIfIndex, atmLoopbackVcIvlVpi, atmLoopbackVcIvlVci, atmLoopbackVcIvlIvl }
      ::= {atmLoopbackVcIvlTable 1}

AtmLoopbackVcIvlEntry ::=
      SEQUENCE {
	atmLoopbackVcIvlIfIndex               Integer32,
	atmLoopbackVcIvlVpi                   Integer32,
	atmLoopbackVcIvlVci                   Integer32,
	atmLoopbackVcIvlIvl 		          Integer32,
	atmLoopbackVcIvlOperStatus            INTEGER,
	atmLoopbackVcIvlCDV	                  Integer32,
	atmLoopbackVcIvlAverageDelay          Integer32,
	atmLoopbackVcIvlMaxDelay              Integer32,
	atmLoopbackVcIvlMinDelay              Integer32,
	atmLoopbackVcIvlErrSessions           Integer32 
	}

atmLoopbackVcIvlIfIndex OBJECT-TYPE
      SYNTAX Integer32 
      MAX-ACCESS read-only
      STATUS current
      DESCRIPTION
      "The interface index of the ATM layer."
      ::= {atmLoopbackVcIvlEntry 1}

atmLoopbackVcIvlVpi OBJECT-TYPE
      SYNTAX Integer32 
      MAX-ACCESS read-only
      STATUS current
      DESCRIPTION
      "The VPI of the OAM VCL."
      ::= {atmLoopbackVcIvlEntry 2}

atmLoopbackVcIvlVci OBJECT-TYPE
      SYNTAX Integer32 
      MAX-ACCESS read-only
      STATUS current
      DESCRIPTION
      "The VCI of the OAM VCL."
      ::= {atmLoopbackVcIvlEntry 3}

atmLoopbackVcIvlIvl OBJECT-TYPE
      SYNTAX Integer32(1..96)
      MAX-ACCESS read-only
      STATUS current
      DESCRIPTION
      "The relevant interval number."
      ::= {atmLoopbackVcIvlEntry 4}

atmLoopbackVcIvlOperStatus OBJECT-TYPE
      SYNTAX INTEGER {
	noActive(1),
	inProgress(2),
               failed(3),
	endSuccessfully(4)
                     } 
      MAX-ACCESS read-only
      STATUS current
      DESCRIPTION
      "-noActive(1) means that the loopback test has not been activated for this VC during this interval.
        -inProgress(2) has no meaning per interval.
        -failed(3) means there was problem for this test during this interval.
        -endSuccessfully(4) means that the test was OK."
      ::= {atmLoopbackVcIvlEntry 5}

atmLoopbackVcIvlCDV OBJECT-TYPE
      SYNTAX Integer32 
      MAX-ACCESS read-only
      STATUS current
      DESCRIPTION
      "Cell Delay Variation for this interval."
      ::= {atmLoopbackVcIvlEntry 6}


atmLoopbackVcIvlAverageDelay OBJECT-TYPE
      SYNTAX Integer32 
      MAX-ACCESS read-only
      STATUS current
      DESCRIPTION
      " Average delay without including lost cells."
      ::= {atmLoopbackVcIvlEntry 7}

atmLoopbackVcIvlMaxDelay OBJECT-TYPE
      SYNTAX Integer32 
      MAX-ACCESS read-only
      STATUS current
      DESCRIPTION
      "The maximum delay without including lost cells."
      ::= {atmLoopbackVcIvlEntry 8}

atmLoopbackVcIvlMinDelay OBJECT-TYPE
      SYNTAX Integer32 
      MAX-ACCESS read-only
      STATUS current
      DESCRIPTION
      "The minimum delay."
      ::= {atmLoopbackVcIvlEntry 9}

atmLoopbackVcIvlErrSessions OBJECT-TYPE
      SYNTAX Integer32 
      MAX-ACCESS read-only
      STATUS current
      DESCRIPTION
      "Errored Sessions. Will be updated once in 5 seconds."
      ::= {atmLoopbackVcIvlEntry 10}


atmNtePM  OBJECT IDENTIFIER  ::=  {atmNtePrt 3}

atmVpPmTable  OBJECT-TYPE
      SYNTAX SEQUENCE OF AtmVpPmEntry
      MAX-ACCESS not-accessible
      STATUS  current
      DESCRIPTION
      "This table contains parameters for VP performance monitoring."
       ::= {atmNtePM 1 }

atmVpPmEntry OBJECT-TYPE
      SYNTAX AtmVpPmEntry
      MAX-ACCESS not-accessible
      STATUS current
	DESCRIPTION  "An entry in table."
	INDEX {atmVpPmIfIndex,atmVpPmVpi}
      ::= {atmVpPmTable 1}

AtmVpPmEntry ::=
      SEQUENCE {
	atmVpPmIfIndex               Integer32,
	atmVpPmVpi                   Integer32,
	atmVpPmAdminStatus           INTEGER,
	atmVpPmDirection             INTEGER,
	atmVpPmBlockSize             Integer32,
	atmVpPmRowStatus             RowStatus,
	atmVpPmSink                  INTEGER,
	atmVpPmSource                INTEGER
      }

atmVpPmIfIndex OBJECT-TYPE
      SYNTAX Integer32 
      MAX-ACCESS read-only
      STATUS current
      DESCRIPTION
      "The interface index of the ATM layer."
      ::= {atmVpPmEntry 1}

atmVpPmVpi OBJECT-TYPE
      SYNTAX Integer32 
      MAX-ACCESS read-only
      STATUS current
      DESCRIPTION
      "The VPI of the Performance Monitoring VPL."
      ::= {atmVpPmEntry 2}

atmVpPmAdminStatus OBJECT-TYPE
      SYNTAX INTEGER {
             up  (2), 
             down(3),
             listenToActivationCells (4),
             originateActivationCells (5)     
      } 
      MAX-ACCESS read-create
      STATUS current
      DESCRIPTION
      "up(2) - Activate PM.
       down(3) - Deactivate PM.
       listenToActivationCells(4) - . 
       originateActivationCells(5) - ."
      ::= {atmVpPmEntry 3}

atmVpPmDirection OBJECT-TYPE
      SYNTAX INTEGER  { 
             source(2), 
             destination(3), 
             bidirectional(4) 
      }
      MAX-ACCESS read-create
      STATUS current
      DESCRIPTION
      "The direction of PM."
      ::= {atmVpPmEntry 4}

atmVpPmBlockSize OBJECT-TYPE
      SYNTAX Integer32 
      MAX-ACCESS read-create
      STATUS current
      DESCRIPTION
      "Valid block sizes (in cells): 128, 256, 512, 1024, 2048, 4096,
       8192, 16384, 32768."
      ::= {atmVpPmEntry 5}

atmVpPmRowStatus OBJECT-TYPE
      SYNTAX RowStatus 
      MAX-ACCESS read-create
      STATUS current
      DESCRIPTION
      "Creation/Deletion of rows in the table."
      ::= {atmVpPmEntry 6}

atmVpPmSink OBJECT-TYPE
      SYNTAX INTEGER {
             off  (1), 
             fwd  (2),
             fwdAndBwdReport(3)     
      } 
      MAX-ACCESS read-create
      STATUS current
      DESCRIPTION
      "off (1) - Deactivate PM.
       fwd (2) - Activate Forward PM only.
       fwdAndBwdReport(3) - Activate Forward PM and Backward reporting."
      ::= {atmVpPmEntry 7}

atmVpPmSource OBJECT-TYPE
      SYNTAX INTEGER {
             off  (1), 
             fwd  (2),
             fwdAndBwdReport(3)     
      } 
      MAX-ACCESS read-create
      STATUS current
      DESCRIPTION
      "off (1) - Deactivate PM.
       fwd (2) - Activate Forward PM only.
       fwdAndBwdReport(3) - Activate Forward PM and Backward reporting."
      ::= {atmVpPmEntry 8}



atmVcPmTable  OBJECT-TYPE
      SYNTAX SEQUENCE OF AtmVcPmEntry
      MAX-ACCESS not-accessible
      STATUS  current
      DESCRIPTION
      "This table contains parameters for VC performance monitoring."
       ::= {atmNtePM 2 }

atmVcPmEntry OBJECT-TYPE
      SYNTAX AtmVcPmEntry
      MAX-ACCESS not-accessible
      STATUS current
	DESCRIPTION  "An entry in table."
	INDEX {atmVcPmIfIndex,atmVcPmVpi,atmVcPmVci}
      ::= {atmVcPmTable 1}

AtmVcPmEntry ::=
      SEQUENCE {
	atmVcPmIfIndex               Integer32,
	atmVcPmVpi                   Integer32,
	atmVcPmVci                   Integer32,
	atmVcPmAdminStatus           INTEGER,
	atmVcPmDirection             INTEGER,
	atmVcPmBlockSize             Integer32,
	atmVcPmRowStatus             RowStatus,
	atmVcPmSink                  INTEGER,
	atmVcPmSource                INTEGER
      }

atmVcPmIfIndex OBJECT-TYPE
      SYNTAX Integer32 
      MAX-ACCESS read-only
      STATUS current
      DESCRIPTION
      "The interface index of the ATM layer."
      ::= {atmVcPmEntry 1}

atmVcPmVpi OBJECT-TYPE
      SYNTAX Integer32 
      MAX-ACCESS read-only
      STATUS current
      DESCRIPTION
      "The VPI of the Performance Monitoring VCL."
      ::= {atmVcPmEntry 2}

atmVcPmVci OBJECT-TYPE
      SYNTAX Integer32 
      MAX-ACCESS read-only
      STATUS current
      DESCRIPTION
      "The VCI of the PM VCL."
      ::= {atmVcPmEntry 3}

atmVcPmAdminStatus OBJECT-TYPE
      SYNTAX INTEGER {
             up  (2), 
             down(3),
             listenToActivationCells (4),
             originateActivationCells (5)     
      } 
      MAX-ACCESS read-create
      STATUS current
      DESCRIPTION
      "up(2) - Activate PM.
       down(3) - Deactivate PM.
       listenToActivationCells(4) - . 
       originateActivationCells(5) - ."
      ::= {atmVcPmEntry 4}

atmVcPmDirection OBJECT-TYPE
      SYNTAX INTEGER  { source(2), destination(3), bidirectional(4)  }
      MAX-ACCESS read-create
      STATUS current
      DESCRIPTION
      "The direction of PM."
      ::= {atmVcPmEntry 5}

atmVcPmBlockSize OBJECT-TYPE
      SYNTAX Integer32 
      MAX-ACCESS read-create
      STATUS current
      DESCRIPTION
      "Valid block sizes (in cells): 128, 256, 512, 1024, 2048, 4096,
       8192, 16384, 32768."
      ::= {atmVcPmEntry 6}

atmVcPmRowStatus OBJECT-TYPE
      SYNTAX RowStatus 
      MAX-ACCESS read-create
      STATUS current
      DESCRIPTION
      "Creation/Deletion of rows in the table."
      ::= {atmVcPmEntry 7}

atmVcPmSink OBJECT-TYPE
      SYNTAX INTEGER {
             off  (1), 
             fwd  (2),
             fwdAndBwdReport(3)     
      } 
      MAX-ACCESS read-create
      STATUS current
      DESCRIPTION
      "off (1) - Deactivate PM.
       fwd (2) - Activate Forward PM only.
       fwdAndBwdReport(3) - Activate Forward PM and Backward reporting."
      ::= {atmVcPmEntry 8}

atmVcPmSource OBJECT-TYPE
      SYNTAX INTEGER {
             off  (1), 
             fwd  (2),
             fwdAndBwdReport(3)     
      } 
      MAX-ACCESS read-create
      STATUS current
      DESCRIPTION
      "off (1) - Deactivate PM.
       fwd (2) - Activate Forward PM only.
       fwdAndBwdReport(3) - Activate Forward PM and Backward reporting."
      ::= {atmVcPmEntry 9}

atmNteMdl  OBJECT IDENTIFIER  ::=  {atmNte 3}

atmNteMdlConfig  OBJECT IDENTIFIER  ::=  {atmNteMdl 1}

atmNteMdlConfigTable  OBJECT-TYPE
      SYNTAX SEQUENCE OF AtmNteMdlConfigEntry
      MAX-ACCESS not-accessible
      STATUS  current
      DESCRIPTION
      "Module configuration table."
       ::= { atmNteMdlConfig 1 }

atmNteMdlConfigEntry OBJECT-TYPE
      SYNTAX AtmNteMdlConfigEntry
      MAX-ACCESS not-accessible
      STATUS current
	  DESCRIPTION  
	  "There is an entry in this table just for those modules that have 
	  parameters that are relevant to module level only."
	  INDEX {atmNteMdlSlotIndex}
      ::= {atmNteMdlConfigTable 1}

AtmNteMdlConfigEntry ::=
      SEQUENCE {
	  atmNteMdlSlotIndex                Integer32,
	  atmNteMdlPrtCpuSharing            INTEGER,
	  atmNteMdlInputPriorityMechanism   INTEGER
	  }

atmNteMdlSlotIndex OBJECT-TYPE
      SYNTAX Integer32 (1..4)
      MAX-ACCESS not-accessible
      STATUS current
      DESCRIPTION
      "The slot number."
      ::= { atmNteMdlConfigEntry 1}

atmNteMdlPrtCpuSharing OBJECT-TYPE
      SYNTAX INTEGER {
             equal      (2),
             port1      (3)     
      } 
      MAX-ACCESS read-write
      STATUS current
      DESCRIPTION
      "This object lets the user decide what will be the CPU sharing 
       between the ports of the module. This object is applicable for 
       modules in which the same CPU handles the traffic of all ports.

       equal - All ports will have the same CPU resource.
       port1 - Port 1 will have higher priority than the other ports."
      ::= {atmNteMdlConfigEntry 2}

atmNteMdlInputPriorityMechanism OBJECT-TYPE
      SYNTAX INTEGER {
             disabled  (2),
             enabled   (3)     
      } 
      MAX-ACCESS read-write
      STATUS current
      DESCRIPTION
      "This object allows the user to Enable/Disable the Input priority mechanism. 
      This object is applicable for modules	with more than one port, in which the 
      total ports input may be greater than the port output. 
      
      disabled - all LAN VCCs will be transmitted through the same queue (queue 1).
                Upon congestion frames will be dropped randomly.
      enabled -  the user should configure each port/connection priority. Upon 
                 congestion frames will be dropped according to priority."
      ::= {atmNteMdlConfigEntry 3}



atmGenSystem  OBJECT IDENTIFIER  ::=  {atmGen 2}

--atmGenModules  OBJECT IDENTIFIER  ::=  {atmGen 3}	 located in ace2002.txt


atmGenSysGen  OBJECT IDENTIFIER  ::=  {atmGenSystem 1}

-- The self test table

atmGenSysSelfTestTable  OBJECT-TYPE
      SYNTAX SEQUENCE OF AtmGenSysSelfTestEntry
      MAX-ACCESS not-accessible
      STATUS  current
      DESCRIPTION
      "A table containing the results of the initial testing of the device."
       ::= { atmGenSysGen 1 }

atmGenSysSelfTestEntry OBJECT-TYPE
      SYNTAX AtmGenSysSelfTestEntry
      MAX-ACCESS not-accessible
      STATUS current
	DESCRIPTION  "An entry in table."
	INDEX {atmGenSysSelfTestIndex}
      ::= {atmGenSysSelfTestTable 1}

AtmGenSysSelfTestEntry ::=
      SEQUENCE {
	  atmGenSysSelfTestIndex		Integer32,
	  atmGenSysSelfTestResult		DisplayString,
	  atmGenSysSelfTestModule		DisplayString
      }

atmGenSysSelfTestIndex OBJECT-TYPE
      SYNTAX 		Integer32
      MAX-ACCESS 	read-only
      STATUS 		current
      DESCRIPTION
      "A running index for the table."
      ::= { atmGenSysSelfTestEntry 1 }

atmGenSysSelfTestResult OBJECT-TYPE
      SYNTAX 		DisplayString
      MAX-ACCESS 	read-only
      STATUS 		current
      DESCRIPTION
      "The results of the initial testing of the device."
      ::= { atmGenSysSelfTestEntry 2 }

atmGenSysSelfTestModule OBJECT-TYPE
      SYNTAX 		DisplayString
      MAX-ACCESS 	read-only
      STATUS 		current
      DESCRIPTION
      "The name of module on which the test was performed."
      ::= { atmGenSysSelfTestEntry 3 }


-- The Log clear all

atmGenSysLogClearAll OBJECT-TYPE
      SYNTAX INTEGER { off(2),clear(3)}
      MAX-ACCESS read-write
      STATUS current
      DESCRIPTION
      "Setting the variable to clear(3) removes all entries in the 
       Log Buffer of the agent. The agent will immediately
       reset the variable to off(2)."
      ::= { atmGenSysGen 2}

-- The Log table

atmGenSysLogTable  OBJECT-TYPE
      SYNTAX SEQUENCE OF AtmGenSysLogEntry
      MAX-ACCESS not-accessible
      STATUS  current
      DESCRIPTION
      "A copy of the log buffer."
       ::= { atmGenSysGen 3 }

atmGenSysLogEntry OBJECT-TYPE
      SYNTAX AtmGenSysLogEntry
      MAX-ACCESS not-accessible
      STATUS current
	DESCRIPTION  "An entry in table."
	INDEX {atmGenSysLogIndex}
      ::= {atmGenSysLogTable 1}

AtmGenSysLogEntry ::=
      SEQUENCE {
	  atmGenSysLogIndex   Integer32,
	  atmGenSysLogMessage DisplayString
      }

atmGenSysLogIndex OBJECT-TYPE
      SYNTAX Integer32 (1..2048)
      MAX-ACCESS read-only
      STATUS current
      DESCRIPTION
      "The index of the log buffer."
      ::= { atmGenSysLogEntry 1}

atmGenSysLogMessage OBJECT-TYPE
      SYNTAX DisplayString (SIZE(80))
      MAX-ACCESS read-only
      STATUS current
      DESCRIPTION
      "The log buffer entry message text."
      ::= { atmGenSysLogEntry 2}

-- Set to default configuration

atmGenSysSetDefaultConfg OBJECT-TYPE
      SYNTAX INTEGER { off(2), on(3) }
      MAX-ACCESS read-write
      STATUS current
      DESCRIPTION
      "When set to on(3), the agent will set all the configuration parameters
       to their default values. The variable is then reset to  off(2)
       by the agent. The agent must be reset for the default configuration
       to apply."
      ::=  {atmGenSysGen 4}

	-- A Cross Reference table for connections between tables. 
         
 atmGenSysCxRefTable OBJECT-TYPE
              SYNTAX  SEQUENCE OF AtmGenSysCxRefEntry
              MAX-ACCESS  not-accessible
              STATUS  current
              DESCRIPTION
                   "A Cross Reference table. The table maintains 
                    an index of an object which is also the table index, 
                    and a counter that indicates how many times this 
                    object was referenced.
                    When using this table for more than one referenced table,
					which uses the same range of indexes, then the index 
					should be shifted by a unique offset per table.
                       
                    In ACE2002 this table is used for TD and for FR Desc. Thus,
                    the index for FR Descriptor is: FR Descriptor index + offset. 
                    The offset is described in the ACE2002 NMS SRS."
              ::= {atmGenSysGen 5}

 atmGenSysCxRefEntry OBJECT-TYPE
              SYNTAX AtmGenSysCxRefEntry
              MAX-ACCESS  not-accessible
              STATUS  current
              DESCRIPTION
                      "The entries will be added by the agent upon
                       an entry addition in the referenced tables 
                       (TD table, FR Descriptor etc.)"
              INDEX   { atmGenSysCxRefIndex }
              ::= { atmGenSysCxRefTable 1 }

 	AtmGenSysCxRefEntry ::=
              SEQUENCE {
		 		atmGenSysCxRefIndex
                      	Integer32,
                atmGenSysCxRefCounter
                      	Gauge32
                }

 	atmGenSysCxRefIndex OBJECT-TYPE
              SYNTAX  Integer32
              MAX-ACCESS  read-only
              STATUS  current
              DESCRIPTION
                      "The index specifies an entry in the table of the object."
              ::= { atmGenSysCxRefEntry 1 }

 	atmGenSysCxRefCounter OBJECT-TYPE
              SYNTAX Gauge32
              MAX-ACCESS  read-only
              STATUS  current
              DESCRIPTION
                      "The counter counts the number of references 
						that have been made to the object ."
              ::= { atmGenSysCxRefEntry 2 }



-- Traps

-- System Layer Traps

atmAceStatusChange NOTIFICATION-TYPE
      OBJECTS  {agnLed,agnIndication}
      STATUS  current
      DESCRIPTION
       "The trap is sent every time there is a change in
	    the state of one of the LEDs."
      ::= { atmNteEvents 1 }

atmAceAlarmTrap NOTIFICATION-TYPE
      OBJECTS  {atmInterfaceAlarmStatus}
      STATUS  current
      DESCRIPTION
	  "The trap is sent whenever there is a transition from a no alarm
	   state to a state with at least one active alarm. An active alarm 
	   state exists if:
	   1) The atmInterfaceActiveAlarms vector is different than 0.
	   2) The atmNteAlarmVpTable contains entries.
	   3) The atmNteAlarmVcTable contains entries. 
	   The trap is also sent when a transition into the no alarm state
	   occurs.
                 The second variable will be atmInterfaceActiveAlarms to 
                 indicate the kind of the alarm.
                 The trap is not sent more than once in a 10 second interval."
      ::= { atmNteEvents 2 }

atmAceModuleChangeTrap NOTIFICATION-TYPE
      OBJECTS  {ifIndex}
      STATUS  current
      DESCRIPTION
	  "The trap is sent every time a module is changed (Hot swapping).
                  The second variable will be atmNteCardType to indicate the 
                  type of card that was inserted. The value empty(255) indicates that 
                  a card was taken out."
      ::= { atmNteEvents 3 }

atmAceRedundancyTrap NOTIFICATION-TYPE
      OBJECTS  {ifIndex }
      STATUS  current
      DESCRIPTION
	  	"The trap is sent upon change in link as a result of redundancy. 
                  The ifIndex parameter indicates the current active link."
      ::= { atmNteEvents 4 }

atmAceModuleMismatchTrap NOTIFICATION-TYPE
      STATUS  current
      DESCRIPTION
	  "The trap is sent upon starting or stopping of
	   a module mismatch state.
	   A possible mismatch is when the inserted module is other
	   than the programmed one."
      ::= { atmNteEvents 5 }


atmAceSystemTrap NOTIFICATION-TYPE
      OBJECTS  { atmNteEventType, agnLed, alarmSeverity }  
      STATUS  current
      DESCRIPTION
	  	"This trap alerts of major problems in the device."
      ::= { radSysAtmEvents  6 }

atmAceAlarmForwardingTrap NOTIFICATION-TYPE
      OBJECTS  { alarmSeverity, alarmState }  
      STATUS  current
      DESCRIPTION
	  	"This trap is sent upon starting or stopping Alarm 
	  	Forwarding Mechanism."
      ::= { radSysAtmEvents  7 }

atmAceDateAndTimeRequest NOTIFICATION-TYPE
      STATUS  current
      DESCRIPTION
	  	"This trap is sent upon restart. Upon recieving this trap the NMS will 
	  	set the device's date and time.	This trap's purpose is to fix a problem 
	  	in ACE2002, ACE-2002E, ACE-202.	The problem is that the Date and Time 
	  	is stored in the NVRAM, and when the NVRAM's battery is empty, the device 
	  	loses this information."
      ::= { radSysAtmEvents  8 }

-- Alarms Traps 
atmAceAlarmLOS NOTIFICATION-TYPE
      OBJECTS  { alarmSeverity, alarmState, ifAlias }  
      STATUS  current
      DESCRIPTION
	  	"This trap indicates Loss Of Signal."
      ::= { radSysAtmEvents  16 }

atmAceAlarmLOF NOTIFICATION-TYPE
      OBJECTS  { alarmSeverity, alarmState, ifAlias }  
      STATUS  current
      DESCRIPTION
	  	"This trap indicates Loss Of Frame."
      ::= { radSysAtmEvents  17 }

atmAceAlarmLCD NOTIFICATION-TYPE
      OBJECTS  { alarmSeverity, alarmState, ifAlias }  
      STATUS  current
      DESCRIPTION
	  	"This trap indicates Loss of Cell Delineation."
      ::= { radSysAtmEvents  18 }

atmAceAlarmSLM NOTIFICATION-TYPE
      OBJECTS  { alarmSeverity, alarmState, ifAlias }  
      STATUS  current
      DESCRIPTION
	  	"This trap indicates Signal Line Mismatch."
      ::= { radSysAtmEvents  19 }

atmAceAlarmLOP NOTIFICATION-TYPE
      OBJECTS  { alarmSeverity, alarmState, ifAlias }  
      STATUS  current
      DESCRIPTION
	  	"This trap indicates Loss of Pointer."
      ::= { radSysAtmEvents  20 }

atmAceAlarmLineAIS NOTIFICATION-TYPE
      OBJECTS  { alarmSeverity, alarmState, ifAlias }  
      STATUS  current
      DESCRIPTION
	  	"This trap indicates Line AIS."
      ::= { radSysAtmEvents  21 }

atmAceAlarmPathAIS NOTIFICATION-TYPE
      OBJECTS  { alarmSeverity, alarmState, ifAlias }  
      STATUS  current
      DESCRIPTION
	  	"This trap indicates Path AIS."
      ::= { radSysAtmEvents  22 }

atmAceAlarmLineRDI NOTIFICATION-TYPE
      OBJECTS  { alarmSeverity, alarmState, ifAlias }  
      STATUS  current
      DESCRIPTION
	  	"This trap indicates Line RDI."
      ::= { radSysAtmEvents  23 }

atmAceAlarmPathRDI NOTIFICATION-TYPE
      OBJECTS  { alarmSeverity, alarmState, ifAlias }  
      STATUS  current
      DESCRIPTION
	  	"This trap indicates Path RDIand Path RAI(Yellow) for
	  	 DS1 interfaces."
      ::= { radSysAtmEvents  24 }

atmAceAlarmSectionBIP NOTIFICATION-TYPE
      OBJECTS  { alarmSeverity, alarmState, ifAlias }  
      STATUS  current
      DESCRIPTION
	  	"This trap indicates Section Bit Interleave Parity."
      ::= { radSysAtmEvents  25 }

atmAceAlarmLineBIP NOTIFICATION-TYPE
      OBJECTS  { alarmSeverity, alarmState, ifAlias }  
      STATUS  current
      DESCRIPTION
	  	"This trap indicates Line Bit Interleave Parity."
      ::= { radSysAtmEvents  26 }

atmAceAlarmPathBIP NOTIFICATION-TYPE
      OBJECTS  { alarmSeverity, alarmState, ifAlias }  
      STATUS  current
      DESCRIPTION
	  	"This trap indicates Path Bit Interleave Parity."
      ::= { radSysAtmEvents  27 }

atmAceAlarmLineFEBE NOTIFICATION-TYPE
      OBJECTS  { alarmSeverity, alarmState, ifAlias }  
      STATUS  current
      DESCRIPTION
	  	"This trap indicates Line Far End Block Error."
      ::= { radSysAtmEvents  28 }

atmAceAlarmPathFEBE NOTIFICATION-TYPE
      OBJECTS  { alarmSeverity, alarmState, ifAlias }  
      STATUS  current
      DESCRIPTION
	  	"This trap indicates Path Far End Block Error."
      ::= { radSysAtmEvents  29 }

atmAceAlarmPlcpLOF NOTIFICATION-TYPE
      OBJECTS  { alarmSeverity, alarmState, ifAlias }  
      STATUS  current
      DESCRIPTION
	  	"This trap indicates T3 PLCP Loss Of Frame."
      ::= { radSysAtmEvents  30 }


atmAceAlarmPlcpYELLOW NOTIFICATION-TYPE
      OBJECTS  { alarmSeverity, alarmState, ifAlias }  
      STATUS  current
      DESCRIPTION
	  	"This trap indicates T3 Plcp Yellow."
      ::= { radSysAtmEvents  31 }

atmAceAlarmPlcpBIP NOTIFICATION-TYPE
      OBJECTS  { alarmSeverity, alarmState, ifAlias }  
      STATUS  current
      DESCRIPTION
	  	"This trap indicates T3 Plcp Bit Interleave Parity."
      ::= { radSysAtmEvents  32 }

atmAceAlarmPlcpFEBE NOTIFICATION-TYPE
      OBJECTS  { alarmSeverity, alarmState, ifAlias }  
      STATUS  current
      DESCRIPTION
	  	"This trap indicates T3 Plcp Far End Block Error."
      ::= { radSysAtmEvents  33 }

atmAceAlarmPlcpP1P2 NOTIFICATION-TYPE
      OBJECTS  { alarmSeverity, alarmState, ifAlias }  
      STATUS  current
      DESCRIPTION
	  	"This trap indicates T3 Plcp Parity errors in P1/P2 bytes."
      ::= { radSysAtmEvents  34 }

atmAceAlarmUAS NOTIFICATION-TYPE
      OBJECTS  { alarmSeverity, alarmState, ifAlias }  
      STATUS  current
      DESCRIPTION
	  	"This trap is sent upon UAS start or end per port."
      ::= { radSysAtmEvents  35 }

atmAceAlarmCluster NOTIFICATION-TYPE
      OBJECTS  { alarmSeverity, alarmState, atmNteAlarmType, atmNteLevel }  
      STATUS  current
      DESCRIPTION
	  	"This trap is sent upon atmNteAlarmType start or end,
	  	for a cluster of VPs/VCs (according to atmNteLevel) with 
	  	the same alarm on the same physical port.
	  	
	  	This trap replaces sending the same alarm for a big 
	  	quantity (the quantity described in the product 
	  	specification document) of VPs/VCs in order to prevent 
	  	flooding the NMS and the network with traps."
      ::= { radSysAtmEvents  36 }

atmAceHwFailure NOTIFICATION-TYPE
      OBJECTS  { alarmSeverity, alarmState, ifAlias }  
      STATUS  current
      DESCRIPTION
	  	"This trap is sent upon HW failure per port."
      ::= { radSysAtmEvents  37 }

atmAceUnavailableBwTrap NOTIFICATION-TYPE
      OBJECTS  { alarmSeverity, ifAlias, atmConfIfInputRate, atmConfIfOutputRate }  
      STATUS  current
      DESCRIPTION
	  	"This trap is sent when Bandwidth allocation is > max possible
	  	value for the installed card.
	  	
	  	For ACE2002 this trap will be sent for the following cases:
	  	
	  	Card insertion - if the total Input and/or Output Bandwidth is over 
	  	allocated, then the specific card rate will be set to 0 and this trap 
	  	will be sent with the Input/Output rates values. 
	  	
	  	Upgrade from former version - when an over allocated Bandwidth is detected, 
	  	this trap will be sent with atmConfIfInputRate=atmConfIfOutputRate=0xFFFFFFFF."
      ::= { radSysAtmEvents  38 }


--   
--   OAM LOOPBACK 
--   atmAceOAMLoopBackCellRx NOTIFICATION-TYPE
--         OBJECTS  { alarmSeverity, alarmState,ifAlias }  
--         STATUS  current
--         DESCRIPTION
--         "This Trap indicates that a loopback has 
--          been activated on device ATM uplink interface
--          by the remote ATM equipment, by means of OAM cells"
--         ::= { radSysAtmEvents  39 }
--   
--   
--   OAM LOOPBACK 
--   atmAceOAMLoopBackCellTx NOTIFICATION-TYPE
--         OBJECTS  { alarmSeverity, alarmState,ifAlias }  
--         STATUS  current
--         DESCRIPTION
--         "This Trap indicates that a loopback has 
--          been initiated by local device on ATM uplink interface
--          towards remote ATM equipment, by sending OAM cells."
--         ::= { radSysAtmEvents  15 }


-- VP Layer Traps

-- atmVplVpi have MAX-ACCESS "not-accessible"
-- and cannot be referenced from NOTIFICATION-TYPE clause
-- in SMIV2 so they where removed from following caluses.
-- Dovi Korngut (28/6/00).

atmAceAlarmVpContinuityLoss NOTIFICATION-TYPE
      OBJECTS  { alarmSeverity, alarmState, ifAlias }  
      STATUS  current
      DESCRIPTION
	  	"This trap indicates Loss of Continuity Check on a VP Connection."
      ::= { radSysAtmEvents  40 }


atmAceAlarmVpAISReception NOTIFICATION-TYPE
      OBJECTS  { alarmSeverity, alarmState, ifAlias }  
      STATUS  current
      DESCRIPTION
	  	"This trap indicates AIS Reception on a VP Connection."
      ::= { radSysAtmEvents  41 }


atmAceAlarmVpRDIReception NOTIFICATION-TYPE
      OBJECTS  { alarmSeverity, alarmState, ifAlias }  
      STATUS  current
      DESCRIPTION
	  	"This trap indicates RDI Reception on a VP Connection."
      ::= { radSysAtmEvents  42 }


atmAceAlarmVpErroredCells NOTIFICATION-TYPE
      OBJECTS  { alarmSeverity, alarmState, ifAlias }  
      STATUS  current
      DESCRIPTION
	  	"This trap indicates Errored Cells on a VP Connection reported by PM."
      ::= { radSysAtmEvents  43 }


atmAceAlarmVpLostCells NOTIFICATION-TYPE
      OBJECTS  { alarmSeverity, alarmState, ifAlias }  
      STATUS  current
      DESCRIPTION
	  	"This trap indicates Lost Cells on a VP Connection reported by PM."
      ::= { radSysAtmEvents  44 }


atmAceAlarmVpMisinsertedCells NOTIFICATION-TYPE
      OBJECTS  { alarmSeverity, alarmState, ifAlias }  
      STATUS  current
      DESCRIPTION
	  	"This trap indicates Misinserted Cells on a VP Connection 
	  	reported by PM."
      ::= { radSysAtmEvents  45 }

atmAceAlarmVpUAS NOTIFICATION-TYPE
      OBJECTS  { alarmSeverity, alarmState, ifAlias }  
      STATUS  current
      DESCRIPTION
	  	"This trap is sent upon UAS start or end per VP."
      ::= { radSysAtmEvents  46 }

atmAceAlarmVpLoopback NOTIFICATION-TYPE
      OBJECTS  { alarmSeverity, alarmState, ifAlias }  
      STATUS  current
      DESCRIPTION
	  	"This trap is sent upon OAM LoopBack fail status per VP."
      ::= { radSysAtmEvents  47 }

atmAceAlarmVpGCRAViolation NOTIFICATION-TYPE
      OBJECTS  { alarmSeverity, alarmState, ifAlias }
      STATUS  current
      DESCRIPTION
	  	"This trap indicates GCRA violation on a VP Connection
		reported by UPC device."
      ::= { radSysAtmEvents  48 }


-- VC Layer Traps

-- atmVclVpi and atmVclVci have MAX-ACCESS "not-accessible"
-- and cannot be referenced from NOTIFICATION-TYPE clause
-- in SMIV2 so they where removed from following caluses.
-- Dovi Korngut (28/6/00).

atmAceAlarmVcContinuityLoss NOTIFICATION-TYPE
      OBJECTS  { alarmSeverity, alarmState, ifAlias }  
      STATUS  current
      DESCRIPTION
	  	"This trap indicates  Loss of Continuity Check on a VC Connection."
      ::= { radSysAtmEvents  56 }

atmAceAlarmVcAISReception NOTIFICATION-TYPE
      OBJECTS  { alarmSeverity, alarmState, ifAlias }  
      STATUS  current
      DESCRIPTION
	  	"This trap indicates AIS Reception on a VC."
      ::= { radSysAtmEvents  57 }

atmAceAlarmVcRDIReception NOTIFICATION-TYPE
      OBJECTS  { alarmSeverity, alarmState, ifAlias }  
      STATUS  current
      DESCRIPTION
	  	"This trap indicates RDI Reception on a VC Connection."
      ::= { radSysAtmEvents  58 }

atmAceAlarmVcErroredCells NOTIFICATION-TYPE
      OBJECTS  { alarmSeverity, alarmState, ifAlias }  
      STATUS  current
      DESCRIPTION
	  	"This trap indicates Errored Cells on a VC Connection reported by PM."
      ::= { radSysAtmEvents  59 }

atmAceAlarmVcLostCells NOTIFICATION-TYPE
      OBJECTS  { alarmSeverity, alarmState, ifAlias }  
      STATUS  current
      DESCRIPTION
	  	"This trap indicates Lost Cells on a VC Connection reported by PM."
      ::= { radSysAtmEvents  60 }

atmAceAlarmVcMisinsertedCells NOTIFICATION-TYPE
      OBJECTS  { alarmSeverity, alarmState, ifAlias }  
      STATUS  current
      DESCRIPTION
	  	"This trap indicates Misinserted Cells on a VC Connection reported 
	  	by PM."
      ::= { radSysAtmEvents  61 }

atmAceAlarmVcUnexpectedCell NOTIFICATION-TYPE
      OBJECTS  { alarmSeverity, alarmState, ifAlias }  
      STATUS  current
      DESCRIPTION
	  	"This trap indicates an unexpected cell from user or network port."
      ::= { radSysAtmEvents  62 }

atmAceAlarmVcUAS NOTIFICATION-TYPE
      OBJECTS  { alarmSeverity, alarmState, ifAlias }  
      STATUS  current
      DESCRIPTION
	  	"This trap is sent upon UAS start or end per VC."
      ::= { radSysAtmEvents  63 }

atmAceAlarmVcLoopback NOTIFICATION-TYPE
      OBJECTS  { alarmSeverity, alarmState, ifAlias }  
      STATUS  current
      DESCRIPTION
	  	"This trap is sent upon OAM LoopBack fail status per VC."
      ::= { radSysAtmEvents  64 }

atmAceAlarmVcGCRAViolation NOTIFICATION-TYPE
      OBJECTS  { alarmSeverity, alarmState, ifAlias }
      STATUS  current
      DESCRIPTION
	  	"This trap indicates GCRA violation on a VC Connection
		reported by UPC device."
      ::= { radSysAtmEvents  65 }

-- number 80 and up are saved for IMA traps

-- END



-- SENDING OAM VC-AIS CELLS ??
--      This message appears when the LA-110 starts/stop
--      transmitting OAM cells of type VC-AIS to the 
--      ATM network the alarm description
--      will be followed with the relevant VP/VC
--

-- SENDING OAM VC-RDI CELLS  ???
--      This message appears when the LA-110 start/stop 
--      transmitting OAM cells of type VC-RDI to the 
--      ATM network the alarm description will be 
--      followed with the relevant VP/VC
-- 



-- 
-- file :D:\Synergy\WorkArea\545\mib_rad\txt\hybces.txt
-- 
-- *************************
-- file  : hybCES.txt
--
-- available for ACE20.
--Version:   1.0
--Date:      10/11/97
--By:        Ilana Schvetz
--File:      v:\doc\rdv\mib\ver470\atm\hybCES.txt 

-- Last Update: 08-Mar-01 By Ilana Schvetz
-- Copyright 1996 RAD Data Communications, Ltd.
-- All Rights Reserved.

-- *******************************************************
--          Protocol  CES Vcls statistics
-- *******************************************************

--atmGen OBJECT IDENTIFIER ::= { radAtm 2 }

--atmPerfHistory OBJECT IDENTIFIER ::= { atmGen 1 }

--atmPvcPerformance OBJECT IDENTIFIER ::= { atmPerfHistory 2 }

--atmVcPerformance OBJECT IDENTIFIER ::= { atmPvcPerformance 2 }

atmCESAAL1StatsTable OBJECT-TYPE
      SYNTAX  SEQUENCE OF AtmCESAAL1StatsEntry
      MAX-ACCESS   not-accessible
      STATUS  current
      DESCRIPTION
       " This table shows statistics of the structured Circuit-Emulation connections."
      ::= { atmVcPerformance  5 }

atmCESAAL1StatsEntry OBJECT-TYPE
      SYNTAX  AtmCESAAL1StatsEntry
      MAX-ACCESS   not-accessible
      STATUS  current
      DESCRIPTION
      "defines an entry in the atmCESAAL1StatsTable"
      INDEX  { ifIndex, atmVclVpi, atmVclVci }
      ::= { atmCESAAL1StatsTable 1}

AtmCESAAL1StatsEntry ::=
      SEQUENCE {
      atmCESAAL1SeqErrors
           Counter32,
      atmCESAAL1HdrErrors
           Counter32,
      atmCESAAL1PointerReframes
           Counter32,
      atmCESAAL1BufUnderflows
           Counter32,
      atmCESAAL1BufOverflows
           Counter32
      }

atmCESAAL1SeqErrors OBJECT-TYPE
      SYNTAX  Counter32  
      MAX-ACCESS  read-only
      STATUS  current
      DESCRIPTION
      "number of cells discarded due to wrong sequence number "
      ::= { atmCESAAL1StatsEntry 1 }

atmCESAAL1HdrErrors OBJECT-TYPE
      SYNTAX  Counter32  
      MAX-ACCESS  read-only
      STATUS  current
      DESCRIPTION
      "number of cells discarded due to bad AAL1 header error.
       this include correctable and uncorrectable CRC, plus bad parity. "
      ::= { atmCESAAL1StatsEntry 2 }

atmCESAAL1PointerReframes OBJECT-TYPE
      SYNTAX  Counter32  
      MAX-ACCESS  read-only
      STATUS  current
      DESCRIPTION
      "number of events in which the AAL1 reassembler found that an SDT pointer isn't
       where it is expected, and the pointer must be reacquired. "
      ::= { atmCESAAL1StatsEntry 3 }

atmCESAAL1BufUnderflows OBJECT-TYPE
      SYNTAX  Counter32  
      MAX-ACCESS  read-only
      STATUS  current
      DESCRIPTION
      "number of buffer underflows events. "
      ::= { atmCESAAL1StatsEntry 4 }

atmCESAAL1BufOverflows OBJECT-TYPE
      SYNTAX  Counter32  
      MAX-ACCESS  read-only
      STATUS  current
      DESCRIPTION
      "number of buffer overflows events. "
      ::= { atmCESAAL1StatsEntry 5 }


-- 
-- file :D:\Synergy\WorkArea\545\mib_rad\txt\confvcta.txt
-- 
-- file  : ConfVcTable.txt
--
--Version:   1.0
--Date:      12.11.97
--By:        Ilana Schvetz
--File:      v:\doc\rdv\mib\ver540\atm\ConfVcTable.txt 
 
--Last Update: 19-Feb-2008 by Shay Harari

-- *******************************************************
--          Configuration Vc Table
-- *******************************************************

--atmNte	 OBJECT IDENTIFIER ::= { radAtm 3 }
--atmNtePrt		OBJECT IDENTIFIER ::= { atmNte 2 }
--atmNtePrtConfig		OBJECT IDENTIFIER ::= { atmNtePrt 1 }


atmNteConfVcTable OBJECT-TYPE
              SYNTAX  SEQUENCE OF AtmNteConfVcEntry
              MAX-ACCESS  not-accessible
              STATUS  current
              DESCRIPTION
                      "The ATM VC configuration table.
                       The table is an extension to the atmVclTable of
                       RFC-2515."
              ::= { atmNtePrtConfig 4 }

          atmNteConfVcEntry OBJECT-TYPE
              SYNTAX  AtmNteConfVcEntry
              MAX-ACCESS  not-accessible
              STATUS  current
              DESCRIPTION
                      "An entry in the ATM VC configuration table.
                       ifIndex of the ATM layer."
              INDEX   { ifIndex , atmVclVpi, atmVclVci}
              ::= { atmNteConfVcTable 1 }

          AtmNteConfVcEntry ::=
              SEQUENCE {
				atmConfVcPolicing            		INTEGER,
				atmConfVcCCAdminStatus       		INTEGER,
				atmConfVcLoopbackAdminStatus 		INTEGER,
			    atmConfVcLoopbackSinkAddress 		OCTET STRING,
			    atmConfVcCongestionControl   		OCTET STRING,
                atmConfVcCCDirection		 		INTEGER,
                atmConfVcCreationTime        		DateAndTime,
                atmConfVcOamSupport          		INTEGER,
				atmConfVcCCActivationCtrl    		INTEGER,
				atmConfVcCCOperStatus        		INTEGER,
				atmConfVcLoopbackTraffic     		INTEGER,
				atmConfVcLoopbackFailureInd	 		INTEGER,
				atmConfVcLoopbackFailureThreshold	Integer32,
			    atmConfVcOamDirection        		INTEGER,
				atmConfVcName				 		DisplayString,
				atmConfVcConnected           		INTEGER,
				atmConfVcOamDescrIndex	 	 		Integer32,
				atmConfVcNoOfUsages					Unsigned32
              }

          atmConfVcPolicing OBJECT-TYPE
              SYNTAX  INTEGER { 
		         none(1),
		         police(2),
		         monitor(3),
		         shaping(4),
                 policingAndShaping(5), 
		         notApplicable(255)
	          }
              MAX-ACCESS  read-write
              STATUS  current
              DESCRIPTION
              "Policing method desired for this VCL."
              ::= { atmNteConfVcEntry 1 }

          atmConfVcCCAdminStatus OBJECT-TYPE
             SYNTAX  INTEGER {
		        up(2), 
             	down(3), 
		        source(4),       -- agent send Oam CC cells 
		        sink(5),         -- agent check received Oam CC cells
                listenToActivationCells (6),
                originateActivationCells(7)     
                            } 
             MAX-ACCESS read-write
             STATUS current
             DESCRIPTION
             "up(2) - Activate Continuity Check (CC).
              down(3) - Deactivate CC.
		      source(4)      - Activate OAM CC(Continuity Check) of local agent
             			( start sending Oam cells to the remote side ).
      		  sink(5)  - Activate CC of remote agent ( start receiving Oam cells from
      		 	         remote side).
      		  listenToActivationCells (6) - Passive listener till gets an activation request
              originateActivationCells(7) - Sands Activation cell according to atmConfVcCCDirection."
             ::= {atmNteConfVcEntry 2}

          atmConfVcLoopbackAdminStatus OBJECT-TYPE
             SYNTAX INTEGER {
		      up(2),
		      down(3),
		      llid(4),
		      segment(5),
		      endToEnd(6),
		      segmentLlid(7),
		      endToEndLlid(8)
	         } 
             MAX-ACCESS read-write
             STATUS current
             DESCRIPTION
             "up(2) - Start loopback OAM cells.
             down(3) - Stop sending loopback OAM cells.
             
             For ace2002:
             up(2)   - Transmitting LB cells with llid all ones 
                       (i.e. FFFF..FF)
             down(3) - Not transmitting LB cells. 
             llid(4) - Transmitting LB cells with llid indicated 
                       in the address field.
             segment(5) - Transmitting Segment LB cells with llid
                       all ones. 
             endToEnd(6) - Transmitting End to End LB cells with llid
                       all ones. 
             segmentLlid(7) - Transmitting Segment LB cells with
                       llid indicated in the address field.  
             endToEndLlid(8) - Transmitting LB cells with llid
                       indicated in the address field.  
             
             This parameter value might be in conflict with 
             atmConfVcOamSupport value, since this parameter is for LB, 
             while atmConfVcOamSupport is for any other OAM cells."                   
             ::= {atmNteConfVcEntry 3}

	     atmConfVcLoopbackSinkAddress OBJECT-TYPE
             SYNTAX OCTET STRING  (SIZE(2..20))
             MAX-ACCESS read-write
             STATUS current
             DESCRIPTION
             "Destination address.
              For ace101: 2 bytes are used.
              For ace2002: 16 bytes are used."
             ::= {atmNteConfVcEntry 4}

	     atmConfVcCongestionControl OBJECT-TYPE
             SYNTAX OCTET STRING
             MAX-ACCESS read-write
             STATUS current
             DESCRIPTION
             "Each bit indicates a selection of one option 
                    as the following description.  All combinations 
                    are possible and legal.
                    The codes are: 
                    1 - EPD
                    2 - CLP
                    4 - EFCI.
                    For ace2002:
                    1 - Packet Discard."
             ::= {atmNteConfVcEntry 5}

         atmConfVcCCDirection OBJECT-TYPE
             SYNTAX  INTEGER {
		    	both  (2),
		    	none  (3), 
                source(4),      
                sink  (5)     
                       } 
             MAX-ACCESS read-write
             STATUS current
             DESCRIPTION
             "both(2)  - Agent sends OAM CC cells and checks received OAM CC cells.
			  none(3) - Agent does not send and does not check received OAM CC cells.
              source(4)- Agent sends OAM CC cells.
 		      sink(5)  - Agent checks received OAM CC cells."    
             ::= {atmNteConfVcEntry 6}

         atmConfVcCreationTime OBJECT-TYPE
         SYNTAX   DateAndTime
         MAX-ACCESS   read-only
         STATUS   current
         DESCRIPTION
         "A date-time in which the VC was created."
         ::= { atmNteConfVcEntry 7 }

         atmConfVcOamSupport OBJECT-TYPE
             SYNTAX  INTEGER {
                  intermediate(1),
                  segmentTermination(2),
                  endToEndTermination(3),
                  endToEndAndSegment(4)
              }
             MAX-ACCESS  read-write
             STATUS  current
             DESCRIPTION
             "OAM support mode, which determines the device location
              in a segment wise.
                              
              endToEndAndSegment -  In this mode the OAM cells are generated 
                                 before the ABM (ATM Buffer Manager), so 
                                 that the PCR and CDVT will not be affected."
             ::= { atmNteConfVcEntry 8 }

         atmConfVcCCActivationCtrl OBJECT-TYPE
             SYNTAX  INTEGER {
		             manual(1), 
                     activator(2), 
		             listener(3) 
                            } 
             MAX-ACCESS read-write
             STATUS current
             DESCRIPTION  
             "manual(1) - CC Activation process is disable
              activator(2) - ACE-101 initiate  CC Activation process
              listener(3) - ACE-101 wait to CC Activation request from remote side."
             ::= { atmNteConfVcEntry 9 }
    
          atmConfVcCCOperStatus OBJECT-TYPE
             SYNTAX  INTEGER {
					 initial(1),
		             up(2), 
            	     down(3), 
		             source(4),    -- agent send Oam CC cells 
		             sink(5),       -- agent check received Oam CC cells
					 both (8),
		 			 timeout (9), 
				     denied (10),
					 conflict (11),
					 manual (12)
                            } 
             MAX-ACCESS read-only
             STATUS current
             DESCRIPTION
             "initial (1) - The CC activation process is not started.
              up (2) -  Continuity Check (CC) activated.
              down (3) - CC deactivated.
              source (4)  -  OAM CC(Continuity Check) of local agent activated.
              sink (5)  -  OAM CC of remote agent activated.
			  both (8) - OAM CC of local and remote agents activation.
		      timeout (9) - Timeout occured on receiving answer from
                           the remote agent.
		      denied  (10) - CC activation process rejected by remote agent.
		      conflict (11) - local and remote sides requested activation
                              simultaneously.
			  manual (12) - OAM CC of local agent activated manually.
			 	"
             ::= { atmNteConfVcEntry 10 }

	      atmConfVcLoopbackTraffic OBJECT-TYPE
               SYNTAX INTEGER { off(2), on(3) } 
               MAX-ACCESS read-write
               STATUS current
               DESCRIPTION
               "This parameter has both command and status meanings: 
                off(2) - Set to 'Off' will Stop traffic loop. Getting this
                        value means that the loop is not running.
                on (3) - Set to 'On' will start traffic loop. Getting 
              	          this value means that the loop is currently running."
             ::= {atmNteConfVcEntry 11}

	      atmConfVcLoopbackFailureInd OBJECT-TYPE
             		SYNTAX INTEGER { 
             		disabled(2), 
             		segmentAis(3),
             		segmentRdi(4),
             		segmentAisAndRdi(5),
             		endToEndAis(6),
             		endToEndRdi(7),
             		endToEndAisAndRdi(8)
             		} 
             		MAX-ACCESS read-write
             		STATUS current
             		DESCRIPTION
    "This object allows user to define the Indication that will be created upon 
     a LB cell failure.
     disabled(2) - no indication will be created.
     segmentAis(3) - will cause Tx of a segment AIS.
     segmentRdi(4) - will cause Tx of a segment RDI.
     segmentAisAndRdi(5) - will cause Tx of a segment AIS & RDI. 
     endToEndAis(6) - will cause Tx of an End to End AIS.
     endToEndRdi(7)	- will cause Tx of an End to End RDI.
     endToEndAisAndRdi(8) - will cause Tx of an End to End AIS & RDI.
     Default: disabled(2)."
             ::= {atmNteConfVcEntry 12}

	atmConfVcLoopbackFailureThreshold OBJECT-TYPE
             		SYNTAX Integer32  
             		MAX-ACCESS read-write
             		STATUS current
             		DESCRIPTION
    "The number of the LB failures before starting transmission of the 
    Indication defined by atmConfVcLoopbackFailureInd.
    Range: 1..16. Default: 1."
             ::= {atmNteConfVcEntry 13}

atmConfVcOamDirection OBJECT-TYPE
	SYNTAX  INTEGER {
		notApplicable  (1), 
		downStream     (2),      
		upStream       (3)     
        } 
	MAX-ACCESS read-write
	STATUS current
	DESCRIPTION
	"The direction of OAM cell insertion.
	 downStream(2) - The OAM cell will be inserted in downStream.     
	 upStream(3)   - The OAM cell will be inserted in upStream."    
	::= {atmNteConfVcEntry 14}

atmConfVcName OBJECT-TYPE
	SYNTAX  DisplayString 
    MAX-ACCESS read-write
	STATUS current
	DESCRIPTION
	"VC Name."    
    ::= {atmNteConfVcEntry 15}

atmConfVcConnected OBJECT-TYPE
	SYNTAX  INTEGER {
		notConnected	(1), 
		mng				(2),      
		bridgePort		(3),
		ds0Bundle		(4),
		atm				(5),
		pw				(6),
		routerInterface	(7),
		qos             (8),
		other           (9),
		logicalMac		(10)
		        } 
	MAX-ACCESS read-write		-- Originally read-only
	STATUS current
	DESCRIPTION
	"This object indicates whether this VC is connected
	 and if connected, what is it connected to.
	 Originally, it was read-only."    
	::= {atmNteConfVcEntry 16}

atmConfVcOamDescrIndex OBJECT-TYPE
	SYNTAX  Integer32 
	MAX-ACCESS read-write
	STATUS current
	DESCRIPTION
	"This parameter indicates the VCL's OAM Descriptor index,
	 according to the OAM Descriptor Configuration Table."    
	::= {atmNteConfVcEntry 17}

atmConfVcNoOfUsages OBJECT-TYPE
	SYNTAX		Unsigned32
	MAX-ACCESS	read-only
	STATUS		current
	DESCRIPTION
		"This object indicates the number of times this VCL is used."
	::= { atmNteConfVcEntry 18 } 


 -- 
-- file :D:\Synergy\WorkArea\545\mib_rad\txt\ace20.txt
-- 
-- file  : Ace20_v3_5.mib
--
--ACE20-MIB
--
--DEFINITIONS ::= BEGIN

--Title:     RAD's ACE20 PRODUCT MIB
--Version:   3.0
--Date:      01/06/99
--By:        Eyal Sadovsky & Isac Winter
--File:      v:\doc\rdv\mib\ver510\atm\Ace20.txt (1st version)

--Last Update:    16-April-2007 by Yig'al Hachmon

-- IMPORTS
--        OBJECT-TYPE , OBJECT-IDENTITY ,
--        Integer32 , Counter32              FROM SNMPv2-SMI

--        TimeStamp, 
--        TEXTUAL-CONVENTION, DisplayString  FROM SNMPv2-TC

--        ifIndex                            FROM SNMPv2-TC

--        atmVclVpi, atmVclVci,
--        AtmTrafficDescrParamIndex		   FROM ATM-MIB

--        frPVCEndptDLCIIndex                FROM FRNETSERV-MIB;

   --   TRAP-TYPE                          FROM RFC-1215
   --     radAtm, agnLed, agnIndication      FROM RAD-GEN-MIB;


   --RowStatus ::= TEXTUAL-CONVENTION
   --    STATUS       current
   --    DESCRIPTION
   --    "."
  --     SYNTAX  INTEGER {
  --        active(1),
--				  notInService(2),
--				  notReady(3),
--				  createAndGo(4),
--				  createAndWait(5),
--				  destroy(6)
--                       }


atmSu           OBJECT IDENTIFIER ::= { radAtm 4 } -- RAD ATM Service Unit
atmSuSystem   OBJECT IDENTIFIER ::= { atmSu 1 }   -- agent system level configuration

-- ***********************************************************************
--   RAD System Software Group
--
--   This table contains software verions parameters.
-- ***********************************************************************

atmSuSystemSwOperStatus OBJECT-TYPE
      SYNTAX INTEGER {
            disable (1) ,
            enable  (2)
      }
      MAX-ACCESS  read-write
      STATUS current
      DESCRIPTION
      "This value indicates if tftp_write operation (for downloading
       software from an external host) is allowed by the agent. "
      DEFVAL { enable }
      ::= { atmSuSystem 1 }

atmSuSystemSwSwitchVersionsCmd OBJECT-TYPE
      SYNTAX INTEGER {
           notActive (1) ,
           active    (2)
      }
      MAX-ACCESS   read-write
      STATUS  current
      DESCRIPTION
       "This command is used to switch beetween software versions stored
        in the flash. setting this value to active will reset the agent
        and re-activate it with the new version ( only if new version is valid).
        on get-request this value will be always notActive. "
      ::= { atmSuSystem 2 }


-- *******************************************************
-- agent Alarms definitions - two alarms table defined :
-- 1. History Table which hold a buffer contains history events.
-- 2. Mandatory Table hold information of all mandatory alarms
--
-- the following alarms ifIndex defined :
-- 0. system alarms
-- 1. physical DS1 alarms - T1/E1 layer
-- 2. ATM alarms
-- 5. ATM-DXI / Frame-Relay alarms
-- *******************************

atmSuSystemHistoryAlrTable OBJECT-TYPE
      SYNTAX SEQUENCE OF AtmSuSystemHistoryAlrEntry
      MAX-ACCESS  not-accessible
      STATUS current
      DESCRIPTION
      "buffer contain history buffer of agent alarms."
      ::= { atmSuSystem 3 }

atmSuSystemHistoryAlrEntry OBJECT-TYPE
      SYNTAX AtmSuSystemHistoryAlrEntry
      MAX-ACCESS  not-accessible
      STATUS current
      DESCRIPTION
       " Agent alarm history list entry."
      INDEX  { atmSuSystemHistoryAlrIndex }
      ::= { atmSuSystemHistoryAlrTable 1}

AtmSuSystemHistoryAlrEntry ::=
      SEQUENCE {
      atmSuSystemHistoryAlrIndex
	     Integer32,
      atmSuSystemHistoryAlrIfIndex
	     Integer32,
      atmSuSystemHistoryAlrDescription
         DisplayString,
      atmSuSystemHistoryAlrStatus
	     INTEGER,
      atmSuSystemHistoryAlrOccurrenceTime
         DisplayString,
	  atmSuSystemHistoryAlrVpi
	  	 Integer32,
	  atmSuSystemHistoryAlrVci
	  	 Integer32

      }

atmSuSystemHistoryAlrIndex OBJECT-TYPE
      SYNTAX  Integer32
      MAX-ACCESS   read-only
      STATUS  current
      DESCRIPTION
      "A unique number to identify an entry in the history alarm table."
      ::= { atmSuSystemHistoryAlrEntry 1 }

atmSuSystemHistoryAlrIfIndex OBJECT-TYPE
      SYNTAX  Integer32
      MAX-ACCESS   read-only
      STATUS  current
      DESCRIPTION
      "This value indicates the port on which the alarms occured.
       configuration(system) alarms have port index equal to 0. "
      ::= { atmSuSystemHistoryAlrEntry 2 }

atmSuSystemHistoryAlrDescription OBJECT-TYPE
      SYNTAX  DisplayString (SIZE (0..255))
      MAX-ACCESS   read-only
      STATUS  current
      DESCRIPTION
      "This attribute is a text description of the alarm.
       The alarm descipion include alarm code and alarm text."
     ::= { atmSuSystemHistoryAlrEntry 3 }

atmSuSystemHistoryAlrStatus OBJECT-TYPE
      SYNTAX  INTEGER {
            on      (1),
            off     (2),
			event   (3)
      }
      MAX-ACCESS   read-only
      STATUS  current
      DESCRIPTION
      "This attribute indicates the status of the alarm."
      ::= { atmSuSystemHistoryAlrEntry 4 }

atmSuSystemHistoryAlrOccurrenceTime OBJECT-TYPE
      SYNTAX   DisplayString
      MAX-ACCESS    read-only
      STATUS   current
      DESCRIPTION
      "This value indicates the  date and time of the occurrence 
       of the event that caused this alarm. 
       Date and time format: YYYY-MM-DD, HH:MM:SS "
      ::= { atmSuSystemHistoryAlrEntry 5 }


atmSuSystemHistoryAlrVpi  OBJECT-TYPE
      SYNTAX      Integer32
      MAX-ACCESS  read-only
      STATUS      current
      DESCRIPTION
      "This value indicates the  ATM VPI of the connection
       associated with the event that caused this alarm. 
       When not applicable, value is 0"
      ::= { atmSuSystemHistoryAlrEntry 6 }
 
atmSuSystemHistoryAlrVci OBJECT-TYPE
      SYNTAX        Integer32
      MAX-ACCESS    read-only
      STATUS        current
      DESCRIPTION
      "This value indicates the ATM VCI of the connection 
       associated with with the event that caused this alarm. 
       When not applicable, value is 0 "
      ::= { atmSuSystemHistoryAlrEntry 7 }


atmSuSystemClearHistoryAlrListCmd  OBJECT-TYPE
      SYNTAX  INTEGER
	      {
    		off(1),
	    	on (2)
	      }
      MAX-ACCESS   read-write
      STATUS  current
      DESCRIPTION
      "Setting this attribute to ON, enforce a  clear operation on
       the agent history event buffer .
       On reading, attribute will always get status 'off' ."
      ::= { atmSuSystem 4 }


atmSuSystemCurrentAlrTable OBJECT-TYPE
      SYNTAX SEQUENCE OF AtmSuSystemCurrentAlrEntry
      MAX-ACCESS  not-accessible
      STATUS current
      DESCRIPTION
      "table which contains all alarms Currently active ( status ON )
       in the agent."
      ::= { atmSuSystem 5 }

atmSuSystemCurrentAlrEntry OBJECT-TYPE
      SYNTAX AtmSuSystemCurrentAlrEntry
      MAX-ACCESS  not-accessible
      STATUS current
      DESCRIPTION
       " Agent alarm list entry."
      INDEX  { atmSuSystemCurrentAlrIndex }
      ::= { atmSuSystemCurrentAlrTable 1}

AtmSuSystemCurrentAlrEntry ::=
      SEQUENCE {
     atmSuSystemCurrentAlrIndex
	    Integer32,
     atmSuSystemCurrentAlrIfIndex
	    Integer32,
     atmSuSystemCurrentAlrDescription
        DisplayString
      }

atmSuSystemCurrentAlrIndex OBJECT-TYPE
      SYNTAX  Integer32
      MAX-ACCESS   read-only
      STATUS  current
      DESCRIPTION
      "A unique number to identify an entry in the Current alarms table."
      ::= { atmSuSystemCurrentAlrEntry 1 }

atmSuSystemCurrentAlrIfIndex OBJECT-TYPE
      SYNTAX  Integer32
      MAX-ACCESS   read-only
      STATUS  current
      DESCRIPTION
      "This value indicates the port on which the alarms occured.
       configuration alarms have port index equal to 0. "
      ::= { atmSuSystemCurrentAlrEntry 2 }

atmSuSystemCurrentAlrDescription OBJECT-TYPE
      SYNTAX  DisplayString (SIZE (0..255))
      MAX-ACCESS   read-only
      STATUS  current
      DESCRIPTION
      "This attribute is a text description of the alarm.
       The alarm descipion include alarm code and alarm text."
     ::= { atmSuSystemCurrentAlrEntry 3 }


-- *******************************************************
--       Agent  Config  Managers  Group
-- *******************************************************

atmSuSystemILMICommunity OBJECT-TYPE
      SYNTAX   DisplayString
      MAX-ACCESS  read-write
      STATUS   current
      DESCRIPTION
       "Community string for ILMI requests. 10 chars."
      ::= { atmSuSystem 6 }

atmSuSystemTrapMaxManagers OBJECT-TYPE
      SYNTAX Integer32
      MAX-ACCESS  read-only
      STATUS current
      DESCRIPTION
       "The maximum number of managers that can be registered
        for receiving traps and sending requests."
      DEFVAL { 10 }
      ::= { atmSuSystem 7 }


-- *******************************************************
--       Agent AAL1 / AAL2 selection
-- *******************************************************

 atmSuSystemAalSelection OBJECT-TYPE
	  SYNTAX  INTEGER
	  {
	   notApplicable (1),
	   aal2  (2),
       aal1  (3)
       }
      MAX-ACCESS  read-write
      STATUS  current
      DESCRIPTION
      "Select ATM adaptation layers AAL1 or AAL2
       Applicable for LA-140"
	  ::= { atmSuSystem 8 }

-- *******************************************************
--       Agent u-Law selection
-- *******************************************************

atmSuSystemCodingLaw OBJECT-TYPE
	  SYNTAX  INTEGER
	  {
	   notApplicable (1),
	   aLaw  (2),
       uLaw  (3)
       }
      MAX-ACCESS  read-write
      STATUS  current
      DESCRIPTION
      "This attribute indicates the Method/Law for decoding/encoding the voice
       information.
       aLaw  (2) is the standard Law for E1 links.
       uLaw  (3) is the standard Law for T1 links.

       Coding law is applicable for all the ports in the system"
	  ::= { atmSuSystem 9 }



-- *******************************************************
--       Agent ISDN selection
-- *******************************************************

atmSuSystemISDNDataLinkActivation OBJECT-TYPE
	  SYNTAX  INTEGER
	  {
	   notApplicable (1),
	   nonPermanent  (2),
       permanent     (3)
       }
      MAX-ACCESS  read-write
      STATUS  current
      DESCRIPTION
      "This attribute indicates data link aactivation for all 
       ISDN ports in the system.
       nonPermanent (2) =  non permanent data link activation
       permanent    (3) =  permanent data link activation"
	  ::= { atmSuSystem 10 }


-- *******************************************************
--       Agent ATM Jitter Buffer
-- *******************************************************

atmSuSystemJitterBuffer OBJECT-TYPE
	  SYNTAX  Integer32
      MAX-ACCESS  read-write
      STATUS  current
      DESCRIPTION
        "The field is set in ms and sets the jitter buffer size. 
         The jitter buffer adapts the size of the LA140 traffic 
         to the cdv (cell  delay variation) of the ATM network."
	  ::= { atmSuSystem 11 }


-- *******************************************************
--       Agent ATM mode of operation
-- *******************************************************


atmSuSystemOperMode OBJECT-TYPE

	  SYNTAX  INTEGER
	  {
	   notApplicable (1),
	   ima           (2),
       miniDslam     (3),
	   multipair     (4)
       }
      MAX-ACCESS  read-write
      STATUS  current
      DESCRIPTION
        "The field indicates device mode of operation:
         ima (2) = Inverse Multiplex ATM - ATM traffic is 
		           distributed between links in IMA group.   
         miniDSLAM (3) => each link serves as separate  
                          ATM interface. (applcable for LA-104)
         multiPair (4)  - 'SHDSL.bis' multi-pair bonding serve as ATM"
	  ::= { atmSuSystem 12 }

atmSuSystemDSPGain OBJECT-TYPE
 	  SYNTAX  Integer32
      MAX-ACCESS  read-write
      STATUS  current
      DESCRIPTION
      "This object indicates DSP Gain.
       Range of possible values is -12....12.
       For LA-110 suset of this range is supported. "
	  ::= { atmSuSystem 13 }

atmSuSystemBundlesApplication OBJECT-TYPE
 	  SYNTAX  OCTET STRING 
      MAX-ACCESS  read-write
      STATUS  current
      DESCRIPTION
      "This object defines application of each bundle .
	   each bundle is represented by two bits:
	   00 - TDM over ATM
	   01 - Frame Relay.
	   bit 0,1 represents bundle 1
	   but 2,3 represents bundle 2, etc..."
	  ::= { atmSuSystem 14 }

atmSuSystemMsOperMode  OBJECT-TYPE
	  SYNTAX  INTEGER
	  {
	   notApplicable (1),
	   msOverAtm     (2),
       msOverPsn     (3)
       }
      MAX-ACCESS  read-write
      STATUS  current
      DESCRIPTION
        "The field indicates device mode of operation:
         msOverAtm (2) = Multi Service over ATM. 
         msOverPsn (3) = Multi Service over PSN (using Pseudo Wires)"
	  ::= { atmSuSystem 15 }


atmSuSystemPwTransportLayer  OBJECT-TYPE
	  SYNTAX  INTEGER
	  {
	   notApplicable (1),
	   atm           (2),
       eth           (3)
       }
      MAX-ACCESS  read-write
      STATUS  current
      DESCRIPTION
        "The field indicates device pseudo wire Transport Layer, 
         when atmSuSystemMsOperMode = msOverPsn."
	  ::= { atmSuSystem 16 }



-- ****************************************************************
-- ****************************************************************
--                    agent ports definitions
-- ****************************************************************
-- ****************************************************************

atmSuPort      OBJECT IDENTIFIER ::= { atmSu 2 } -- agent ports definitions


-- ********************************
--  global data port definitions
-- ********************************

--
-- the following table uses parameters which define the physical data port
-- and they are the same for FR and ATM-DXI interfaces
--
atmSuPortDataCnfgTable OBJECT-TYPE
      SYNTAX  SEQUENCE OF AtmSuPortDataCnfgEntry
      MAX-ACCESS   not-accessible
      STATUS  current
      DESCRIPTION
       " Data Port global configuration table.
         this table include parametes which are common to the physical port
         and not depend on whether the port interface is Frame-Relay or
         ATM-DXI."
      ::= { atmSuPort 1 }

atmSuPortDataCnfgEntry OBJECT-TYPE
      SYNTAX  AtmSuPortDataCnfgEntry
      MAX-ACCESS   not-accessible
      STATUS  current
      DESCRIPTION
      "the entries at this table describes the configuration
	   of the Data-Port."
      INDEX { ifIndex }
      ::= { atmSuPortDataCnfgTable 1}

AtmSuPortDataCnfgEntry ::=
      SEQUENCE {
      atmSuPortDataApplication
	          INTEGER,
      atmSuPortDataRate
	          INTEGER,
      atmSuPortDataDCD
	          INTEGER,
      atmSuPortDataMode
	          INTEGER,
      atmSuPortDataCRC
              INTEGER,
      atmSuPortDataClock
	          INTEGER,
      atmSuPortDataMaxNoOfConns
            Integer32,
      atmSuPortDataConfNoOfConns
            Integer32,
      atmSuPortDataIdleCode
            Integer32,
	  atmSuPortDataInterfaceType
	        INTEGER,
	  atmSuPortDataClkPolarity
			INTEGER,
	  atmSuPortDataCtsStatus
			INTEGER,
	  atmSuPortDataRtsStatus
			INTEGER
        }

atmSuPortDataApplication OBJECT-TYPE
      SYNTAX  INTEGER
	      {
        frameRelay		(1),
        atmDxi			(2),
		bridgedEthernet (3),
        smdsDxi         (4),  -- for future use
        aal1Stream		(5),
		routedEthernet	(6),
		satop    		(7),
		tdmoIp          (8),
		frDlci			(9),
		hdlc           (10),
		notApplicable (255)
	      }

      MAX-ACCESS   read-write
      STATUS  current
      DESCRIPTION
      "This attribute indicates the protocol application which runs
       above the physical port."
      ::= { atmSuPortDataCnfgEntry 1 }

atmSuPortDataRate OBJECT-TYPE
      SYNTAX  INTEGER
	      {
        r64KBps      (1),
        r128KBps     (2),
        r192KBps     (3),
        r256KBps     (4),
        r320KBps     (5),
        r384KBps     (6),
        r448KBps     (7),
        r512KBps     (8),
        r576KBps     (9),
        r640KBps     (10),
        r704KBps     (11),
        r768KBps     (12),
        r832KBps     (13),
        r896KBps     (14),
        r960KBps     (15),
        r1024KBps    (16),
        r1088KBps    (17),
        r1152KBps    (18),
        r1216KBps    (19),
        r1280KBps    (20),
        r1344KBps    (21),
        r1408KBps    (22),
        r1472KBps    (23),
        r1536KBps    (24),
        r1544network (25), -- take the clock from the T1 network clock for ACE-20T/ACE-2T1
        r1600KBps    (26),
        r1664KBps    (27),
        r1728KBps    (28),
        r1792KBps    (29),
        r1856KBps    (30),
        r1920KBps    (31),
        r1984KBps    (32),
        r2048KBps    (33),
        r2048network (34),  -- take the clock from the E1 network clock for ACE-20E/ACE-2E1
		r8192KBps    (35),  -- for IMXi4
		notApplicable (255)
	      }
      MAX-ACCESS   read-write
      STATUS  current
      DESCRIPTION
      "This attribute indicates the operation rate of the port.
       AmcdT1 / Ace-20T allowes rates up to 1536KBps ( options 1-12 ),
       while AmcdE1 / Ace-20E allowes all options. "
      ::= { atmSuPortDataCnfgEntry 2 }

atmSuPortDataDCD OBJECT-TYPE
      SYNTAX  INTEGER
	      {
            off (1),
            on  (2),
			notApplicable (255)
	      }
      MAX-ACCESS   read-write
      STATUS  current
      DESCRIPTION
      "This attribute indicates if the bits CtsCd( Clear-to-send Carry-detect)
       are being checked. In AMCD CTS is also checked.
       off - ignore DCD signal
	   on  - obey DCD signal" 
      ::= { atmSuPortDataCnfgEntry 3 }

atmSuPortDataMode OBJECT-TYPE
      SYNTAX  INTEGER
	      {
            nrzi  (1),
            nrz   (2),
			notApplicable (255)
	      }
      MAX-ACCESS   read-only
      STATUS  deprecated
      DESCRIPTION
      "This attribute indicates the port mode of sampling data physical. "
      ::= { atmSuPortDataCnfgEntry 4 }

atmSuPortDataCRC OBJECT-TYPE
      SYNTAX  INTEGER
	      {
            cRC16  (1),
            cRC32  (2),
            noCRC  (3),
			notApplicable (255)
	      }
      MAX-ACCESS   read-write
      STATUS  current
      DESCRIPTION
      "This attribute indicates the type of CRC checking 
      on receiving/transmiting frames. "
      ::= { atmSuPortDataCnfgEntry 5 }

atmSuPortDataClock OBJECT-TYPE
      SYNTAX  INTEGER
	      {
            dce  (1),
            edce (2), -- for future use
            dte  (3),
			notApplicable (255)
	      }
      MAX-ACCESS   read-write
      STATUS  current
      DESCRIPTION
      "This attribute indicates the clock using for synchronization 
      for the data port. "
      ::= { atmSuPortDataCnfgEntry 6 }

atmSuPortDataMaxNoOfConns  OBJECT-TYPE
      SYNTAX  Integer32
      MAX-ACCESS   read-only
      STATUS  current
      DESCRIPTION
       " this object indicates the maximum number of cross-connect
         connections allowed beetween the ATM port and the Data Port
         identified by IfIndex. "
      ::= { atmSuPortDataCnfgEntry 7 }

atmSuPortDataConfNoOfConns  OBJECT-TYPE
      SYNTAX  Integer32
      MAX-ACCESS   read-only
      STATUS  current
      DESCRIPTION
       " this object indicates the configured number of cross-connect
         connections exist beetween the ATM port and the Data Port
         identified by IfIndex. "
      ::= { atmSuPortDataCnfgEntry 8 }

atmSuPortDataIdleCode  OBJECT-TYPE
      SYNTAX  Integer32 (0..255)
      MAX-ACCESS   read-write
      STATUS  current
      DESCRIPTION
       " This attribute is applicable only for application aal1Stream.
         It indicates the value to be transmitted whenever the port is idle. "
      ::= { atmSuPortDataCnfgEntry 9 }

atmSuPortDataInterfaceType OBJECT-TYPE
    SYNTAX INTEGER 
       {
       notApplicable(1),
       x21 (2),
       v35 (3),
	   v36 (4),
	   rs530 (5),
	   rs232 (6)
	   }
	MAX-ACCESS read-write
	STATUS current
	DESCRIPTION
	"Physical layer interface type. (Configureable or Non-Configureable)"
	::= {atmSuPortDataCnfgEntry 10 }

atmSuPortDataClkPolarity   OBJECT-TYPE     
	 SYNTAX  INTEGER
       {
       notApplicable   (1),
       normal          (2),
       inverted        (3)
       }
      MAX-ACCESS  read-write
      STATUS  current
      DESCRIPTION
      "This object indicates the clock polarity.
       For LA-110/140  this object will be applicable only for 
       X.21/V.35/data port "
      ::= {atmSuPortDataCnfgEntry 11}
  
atmSuPortDataCtsStatus  OBJECT-TYPE
     SYNTAX INTEGER 
       {
       notApplicable (1),
       off           (2), --down
       on            (3)
       }
     MAX-ACCESS  read-only
     STATUS  current
     DESCRIPTION
    	"CTS status - the signal state received from ATM network  
    	 (for the local DTE usage). 
    	 LA110 receiving RTS down from remote DTE device
    	  via ATM network, will change CTS signal state 
    	  to down (off) toward local DTE device"	 
     ::= { atmSuPortDataCnfgEntry 12 }

atmSuPortDataRtsStatus  OBJECT-TYPE
     SYNTAX INTEGER 
       {
       notApplicable (1),
       off           (2), --down
       on            (3)
       }
     MAX-ACCESS  read-only
     STATUS  current
     DESCRIPTION
    	"RTS status - the signal state received from local DTE
    	 (to be forwarded to ATM network).
	     LA110 receiving RTS down from the local DTE device
	     will transmit all '1' to ATM (in order to carry the 
	     signaling to remote LA110), and forward it (RTS-down) 
	     to far end through ATM cell (pointer field)."
     ::= { atmSuPortDataCnfgEntry 13 }



-- *************************************************************
--    agent physical network definitions ( T1/E1 interface )
-- *************************************************************

atmSuPortDs1   OBJECT IDENTIFIER ::= { atmSuPort 2 } -- DS1 definitions

--
-- this table include expansion to the config table in rfc1406
--
atmSuPortDs1CnfgTable OBJECT-TYPE
      SYNTAX  SEQUENCE OF AtmSuPortDs1CnfgEntry
      MAX-ACCESS   not-accessible
      STATUS  current
      DESCRIPTION
       " This table include expansion configuration to the DS1 physical port."
      ::= { atmSuPortDs1 1 }

atmSuPortDs1CnfgEntry OBJECT-TYPE
      SYNTAX  AtmSuPortDs1CnfgEntry
      MAX-ACCESS   not-accessible
      STATUS  current
      DESCRIPTION
      "the entries at this table describes the configuration
	   of the agent physical."
      INDEX  { ifIndex }
      ::= { atmSuPortDs1CnfgTable 1}

AtmSuPortDs1CnfgEntry ::=
      SEQUENCE {
      atmSuPortDs1CnfgRxSensitivity
	        INTEGER,
      atmSuPortDs1CnfgLBO
	        INTEGER,
      atmSuPortDs1CnfgRestoreTime
            INTEGER,
      atmSuPortDs1CnfgInbandMng
 	        INTEGER,
      atmSuPortDs1CnfgDedicatedTs 
            Integer32

      }

atmSuPortDs1CnfgRxSensitivity OBJECT-TYPE
      SYNTAX  INTEGER
	  {
		s12dB      (1),	 -- for E1 Interface
        s30dB      (2),	 -- for T1/E1 Interface
        s36dB      (3),	 -- for T1 Interface
		s15dB      (4),	 
		s43dB      (5)

	  }
      MAX-ACCESS   read-write
      STATUS  current
      DESCRIPTION
      "This attribute is the rx line sensetivity parameter used only for
       T1/CSU and E1/LTU interfaces."
      ::= { atmSuPortDs1CnfgEntry 1 }

atmSuPortDs1CnfgLBO OBJECT-TYPE
      SYNTAX  INTEGER
      {
        txGain0db(1),
        txGain7dot5db  (2),	 --
        txGain15db     (3),  -- for T1/CSU Interface
        txGain22dot5db (4),  --

        len0p133ft     (5),  --
        len133p266ft   (6),  --
        len266p399ft   (7),  --	for T1/DSU Interface
        len399p533ft   (8),  --
        len533p655ft   (9),  --

        unbalanceE1    (10),	 -- for E1 Interface
		balanceE1      (11)  --
      }
      MAX-ACCESS   read-write
      STATUS  current
      DESCRIPTION
      "This attribute is the line-Build-Out indicates sensitivity of the DS1 interface.
       The user can define if the agent will be CSU or DSU (for T1 only) by choosing the
       right option.
       On E1 interface this is done by hardware, so this parameter cannot be written. "
      ::= { atmSuPortDs1CnfgEntry 2 }

atmSuPortDs1CnfgRestoreTime OBJECT-TYPE
      SYNTAX  INTEGER
      {
        ccittE1               (1),
        restoreT1secFast      (2),
        restoreT10sec62411    (3)
      }
      MAX-ACCESS   read-write
      STATUS  current
      DESCRIPTION
      "Determines the time passing from the disappearance of the loss of
       synchronization condition (red alarm) to the restoration of normal
       service. The options 1secFast(2) and 10sec62411(3) for E1 interfaces
       are proprietary implementation of the T1 standard to the E1 interface."
      ::= { atmSuPortDs1CnfgEntry 3 }

atmSuPortDs1CnfgInbandMng OBJECT-TYPE
      SYNTAX  INTEGER
      {
       off         (2),
       dedicatedTs (4),	-- RAD proprietary
       --dedicatedPpp (5),
       dedicatedFr (6)
      }
      MAX-ACCESS   read-write
      STATUS  current
      DESCRIPTION
      "A unique number to identify type of 
       inband management over the link.
       For LA-104 and IMXi4, only one port may be used
       for inband management "
      ::= { atmSuPortDs1CnfgEntry 4 }

atmSuPortDs1CnfgDedicatedTs OBJECT-TYPE
      SYNTAX  Integer32
      MAX-ACCESS  read-write
      STATUS  current
      DESCRIPTION
      "A unique number to identify Dedicated Time Slot  for inband management
       of the T1/E1 port.
       It is applicable only when atmSuPortDs1CnfgInbandMng 
       selected is not off.

       1..24 - Dedicated TS of T1
       1..31 - Dedicated TS of E1
       255   - notApplicable (for agents that do not support this 
               feature)
       Other values are invalid."
	   ::= {atmSuPortDs1CnfgEntry 5}


-- *********************************************************
--          Protocol  DS1-CBR Port   Definitions
-- *********************************************************

-- this table include parameters in T1/E1 level which
-- are relevant to cbr port	only.


atmSuPortDs1CbrCnfgTable OBJECT-TYPE
      SYNTAX  SEQUENCE OF AtmSuPortDs1CbrCnfgEntry
      MAX-ACCESS   not-accessible
      STATUS  current
      DESCRIPTION
       " This table include expansion configuration to the DS1 physical port."
      ::= { atmSuPortDs1 2 }

atmSuPortDs1CbrCnfgEntry OBJECT-TYPE
      SYNTAX  AtmSuPortDs1CbrCnfgEntry
      MAX-ACCESS   not-accessible
      STATUS  current
      DESCRIPTION
      "the entries at this table describes the configuration
	   of the agent physical."
      INDEX  { ifIndex }
      ::= { atmSuPortDs1CbrCnfgTable 1}

AtmSuPortDs1CbrCnfgEntry ::=
      SEQUENCE {
      atmSuPortDs1CbrIdleCode
            Integer32,
      atmSuPortDs1CbrRxTimeSlots
	 TimeSlots,
      atmSuPortDs1CbrTxTimeSlots
	 TimeSlots,
      atmSuPortDs1CbrMaxNoOfConns
            Integer32,
      atmSuPortDs1CbrConfNoOfConns
            Integer32,
      atmSuPortDs1CbrSignallingSampleTime
            INTEGER
      }

atmSuPortDs1CbrIdleCode OBJECT-TYPE
      SYNTAX  Integer32
      MAX-ACCESS   read-write
      STATUS  current
      DESCRIPTION
      "An Idle code which sent on unused time-slots at CBR port ."
      ::= { atmSuPortDs1CbrCnfgEntry 1 }

atmSuPortDs1CbrRxTimeSlots   OBJECT-TYPE
      SYNTAX TimeSlots 
      MAX-ACCESS  read-only
      STATUS current
      DESCRIPTION
"This value indicates the time-slots used by the port for receiving.
        It uses 32 bits ( in 4 bytes octet string ) for E1 and low 24 bits for T1.
        each bit represents a time slot for receiving :
        time-slot 0  = bit 0 (LSB - most right bit in last byte),
           ...
           ...
        time-slot 31 = bit 31 (MSB - most left bit in first byte ).
        value '0' indicate unused time-slot and value '1' indicates used time-slot.
        note : time-slots '0' and '16' are used for signalling in E1 interface. "
      ::= { atmSuPortDs1CbrCnfgEntry 2 }

atmSuPortDs1CbrTxTimeSlots   OBJECT-TYPE
      SYNTAX TimeSlots 
      MAX-ACCESS  read-only
      STATUS current
      DESCRIPTION
      "This value indicates the time-slots used by the port for transmiting.
        It uses 32 bits for E1 and low 24 bits for T1.
        each bit represents a time slot for transmiting :
        time-slot 0  = bit 0 (LSB - most right bit in last byte),
           ...
           ...
        time-slot 31 = bit 31 (MSB - most left bit in first byte ).
        value '0' indicate unused time-slot and value '1' indicates used time-slot.
        note : time-slots '0' and '16' are used for signalling in E1 interface. "
      ::= { atmSuPortDs1CbrCnfgEntry 3 }

atmSuPortDs1CbrMaxNoOfConns  OBJECT-TYPE
      SYNTAX  Integer32
      MAX-ACCESS   read-only
      STATUS  current
      DESCRIPTION
       " this object indicates the maximum number of cross-connect
         connections allowed beetween the ATM port and the CBR Port
         identified by IfIndex. "
      ::= { atmSuPortDs1CbrCnfgEntry 4 }

atmSuPortDs1CbrConfNoOfConns  OBJECT-TYPE
      SYNTAX  Integer32
      MAX-ACCESS   read-only
      STATUS  current
      DESCRIPTION
       " this object indicates the configured number of cross-connect
         connections exist beetween the ATM port and the CBR Port
         identified by IfIndex. "
      ::= { atmSuPortDs1CbrCnfgEntry 5 }

atmSuPortDs1CbrSignallingSampleTime  OBJECT-TYPE
      SYNTAX  INTEGER {
                msec100  (1),
                msec200  (2),
                msec500  (3),
                msec1000 (4),
                msec1500 (5),
                msec2000 (6)
	  }
      MAX-ACCESS   read-write
      STATUS  current
      DESCRIPTION
       " determines how often the signalling of the DBCES connections are sampled
		 and thier activity determined. "
      DEFVAL { msec500 }
      ::= { atmSuPortDs1CbrCnfgEntry 6 }


-- *********************************************************
--             Protocol   ATM    Definitions
-- *********************************************************

atmSuPortAtm     OBJECT IDENTIFIER ::= { atmSuPort 3 } -- ATM expansions to RFC1695

atmSuPortAtmCnfgTable OBJECT-TYPE
      SYNTAX  SEQUENCE OF AtmSuPortAtmCnfgEntry
      MAX-ACCESS   not-accessible
      STATUS  current
      DESCRIPTION
       "This table contains global configuration to the ATM port."
      ::= { atmSuPortAtm 1 }

atmSuPortAtmCnfgEntry OBJECT-TYPE
      SYNTAX  AtmSuPortAtmCnfgEntry
      MAX-ACCESS   not-accessible
      STATUS  current
      DESCRIPTION
       "This object contains information about agent ATM configuration."
      INDEX   { ifIndex }
      ::= { atmSuPortAtmCnfgTable 1 }

AtmSuPortAtmCnfgEntry ::= SEQUENCE {
      atmSuPortAtmCnfgIdleCellCLP
             INTEGER,
      atmSuPortAtmCnfgScramble
             INTEGER,
      atmSuPortAtmSNMPVpi
             Integer32,
      atmSuPortAtmSNMPVci
             Integer32,
      atmSuPortAtmSNMPStatus
             INTEGER,
      atmSuPortAtmILMIStatus
             INTEGER,
      atmSuPortAtmSNMPIp
             IpAddress, 
      atmSuPortAtmCnfgCDVOptimization
             INTEGER,
	  atmSuPortAtmCnfgShapingMode
	         INTEGER,
	  atmSuPortAtmSNMPTrafficDescrIndex
		     AtmTrafficDescrParamIndex,
	  atmSuPortAtmTrafficDescrIndex
		     AtmTrafficDescrParamIndex      
    }

atmSuPortAtmCnfgIdleCellCLP OBJECT-TYPE
      SYNTAX  INTEGER  {
          clp0 (1) , --> ATM Forum
          clp1 (2)   --> ITU
      }
      MAX-ACCESS   read-write
      STATUS  current
      DESCRIPTION
     "Determines the clp bit value for transmition
      in empty time slots."
      ::= { atmSuPortAtmCnfgEntry 1 }

atmSuPortAtmCnfgScramble OBJECT-TYPE
      SYNTAX  INTEGER  {
          enable  (1) ,
          disable (2)
      }
      MAX-ACCESS   read-write
      STATUS  current
      DESCRIPTION
     "Determined by the standards if the cell will be scrambled or not."
      ::= { atmSuPortAtmCnfgEntry 2 }

atmSuPortAtmSNMPVpi  OBJECT-TYPE
      SYNTAX Integer32
      MAX-ACCESS   read-write
      STATUS  current
      DESCRIPTION
       "The Vcc Vpi for SNMP requests."
      ::= { atmSuPortAtmCnfgEntry 3 }

atmSuPortAtmSNMPVci  OBJECT-TYPE
      SYNTAX Integer32
      MAX-ACCESS   read-write
      STATUS  current
      DESCRIPTION
       "The Vcc Vci for SNMP requests."
      ::= { atmSuPortAtmCnfgEntry 4 }

atmSuPortAtmSNMPStatus  OBJECT-TYPE
      SYNTAX INTEGER   {
            active    (1) ,
            notActive (2)
      }
      MAX-ACCESS   read-write
      STATUS  current
      DESCRIPTION
       "value indicates if the SNMP Vcc is available for management."
      ::= { atmSuPortAtmCnfgEntry 5 }

atmSuPortAtmILMIStatus  OBJECT-TYPE
      SYNTAX  INTEGER   {
            active    (1) ,
            notActive (2)
      }
      MAX-ACCESS   read-write
      STATUS  current
      DESCRIPTION
       "Value indicates if agent should respond to ILMI requests from the
        Atm switch or forward it.
        note: when using Atm to Frame-Relay configuration this value should be
              active to support ILMI.
              when using Atm-AtmDxi configuration the ILMI requests should be
              moved forward to the DTE or may be answered by the DCE. "
      DEFVAL { active }
      ::= { atmSuPortAtmCnfgEntry 6 }

atmSuPortAtmSNMPIp OBJECT-TYPE
      SYNTAX  IpAddress 
      MAX-ACCESS  read-write
      STATUS  current
      DESCRIPTION
       "The interface IP address for SNMP requests."
      ::= { atmSuPortAtmCnfgEntry 7 }

atmSuPortAtmCnfgCDVOptimization  OBJECT-TYPE
      SYNTAX INTEGER   {
          notApplicable  (1),
          disable        (2),
          enable         (3)
      }
      MAX-ACCESS   read-write
      STATUS  current
      DESCRIPTION
       "value indicates if optimization of CDV (Cell Delay Varation)
         is enbabled."
      ::= { atmSuPortAtmCnfgEntry 8 }

atmSuPortAtmCnfgShapingMode	 OBJECT-TYPE
      SYNTAX INTEGER   {
          notApplicable  (1),
          sw       (2),
          hwNcits1 (3), -- HW Shaping, APC with NCITS = 1
		  hwNcits2 (4)  -- HW Shaping, APC with NCITS = 2 
		  }
      MAX-ACCESS   read-write
      STATUS  current
      DESCRIPTION
       "ATM Shaping mode.
        Three possible values:
         SW Shaping.                 
         HW Shaping - APC with NCITS = 1.
         HW Shaping - APC with NCITS = 2
         The difference between the two hardware modes
         is in the connection cell granularity 
         and maximum bandwidth (BW):
         * For NCITS=1, the granularity is of one cell
           and the max. BW is the uplink BW, 
         * For NCITS=2, the granularity is of every two cells   
           and the max. BW is half of  the uplink BW."
      ::= { atmSuPortAtmCnfgEntry 9 } 

	    	    
atmSuPortAtmSNMPTrafficDescrIndex  OBJECT-TYPE
      SYNTAX       AtmTrafficDescrParamIndex
      MAX-ACCESS   read-write
      STATUS       current
      DESCRIPTION
       "The value of this object identifies the row
        in the atmTrafficDescrParamTable which
        applies to the transmit direction of the VCL."
       ::= { atmSuPortAtmCnfgEntry 10 }


atmSuPortAtmTrafficDescrIndex  OBJECT-TYPE
      SYNTAX       AtmTrafficDescrParamIndex
      MAX-ACCESS   read-write
      STATUS       current
      DESCRIPTION
       "The value of this object identifies the row
        in the atmTrafficDescrParamTable which
        applies to whole ATM WAN port."
       ::= { atmSuPortAtmCnfgEntry 11 }



-- *************************************************************
--  RAD private ATM Interface statistics table. The table adds
--  more columns to the RFC1695 atmInterfaceConfTable
-- *************************************************************

atmSuPortAtmIfStatsTable OBJECT-TYPE
      SYNTAX SEQUENCE OF AtmSuPortAtmIfStatsEntry
      MAX-ACCESS  not-accessible
      STATUS current
      DESCRIPTION
       "The table contains additional statistics information about
        the ATM interface."
      ::= { atmSuPortAtm 2 }


atmSuPortAtmIfStatsEntry OBJECT-TYPE
      SYNTAX AtmSuPortAtmIfStatsEntry
      MAX-ACCESS  not-accessible
      STATUS current
      DESCRIPTION
       "An entry in the ATM Interface statistics table."
      INDEX { ifIndex }
      ::= { atmSuPortAtmIfStatsTable 1 }

AtmSuPortAtmIfStatsEntry ::= SEQUENCE {
      atmSuPortAtmRxClp0Cells
           Counter32,
      atmSuPortAtmRxClp1Cells
           Counter32,
     atmSuPortAtmRxEfciSetCells
           Counter32,
      atmSuPortAtmRxOamCells
           Counter32,
      atmSuPortAtmTxClp0Cells
           Counter32,
      atmSuPortAtmTxClp1Cells
           Counter32,
      atmSuPortAtmTxEfciSetCells
           Counter32,
      atmSuPortAtmTxOamCells
           Counter32
      }

atmSuPortAtmRxClp0Cells   OBJECT-TYPE
      SYNTAX Counter32
      MAX-ACCESS  read-only
      STATUS current
      DESCRIPTION
       "The number of cells received with correct
        HECs and CLP=0 and not misrouted"
      ::= { atmSuPortAtmIfStatsEntry 1 }

atmSuPortAtmRxClp1Cells   OBJECT-TYPE
      SYNTAX Counter32
      MAX-ACCESS  read-only
      STATUS current
      DESCRIPTION
       "The number of cells received with correct
        HEC's and CLP=1 and not misrouted."
      ::= { atmSuPortAtmIfStatsEntry 2 }

atmSuPortAtmRxEfciSetCells   OBJECT-TYPE
      SYNTAX Counter32
      MAX-ACCESS read-only
      STATUS current
      DESCRIPTION
       "The number of cells received with EFCI bit set by
        the Agent"
      ::= { atmSuPortAtmIfStatsEntry 3 }

atmSuPortAtmRxOamCells   OBJECT-TYPE
      SYNTAX Counter32
      MAX-ACCESS  read-only
      STATUS current
      DESCRIPTION
       "The number of OAM cells received with correct HECs."
::= { atmSuPortAtmIfStatsEntry 4 }

atmSuPortAtmTxClp0Cells   OBJECT-TYPE
      SYNTAX Counter32
      MAX-ACCESS  read-only
      STATUS current
      DESCRIPTION
       "The number of cells transmitted with CLP=0."
      ::= { atmSuPortAtmIfStatsEntry 5 }

atmSuPortAtmTxClp1Cells   OBJECT-TYPE
      SYNTAX Counter32
      MAX-ACCESS  read-only
      STATUS current
      DESCRIPTION
       "The number of cells transmitted with CLP=1."
      ::= { atmSuPortAtmIfStatsEntry 6 }

atmSuPortAtmTxEfciSetCells   OBJECT-TYPE
      SYNTAX Counter32
      MAX-ACCESS read-only
      STATUS current
      DESCRIPTION
       "The number of cells transmitted with EFCI bit set by
        the Agent"
      ::= { atmSuPortAtmIfStatsEntry 7 }

atmSuPortAtmTxOamCells   OBJECT-TYPE
      SYNTAX Counter32
      MAX-ACCESS  read-only
      STATUS current
      DESCRIPTION
       "The number of transmitted OAM cells."
      ::= { atmSuPortAtmIfStatsEntry 8 }

-- **************************************************************
--  RAD Vcl Statistics table. The table adds more columns to
--  the RFC1695 atmVclTable
-- **************************************************************

atmSuPortAtmVclStatsTable OBJECT-TYPE
      SYNTAX SEQUENCE OF AtmSuPortAtmVclStatsEntry
      MAX-ACCESS  not-accessible
      STATUS current
      DESCRIPTION
       "The table contains additional information about
        the ATM Vcl end points."
      ::= { atmSuPortAtm 3 }


atmSuPortAtmVclStatsEntry  OBJECT-TYPE
      SYNTAX  AtmSuPortAtmVclStatsEntry
      MAX-ACCESS   not-accessible
      STATUS  current
      DESCRIPTION
       "An entry in the ATM Vcl statistics table.
        For Vpl statistics, use atmVclVci = 65536 
        (maximum valid value of atmVclVci +1)"
      INDEX  {ifIndex, atmVclVpi, atmVclVci }
      ::= { atmSuPortAtmVclStatsTable 1 }

AtmSuPortAtmVclStatsEntry ::= SEQUENCE {
      atmSuPortAtmVclStatsRxCells
                Counter32,
      atmSuPortAtmVclStatsRxClp0Cells
                Counter32,
      atmSuPortAtmVclStatsRxClp1Cells
                Counter32,
      atmSuPortAtmVclStatsRxDiscardsCells
                Counter32,
      atmSuPortAtmVclStatsTxCells
                Counter32,
      atmSuPortAtmVclStatsTxClp0Cells
                Counter32,
      atmSuPortAtmVclStatsTxClp1Cells
                Counter32,
      atmSuPortAtmVclStatsRxTotalAISCells 
                Counter32,
      atmSuPortAtmVclStatsRxTotalCCCells  
                Counter32,
      atmSuPortAtmVclStatsTotalSuccLoopbacks 
                Counter32,
      atmSuPortAtmVclStatsTotalFailLoopbacks 
                Counter32,
      atmSuPortAtmVclStatsRxTotalRDICells  
                Counter32,
      atmSuPortAtmVclStatsTotalLOCSeconds
                Counter32,
      atmSuPortAtmVclStatsRxTotalLoopbackRequests 
                Counter32,
      atmSuPortAtmVclStatsTxTotalAISCells 
                Counter32,
      atmSuPortAtmVclStatsTxTotalCCCells 
                Counter32,
      atmSuPortAtmVclStatsTxTotalRDICells 
                Counter32,
      atmSuPortAtmVclStatsTxTotalLoopbackResponses 
                Counter32,
      atmSuPortAtmVclStatsTxTotalLoopbackRequests 
                Counter32,
      atmSuPortAtmVclStatsRxTotalLoopbackResponses 
                Counter32
      }

atmSuPortAtmVclStatsRxCells   OBJECT-TYPE
      SYNTAX Counter32
      MAX-ACCESS  read-only
      STATUS current
      DESCRIPTION
       "The total number of cells received with
        correct HEC's."
      ::= { atmSuPortAtmVclStatsEntry 1 }

atmSuPortAtmVclStatsRxClp0Cells   OBJECT-TYPE
      SYNTAX Counter32
      MAX-ACCESS  read-only
      STATUS current
      DESCRIPTION
       "The number of cells received with correct
        HEC's and CLP=0."
      ::= { atmSuPortAtmVclStatsEntry 2 }

atmSuPortAtmVclStatsRxClp1Cells   OBJECT-TYPE
      SYNTAX Counter32
      MAX-ACCESS  read-only
      STATUS current
      DESCRIPTION
       "The number of cells received with correct
        HEC's and CLP=1."
      ::= { atmSuPortAtmVclStatsEntry 3 }

atmSuPortAtmVclStatsRxDiscardsCells   OBJECT-TYPE
      SYNTAX Counter32
      MAX-ACCESS  read-only
      STATUS current
      DESCRIPTION
       "The number of cells, in ingress direction,
        discarded due to policing violation."
      ::= { atmSuPortAtmVclStatsEntry 4 }

atmSuPortAtmVclStatsTxCells   OBJECT-TYPE
      SYNTAX Counter32
      MAX-ACCESS  read-only
      STATUS current
      DESCRIPTION
       "The total number of cells transmitted."
      ::= { atmSuPortAtmVclStatsEntry 5 }

atmSuPortAtmVclStatsTxClp0Cells   OBJECT-TYPE
      SYNTAX Counter32
      MAX-ACCESS  read-only
      STATUS current
      DESCRIPTION
       "The number of cells transmitted with CLP=0."
      ::= { atmSuPortAtmVclStatsEntry 6 }

atmSuPortAtmVclStatsTxClp1Cells   OBJECT-TYPE
      SYNTAX Counter32
      MAX-ACCESS  read-only
      STATUS current
      DESCRIPTION
       "The number of cells transmitted with CLP=1."
      ::= { atmSuPortAtmVclStatsEntry 7 }

atmSuPortAtmVclStatsRxTotalAISCells   OBJECT-TYPE
      SYNTAX Counter32
      MAX-ACCESS  read-only
      STATUS current
      DESCRIPTION
       "Total number of AIS cells received on the VC."
      ::= { atmSuPortAtmVclStatsEntry 8 }

atmSuPortAtmVclStatsRxTotalCCCells   OBJECT-TYPE
      SYNTAX Counter32
      MAX-ACCESS  read-only
      STATUS current
      DESCRIPTION
       "Total number of Continuity Check cells that were
        received on the VC."
      ::= { atmSuPortAtmVclStatsEntry 9 }

atmSuPortAtmVclStatsTotalSuccLoopbacks   OBJECT-TYPE
      SYNTAX Counter32
      MAX-ACCESS  read-only
      STATUS current
      DESCRIPTION
       "Total number of loopbacks that were requested by the ACE20
        and for which there was a response (not supported)."
      ::= { atmSuPortAtmVclStatsEntry 10 }

atmSuPortAtmVclStatsTotalFailLoopbacks   OBJECT-TYPE
      SYNTAX Counter32
      MAX-ACCESS  read-only
      STATUS current
      DESCRIPTION
       "Total number of loopbacks that were requested by the ACE20
        and for which there was no response (not supported)."
      ::= { atmSuPortAtmVclStatsEntry 11 }

atmSuPortAtmVclStatsRxTotalRDICells   OBJECT-TYPE
      SYNTAX Counter32
      MAX-ACCESS  read-only
      STATUS current
      DESCRIPTION
       "Total number of RDI cells received on a VC."
      ::= { atmSuPortAtmVclStatsEntry 12 }

atmSuPortAtmVclStatsTotalLOCSeconds   OBJECT-TYPE
      SYNTAX Counter32
      MAX-ACCESS  read-only
      STATUS current
      DESCRIPTION
       "Total number of seconds during which there was loss of 
       continuity on the VC - no data and no continuity check cells 
       were received on the VC whilst it was in 'sink' continuity 
       check mode."
      ::= { atmSuPortAtmVclStatsEntry 13 }

atmSuPortAtmVclStatsRxTotalLoopbackRequests   OBJECT-TYPE
      SYNTAX Counter32
      MAX-ACCESS  read-only
      STATUS current
      DESCRIPTION
       "Total number of loopback requests received by the ACE20 on a VC."
      ::= { atmSuPortAtmVclStatsEntry 14 }

atmSuPortAtmVclStatsTxTotalAISCells   OBJECT-TYPE
      SYNTAX Counter32
      MAX-ACCESS  read-only
      STATUS current
      DESCRIPTION
       "Total number of AIS cells that were transmitted on a VC."
      ::= { atmSuPortAtmVclStatsEntry 15 }

atmSuPortAtmVclStatsTxTotalCCCells   OBJECT-TYPE
      SYNTAX Counter32
      MAX-ACCESS  read-only
      STATUS current
      DESCRIPTION
       "Total number of continuity check cells that were transmitted on
        a VC (when there is no data cells and the connection is in
        'source' continuity check mode)."
      ::= { atmSuPortAtmVclStatsEntry 16 }

atmSuPortAtmVclStatsTxTotalRDICells   OBJECT-TYPE
      SYNTAX Counter32
      MAX-ACCESS  read-only
      STATUS current
      DESCRIPTION
       "Total number of RDI cells transmitted on a VC."
      ::= { atmSuPortAtmVclStatsEntry 17 }

atmSuPortAtmVclStatsTxTotalLoopbackResponses   OBJECT-TYPE
      SYNTAX Counter32
      MAX-ACCESS  read-only
      STATUS current
      DESCRIPTION
       "Total number of loopback responses that were transmitted as a 
        result of loopback requests received."
      ::= { atmSuPortAtmVclStatsEntry 18 }

atmSuPortAtmVclStatsTxTotalLoopbackRequests   OBJECT-TYPE
      SYNTAX Counter32
      MAX-ACCESS  read-only
      STATUS current
      DESCRIPTION
       "Total number of loopback requests that were transmitted by the ACE20 on a VC."
      ::= { atmSuPortAtmVclStatsEntry 19 }

atmSuPortAtmVclStatsRxTotalLoopbackResponses   OBJECT-TYPE
      SYNTAX Counter32
      MAX-ACCESS  read-only
      STATUS current
      DESCRIPTION
       "Total number of loopback responses that were received as a 
        result of loopback transmitted by the ACE20."
      ::= { atmSuPortAtmVclStatsEntry 20 }


-- **************************************************************
--  RAD AAL1 Vcc Statistics table. This table includes all AAL1
--  connections which are not from CES/DBCES type.
-- **************************************************************

-- Use atmCESAAL1StatsTable instead atmAAL1StatsTable

--atmAAL1StatsTable  OBJECT-TYPE
--    SYNTAX         SEQUENCE OF atmAAL1StatsEntry
--    MAX-ACCESS     not-accessible
--    STATUS         current
--    DESCRIPTION
--     "This table contains AAL1 VCC performance parameters."
--    ::= { atmSuPortAtm 4 }
--
--atmAAL1StatsEntry  OBJECT-TYPE
--    SYNTAX         atmAAL1StatsEntry
--    MAX-ACCESS     not-accessible
--    STATUS         current
--    DESCRIPTION
--     "This list contains the AAL1 VCC performance parameters."
--    INDEX  { ifIndex }
--    ::= { atmAAL1StatsTable 1 }
--
--atmAAL1StatsEntry    ::= SEQUENCE  {
--    atmVclVpi
--        Integer32,
--    atmVclVci
--        Integer32,
--    atmAAL1HdrErrors
--        Counter32,
--    atmAAL1SeqErrors
--        Counter32
--    }
--
--atmAAL1VclVpi    OBJECT-TYPE
--    SYNTAX         Integer32
--    MAX-ACCESS     read-only
--    STATUS         current
--    DESCRIPTION
--     "The SNMP Vpi of this entry."
--    ::= { atmAAL1StatsEntry 1 }
--
--atmAAL1VclVci    OBJECT-TYPE
--    SYNTAX         Integer32
--    MAX-ACCESS     read-only
--    STATUS         current
--    DESCRIPTION
--     "The SNMP Vci of this entry."
--    ::= { atmAAL1StatsEntry 2 }
--
--atmAAL1HdrErrors    OBJECT-TYPE
--    SYNTAX         Counter32
--    MAX-ACCESS     read-only
--    STATUS         current
--    DESCRIPTION
--     "The count of the number of AAL1 header errors detected,
--      including those corrected.  Header errors include correctable
--      and uncorrectable CRC, plus bad parity."
--    ::= { atmAAL1StatsEntry 3 }
--
--atmAAL1SeqErrors    OBJECT-TYPE
--    SYNTAX         Counter32
--    MAX-ACCESS     read-only
--    STATUS         current
--    DESCRIPTION
--     "Number of AAL1 sequence violations which the AAL Convergence
--      sublayer interprets as a misinserted cell, as defined by
--      ITU-T I.363.1."
--    ::= { atmAAL1StatsEntry 4 }


-- **********************************************************
-- **********************************************************
--              Protocol   FR     Definitions
-- **********************************************************
-- **********************************************************

atmSuPortFr     OBJECT IDENTIFIER ::= { atmSuPort 4 }

-- **********************************************************
--  the Frame Relay Logical Port Group
-- **********************************************************

atmSuPortFrLportTable OBJECT-TYPE
      SYNTAX  SEQUENCE OF  AtmSuPortFrLportEntry
      MAX-ACCESS   not-accessible
      STATUS  current
      DESCRIPTION
       "The table Contains configuration parameters of the Frame-Relay
        port and has expansion to  frLportTable in RFC1604 MIB."
      ::= { atmSuPortFr 1 }

atmSuPortFrLportEntry OBJECT-TYPE
      SYNTAX  AtmSuPortFrLportEntry
      MAX-ACCESS   not-accessible
      STATUS  current
      DESCRIPTION
       "An entry in the Frame Relay Logical Port
        Information table."
      INDEX   { ifIndex }
      ::= { atmSuPortFrLportTable 1 }


AtmSuPortFrLportEntry ::=
      SEQUENCE {
         atmSuPortFrLportSNMPDlci
              Integer32,
         atmSuPortFrLportSNMPStatus
              INTEGER,
         atmSuPortFrLportVCSigProtocol
              INTEGER,
         atmSuPortFrLportVCSigProcedure
              INTEGER,
         atmSuPortFrLportCLLM
              INTEGER,
         atmSuPortFrLportSNMPIp
              IpAddress
      }

atmSuPortFrLportSNMPDlci  OBJECT-TYPE
      SYNTAX Integer32
      MAX-ACCESS   read-write
      STATUS  current
      DESCRIPTION
       "The SNMP Dlci of this entry."
      ::= { atmSuPortFrLportEntry 1 }

atmSuPortFrLportSNMPStatus  OBJECT-TYPE
      SYNTAX INTEGER   {
            active    (1) ,
            notActive (2)
      }
      MAX-ACCESS   read-write
      STATUS  current
      DESCRIPTION
       "value indicates if SNMP over FR is available for management."
      ::= { atmSuPortFrLportEntry 2 }

atmSuPortFrLportVCSigProtocol OBJECT-TYPE
      SYNTAX  INTEGER {
                none(1),
                ccittQ933A(2),
                ansiT1617D(3),
                lmi(4) 
      }
      MAX-ACCESS   read-write
      STATUS  current
      DESCRIPTION
       "The value of this object identifies the Local
        In-Channel Signaling Protocol that is used for
        this frame relay UNI/NNI logical port."
      DEFVAL { none }
      ::= { atmSuPortFrLportEntry 3 }

 atmSuPortFrLportVCSigProcedure  OBJECT-TYPE
     SYNTAX  INTEGER {
               notApplicable (1),
               u2nnet(2),
               u2nuser(3),
               bidirect(4)
             }
      MAX-ACCESS   read-write
      STATUS  current
      DESCRIPTION
       "The value of this object identifies the Local
        In-Channel Signaling Procedure that is used for
        this UNI/NNI logical port.  The UNI/NNI logical
        port can be performing user-to-network
        network-side and user-to-network user-side procedures
        or bidirectional procedures.
        this parameter gets value 'notApplicable when the VCSigProtocol is none"
      ::= { atmSuPortFrLportEntry 4 }

atmSuPortFrLportCLLM OBJECT-TYPE
      SYNTAX  INTEGER {
                active   (1),
                notActive(2)
      }
      MAX-ACCESS   read-write
      STATUS  current
      DESCRIPTION
       " indicate if the configuration is supporting CLLM ( Consolidated Link
         Layer Management ) ."
      ::= { atmSuPortFrLportEntry 5 }

atmSuPortFrLportSNMPIp OBJECT-TYPE
      SYNTAX  IpAddress 
      MAX-ACCESS  read-write
      STATUS  current
      DESCRIPTION
       "The interface IP address of this entry."
      ::= { atmSuPortFrLportEntry 6 }


-- ***************************************************************
--  RAD Frame Relay Statistics table. The table add more
--  columns to the RFC1604 frPVCEndptTable
-- ***************************************************************


atmSuPortFrPvcEndptTable OBJECT-TYPE
      SYNTAX SEQUENCE OF  AtmSuPortFrPvcEndptEntry
      MAX-ACCESS  not-accessible
      STATUS current
      DESCRIPTION
       "The table contains additional information about
        the Frame Relay end point."
      ::= {  atmSuPortFr 2 }


atmSuPortFrPvcEndptEntry OBJECT-TYPE
      SYNTAX  AtmSuPortFrPvcEndptEntry
      MAX-ACCESS  not-accessible
      STATUS current
      DESCRIPTION
       "An entry for FR end-point statistics ( expansion to RFC 1604 )."
      INDEX   { ifIndex, frPVCEndptDLCIIndex }
      ::= { atmSuPortFrPvcEndptTable 1 }

AtmSuPortFrPvcEndptEntry ::= SEQUENCE {
      atmSuPortFrPvcEndptTxFECNs
               Counter32,
      atmSuPortFrPvcEndptTxBECNs
               Counter32,
      atmSuPortFrPvcEndptTxDEs
               Counter32,
      atmSuPortFrPvcEndptRxFECNs
               Counter32,
      atmSuPortFrPvcEndptRxBECNs
               Counter32
      }

atmSuPortFrPvcEndptTxFECNs   OBJECT-TYPE
      SYNTAX Counter32
      MAX-ACCESS  read-only
      STATUS current
      DESCRIPTION
       "number of frames transmited with FECN ( Forward Explicit
        Congestion Notification )."
      ::= { atmSuPortFrPvcEndptEntry 1 }

atmSuPortFrPvcEndptTxBECNs   OBJECT-TYPE
      SYNTAX Counter32
      MAX-ACCESS  read-only
      STATUS current
      DESCRIPTION
       "number of frames transmited with BECN ( Backward Explicit
        Congestion Notification )."
      ::= { atmSuPortFrPvcEndptEntry 2 }

atmSuPortFrPvcEndptTxDEs   OBJECT-TYPE
      SYNTAX Counter32
      MAX-ACCESS  read-only
      STATUS current
      DESCRIPTION
       "number of frames transmited with the DE ( Discarded Eligible ) bit set."
      ::= { atmSuPortFrPvcEndptEntry 3 }

atmSuPortFrPvcEndptRxFECNs    OBJECT-TYPE
      SYNTAX Counter32
      MAX-ACCESS  read-only
      STATUS current
      DESCRIPTION
       "number of frames received with FECN ( Forward Explicit
        Congestion Notification )."
      ::= { atmSuPortFrPvcEndptEntry 4 }

atmSuPortFrPvcEndptRxBECNs   OBJECT-TYPE
      SYNTAX Counter32
      MAX-ACCESS  read-only
      STATUS current
      DESCRIPTION
       "number of frames received with BECN ( Backward Explicit
        Congestion Notification )."
      ::= { atmSuPortFrPvcEndptEntry 5 }


-- ***************************************************************
--          ATM-DXI Managment LMI Addresses
-- ***************************************************************

atmSuPortDxi  OBJECT IDENTIFIER ::= { atmSuPort 5 }   -- ATM-DXI definitions

atmSuPortDxiConfTable OBJECT-TYPE
      SYNTAX   SEQUENCE OF AtmSuPortDxiConfEntry
      MAX-ACCESS   not-accessible
      STATUS      current
      DESCRIPTION
       "This table contains ATM-DXI managment
        address (DFA) ending at the local agent.
        only LMI managment supported for ATM-DXI."
      ::= { atmSuPortDxi 1 }

atmSuPortDxiConfEntry OBJECT-TYPE
      SYNTAX  AtmSuPortDxiConfEntry
      MAX-ACCESS   not-accessible
      STATUS  current
      DESCRIPTION
       "This object contains information about agent Dxi interface."
      INDEX   { ifIndex }
      ::= { atmSuPortDxiConfTable 1 }

AtmSuPortDxiConfEntry ::= SEQUENCE {
      atmSuPortDxiPortMode
             INTEGER,
      atmSuPortDxiSigProtocol
             INTEGER,
      atmSuPortDxiSigDfa
             Integer32
      }

atmSuPortDxiPortMode   OBJECT-TYPE
      SYNTAX  INTEGER  {
             mode1a  (1),
             mode1b  (2),
             mode2   (3)
      }
      MAX-ACCESS   read-write
      STATUS  current
      DESCRIPTION
       "This object identifies the dxi mode being used by
        the atm dxi port."
      ::= { atmSuPortDxiConfEntry 1 }

atmSuPortDxiSigProtocol  OBJECT-TYPE
      SYNTAX INTEGER   {
            none (1) ,
            lmi  (2)
      }
      MAX-ACCESS   read-write
      STATUS  current
      DESCRIPTION
       "This value indicates if we using LMI signalling protocol
        or not using any signalling ."
      ::= { atmSuPortDxiConfEntry 2 }

atmSuPortDxiSigDfa  OBJECT-TYPE
      SYNTAX Integer32
      MAX-ACCESS   read-write
      STATUS  current
      DESCRIPTION
       "The Signalling Dfa address .
        the default LMI Dfa defined for LMI by the AtmForum is 0."
      DEFVAL { 0 }
      ::= { atmSuPortDxiConfEntry 3 }

--  **************************************************************

atmSuPortCmdTable OBJECT-TYPE
      SYNTAX   SEQUENCE OF AtmSuPortCmdEntry
      MAX-ACCESS   not-accessible
      STATUS      current
      DESCRIPTION
       "General commands to be done on agent's ports."
      ::= { atmSuPort 6 }

atmSuPortCmdEntry OBJECT-TYPE
      SYNTAX  AtmSuPortCmdEntry
      MAX-ACCESS   not-accessible
      STATUS  current
      DESCRIPTION
       "This object contains entry information."
      INDEX   { ifIndex }
      ::= { atmSuPortCmdTable 1 }

AtmSuPortCmdEntry ::= SEQUENCE {
      atmSuResetPortStatsCmd
             INTEGER,
      atmSuResetConnsStatsCmd
             INTEGER
      }

atmSuResetPortStatsCmd OBJECT-TYPE
      SYNTAX  INTEGER
	      {
    		off(1),
	    	on (2)
	      }
      MAX-ACCESS   read-write
      STATUS  current
      DESCRIPTION
       " reset statistics of port."
      ::= { atmSuPortCmdEntry 1 }

atmSuResetConnsStatsCmd OBJECT-TYPE
      SYNTAX  INTEGER
	      {
    		off(1),
	    	on (2)
	      }
      MAX-ACCESS   read-write
      STATUS  current
      DESCRIPTION
      " reset statistics of all cross connections attached to this port.
             set-request is allowed only on the DATA Ports .
         for get-request value is always 'off' "
      ::= { atmSuPortCmdEntry 2 }

-- **********************************************************
-- **********************************************************
--              Protocol   Ethernet   Definitions
-- **********************************************************
-- **********************************************************

atmSuPortEther   OBJECT IDENTIFIER ::= { atmSuPort 7 }

-- **********************************************************
--  the Ethernet Port Group
-- **********************************************************

atmSuPortEtherTable OBJECT-TYPE
      SYNTAX  SEQUENCE OF  AtmSuPortEtherEntry
      MAX-ACCESS   not-accessible
      STATUS  current
      DESCRIPTION
       "The table Contains configuration parameters of the Ethernet port."
      ::= { atmSuPortEther 1 }

atmSuPortEtherEntry OBJECT-TYPE
      SYNTAX  AtmSuPortEtherEntry
      MAX-ACCESS   not-accessible
      STATUS  current
      DESCRIPTION
       "An entry in the Ethernet Port Information table."
      INDEX   { ifIndex }
      ::= { atmSuPortEtherTable 1 }

AtmSuPortEtherEntry ::=
      SEQUENCE {
         atmSuPortEtherIP
              IpAddress,
         atmSuPortEtherMask
              IpAddress,
         atmSuPortEtherDefaultGateWayIp
              IpAddress,
		 atmSuPortEtherDefaultCrossConnectId
              Integer32,
		 atmSuPortEtherDefaultGatewayStatus
              INTEGER,
         atmSuPortEtherSNMPStatus
              INTEGER,
         atmSuPortEtherFragmentation
              INTEGER,
         atmSuPortEtherRIPMode
              INTEGER,
         atmSuPortEtherBridgingMode
              INTEGER,
         atmSuPortEtherARPTimeout
              Integer32,
		 atmSuPortEtherAgingTime
              Integer32,
		 atmSuPortEtherPppOEEnable
		      INTEGER,
		 atmSuPortEtherStatus
		      INTEGER
      }

atmSuPortEtherIP OBJECT-TYPE
     SYNTAX  IpAddress
 	 MAX-ACCESS  read-write
     STATUS  current
     DESCRIPTION
      "The interface IP address for SNMP requests."
     ::= { atmSuPortEtherEntry 1 }

atmSuPortEtherMask OBJECT-TYPE
     SYNTAX  IpAddress
 	 MAX-ACCESS  read-write
     STATUS  current
     DESCRIPTION
      "The interface IP address mask for SNMP requests."
     ::= { atmSuPortEtherEntry 2 }

atmSuPortEtherDefaultGateWayIp OBJECT-TYPE
     SYNTAX  IpAddress
     MAX-ACCESS  read-write
     STATUS  current
     DESCRIPTION
      "The Ethernet bridge default gateway IP address."
     ::= { atmSuPortEtherEntry 3 }

atmSuPortEtherDefaultCrossConnectId OBJECT-TYPE
     SYNTAX  Integer32
     MAX-ACCESS  read-write
     STATUS  current
     DESCRIPTION
     "Default Cross Connect Id. "
     ::= { atmSuPortEtherEntry 4 }

atmSuPortEtherDefaultGatewayStatus OBJECT-TYPE
     SYNTAX  INTEGER   {
     active    (1) ,
     notActive (2) ,
     notApplicable (255)
     }
     MAX-ACCESS  read-write
     STATUS  current
     DESCRIPTION
     "Default Gateway Status."
     ::= { atmSuPortEtherEntry 5 }

atmSuPortEtherSNMPStatus  OBJECT-TYPE
     SYNTAX INTEGER   {
     active    (1) ,
     notActive (2) ,
     notApplicable (255)
     }
     MAX-ACCESS   read-write
     STATUS  current
     DESCRIPTION
     "The value indicates if the SNMP of Ethernet bridge interface is available
      for management."
     ::= { atmSuPortEtherEntry 6 }

atmSuPortEtherFragmentation OBJECT-TYPE
     SYNTAX  INTEGER {
     no			   (2),
     yes		   (3),
	 notApplicable (255)
     }
	 MAX-ACCESS  read-write
     STATUS  current
     DESCRIPTION
     "Fragmentation. When application is not router value must be 'notApplicable'."
     ::= { atmSuPortEtherEntry 7 }

atmSuPortEtherRIPMode OBJECT-TYPE
     SYNTAX  INTEGER {
     rip1					   (1),
     rip2					   (2),
     rip1And2			       (3),
     none					   (4),
	 notApplicable           (255)
     }
	 MAX-ACCESS  read-write
     STATUS  current
     DESCRIPTION
     "RIP Mode. When application is not router value must be 'notApplicable'."
     ::= { atmSuPortEtherEntry 8 }

atmSuPortEtherBridgingMode OBJECT-TYPE
     SYNTAX  INTEGER {
     accessOnly         (1),
     accessAndSwitching (2),
	 notApplicable    (255)
     }
 	 MAX-ACCESS  read-write
     STATUS  current
     DESCRIPTION
     "Bridging mode can be one of the following: 
			ATM <> Ethernet - Bridging is between the Ethernet 
			port and the ATM port (there is no bridging between VCs).
			ATM <> Ethernet + ATM - Bridging is done both between 
			the Ethernet port and the ATM port and also between VCs.
			When application is router value must be 'notApplicable'."
     ::= { atmSuPortEtherEntry 9 }

atmSuPortEtherARPTimeout OBJECT-TYPE
     SYNTAX  Integer32 (0..10)
	 MAX-ACCESS  read-write
     STATUS  current
     DESCRIPTION
     "ARP Timeout. When application is not router or when 
     this object is not applicable, value must be 0."
	 DEFVAL { 5 }
     ::= { atmSuPortEtherEntry 10 }

atmSuPortEtherAgingTime OBJECT-TYPE
	 SYNTAX   Integer32 (0..1000000)
	 MAX-ACCESS   read-write
	 STATUS   current
	 DESCRIPTION
     "The timeout period in seconds for aging out stored information.
      valid values are 10...1000000. The value of (0) has
      the special meaning - not applicable. "
     ::= { atmSuPortEtherEntry 11 }

atmSuPortEtherPppOEEnable OBJECT-TYPE
	 SYNTAX   INTEGER  {
	 notApplicable (1),
	 off           (2),
	 on            (3)
	 }
	 MAX-ACCESS   read-write
	 STATUS   current
	 DESCRIPTION
     "Enable or Disable transparent PPP over ethernet bridge.
      When PPP over Ethernet is enabled, non PPP traffic is 
      blocked by the bridge."
     ::= { atmSuPortEtherEntry 12 }

atmSuPortEtherStatus OBJECT-TYPE
	 SYNTAX   INTEGER  {
	 active     (1),
	 createAndGo(4),
	 destroy    (6)
	 }
	 MAX-ACCESS   read-write
	 STATUS   current
	 DESCRIPTION
     "This object allows user to add/remove entries to/from this table.
      It will be supported only by certain devices.
      destroy - may not be possible for certain interfaces."
     ::= { atmSuPortEtherEntry 13 }


-- *************************************************************
-- *************************************************************
--            Cross-Connect connections definitions
-- *************************************************************
-- *************************************************************

atmSuCrossConnect   OBJECT IDENTIFIER ::= { atmSu 3 } -- cross connect definitions


-- *************************************************************
--      RAD ATM to Frame Relay endpoints Connections group
-- *************************************************************

atmSuCrossConnectAtmFr   OBJECT IDENTIFIER ::= { atmSuCrossConnect 1 }

--AtmSuCrossConnectAtmFrDescrIndex ::= TEXTUAL-CONVENTION
--      STATUS     current
--      DESCRIPTION
--       "The value of this object identifies the row
--        in the atmSuCrossConnectAtmFrDescrTable."
--      SYNTAX     Integer32


atmSuCrossConnectAtmFrDescriptor
      OBJECT IDENTIFIER ::= { atmSuCrossConnectAtmFr 1 }


-- *************************************************************
--  RAD ATM to Frame Relay connection types group
--  The group contains ATM to Frame Relay connection modes,
--  defining the connection parameters.
-- *************************************************************

atmFrCrossConnectNetwork OBJECT IDENTIFIER ::= { atmSuCrossConnectAtmFrDescriptor  1 }
     -- atmFrCrossConnectNetwork OBJECT-IDENTITY
     -- STATUS     current
     -- DESCRIPTION
     --  "This connection descriptor is network connection mode.
     --   The use of the parameter vector for this type:

     --   Clp2De : ATM CLP to Frame Relay DE mapping mode.
     --          The following values are allowed:
     --     convSscs- The DE bit of the FR-SSCS PDU is copied Q.922
     --               DE field.
     --     conv- If one or more ATM cells belonging to a frame has
     --           its CLP bit set, or the DE field
     --           of the FR-SSCS PDU is set, then the DE bit
     --           of the Q.922 core frame is set.

     --   De2Clp: Frame Relay DE to ATM CLP mapping mode.
--		        ( DE bit is always copied unchanged to the FR-SSCS PDU header ).
  --            The following values are allowed:
  --        conv   - The Q.922 DE bit is mapped to every CLP bit.
  --        always0- CLP bit is always 0.
  --        always1- CLP bit is always 1.

  --      Fecn2Efci  : Not used

  --      MappingMode: Not used
  --     "
  --    ::= { atmSuCrossConnectAtmFrDescriptor 1}

 --     atmFrCrossConnectService OBJECT-IDENTITY
 --     STATUS     current
 --     DESCRIPTION
 --      "This connection descriptor is service connection mode.
 --       The use of the parameter vector for this type:

--        Clp2De : ATM CLP to Frame Relay DE mapping mode.
--               The following values are allowed:
--          conv   - If one or more ATM cells belonging to a frame has
--                   its CLP bit set, then the DE bit
--                   of the Q.922 core frame is set.
--          always0- The DE bit is always 0.
--          always1- The DE bit is always 1.

--        De2Clp : Frame Relay DE to ATM CLP mapping mode.
--               The following values are allowed:
--          conv   - The DE bit is mapped to every CLP bit.
--          always0- CLP bit is always 0
--          always1- CLP bit is always 1

--        Fecn2Efci: Frame Relay FECN to ATM EFCI mapping mode.
--                 The following values are allowed:
--          conv   - The FECN bit is mapped to every EFCI bit.
--          always0- EFCI bit is always 0.

--        MappingMode: Upper Layer mapping mode.
--            The following values are allowed:
--          transparent - trasparent	mode
--          translation - translation mode

--        note : value 0 for parameter means that it is not supported .
--        "
-- ::= { atmSuCrossConnectAtmFrDescriptor 2 }

atmFrCrossConnectService OBJECT IDENTIFIER ::= { atmSuCrossConnectAtmFrDescriptor 2 }

-- *************************************************************
--  RAD ATM to Frame Relay connection descriptor table.
-- *************************************************************


atmFrDescrTable    OBJECT-TYPE
      SYNTAX      SEQUENCE OF AtmFrDescrEntry
      MAX-ACCESS    not-accessible
      STATUS       current
      DESCRIPTION
       "This table contains information on ATM to FR Connection
        descriptor types, and their associated parameters."
      ::= { atmSuCrossConnectAtmFr 2 }

atmFrDescrEntry    OBJECT-TYPE
      SYNTAX           AtmFrDescrEntry
      MAX-ACCESS        not-accessible
      STATUS           current
      DESCRIPTION
       "This list contains ATM to FR Connection descriptor
        type, and its associated parameters."
      INDEX  { atmFrDescrIndex }
      ::= { atmFrDescrTable 1}

AtmFrDescrEntry    ::= SEQUENCE  {
      atmFrDescrIndex
            Integer32, -- was AtmSuCrossConnectAtmFrDescrIndex,
      atmFrDescrType
            OBJECT IDENTIFIER,
      atmFrDescrClp2De
            INTEGER,
      atmFrDescrDe2Clp
            INTEGER,
      atmFrDescrFecn2Efci
            INTEGER,
      atmFrDescrMappingMode
            INTEGER,
      atmFrDescrRowStatus
            RowStatus
      }

atmFrDescrIndex  OBJECT-TYPE
      SYNTAX  Integer32 -- was AtmSuCrossConnectAtmFrDescrIndex
      MAX-ACCESS  read-only
      STATUS  current
      DESCRIPTION
       "This object is used to identify the row index of
        the ATM to FR connection descriptor table."
      ::= { atmFrDescrEntry 1 }

atmFrDescrType  OBJECT-TYPE
      SYNTAX  OBJECT IDENTIFIER
      MAX-ACCESS  read-create
      STATUS  current
      DESCRIPTION
       "The value of this object identifies the type
        of the ATM to FR Connection descriptor.
        The type may indicate Network connection descriptor
        or a Service connection descriptor with one or more
        parameters.
        These parameters are specified as a parameter
        vector, in the corresponding instances of the
        objects:
                          atmFrDescrClp2De
                          atmFrDescrDe2Clp
                          atmFrDescrFecn2Efci
                          atmFrDescrMappingMode."
      ::= { atmFrDescrEntry 2 }

atmFrDescrClp2De    OBJECT-TYPE
      SYNTAX  INTEGER
	  {
		convSscs (1),
	    conv     (2),
		always0  (3),
		always1  (4)
	  }
      MAX-ACCESS  read-create
      STATUS  current
      DESCRIPTION
       "The first parameter of the ATM to FR Connection
        descriptor used according to the value of atmFrDescrType."
      DEFVAL { conv }
      ::= { atmFrDescrEntry 3 }

atmFrDescrDe2Clp    OBJECT-TYPE
      SYNTAX  INTEGER
	  {
	    conv     (1),
		always0  (2),
		always1  (3)
	  }
      MAX-ACCESS  read-create
      STATUS  current
      DESCRIPTION
       "The second parameter of the ATM to FR Connection
        descriptor used according to the value of atmFrDescrType."
      DEFVAL { conv }
      ::= { atmFrDescrEntry 4 }

atmFrDescrFecn2Efci    OBJECT-TYPE
      SYNTAX  INTEGER
	  {
	    conv     (1),
		always0  (2)
	  }
      MAX-ACCESS  read-create
      STATUS  current
      DESCRIPTION
       "The third parameter of the ATM to FR Connection
        descriptor used according to the value of atmFrDescrType."
      DEFVAL { conv }
      ::= { atmFrDescrEntry 5 }

atmFrDescrMappingMode    OBJECT-TYPE
      SYNTAX  INTEGER
	  {
		transparent  (1),
	    translation  (2)
      }
      MAX-ACCESS  read-create
      STATUS  current
      DESCRIPTION
       "The fourth parameter of the ATM to FR Connection
        descriptor used according to the value of atmFrDescrType."
      DEFVAL { translation }
      ::= { atmFrDescrEntry 6 }

atmFrDescrRowStatus       OBJECT-TYPE
      SYNTAX  RowStatus
      MAX-ACCESS  read-create
      STATUS  current
      DESCRIPTION
       "This object is used to create,
        modify or delete a row in this table."
      DEFVAL { active }
      ::= { atmFrDescrEntry 7 }


-- *************************************************************
--  RAD ATM to Frame Relay connection table group
-- *************************************************************

--  RAD ATM to Frame Relay connection table.

atmSuCrossConnectAtmFrIndexNext    OBJECT-TYPE
     SYNTAX  Integer32 
     MAX-ACCESS   read-only
     STATUS  current
     DESCRIPTION
      "This object contains an appropriate value to
       be used for atmFrCnfgCrossConnectIndex when creating
       entries in the atmFrCnfgTable.  The value
       0 indicates that no unassigned entries are
       available. To obtain the atmFrCnfgCrossConnectIndex
       value for a new entry, the manager issues a
       management protocol retrieval operation to obtain
       the mandatory value of this object.  After each
       retrieval, the agent should modify the value to
       the next unassigned index."
    ::= { atmSuCrossConnectAtmFr 3 }

atmFrCnfgTable OBJECT-TYPE
      SYNTAX SEQUENCE OF AtmFrCnfgEntry
      MAX-ACCESS  not-accessible
      STATUS current
      DESCRIPTION
       "This table defines virtual connections between ATM and
        Frame Relay endpoints."
      ::= { atmSuCrossConnectAtmFr 4 }


atmFrCnfgEntry OBJECT-TYPE
      SYNTAX  AtmFrCnfgEntry
      MAX-ACCESS  not-accessible
      STATUS current
      DESCRIPTION
       "An entry defines virtual connection between ATM and
        Frame Relay endpoint."
      INDEX {
              atmFrCnfgCrossConnectIndex,
              atmFrCnfgAtmIfIndex,
              atmFrCnfgAtmVpi,
              atmFrCnfgAtmVci,
              atmFrCnfgFrIfIndex,
              atmFrCnfgDlci
            }
      ::= { atmFrCnfgTable 1 }

AtmFrCnfgEntry ::= SEQUENCE {
      atmFrCnfgCrossConnectIndex
              Integer32,
      atmFrCnfgAtmIfIndex
              Integer32,
      atmFrCnfgAtmVpi
              Integer32,
      atmFrCnfgAtmVci
              Integer32,
      atmFrCnfgFrIfIndex
              Integer32,
      atmFrCnfgDlci
              Integer32,
      atmFrCnfgAdminStatus
              INTEGER,
      atmFrCnfgOperStatus
              INTEGER,
      atmFrCnfgLastChange
              TimeStamp,
      atmFrCnfgMappingDescrIndex
              Integer32, -- was AtmSuCrossConnectAtmFrDescrIndex,
      atmFrCnfgSscsDlci
              Integer32,
      atmFrCnfgTrafficDescrIndex
              AtmTrafficDescrParamIndex,
      atmFrCnfgPriority
              INTEGER,
      atmFrCnfgRowStatus
              RowStatus,
	  atmFrCnfgAllocatedBuffers
	          Integer32
      }

atmFrCnfgCrossConnectIndex OBJECT-TYPE
     SYNTAX  Integer32 
     MAX-ACCESS   read-only
     STATUS  current
     DESCRIPTION
      "A unique value to identify this cross-connect."
      ::= { atmFrCnfgEntry 1 }

atmFrCnfgAtmIfIndex OBJECT-TYPE
      SYNTAX Integer32
      MAX-ACCESS  read-only
      STATUS current
      DESCRIPTION
       "The ifIndex associated to the ATM interface."
      ::= { atmFrCnfgEntry 2 }

atmFrCnfgAtmVpi   OBJECT-TYPE
      SYNTAX Integer32  (1..4095)
      MAX-ACCESS   read-only
      STATUS current
      DESCRIPTION
       "The Vpi number of the ATM end point."
      ::= { atmFrCnfgEntry 3 }

atmFrCnfgAtmVci   OBJECT-TYPE
      SYNTAX Integer32  (0..65535)
      MAX-ACCESS   read-only
      STATUS current
      DESCRIPTION
       "The Vci number of the ATM end point."
      ::= { atmFrCnfgEntry 4 }

atmFrCnfgFrIfIndex   OBJECT-TYPE
      SYNTAX  Integer32
      MAX-ACCESS   read-only
      STATUS current
      DESCRIPTION
       "The ifIndex associated to the Frame Relay
        interface."
      ::= { atmFrCnfgEntry 5 }

atmFrCnfgDlci   OBJECT-TYPE
      SYNTAX Integer32
      MAX-ACCESS   read-only
      STATUS current
      DESCRIPTION
       "The DLCI number of the FR end point."
      ::= { atmFrCnfgEntry 6 }

atmFrCnfgAdminStatus   OBJECT-TYPE
      SYNTAX INTEGER {
             up(1),
             down(2)
      }
      MAX-ACCESS  read-create
      STATUS current
      DESCRIPTION
       "This object indicates the connection status requested by the user."
      ::= { atmFrCnfgEntry 7 }

atmFrCnfgOperStatus   OBJECT-TYPE
      SYNTAX INTEGER {
             up(1),
             down(2)
      }
      MAX-ACCESS  read-only
      STATUS current
      DESCRIPTION
       "This object indicates the Operational status of the connection."
      ::= { atmFrCnfgEntry 8 }

atmFrCnfgLastChange   OBJECT-TYPE
      SYNTAX TimeStamp
      MAX-ACCESS  read-only
      STATUS current
      DESCRIPTION
       "The value of sysUpTime at the time the ATM to FR
        connection entered its mandatory operational state.
        If the mandatory state was entered prior to the last
        re-initialization of the local network management
        subsystem, then this object contains a zero value."
      ::= { atmFrCnfgEntry 9 }

atmFrCnfgMappingDescrIndex    OBJECT-TYPE
      SYNTAX     Integer32 -- was AtmSuCrossConnectAtmFrDescrIndex
      MAX-ACCESS   read-create
      STATUS   current
      DESCRIPTION
       "The value of this object identifies the row
        in the atmFrDescrTable."
      ::= { atmFrCnfgEntry 10 }

atmFrCnfgSscsDlci   OBJECT-TYPE
      SYNTAX Integer32
      MAX-ACCESS   read-create
      STATUS current
      DESCRIPTION
       "The DLCI number given to the SSCS Sub-layer for network interworking only
       ( the default value is 'atmFrCnfgDlci' ).
        for Service Interworking do not implement this variable."
      ::= { atmFrCnfgEntry 11 }

-- atmFrCnfgBitRate   OBJECT-TYPE
--       SYNTAX INTEGER
--	  {
--	    ubr  (1) ,
--		vbr  (2) ,
--	    abr  (3)
--	  }
--       MAX-ACCESS   read-create
--       STATUS current
--       DESCRIPTION
--        "The traffic bit rate mode for this connection.
--         note :setting this value is allowed only to point2point connections.
--               for many2one connections is being set by the
--               atmFrCrossConnectMany2OneRootsTable and this field is equal
--               to this setting."
--       ::= { atmFrCnfgEntry 12 }

atmFrCnfgTrafficDescrIndex  OBJECT-TYPE
      SYNTAX             AtmTrafficDescrParamIndex
      MAX-ACCESS          read-create
      STATUS             current
      DESCRIPTION
       "The value of this object identifies the row
        in the atmTrafficDescrParamTable which
        applies to the transmit direction of the VCL.
        note :setting this value is allowed only to point2point connections.
              for many2one connections is being set by the
              atmFrCrossConnectMany2OneRootsTable and this field is equal
              to this setting."
      ::= { atmFrCnfgEntry 12 }

atmFrCnfgPriority   OBJECT-TYPE
      SYNTAX  INTEGER
	  {
	    highPriority   (1),
	    mediumPriority (2),
	    lowPriority    (3)
      }
      MAX-ACCESS  read-create
      STATUS current
      DESCRIPTION
       "This object define the priority of connection.
        The first parameter affects the transmition of cells in Conjested
        network is the bitRate( Cbr has the highest priority and then Vbr,Ubr )
        In connections with the same bitRate this object will define the priority."
      ::= { atmFrCnfgEntry 13 }

atmFrCnfgRowStatus   OBJECT-TYPE
      SYNTAX RowStatus
      MAX-ACCESS  read-create
      STATUS current
      DESCRIPTION
       "This object is used to create
        a new row or modify or delete an
        existing row in this table."
      ::= { atmFrCnfgEntry 14 }


atmFrCnfgAllocatedBuffers  OBJECT-TYPE
      SYNTAX       Integer32 (10..217)
      MAX-ACCESS   read-create
      STATUS current
      DESCRIPTION
       "This object enables user to limit the amount of buffers 
       used by the connection.
       The limit set by this object will give 
       the effect of a virtual buffer pool per connection. 

       The user can allocate between 10 to 217 buffers 
       to every connection. By default the limit is 50 buffers.

       Sum of limits allocated to all connections 
       must not exceed the total amount of available buffers. 

       Whenever a connection exceeds it's buffer limit 
       due to congestion or burst - traffic is discarded"
	   DEFVAL { 50 }
      ::= { atmFrCnfgEntry 15 }


atmFrMaxMany2OneConnsPerVcc OBJECT-TYPE
      SYNTAX Integer32
      MAX-ACCESS  read-only
      STATUS current
      DESCRIPTION
       "The Maximum Number of many2one cross-connect connections
        allowed per Vcc ."
      ::= { atmSuCrossConnectAtmFr 5 }


-- *************************************************************
--      RAD ATM to ATM-DXI endpoints Connections group
-- *************************************************************

atmSuCrossConnectAtmDxi   OBJECT IDENTIFIER ::= { atmSuCrossConnect 2 }


atmSuCrossConnectAtmDxiIndexNext    OBJECT-TYPE
     SYNTAX  Integer32 
     MAX-ACCESS   read-only
     STATUS  current
     DESCRIPTION
      "This object contains an appropriate value to
       be used for atmDxiCnfgCrossConnectIndex when creating
       entries in the atmDxiCnfgTable.  The value
       0 indicates that no unassigned entries are
       available. To obtain the atmDxiCnfgCrossConnectIndex
       value for a new entry, the manager issues a
       management protocol retrieval operation to obtain
       the mandatory value of this object.  After each
       retrieval, the agent should modify the value to
       the next unassigned index."
    ::= { atmSuCrossConnectAtmDxi 1 }

atmDxiCnfgTable OBJECT-TYPE
      SYNTAX  SEQUENCE OF AtmDxiCnfgEntry
      MAX-ACCESS  not-accessible
      STATUS current
      DESCRIPTION
       "This table defines virtual connections between ATM and
        ATM-DXI endpoints."
      ::= { atmSuCrossConnectAtmDxi 2 }


atmDxiCnfgEntry OBJECT-TYPE
      SYNTAX  AtmDxiCnfgEntry
      MAX-ACCESS  not-accessible
      STATUS current
      DESCRIPTION
       "An entry defines virtual connection between ATM and
        ATM-DXI endpoint."
      INDEX {
              atmDxiCnfgCrossConnectIndex,
              atmDxiCnfgAtmIfIndex,
              atmDxiCnfgAtmVpi,
              atmDxiCnfgAtmVci,
              atmDxiCnfgDxiIfIndex,
              atmDxiCnfgDfa
            }
      ::= { atmDxiCnfgTable 1 }

AtmDxiCnfgEntry ::= SEQUENCE {
         atmDxiCnfgCrossConnectIndex
                  Integer32,
         atmDxiCnfgAtmIfIndex
                  Integer32,
         atmDxiCnfgAtmVpi
                  Integer32,
         atmDxiCnfgAtmVci
                  Integer32,
         atmDxiCnfgDxiIfIndex
                  Integer32,
         atmDxiCnfgDfa
                  Integer32,
         atmDxiCnfgAdminStatus
                  INTEGER,
         atmDxiCnfgOperStatus
                  INTEGER,
         atmDxiCnfgLastChange
                  TimeStamp,
         atmDxiCnfgTrafficDescrIndex
              AtmTrafficDescrParamIndex,
         atmDxiCnfgPriority
                  INTEGER,
         atmDxiCnfgRowStatus
                  RowStatus

         }

atmDxiCnfgCrossConnectIndex OBJECT-TYPE
     SYNTAX  Integer32 
     MAX-ACCESS   read-only
     STATUS  current
     DESCRIPTION
      "A unique value to identify this cross-connect."
      ::= { atmDxiCnfgEntry 1 }

atmDxiCnfgAtmIfIndex OBJECT-TYPE
      SYNTAX Integer32
      MAX-ACCESS  read-only
      STATUS current
      DESCRIPTION
       "The ifIndex associated to the ATM interface."
      ::= { atmDxiCnfgEntry 2 }

atmDxiCnfgAtmVpi   OBJECT-TYPE
      SYNTAX Integer32 (1..4095)
      MAX-ACCESS  read-only
      STATUS current
      DESCRIPTION
       "The Vpi number of the ATM end point."
      ::= { atmDxiCnfgEntry 3 }

atmDxiCnfgAtmVci   OBJECT-TYPE
      SYNTAX Integer32 (0..65535)
      MAX-ACCESS  read-only
      STATUS current
      DESCRIPTION
       "The Vci number of the ATM end point."
      ::= { atmDxiCnfgEntry 4 }

atmDxiCnfgDxiIfIndex   OBJECT-TYPE
      SYNTAX Integer32
      MAX-ACCESS  read-only
      STATUS current
      DESCRIPTION
       "The ifIndex associated to the atm-dxi interface."
      ::= { atmDxiCnfgEntry 5 }

atmDxiCnfgDfa   OBJECT-TYPE
      SYNTAX Integer32
      MAX-ACCESS  read-only
      STATUS current
      DESCRIPTION
       "The DFA number of the DXI end point."
      ::= { atmDxiCnfgEntry 6 }

atmDxiCnfgAdminStatus   OBJECT-TYPE
      SYNTAX INTEGER {
          up(1),
          down(2)
      }
      MAX-ACCESS  read-create
      STATUS current
      DESCRIPTION
       "The requested state of the ATM to DXI connection."
      ::= { atmDxiCnfgEntry 7 }

atmDxiCnfgOperStatus   OBJECT-TYPE
      SYNTAX INTEGER {
          up(1),
          down(2)
      }
      MAX-ACCESS  read-only
      STATUS current
      DESCRIPTION
       "The real operational status of the ATM to DXI connection."
      ::= { atmDxiCnfgEntry 8 }

atmDxiCnfgLastChange   OBJECT-TYPE
      SYNTAX TimeStamp
      MAX-ACCESS  read-only
      STATUS current
      DESCRIPTION
       "The value of sysUpTime at the time the ATM to DXI
        connection entered its mandatory operational state.
        If the mandatory state was entered prior to the last
        re-initialization of the local network management
        subsystem, then this object contains a zero value.
        Same value define both direction ( Atm2Dxi and Dxi2Atm )."
      ::= { atmDxiCnfgEntry 9 }

-- atmDxiCnfgBitRate   OBJECT-TYPE
--       SYNTAX INTEGER
--	  {
--         ubr  (1) ,
--         vbr  (2) ,
--         abr  (3)
--	  }
--       MAX-ACCESS   read-create
--       STATUS current
--       DESCRIPTION
--        "The traffic bit rate mode for this connection."
--       ::= { atmDxiCnfgEntry 10 }

atmDxiCnfgTrafficDescrIndex  OBJECT-TYPE
      SYNTAX             AtmTrafficDescrParamIndex
      MAX-ACCESS          read-create
      STATUS             current
      DESCRIPTION
       "The value of this object identifies the row
        in the atmTrafficDescrParamTable which
        applies to the transmit direction of the VCL."
      ::= { atmDxiCnfgEntry 10 }

atmDxiCnfgPriority   OBJECT-TYPE
      SYNTAX  INTEGER
	  {
	    highPriority   (1),
	    mediumPriority (2),
	    lowPriority    (3)
      }
      MAX-ACCESS  read-create
      STATUS current
      DESCRIPTION
       "This object define the priority of connection.
        The first parameter affects the transmition of cells in Conjested
        network is the bitRate( Cbr has the highest priority and then Vbr,Ubr )
        In connections with the same bitRate this object will define the priority."
      ::= { atmDxiCnfgEntry 11 }

atmDxiCnfgRowStatus   OBJECT-TYPE
      SYNTAX  RowStatus
      MAX-ACCESS  read-create
      STATUS current
      DESCRIPTION
       "This object is used to create a new row or
        modify or delete an existing row in this table."
      ::= { atmDxiCnfgEntry 12 }



-- *************************************************************
--      RAD ATM to CBR Connections group (excluded CES/DBCES
--      connections which are handled in the CES table)
-- *************************************************************

atmSuAtmCbr   OBJECT IDENTIFIER ::= { atmSuCrossConnect 3 }


atmCbrCnfgTable OBJECT-TYPE
      SYNTAX  SEQUENCE OF AtmCbrCnfgEntry
      MAX-ACCESS  not-accessible
      STATUS current
      DESCRIPTION
       "This table defines AAL1 virtual connections (not CES) 
        between ATM port and DS1-CBR port."
      ::= { atmSuAtmCbr 1 }


atmCbrCnfgEntry OBJECT-TYPE
      SYNTAX  AtmCbrCnfgEntry
      MAX-ACCESS  not-accessible
      STATUS current
      DESCRIPTION
       "An entry defines virtual connection between ATM port and
        DS1-CBR port."
      INDEX {
              atmCbrCnfgAtmIfIndex,
              atmCbrCnfgAtmVpi,
              atmCbrCnfgAtmVci,
              atmCbrCnfgCbrIfIndex
            }
      ::= { atmCbrCnfgTable 1 }

AtmCbrCnfgEntry ::= SEQUENCE {
         atmCbrCnfgAtmIfIndex
                  Integer32,
         atmCbrCnfgAtmVpi
                  Integer32,
         atmCbrCnfgAtmVci
                  Integer32,
         atmCbrCnfgCbrIfIndex
                  Integer32,
         atmCbrCnfgAdminStatus
                  INTEGER,
         atmCbrCnfgOperStatus
                  INTEGER,
         atmCbrCnfgLastChange
                  TimeStamp,
         atmCbrCnfgAAL1Signalling
                  INTEGER,
         atmCbrCnfgRxTimeSlots
 	   TimeSlots,
         atmCbrCnfgRxBytesPerCell
                  Integer32,
         atmCbrCnfgTxTimeSlots
 	    TimeSlots,
         atmCbrCnfgTxBytesPerCell
                  Integer32,
 	atmCbrCnfgParity
	     INTEGER,
	atmCbrCnfgRowStatus
           RowStatus,
    atmCbrCnfgService
	      INTEGER
         }


atmCbrCnfgAtmIfIndex OBJECT-TYPE
      SYNTAX Integer32
      MAX-ACCESS  read-only
      STATUS current
      DESCRIPTION
       "The ifIndex associated to the ATM interface."
      ::= { atmCbrCnfgEntry 1 }

atmCbrCnfgAtmVpi   OBJECT-TYPE
      SYNTAX Integer32 (1..4095)
      MAX-ACCESS  read-only
      STATUS current
      DESCRIPTION
       "The Vpi number of the ATM end point."
      ::= { atmCbrCnfgEntry 2 }

atmCbrCnfgAtmVci   OBJECT-TYPE
      SYNTAX Integer32 (0..65535)
      MAX-ACCESS  read-only
      STATUS current
      DESCRIPTION
       "The Vci number of the ATM end point."
      ::= { atmCbrCnfgEntry 3 }

atmCbrCnfgCbrIfIndex OBJECT-TYPE
      SYNTAX Integer32
      MAX-ACCESS  read-only
      STATUS current
      DESCRIPTION
       "The ifIndex associated to the logical interface of DS0s bundle
        or to ifIndex of one of the data ports."
      ::= { atmCbrCnfgEntry 4 }

atmCbrCnfgAdminStatus   OBJECT-TYPE
      SYNTAX INTEGER {
          up   (1),
          down (2)
      }
      MAX-ACCESS  read-create
      STATUS current
      DESCRIPTION
       "The requested status of the connection."
      ::= { atmCbrCnfgEntry 5 }

atmCbrCnfgOperStatus   OBJECT-TYPE
      SYNTAX INTEGER {
          up   (1),
          down (2)
      }
      MAX-ACCESS  read-only
      STATUS current
      DESCRIPTION
       "The real operational status of the connection."
      ::= { atmCbrCnfgEntry 6 }

atmCbrCnfgLastChange   OBJECT-TYPE
      SYNTAX TimeStamp
      MAX-ACCESS  read-only
      STATUS current
      DESCRIPTION
       "The value of sysUpTime at the time the ATM to CBR
        connection entered its mandatory operational state.
        If the mandatory state was entered prior to the last
        re-initialization of the local network management
        subsystem, then this object contains a zero value.
        Same value define both direction ( Atm2Cbr and Cbr2Atm )."
      ::= { atmCbrCnfgEntry 7 }

atmCbrCnfgAAL1Signalling OBJECT-TYPE
      SYNTAX  INTEGER
      {
            off (1),
            on  (2)
      }
      MAX-ACCESS  read-create
      STATUS  current
      DESCRIPTION
      "Not in use. Must be always 'off'."
      ::= { atmCbrCnfgEntry 8 }

atmCbrCnfgRxTimeSlots   OBJECT-TYPE
      SYNTAX TimeSlots 
      MAX-ACCESS read-create
      STATUS current
      DESCRIPTION
     "This value indicates the time-slots used by this connection for receiving.
        It uses 32 bits for E1 and low 24 bits for T1.
        each bit represents a time slot for receiving :
        time-slot 0  = bit 0 (LSB - most right bit in last byte),
           ...
           ...
        time-slot 31 = bit 31 (MSB - most left bit in first byte ).
        value '0' indicate unused time-slot and value '1' indicates used time-slot.
        On set-request the user indicates the time-slot he needs for requested ATM-Vcc
        by putting '1' to the right bits.
        note : time-slots '0' and '16' are used for signalling in E1 interface.
        Currently not in use. Must be '0'."
      ::= { atmCbrCnfgEntry 9 }

atmCbrCnfgRxBytesPerCell   OBJECT-TYPE
      SYNTAX  Integer32
      MAX-ACCESS read-create
      STATUS current 
      DESCRIPTION
       "number of bytes to be receive in order per cell to low the delay. "
      DEFVAL { 47 }
      ::= { atmCbrCnfgEntry 10 }

atmCbrCnfgTxTimeSlots   OBJECT-TYPE
      SYNTAX TimeSlots 
      MAX-ACCESS read-create
      STATUS current 
      DESCRIPTION
     "This value indicates the time-slots used by this connection for receiving.
        It uses 32 bits for E1 and low 24 bits for T1.
        each bit represents a time slot for receiving :
        time-slot 0  = bit 0 (LSB - most right bit in last byte),
           ...
           ...
        time-slot 31 = bit 31 (MSB - most left bit in first byte ).
        value '0' indicate unused time-slot and value '1' indicates used time-slot.
        On set-request the user indicates the time-slot he needs for requested ATM-Vcc
        by putting '1' to the right bits.
        note : time-slots '0' and '16' are used for signalling in E1 interface.
        Currently not in use. Must be '0'."
      ::= { atmCbrCnfgEntry 11 }

atmCbrCnfgTxBytesPerCell   OBJECT-TYPE
      SYNTAX  Integer32
      MAX-ACCESS read-create
      STATUS current 
      DESCRIPTION
       "number of bytes to be transmit in order per cell to low the delay. "
      DEFVAL { 47 }
      ::= { atmCbrCnfgEntry 12 }

atmCbrCnfgParity OBJECT-TYPE
      SYNTAX INTEGER 
      {
            off (1),
            on  (2),
            notApplicable (3)
      }
      MAX-ACCESS read-create
      STATUS current
      DESCRIPTION
      " Controls the use of pointer parity when using 
        the STRUCTURED or STRUCTURED WITH POINTER connection type. 
		as defined by atmCbrCnfgService.
	    ON  - Pointer parity bit generation at the transmit side, 
	          and checking of parity bit for error detection at 
	          the receiving side enabled. 
	          Supported only for STRUCTURED or STRUCTURED WITH POINTER service.
	    OFF -  Pointer parity generation and checking disabled. 
	           Supported only for STRUCTURED or STRUCTURED WITH POINTER service.
		N/A -  Not applicable. This is the only option 
		       when selecting UNSTRUCTURED or STRUCTURED WITHOUT POINTER."
      ::= { atmCbrCnfgEntry 13 }

atmCbrCnfgRowStatus   OBJECT-TYPE
      SYNTAX  RowStatus
      MAX-ACCESS read-create
      STATUS current 
      DESCRIPTION
       "This object is used to create a new row or
        modify or delete an existing row in this table."
      ::= { atmCbrCnfgEntry 14 }
	  
atmCbrCnfgService      OBJECT-TYPE
    SYNTAX   INTEGER 
    {
    notApplicable                     (1),
    unstructured                      (2),
    structured                        (3), 
    structuredWithPointer             (4), 
    structuredWithoutPointer          (5),
	structuredControlSignalsTransport (6)
	    }
    MAX-ACCESS    read-create
    STATUS        current
    DESCRIPTION
    "Define if DSx service is structured or unstructured.
     A structured(3) interface is some nx64Kbps. (n x DS0 = n Time Slots)
     An unstructured (2) interface is  full DSx, x >0. 
     (1.544Mbps, 2.048Mbps, 6.312Mbps, 44.736 Mbps, or 34.368 Mbps.)

     This objects selects the connection type also 
     for AAL1 Stream for Data port.

     The available selections depend on the data rate
     selected. 

     For the 64 kbps rate:
	 STRUCTURED WITH POINTER  = structure(4)
	 Use of the structured service as defined in ATMF AF-VTOA-0078.000.

     STRUCTURED WITHOUT POINTER : same as above, but without 
     using a pointer (the resulting cell structure is similar
     to that of the unstructured service cells).

     Default: STRUCTURED WITH POINTER

	 structuredControlSignalsTransport -Pointer is used to
	 transfer Data Control Signals through ATM network.  

     For other rates:
     STRUCTURED : Use of structured service as defined in ATMF AF-VTOA-0078.000.
     UNSTRUCTURED : Use of unstructured service as defined in
      ATMF document AF-VTOA-0078.000." 
    ::= { atmCbrCnfgEntry 15 }
								  

-- *************************************************************
--      RAD ATM to CES ( Circuit-Emulation or DBCES data over DS1 )
--      Connections group
-- *************************************************************

atmCESConfExtnsTable OBJECT-TYPE
      SYNTAX  SEQUENCE OF AtmCESConfExtnsEntry
      MAX-ACCESS  not-accessible
      STATUS current
      DESCRIPTION
       "This table defines virtual connections between ATM port and
        DS1-CBR port."
      ::= { atmSuAtmCbr 2 }


atmCESConfExtnsEntry OBJECT-TYPE
      SYNTAX  AtmCESConfExtnsEntry
      MAX-ACCESS  not-accessible
      STATUS current
      DESCRIPTION
       "An entry defines virtual connection between ATM port and
        DS1-CBR port."
--      AUGMENTS    { atmfCESConfEntry }
      INDEX { atmfCESCbrIndex }
      ::= { atmCESConfExtnsTable 1 }

AtmCESConfExtnsEntry ::= SEQUENCE {
      atmCESLastChange
            TimeStamp,
      atmCESRxBytesPerCell
            Integer32,
      atmCESTxBytesPerCell
            Integer32,
      atmCESAal1Type
            INTEGER,
      atmCESParity
            INTEGER,
      atmCESSigType
            INTEGER,
      atmCESSigABBits
            OCTET STRING,
	  atmCESConnectionName
            SnmpAdminString,
	  atmCESTcPattern
			Integer32
      }

atmCESLastChange   OBJECT-TYPE
      SYNTAX TimeStamp
      MAX-ACCESS  read-only
      STATUS current
      DESCRIPTION
       "The value of sysUpTime at the time the ATM to CBR
        connection entered its mandatory operational state.
        If the mandatory state was entered prior to the last
        re-initialization of the local network management
        subsystem, then this object contains a zero value."
      ::= { atmCESConfExtnsEntry 1 }

atmCESRxBytesPerCell   OBJECT-TYPE
      SYNTAX  Integer32  (1..47) 
      MAX-ACCESS read-write
      STATUS current 
      DESCRIPTION
       "Number of bytes to be received per cell, in order to decrease the delay. "
      DEFVAL { 47 }
      ::= { atmCESConfExtnsEntry 2 }

atmCESTxBytesPerCell   OBJECT-TYPE
      SYNTAX  Integer32  (1..47) 
      MAX-ACCESS read-write
      STATUS current 
      DESCRIPTION
       "Number of bytes to be transmitted per cell, in order to decrease the delay. "
      DEFVAL { 47 }
      ::= { atmCESConfExtnsEntry 3 }

atmCESAal1Type   OBJECT-TYPE
      SYNTAX INTEGER {
          ces(1),
          dbces(2),
		  transparent(3)
      }
      MAX-ACCESS read-write
      STATUS current
      DESCRIPTION
       "Type of CBR connection: CES , DBCES or transparent ."
      ::= { atmCESConfExtnsEntry 4 }

atmCESParity   OBJECT-TYPE
      SYNTAX INTEGER 
      {
            off (1),
            on  (2)
      }
      MAX-ACCESS read-write
      STATUS current
      DESCRIPTION
      " Indicate if we'll add even parity to the pointer of the structure of CES."
      ::= { atmCESConfExtnsEntry 5 }

atmCESSigType   OBJECT-TYPE
      SYNTAX INTEGER
      {
            eAndmOrPlar    (1),
            fxoLoopStart   (2),
            fxsLoopStart   (3),
            fxoGroundStart (4),
            fxsGroundStart (5),
            r2             (6),
            other          (7)
      }
      MAX-ACCESS read-write
      STATUS current
      DESCRIPTION
       "type of signalling for a DBCES connection.
        Must be 'other' for CES connection."
      ::= { atmCESConfExtnsEntry 6 }

atmCESSigABBits   OBJECT-TYPE
      SYNTAX OCTET STRING (SIZE(1))
      MAX-ACCESS read-write
      STATUS current
      DESCRIPTION
       "This attribute is applicable only when value of atmCESSigType is other.
        Represents the AB bits for Rx/Tx and their masks in this way:
        bits 7..6: Tx AB bits value,
        bits 5..4: Tx AB bits mask,
        bits 3..2: Rx AB bits value,
        bits 1..0: Rx AB bits mask.
        All bits must be 0 for CES connection."
      ::= { atmCESConfExtnsEntry 7 }

atmCESConnectionName   OBJECT-TYPE
      SYNTAX SnmpAdminString (SIZE (0..32))
      MAX-ACCESS read-write
      STATUS current
      DESCRIPTION
       "The Connection's name."
      ::= { atmCESConfExtnsEntry 8 }

atmCESTcPattern   OBJECT-TYPE
      SYNTAX Integer32
      MAX-ACCESS read-write
      STATUS current
      DESCRIPTION
       "Trunk conditioning data pattern to be sent upon a DS0 fail.
	  	Range is 0x0..0xFF."
      ::= { atmCESConfExtnsEntry 9 }

	  
-- *************************************************************
--      RAD ATM to ETHERNET endpoints Connections group
-- *************************************************************

atmSuCrossConnectAtmEther   OBJECT IDENTIFIER ::= { atmSuCrossConnect 4 }


atmSuCrossConnectAtmEtherIndexNext    OBJECT-TYPE
     SYNTAX  Integer32
     MAX-ACCESS  read-only
     STATUS  current
     DESCRIPTION
      "This object contains an appropriate value to
       be used for atmEtherCnfgCrossConnectIndex when creating
       entries in the atmEtherCnfgTable.  The value
       0 indicates that no unassigned entries are
       available. To obtain the atmEtherCnfgCrossConnectIndex
       value for a new entry, the manager issues a
       management protocol retrieval operation to obtain
       the current value of this object.  After each
       retrieval, the agent should modify the value to
       the next unassigned index."
    ::= { atmSuCrossConnectAtmEther 1 }

atmEtherCnfgTable OBJECT-TYPE
      SYNTAX  SEQUENCE OF AtmEtherCnfgEntry
      MAX-ACCESS  not-accessible
      STATUS  current
      DESCRIPTION
       "This table defines virtual connections between ATM and
        ATM-BridgedEthernet endpoints."
      ::= { atmSuCrossConnectAtmEther 2 }


atmEtherCnfgEntry OBJECT-TYPE
      SYNTAX  AtmEtherCnfgEntry
      MAX-ACCESS  not-accessible
      STATUS  current
      DESCRIPTION
       "An entry defines virtual connection between ATM and
        ATM-Ethernet endpoint."
      INDEX {
              atmEtherCnfgCrossConnectIndex,
              atmEtherCnfgAtmIfIndex,
              atmEtherCnfgAtmVpi,
              atmEtherCnfgAtmVci,
              atmEtherCnfgEtherIfIndex
            }
      ::= { atmEtherCnfgTable 1 }

AtmEtherCnfgEntry ::= SEQUENCE {
         atmEtherCnfgCrossConnectIndex
                  Integer32,
         atmEtherCnfgAtmIfIndex
                  Integer32,
         atmEtherCnfgAtmVpi
                  Integer32,
         atmEtherCnfgAtmVci
                  Integer32,
         atmEtherCnfgEtherIfIndex
                  Integer32,
         atmEtherCnfgMacAddr
                  MacAddress,
         atmEtherCnfgAdminStatus
                  INTEGER,
         atmEtherCnfgOperStatus
                  INTEGER,
         atmEtherCnfgLastChange
                  TimeStamp,
         atmEtherCnfgTrafficDescrIndex
                  AtmTrafficDescrParamIndex,
         atmEtherCnfgEncapsulationMode
                  INTEGER,
         atmEtherCnfgPriority
                  INTEGER,
         atmEtherCnfgRowStatus
                  RowStatus,
         atmEtherCnfgRouterIP
		              IpAddress,
         atmEtherCnfgRouterMask
				          IpAddress,
         atmEtherCnfgRouterFragmentation
						      INTEGER,
         atmEtherCnfgRouterRIPMode
								  INTEGER,
         atmEtherCnfgRouterMTU
                  Integer32,
         atmEtherCnfgPPPEncapsulation
                  INTEGER,
         atmEtherCnfgAllocatedBuffers
                  Integer32,               
         atmEtherCnfgPauseTrigger
                  INTEGER						 
         }

atmEtherCnfgCrossConnectIndex OBJECT-TYPE
     SYNTAX  Integer32
     MAX-ACCESS  read-only
     STATUS  current
     DESCRIPTION
      "A unique value to identify this cross-connect."
      ::= { atmEtherCnfgEntry 1 }

atmEtherCnfgAtmIfIndex OBJECT-TYPE
      SYNTAX Integer32
      MAX-ACCESS read-only
      STATUS current
      DESCRIPTION
       "The ifIndex associated to the ATM interface."
      ::= { atmEtherCnfgEntry 2 }

atmEtherCnfgAtmVpi   OBJECT-TYPE
      SYNTAX Integer32 (1..4095)
      MAX-ACCESS read-only
      STATUS current
      DESCRIPTION
       "The Vpi number of the ATM end point."
      ::= { atmEtherCnfgEntry 3 }

atmEtherCnfgAtmVci   OBJECT-TYPE
      SYNTAX Integer32 (0..65535)
      MAX-ACCESS read-only
      STATUS current
      DESCRIPTION
       "The Vci number of the ATM end point."
      ::= { atmEtherCnfgEntry 4 }

atmEtherCnfgEtherIfIndex   OBJECT-TYPE
      SYNTAX Integer32
      MAX-ACCESS read-only
      STATUS current
      DESCRIPTION
       "The ifIndex associated to the atm-Ethernet interface."
      ::= { atmEtherCnfgEntry 5 }

atmEtherCnfgMacAddr   OBJECT-TYPE
      SYNTAX MacAddress
      MAX-ACCESS read-only
      STATUS deprecated
      DESCRIPTION
       "The DFA number of the Ethernet end point."
      ::= { atmEtherCnfgEntry 6 }

atmEtherCnfgAdminStatus   OBJECT-TYPE
      SYNTAX INTEGER {
          up(1),
          down(2)
      }
      MAX-ACCESS read-create
      STATUS current
      DESCRIPTION
       "The requested state of the ATM to Ethernet connection."
      ::= { atmEtherCnfgEntry 7 }

atmEtherCnfgOperStatus   OBJECT-TYPE
      SYNTAX INTEGER {
          up(1),
          down(2)
      }
      MAX-ACCESS read-only
      STATUS current
      DESCRIPTION
       "The real operational status of the ATM to Ethernet connection."
      ::= { atmEtherCnfgEntry 8 }

atmEtherCnfgLastChange   OBJECT-TYPE
      SYNTAX TimeStamp
      MAX-ACCESS read-only
      STATUS current
      DESCRIPTION
       "The value of sysUpTime at the time the ATM to Ethernet
        connection entered its current operational state.
        If the current state was entered prior to the last
        re-initialization of the local network management
        subsystem, then this object contains a zero value.
        Same value define both direction ( Atm2Ether and Ether2Atm )."
      ::= { atmEtherCnfgEntry 9 }

atmEtherCnfgTrafficDescrIndex  OBJECT-TYPE
      SYNTAX         AtmTrafficDescrParamIndex
      MAX-ACCESS         read-create
      STATUS         current
      DESCRIPTION
       "The value of this object identifies the row
        in the atmTrafficDescrParamTable which
        applies to the transmit direction of the VCL."
      ::= { atmEtherCnfgEntry 10 }

atmEtherCnfgEncapsulationMode  OBJECT-TYPE
      SYNTAX  INTEGER
	  {
	    atmBridgedEther    (1),
	    atmBridgedEtherCRC (2)

      }
      MAX-ACCESS read-create
      STATUS deprecated
      DESCRIPTION
       "This object define the encapsulation type requested 
        for the connection.
        it indicates if we transfer the Ethernet frame to the 
        atm side without the Crc32- AtmBridgedEther, 
        or with it - AtmBridgedEther_CRC. "

      DEFVAL { atmBridgedEther }
      ::= { atmEtherCnfgEntry 11 }

atmEtherCnfgPriority   OBJECT-TYPE
      SYNTAX  INTEGER
	  {
	    highPriority   (1),
	    mediumPriority (2),
	    lowPriority    (3)
      }
      MAX-ACCESS read-create
      STATUS current
      DESCRIPTION
       "This object define the priority of connection.
        The first parameter affects the transmition of cells in Conjested
        network is the Service Category( Cbr has the highest priority and then Vbr,Ubr )
        In connections with the same category this object will define the priority."
      ::= { atmEtherCnfgEntry 12 }

atmEtherCnfgRowStatus   OBJECT-TYPE
      SYNTAX  RowStatus
      MAX-ACCESS  read-create
      STATUS  current
      DESCRIPTION
       "This object is used to create a new row or
        modify or delete an existing row in this table."
      ::= { atmEtherCnfgEntry 13 }

atmEtherCnfgRouterIP OBJECT-TYPE
     SYNTAX  IpAddress
 		 MAX-ACCESS  read-create
     STATUS  current
     DESCRIPTION
      "The interface IP address for SNMP requests."
     ::= { atmEtherCnfgEntry 14 }

atmEtherCnfgRouterMask OBJECT-TYPE
     SYNTAX  IpAddress
 		 MAX-ACCESS  read-create
     STATUS  current
     DESCRIPTION
      "The interface IP address mask for SNMP requests."
     ::= { atmEtherCnfgEntry 15 }

atmEtherCnfgRouterFragmentation OBJECT-TYPE
     SYNTAX  INTEGER {
             no							 (2),
             yes						 (3),
						 notApplicable (255)
     }
		 MAX-ACCESS  read-create
     STATUS  current
     DESCRIPTION
     "Fragmentation. When application is not router value must be 'notApplicable'."
     ::= { atmEtherCnfgEntry 16 }

atmEtherCnfgRouterRIPMode OBJECT-TYPE
     SYNTAX  INTEGER {
             rip1					   (1),
             rip2					   (2),
             rip1And2			   (3),
             none					   (4),
						 notApplicable (255)
     }
		 MAX-ACCESS  read-create
     STATUS  current
     DESCRIPTION
     "RIP Mode. When application is not router value must be 'notApplicable'."
     ::= { atmEtherCnfgEntry 17 }

atmEtherCnfgRouterMTU OBJECT-TYPE
      SYNTAX  Integer32
      MAX-ACCESS read-create
      STATUS deprecated
      DESCRIPTION
       " ."
      ::= { atmEtherCnfgEntry 18 }


atmEtherCnfgPPPEncapsulation   OBJECT-TYPE
      SYNTAX  INTEGER
	  {
        notApplicable      (1),
		none               (2),
        rfc1483            (3),	-- RFC1483 LLC Muxed
        pppVcMuxed	       (4),
        pppLlcMuxed        (5),
		rfc1483VcMuxed     (6),
		rfc1483BridgePdu   (7) -- with LLC encapsulation 

      }
      MAX-ACCESS read-create
      STATUS current
      DESCRIPTION
       "This object define the encapsulation type requested 
        for the connection.
             
        rfc1483        - Multiprotocol Encapsulation over 
                         ATM Adaptation Layer 5 (no PPP),
						 LLC Muxed.

		PPP VC Muxed   - For VC Based Multiplexing,
		the carried network interconnect protocol  is identified 
		implicitly by the VC connecting the two ATM stations,
        i.e.  each protocol must be carried over a separate VC.
        There is  therefore no need to include explicit multiplexing 
        information in the   Payload of the AAL5 CPCS-PDU. 
        This results in minimal bandwidth and  processing overhead.
				
		PPP LLC Muxed  - LLC  (Low layer compatibility) Encapsulation 
		is needed when several protocols are carried over the same VC.
		In order to allow the receiver 	to properly process the incoming 
		AAL5 CPCS-PDU, the Payload 	Field must contain information necessary 
		to identify the protocol of the routed or bridged PDU.  
		In LLC Encapsulation this informationis encoded in an LLC header 
		placed in front of the carried PDU."

      DEFVAL { rfc1483 }
      ::= { atmEtherCnfgEntry 19 }



atmEtherCnfgAllocatedBuffers  OBJECT-TYPE
      SYNTAX       Integer32 (10..217)
      MAX-ACCESS   read-create
      STATUS current
      DESCRIPTION
       "This object enables user to limit the amount of buffers 
       used by the connection.
       The limit set by this object will give 
       the effect of a virtual buffer pool per connection. 

       The user can allocate between 10 to 217 buffers 
       to every connection. By default the limit is 50 buffers.

       Sum of limits allocated to all connections 
       must not exceed the total amount of available buffers. 

       Whenever a connection exceeds it's buffer limit 
       due to congestion or burst traffic is discarded"
	   DEFVAL { 50 }
      ::= { atmEtherCnfgEntry 20 }

atmEtherCnfgPauseTrigger  OBJECT-TYPE
      SYNTAX  INTEGER
	  {
       notApplicable (1),
	   disable       (2),
       enable        (3)
      }
      MAX-ACCESS read-create
      STATUS current
      DESCRIPTION
	  "Enable/Disable LAN Pause triger from WAN connection"
      ::= { atmEtherCnfgEntry 21 }



-- *************************************************************
--      RAD ATM's index to User port's index Translation table
-- *************************************************************

atmSuCrossConnectTranslate   OBJECT IDENTIFIER ::= { atmSuCrossConnect 5 }

atmTranslateTable OBJECT-TYPE
      SYNTAX  SEQUENCE OF AtmTranslateEntry
      MAX-ACCESS  not-accessible
      STATUS current
      DESCRIPTION
       "This table translates the three of AtmIfIndex,AtmVpi,AtmVci
        to ifIndex of the interface on the user port's side."
      ::= { atmSuCrossConnectTranslate 1 }


atmTranslateEntry OBJECT-TYPE
      SYNTAX  AtmTranslateEntry
      MAX-ACCESS  not-accessible
      STATUS current
      DESCRIPTION
       "An entry includes the User side interface's ifIndex of any virtual
        connection along with the ATM connection indices."
      INDEX { atmTranslateAtmIfIndex, atmTranslateAtmVpi, atmTranslateAtmVci }
      ::= { atmTranslateTable 1 }

AtmTranslateEntry ::= SEQUENCE {
         atmTranslateAtmIfIndex
                  Integer32,
         atmTranslateAtmVpi
                  Integer32,
         atmTranslateAtmVci
                  Integer32,
         atmTranslateUserIfIndex
                  Integer32
         }

atmTranslateAtmIfIndex OBJECT-TYPE
      SYNTAX Integer32
      MAX-ACCESS  read-only
      STATUS current
      DESCRIPTION
       "The ifIndex associated to the ATM interface."
      ::= { atmTranslateEntry 1 }

atmTranslateAtmVpi   OBJECT-TYPE
      SYNTAX Integer32 (1..4095)
      MAX-ACCESS  read-only
      STATUS current
      DESCRIPTION
       "The Vpi number of the ATM end point."
      ::= { atmTranslateEntry 2 }

atmTranslateAtmVci   OBJECT-TYPE
      SYNTAX Integer32 (0..65535)
      MAX-ACCESS  read-only
      STATUS current
      DESCRIPTION
       "The Vci number of the ATM end point."
      ::= { atmTranslateEntry 3 }

atmTranslateUserIfIndex   OBJECT-TYPE
      SYNTAX Integer32
      MAX-ACCESS  read-only
      STATUS current
      DESCRIPTION
       "The ifIndex associated to the user interface."
      ::= { atmTranslateEntry 4 }


-- *************************************************************
-- *************************************************************
--                            Traps
-- *************************************************************
-- *************************************************************

--NOTIFICATIONS

	radAtmEvents OBJECT-IDENTITY
	    STATUS  current
    	DESCRIPTION
		"The events for RAD ATM."
    	::= { radAtm 0 }

    alarmTrap  NOTIFICATION-TYPE
        STATUS current
        DESCRIPTION
        "This trap is sent whenever an alarm
          occurs in the agent."
        ::= { radAtmEvents 1 }

    statusChangeTrap  NOTIFICATION-TYPE
        OBJECTS       { agnLed, agnIndication }
        STATUS current
        DESCRIPTION     
        "This trap is sent whenever a led in the agent
         change it's status."
        ::= { radAtmEvents 2 }


-- NO BUFFER TO NETWORK
atmSuAgnNoBufferToNetwork NOTIFICATION-TYPE		
      OBJECTS  {alarmSeverity}
      STATUS  current
      DESCRIPTION
      "This trap usualy indicates timing problem;
       incorrect selection of timing references 
       between end users."	
      ::= { radAtmEvents 3 }


--   JITTER BUFFER OVERRUN 
atmSuJitterBufferOverrun NOTIFICATION-TYPE		
      OBJECTS  {alarmSeverity, ifAlias}
      STATUS  current
      DESCRIPTION
      "This trap indicates that an overrun event
       occurred in the ATM jitter buffer serving the
       transmit to user direction of the 
       user interface specified by ifAlias"	
      ::= { radAtmEvents 4 }


--   JITTER BUFFER UNDERRUN
atmSuJitterBufferUnderrun NOTIFICATION-TYPE		
      OBJECTS  {alarmSeverity, ifAlias}
      STATUS  current
      DESCRIPTION
      "This trap indicates that an underrun event
       occurred in the atm jitter buffer serving the
       transmit to user direction of the
       user interface specified by ifAlias."
      ::= { radAtmEvents 5 }
 
-- DATA LOCAL LOOP
atmSuDataLocalLoopbackTrap NOTIFICATION-TYPE		
      OBJECTS  {alarmSeverity, alarmState,ifAlias}
      STATUS  current
      DESCRIPTION
      "This trap indicates that a local loopback
       has been activated on the local data port."
      ::= { radAtmEvents 6 }

-- DATA REMOTE LOOP
atmSuDataRemoteLoopbackTrap NOTIFICATION-TYPE		
      OBJECTS  {alarmSeverity, alarmState,ifAlias}
      STATUS  current
      DESCRIPTION
      "This trap indicates that a remote loopback
       has been activated on the local data port."
      ::= { radAtmEvents 7}

 
-- END
-- 
-- file :D:\Synergy\WorkArea\545\mib_rad\txt\radsonet.txt
-- 
-- RAD-SONET-MIB DEFINITIONS ::= BEGIN

--Title:    RAD-SONET   MIB	 ver 545
--

--     IMPORTS
--     Gauge32                         FROM RFC1155-SMI
--     ifIndex                         FROM RFC1213-MIB
--     OBJECT-TYPE                     FROM RFC-1212
--     radWan                          FROM RAD-GEN-MIB;



--                RAD-SONET MIB   

--Title:     RAD's SONET INTERFACE MIB
--Version:   1.0
--Date:      13.10.96
--By:        Yair Arian
--File:      radsonet.txt
--
--Last update: 5-Feb-2008 by Shay Harari


sonetInterface  OBJECT IDENTIFIER  ::=  {diverseIfWanGen 2}

prtSonetEvents  	 OBJECT IDENTIFIER  ::=  {sonetInterface 0}
prtSonetPerfHistory  OBJECT IDENTIFIER  ::=  {sonetInterface 1}


-- The SONET Medium Table

prtSonetMediumTable OBJECT-TYPE
    SYNTAX  SEQUENCE OF PrtSonetMediumEntry
    MAX-ACCESS  not-accessible
    STATUS  current
    DESCRIPTION
            "The SONET Medium table."
    ::= { prtSonetPerfHistory 1 }

prtSonetMediumEntry OBJECT-TYPE
    SYNTAX  PrtSonetMediumEntry
    MAX-ACCESS  not-accessible
    STATUS  current
    DESCRIPTION
            "An entry in the SONET Medium table. ifIndex of the
             lowest SONET layer of type sonet(39)."
    INDEX   { ifIndex }
    ::= { prtSonetMediumTable 1 }

PrtSonetMediumEntry ::=
    SEQUENCE {
        prtSonetMediumTimeElapsed
            Integer32,
        prtSonetMediumValidIntervals
            Integer32,
		prtSonetMediumSsmRX
		    OCTET STRING,
		prtSonetMediumSsmTX
		    OCTET STRING
           }

prtSonetMediumTimeElapsed OBJECT-TYPE
     SYNTAX  Integer32 (0..899)
     MAX-ACCESS  read-only
     STATUS  current
     DESCRIPTION
     "The number of seconds that have elapsed since
     the beginning of the near end current error-
     measurement period."
    ::= { prtSonetMediumEntry 1 }

prtSonetMediumValidIntervals OBJECT-TYPE
     SYNTAX  Integer32 (0..96)
     MAX-ACCESS  read-only
     STATUS  current
     DESCRIPTION
     "The number of previous near end intervals for
     which valid data was collected.  The value will be
     96 unless the interface was brought online within
     the last 24 hours, in which case the value will be
     the number of complete 15 minute near end
     intervals since the interface has been online."
    ::= { prtSonetMediumEntry 2 }

prtSonetMediumSsmRX OBJECT-TYPE
     SYNTAX  OCTET STRING	(SIZE (1))
     MAX-ACCESS  read-only
     STATUS  current
     DESCRIPTION
     "This parameter indicates SSM RX value (quality level of clock signal).
      SSM (Synchronization Status Messages) octet is encoded as follows:
	  Bit1 = '1' - indicates all octet is Not Applicable
	  Bits 8-5 (when bit1=0):
	  Left is MSB, where - MSB(8) ---> LSB(5)
	  8765       
	  0000	Quality Unknown
	  0001  PRS (Stratum 1 Traceable)
      0010	PRC (Primary Reference Clock)    - Rec. G.811
      0100	SSU-T (Sync. Source Unit-Transit)- Rec. G.812 Transit for SDH
	        TNC (Transit Node Clock Traceable) - for SONET
	  0111  ST2 (Stratum 2 Traceable)
      1000	SSU-L (Sync. Source Unit Local)	 - Rec. G.812 Local
	  1010  ST3 (Stratum 3 Traceable)
      1011	SEC (SDH Equipment Clock)
	  1100  SMC (SONET Minimum Clock Traceable)
	  1101  STS3E (Stratum 3E Traceable)
      1111	DNU (do not use for synchronization) "
    ::= {prtSonetMediumEntry 3}

prtSonetMediumSsmTX OBJECT-TYPE
     SYNTAX  OCTET STRING	(SIZE (1))
     MAX-ACCESS  read-only
     STATUS  current
     DESCRIPTION
     "This parameter indicates SSM TX value (quality level of clock signal).
      SSM (Synchronization Status Messages) octet is encoded the same as 
      prtSonetMediumSsmRX."
    ::= {prtSonetMediumEntry 4}


-- The SONET Section/Line Current	Table

-- The SONET Section/Line Current table contains various statistics being
-- collected for the current 15 minute interval.

prtSonetSectionLineCurrentTable OBJECT-TYPE
    SYNTAX  SEQUENCE OF PrtSectionLineCurrentEntry
    MAX-ACCESS  not-accessible
    STATUS  current
    DESCRIPTION
            "The SONET Section/Line Current table."
    ::= { prtSonetPerfHistory 2 }

prtSectionLineCurrentEntry OBJECT-TYPE
    SYNTAX  PrtSectionLineCurrentEntry
    MAX-ACCESS  not-accessible
    STATUS  current
    DESCRIPTION
            "An entry in the SONET Section/Line Current table.
             ifIndex of the section/line SONET layer of type 
             sonet(39)."
    INDEX   { ifIndex }
    ::= { prtSonetSectionLineCurrentTable 1 }

PrtSectionLineCurrentEntry ::=
    SEQUENCE {
        prtSonetCurrentLOS
            Gauge32,
        prtSonetCurrentLOF
            Gauge32,
        prtSonetCurrentLineAIS
            Gauge32,
        prtSonetCurrentLineFERF
            Gauge32,
        prtSonetCurrentSectionBIP
            Gauge32,
        prtSonetCurrentLineBIP
            Gauge32,
        prtSonetCurrentLineFEBE
            Gauge32,
        prtSonetCurrentUAS
            Gauge32,
        prtSonetCurrentSES
            Gauge32,
        prtSonetCurrentES 
            Gauge32,
        prtSonetCurrentStatus 
            OCTET STRING,
        prtSonetCurrentLSV 
            Gauge32,
		prtSonetCurrentXStatus
			Integer32,
        prtSonetCurrentLineRDI
            Gauge32
    }

prtSonetCurrentLOS OBJECT-TYPE
    SYNTAX  Gauge32
    MAX-ACCESS  read-only
    STATUS  current
    DESCRIPTION
            "The counter associated with the number of LOS
             seconds, encountered by a SONET interface in
            the current 15 minute interval."
    ::= { prtSectionLineCurrentEntry 1 }

prtSonetCurrentLOF OBJECT-TYPE
    SYNTAX  Gauge32
    MAX-ACCESS  read-only
    STATUS  current
    DESCRIPTION
            "The counter associated with the number of LOF
             seconds, encountered by a SONET
             interface in the current 15 minute interval."
    ::= { prtSectionLineCurrentEntry 2 }

prtSonetCurrentLineAIS OBJECT-TYPE
    SYNTAX  Gauge32
    MAX-ACCESS  read-only
    STATUS  current
    DESCRIPTION
            "The counter associated with the number of Line AIS
            seconds, encountered by a SONET
            interface in the current 15 minute interval."
    ::= { prtSectionLineCurrentEntry 3 }

prtSonetCurrentLineFERF OBJECT-TYPE
    SYNTAX  Gauge32
    MAX-ACCESS  read-only
    STATUS  current
    DESCRIPTION
            "The counter associated with the number of Line
            FERF seconds, encountered by a SONET
            interface in the current 15 minute interval."
    ::= { prtSectionLineCurrentEntry 4 }

prtSonetCurrentSectionBIP OBJECT-TYPE
    SYNTAX  Gauge32
    MAX-ACCESS  read-only
    STATUS  current
    DESCRIPTION
            "The counter associated with the number of Section
            BIP errors, encountered by a SONET
            interface in the current 15 minute interval."
    ::= { prtSectionLineCurrentEntry 5 }

prtSonetCurrentLineBIP OBJECT-TYPE
    SYNTAX  Gauge32
    MAX-ACCESS  read-only
    STATUS  current
    DESCRIPTION
            "The counter associated with the number of Line
            BIP errors, encountered by a SONET
            interface in the current 15 minute interval."
    ::= { prtSectionLineCurrentEntry 6 }

prtSonetCurrentLineFEBE OBJECT-TYPE
    SYNTAX  Gauge32
    MAX-ACCESS  read-only
    STATUS  current
    DESCRIPTION
            "The counter associated with the number of Line
            FEBE errors, encountered by a SONET
            interface in the current 15 minute interval."
    ::= { prtSectionLineCurrentEntry 7 }

prtSonetCurrentUAS OBJECT-TYPE
    SYNTAX  Gauge32
    MAX-ACCESS  read-only
    STATUS  current
    DESCRIPTION
            "The counter associated with the number of UAS
             encountered by a SONET
             interface in the current 15 minute interval."
    ::= { prtSectionLineCurrentEntry 8 }

prtSonetCurrentSES OBJECT-TYPE
    SYNTAX  Gauge32
    MAX-ACCESS  read-only
    STATUS  current
    DESCRIPTION
            "The counter associated with the number of SES
             encountered by a SONET
             interface in the current 15 minute interval."
    ::= { prtSectionLineCurrentEntry 9 }

prtSonetCurrentES OBJECT-TYPE
     SYNTAX Gauge32 
     MAX-ACCESS  read-only
     STATUS  current
     DESCRIPTION
            "The number of Errored Seconds, encountered  by a
              SONET interface in the current 15 minute interval."
     ::= { prtSectionLineCurrentEntry 10 }

prtSonetCurrentStatus OBJECT-TYPE
     SYNTAX OCTET STRING  (SIZE (4))
    MAX-ACCESS  read-only
    STATUS  current
    DESCRIPTION
            "The statuses of the current interval:
              0 - O.K.
              1 - The link has been switched by a redundancy mechanism.
              2 - Module is in/out.
              4 - Empty - card is out."
    ::= { prtSectionLineCurrentEntry 11 }

prtSonetCurrentLSV OBJECT-TYPE
     SYNTAX  Gauge32
     MAX-ACCESS  read-only
     STATUS  current
     DESCRIPTION
             "The counter associated with the number of LSV
              seconds (Line Symbol Violation), encountered by a 
              SONET interface in the current 15 minute interval."
     ::= { prtSectionLineCurrentEntry 12 }

prtSonetCurrentXStatus OBJECT-TYPE
     SYNTAX  Integer32
     MAX-ACCESS  read-only
     STATUS  current
     DESCRIPTION
     "This variable indicates the Status of the interface.  
     It contains failure state information.  
     The variable is a bit map represented as a sum, therefore, it
     can represent multiple failures simultaneously.  
     The sonetSectionLineNoDefect must be set if and only if no other flag is set.

     The various bit positions are:
       	1   sonetSectionLineNoDefect
       	2   sonetSectionLOS	  	Loss Of Signal
       	4   sonetSectionLOF	  	Loss Of Frame
       	8   sonetSectionLOC    	Loss Of Clock
       16  	sonetLineAIS   	 	Alarm Indication Signal
       32  	sonetLineRDI  	 	Remote Defect Indication
       64   sonetLineRFI   	 	Remote Failure Indication (RDI lasts for 2.5 (+-0.5) seconds)
      128   sonetLineEBER  	 	Excessive Bit Error Rate 
      256   sonetLineSD    	 	Signal Degradation
	  512	sonetOOF			Out Of Frame."
     ::= { prtSectionLineCurrentEntry 13 }

prtSonetCurrentLineRDI  OBJECT-TYPE
    SYNTAX  Gauge32
    MAX-ACCESS  read-only
    STATUS  current
    DESCRIPTION
            "The counter associated with the number of Line RDI
            seconds, encountered by a SONET
            interface in the current 15 minute interval."
    ::= { prtSectionLineCurrentEntry 14 }


 -- The SONET Section/Line interface Interval

 -- The SONET Section/Line Interval Table contains various statistics
 -- collected by the Interface over the previous 24
 -- hours of operation.  The past 24 hours are broken into 96
 -- completed 15 minute intervals.

 prtSonetSectionLineIntervalTable OBJECT-TYPE
     SYNTAX  SEQUENCE OF PrtSectionLineIntervalEntry
     MAX-ACCESS  not-accessible
     STATUS  current
     DESCRIPTION
             "The Section/Line Interval table."
     ::= { prtSonetPerfHistory 3 }

 prtSectionLineIntervalEntry OBJECT-TYPE
     SYNTAX  PrtSectionLineIntervalEntry
     MAX-ACCESS  not-accessible
     STATUS  current
     DESCRIPTION
             "An entry in the SONET Section/Line Interval table.
              ifIndex of the section/line SONET layer of type 
              sonet(39)."
     INDEX   { ifIndex, prtSonetLineIntervalNumber }
     ::= { prtSonetSectionLineIntervalTable 1 }

PrtSectionLineIntervalEntry ::=
     SEQUENCE {
         prtSonetLineIntervalNumber
             Integer32,
         prtSonetIntervalLOS
             Gauge32,
         prtSonetIntervalLOF
             Gauge32,
         prtSonetIntervalLineAIS
             Gauge32,
         prtSonetIntervalLineFERF
             Gauge32,
         prtSonetIntervalSectionBIP
             Gauge32,
         prtSonetIntervalLineBIP
             Gauge32,
         prtSonetIntervalLineFEBE
             Gauge32,
         prtSonetIntervalUAS
             Gauge32,
         prtSonetIntervalSES
             Gauge32,
         prtSonetIntervalES
             Gauge32,
     	 prtSonetIntervalStatus
             OCTET STRING,
	     prtSonetIntervalLSV
             Gauge32,   
         prtSonetIntervalLineRDI
             Gauge32            
              }

prtSonetLineIntervalNumber OBJECT-TYPE
    SYNTAX  Integer32 (1..96)
    MAX-ACCESS  read-only
    STATUS  current
    DESCRIPTION
            "A number between 1 and 96, where 1 is the most
            recently completed 15 minute interval and 96 is
            the least recently completed 15 minutes interval
            (assuming that all 96 intervals are valid)."
    ::= { prtSectionLineIntervalEntry 1 }

prtSonetIntervalLOS OBJECT-TYPE
    SYNTAX  Gauge32
    MAX-ACCESS  read-only
    STATUS  current
    DESCRIPTION
            "The counter associated with the number of LOS
            seconds , encountered by a SONET interface in
            one of the previous 96, individual 15 minute,
            intervals."
    ::= { prtSectionLineIntervalEntry 2 }

prtSonetIntervalLOF OBJECT-TYPE
    SYNTAX  Gauge32
    MAX-ACCESS  read-only
    STATUS  current
    DESCRIPTION
            "The counter associated with the number of LOF
            seconds, encountered by a SONET
            interface in one of the previous 96, individual 15
            minute, intervals."
    ::= { prtSectionLineIntervalEntry 3 }

prtSonetIntervalLineAIS OBJECT-TYPE
    SYNTAX  Gauge32
    MAX-ACCESS  read-only
    STATUS  current
    DESCRIPTION
           "The counter associated with the number of Line
           AIS seconds, encountered by a SONET
           interface in one of the previous 96,
           individual 15 minute, intervals."
   ::= { prtSectionLineIntervalEntry 4 }

prtSonetIntervalLineFERF OBJECT-TYPE
    SYNTAX  Gauge32
    MAX-ACCESS  read-only
    STATUS  current
    DESCRIPTION
            "The counter associated with the number of Line
            FERF seconds, encountered by a SONET
            interface in one of the previous 96, individual 15
            minute, intervals."
    ::= { prtSectionLineIntervalEntry 5 }

prtSonetIntervalSectionBIP OBJECT-TYPE
    SYNTAX  Gauge32
    MAX-ACCESS  read-only
    STATUS  current
    DESCRIPTION
            "The counter associated with the number of Section
            BIP errors, encountered by a SONET
            interface in one of the previous 96, individual 15
            minute, intervals."
    ::= { prtSectionLineIntervalEntry 6 }

prtSonetIntervalLineBIP OBJECT-TYPE
    SYNTAX  Gauge32
    MAX-ACCESS  read-only
    STATUS  current
    DESCRIPTION
            "The counter associated with the number of Line
            BIP errors, encountered by a SONET 
            interface in one of the previous 96, individual 15
            minute, intervals."
    ::= { prtSectionLineIntervalEntry 7 }

prtSonetIntervalLineFEBE OBJECT-TYPE
    SYNTAX  Gauge32
    MAX-ACCESS  read-only
    STATUS  current
    DESCRIPTION
            "The counter associated with the number of Line
            FEBE errors, encountered by a SONET
            interface in one of the previous 96, individual 15
            minute, intervals."
    ::= { prtSectionLineIntervalEntry 8 }

prtSonetIntervalUAS OBJECT-TYPE
    SYNTAX  Gauge32
    MAX-ACCESS  read-only
    STATUS  current
    DESCRIPTION
             "The counter associated with the number of UAS
             encountered by a SONET
             interface in one of the previous 96, individual 15
             minute, intervals."
     ::= { prtSectionLineIntervalEntry 9 }

prtSonetIntervalSES OBJECT-TYPE
     SYNTAX  Gauge32
     MAX-ACCESS  read-only
     STATUS  current
     DESCRIPTION
             "The counter associated with the number of SES
             encountered by a SONET
             interface in one of the previous 96, individual 15
             minute, intervals."
     ::= { prtSectionLineIntervalEntry 10 }

prtSonetIntervalES OBJECT-TYPE
     SYNTAX Gauge32 
     MAX-ACCESS  read-only
     STATUS current 
     DESCRIPTION
            "The number of Errored Seconds, encountered  by a
            SONET interface in one of the previous 96, individual 15
            minute, intervals."
     ::= { prtSectionLineIntervalEntry 11 }

prtSonetIntervalStatus OBJECT-TYPE
     SYNTAX OCTET STRING  (SIZE (4))
     MAX-ACCESS  read-only
     STATUS  current
     DESCRIPTION
             " The statuses of the current interval:
               0 - O.K.
               1 - The link has been switched by a redundancy mechanism.
               2 - Module is in/out.
               4 - Empty - card is out."
     ::= { prtSectionLineIntervalEntry 12 }

prtSonetIntervalLSV OBJECT-TYPE
     SYNTAX  Gauge32
     MAX-ACCESS  read-only
     STATUS  current
     DESCRIPTION
             "The counter associated with the number of LSV seconds 
             (Line Symbol Violation), encountered by a SONET interface 
             in one of the previous 96, individual 15 minute, intervals."
     ::= { prtSectionLineIntervalEntry 13 }

prtSonetIntervalLineRDI OBJECT-TYPE
    SYNTAX  Gauge32
    MAX-ACCESS  read-only
    STATUS  current
    DESCRIPTION
           "The counter associated with the number of Line
           RDI seconds, encountered by a SONET
           interface in one of the previous 96,
           individual 15 minute, intervals."
   ::= { prtSectionLineIntervalEntry 14 }
                             
        
  -- The SONET Path Current	Table

-- The SONET Path Current table contains various statistics being
-- collected for the current 15 minute interval.

prtSonetPathCurrentTable OBJECT-TYPE
    SYNTAX  SEQUENCE OF PrtPathCurrentEntry
    MAX-ACCESS  not-accessible
    STATUS  current
    DESCRIPTION
            "The SONET Path Current table."
    ::= { prtSonetPerfHistory 4 }

prtPathCurrentEntry OBJECT-TYPE
    SYNTAX  PrtPathCurrentEntry
    MAX-ACCESS  not-accessible
    STATUS  current
    DESCRIPTION
            "An entry in the SONET Path Current table.
             ifIndex of the Path SONET layer of type 
             sonetPath(50)."
    INDEX   { ifIndex }
    ::= { prtSonetPathCurrentTable 1 }

PrtPathCurrentEntry ::=
    SEQUENCE {
        prtSonetCurrentPathAIS
            Gauge32,
        prtSonetCurrentPathFERF
            Gauge32,
        prtSonetCurrentLOP
            Gauge32,
        prtSonetCurrentSLM
            Gauge32,
        prtSonetCurrentLOC
            Gauge32,
        prtSonetCurrentPathBIP
            Gauge32,
        prtSonetCurrentPathFEBE
            Gauge32,
		prtSonetPathCurrentStatus
    		Integer32,
		prtSonetCurrentPathRDI
		     Gauge32
    }		

prtSonetCurrentPathAIS OBJECT-TYPE
    SYNTAX  Gauge32
    MAX-ACCESS  read-only
    STATUS  current
    DESCRIPTION
            "The counter associated with the number of Path AIS
             seconds, encountered by a SONET interface in
            the current 15 minute interval."
    ::= { prtPathCurrentEntry 1 }

prtSonetCurrentPathFERF OBJECT-TYPE
    SYNTAX  Gauge32
    MAX-ACCESS  read-only
    STATUS  current
    DESCRIPTION
            "The counter associated with the number of Path FERF
             seconds, encountered by a SONET
             interface in the current 15 minute interval."
    ::= { prtPathCurrentEntry 2 }

prtSonetCurrentLOP OBJECT-TYPE
    SYNTAX  Gauge32
    MAX-ACCESS  read-only
    STATUS  current
    DESCRIPTION
            "The counter associated with the number LOP
            seconds, encountered by a SONET
            interface in the current 15 minute interval."
    ::= { prtPathCurrentEntry 3 }

prtSonetCurrentSLM OBJECT-TYPE
    SYNTAX  Gauge32
    MAX-ACCESS  read-only
    STATUS  current
    DESCRIPTION
            "The counter associated with the number of SLM
             seconds, encountered by a SONET
             interface in the current 15 minute interval."
    ::= { prtPathCurrentEntry 4 }

prtSonetCurrentLOC OBJECT-TYPE
    SYNTAX  Gauge32
    MAX-ACCESS  read-only
    STATUS  current
    DESCRIPTION
            "The counter associated with the number of LOC
            seconds, encountered by a SONET
            interface in the current 15 minute interval."
    ::= { prtPathCurrentEntry 5 }

prtSonetCurrentPathBIP OBJECT-TYPE
    SYNTAX  Gauge32
    MAX-ACCESS  read-only
    STATUS  current
    DESCRIPTION
            "The counter associated with the number of Path
            BIP errors, encountered by a SONET
            interface in the current 15 minute interval."
    ::= { prtPathCurrentEntry 6 }

prtSonetCurrentPathFEBE OBJECT-TYPE
    SYNTAX  Gauge32
    MAX-ACCESS  read-only
    STATUS  current
    DESCRIPTION
            "The counter associated with the number of Path
            FEBE errors, encountered by a SONET
            interface in the current 15 minute interval."
    ::= { prtPathCurrentEntry 7 }

prtSonetPathCurrentStatus OBJECT-TYPE
     SYNTAX  Integer32
     MAX-ACCESS  read-only
     STATUS  current
     DESCRIPTION
     "This variable indicates the Status of the interface.  
     It contains failure state information.  
     The variable is a bit map represented as a sum, therefore, it
     can represent multiple failures simultaneously.  
     The sonetPathNoDefect must be set if and only if no other flag is set.

     The various bit positions are:
        1   sonetPathNoDefect
        2   sonetPathSTSLOP		   			Loss Of Pointer
        4   sonetPathSTSAIS		   			Alarm Indication Signal
        8   sonetPathSTSRDI		  	 		Remote Defect Indication
       16   sonetPathUnequipped	   			Signal Label Unequipped
       32   sonetPathSignalLabelMismatch	Signal Label Mismatch
       64   sonetPathRFI   	 				Remote Failure Indication 
       										(RDI lasts for 2.5 (+-0.5) seconds)
      128   sonetPathEBER  	 				Excessive Bit Error Rate 
      256   sonetPathSD    	 				Signal Degradation
      512   sonetPathLOM   	 				Loss Of Multiframe."
    ::= { prtPathCurrentEntry 8 }

prtSonetCurrentPathRDI OBJECT-TYPE
    SYNTAX      Gauge32
    MAX-ACCESS  read-only
    STATUS      current
    DESCRIPTION
            "The counter associated with the number of Path RDI
             seconds, encountered by a SONET interface in
             the current 15 minute interval."
    ::= { prtPathCurrentEntry 9 }



-- The SONET Path interface Interval

-- The SONET Path Interval Table contains various statistics
-- collected by the Interface over the previous 24
-- hours of operation.  The past 24 hours are broken into 96
-- completed 15 minute intervals.

prtSonetPathIntervalTable OBJECT-TYPE
    SYNTAX  SEQUENCE OF PrtPathIntervalEntry
    MAX-ACCESS  not-accessible
    STATUS  current
    DESCRIPTION
            "The Path Interval table."
    ::= { prtSonetPerfHistory 5 }

prtPathIntervalEntry OBJECT-TYPE
    SYNTAX  PrtPathIntervalEntry
    MAX-ACCESS  not-accessible
    STATUS  current
    DESCRIPTION
            "An entry in the SONET Path Interval table."
    INDEX   { ifIndex, prtSonetPathIntervalNumber }
    ::= { prtSonetPathIntervalTable 1 }

PrtPathIntervalEntry ::=
    SEQUENCE {
        prtSonetPathIntervalNumber
            Integer32,
        prtSonetIntervalPathAIS
            Gauge32,
        prtSonetIntervalPathFERF
            Gauge32,
        prtSonetIntervalLOP
            Gauge32,
        prtSonetIntervalSLM
            Gauge32,
        prtSonetIntervalLOC
            Gauge32,
        prtSonetIntervalPathBIP
            Gauge32,
        prtSonetIntervalPathFEBE
            Gauge32,
        prtSonetIntervalPathRDI
            Gauge32
    }

prtSonetPathIntervalNumber OBJECT-TYPE
    SYNTAX  Integer32 (1..96)
    MAX-ACCESS  read-only
    STATUS  current
    DESCRIPTION
            "A number between 1 and 96, where 1 is the most
            recently completed 15 minute interval and 96 is
            the least recently completed 15 minutes interval
            (assuming that all 96 intervals are valid)."
    ::= { prtPathIntervalEntry 1 }

prtSonetIntervalPathAIS OBJECT-TYPE
    SYNTAX  Gauge32
    MAX-ACCESS  read-only
    STATUS  current
    DESCRIPTION
            "The counter associated with the number of Path
            AIS seconds , encountered by a SONET interface in
            one of the previous 96, individual 15 minute,
            intervals."
    ::= { prtPathIntervalEntry 2 }

prtSonetIntervalPathFERF OBJECT-TYPE
    SYNTAX  Gauge32
    MAX-ACCESS  read-only
    STATUS  current
    DESCRIPTION
            "The counter associated with the number of Path
            FERF seconds, encountered by a SONET
            interface in one of the previous 96, individual 15
            minute, intervals."
    ::= { prtPathIntervalEntry 3 }

prtSonetIntervalLOP OBJECT-TYPE
    SYNTAX  Gauge32
    MAX-ACCESS  read-only
    STATUS  current
    DESCRIPTION
            "The counter associated with the number of LOP
            seconds, encountered by a SONET
            interface in one of the previous 96,
            individual 15 minute, intervals."
    ::= { prtPathIntervalEntry 4 }

prtSonetIntervalSLM OBJECT-TYPE
    SYNTAX  Gauge32
    MAX-ACCESS  read-only
    STATUS  current
    DESCRIPTION
            "The counter associated with the number of SLM
            seconds, encountered by a SONET
            interface in one of the previous 96, individual 15
            minute, intervals."
    ::= { prtPathIntervalEntry 5 }

prtSonetIntervalLOC OBJECT-TYPE
    SYNTAX  Gauge32
    MAX-ACCESS  read-only
    STATUS  current
    DESCRIPTION
            "The counter associated with the number of LOC
            seconds, encountered by a SONET
            interface in one of the previous 96, individual 15
            minute, intervals."
    ::= { prtPathIntervalEntry 6 }

prtSonetIntervalPathBIP OBJECT-TYPE
    SYNTAX  Gauge32
    MAX-ACCESS  read-only
    STATUS  current
    DESCRIPTION
            "The counter associated with the number of Path
            BIP errors, encountered by a SONET 
            interface in one of the previous 96, individual 15
            minute, intervals."
    ::= { prtPathIntervalEntry 7 }

prtSonetIntervalPathFEBE OBJECT-TYPE
    SYNTAX  Gauge32
    MAX-ACCESS  read-only
    STATUS  current
    DESCRIPTION
            "The counter associated with the number of Path
            FEBE errors, encountered by a SONET
            interface in one of the previous 96, individual 15
            minute, intervals."
    ::= { prtPathIntervalEntry 8 }

prtSonetIntervalPathRDI OBJECT-TYPE
    SYNTAX  Gauge32
    MAX-ACCESS  read-only
    STATUS  current
    DESCRIPTION
            "The counter associated with the number of Path
            RDI seconds , encountered by a SONET interface in
            one of the previous 96, individual 15 minute,
            intervals."
    ::= { prtPathIntervalEntry 9 }



virtualIfStatistics  OBJECT IDENTIFIER  ::=  { prtSonetPerfHistory 6}


-- the Virtual Interface Current Table

virtualIfCurrentTable OBJECT-TYPE
    SYNTAX  SEQUENCE OF VirtualIfCurrentEntry
    MAX-ACCESS  not-accessible
    STATUS  current
    DESCRIPTION
       "The Virtual Interface Current table."
     ::= { virtualIfStatistics 1 }

virtualIfCurrentEntry OBJECT-TYPE
    SYNTAX  VirtualIfCurrentEntry
    MAX-ACCESS  not-accessible
    STATUS  current
    DESCRIPTION
       "An entry in the Virtual Interface Current table."
    INDEX   { ifIndex  }
     ::= { virtualIfCurrentTable 1 }

VirtualIfCurrentEntry ::=
    SEQUENCE {
 		 virtualIfCurrentMinActiveVC	           Integer32,
 		 virtualIfCurrentMaxActiveVC	           Integer32,
         virtualIfCurrentRxFrames                  Counter64,
         virtualIfCurrentTxFrames				   Counter64,
         virtualIfCurrentRxAbortFrames		   	   PerfCurrentCount,
         virtualIfCurrentTxAbortFrames		   	   PerfCurrentCount,
         virtualIfCurrentMinLengthViolation		   PerfCurrentCount,
         virtualIfCurrentMaxLengthViolation        PerfCurrentCount,
		 virtualIfCurrentFcsError				   PerfCurrentCount,
		 virtualIfCurrentByteDestuffingViolation   PerfCurrentCount,
		 virtualIfCurrentAdressMismatch			   PerfCurrentCount,
		 virtualIfCurrentControlMismatch		   PerfCurrentCount,
		 virtualIfCurrentActiveVC				   Integer32

    }
								
virtualIfCurrentMinActiveVC OBJECT-TYPE
     SYNTAX  Integer32 (1..63)
     MAX-ACCESS  read-only
     STATUS  current
     DESCRIPTION
       "This object holds the minimum number of active virtual containers (VCs)  
        of the Virtual Concatenation Group in the current 15-minute interval."
      ::= { virtualIfCurrentEntry 1 }
 
 virtualIfCurrentMaxActiveVC OBJECT-TYPE
     SYNTAX  Integer32 (1..63)
     MAX-ACCESS  read-only
     STATUS  current
     DESCRIPTION
       "This object holds the maximum number of active virtual containers (VCs)  
        of the Virtual Concatenation Group in the current 15-minute interval."
      ::= {virtualIfCurrentEntry 2 }

virtualIfCurrentRxFrames OBJECT-TYPE
    SYNTAX  Counter64
    MAX-ACCESS  read-only
    STATUS  current
    DESCRIPTION
       "This counter is associated with the number of frames received from STS-3/STM-1 
        by a Virtual Interface in the current 15-minute interval."
     ::= { virtualIfCurrentEntry 3}

virtualIfCurrentTxFrames OBJECT-TYPE
    SYNTAX  Counter64
    MAX-ACCESS  read-only
    STATUS  current
    DESCRIPTION
       "This counter is associated with the number of frames transmitted to STS-3/STM-1 
        by a Virtual Interface in the current 15-minute interval."
    ::= { virtualIfCurrentEntry 4 }
 
 virtualIfCurrentRxAbortFrames OBJECT-TYPE
    SYNTAX  PerfCurrentCount
    MAX-ACCESS  read-only
    STATUS  current
    DESCRIPTION
       "The counter associated with the number of Received Aborted frames
        encountered by a Virtual Interface in the current 15-minute interval."
      ::= { virtualIfCurrentEntry 5 }

virtualIfCurrentTxAbortFrames OBJECT-TYPE
    SYNTAX  PerfCurrentCount
    MAX-ACCESS  read-only
    STATUS  current
    DESCRIPTION
       "The counter associated with the number of Transmitted Aborted frames
        encountered by a Virtual Interface in the current 15-minute interval."
      ::= { virtualIfCurrentEntry 6 }

virtualIfCurrentMinLengthViolation OBJECT-TYPE
    SYNTAX  PerfCurrentCount
    MAX-ACCESS  read-only
    STATUS  current
    DESCRIPTION
       "This counter is associated with the number of
        Rx payload Min Length Violation frames encountered by a Virtual Interface 
        in the current 15-minute interval."
    ::= { virtualIfCurrentEntry 7 }

virtualIfCurrentMaxLengthViolation OBJECT-TYPE
    SYNTAX  PerfCurrentCount
    MAX-ACCESS  read-only
    STATUS  current
    DESCRIPTION
       "This counter is associated with the number of
        Rx payload Max Length Violation frames  
        encountered by a Virtual Interface in the current 15-minute interval."
    ::= { virtualIfCurrentEntry 8 }

virtualIfCurrentFcsError OBJECT-TYPE
    SYNTAX  PerfCurrentCount
    MAX-ACCESS  read-only
    STATUS  current
    DESCRIPTION
       "The counter is associated with the number of
        Frame Check Sequence errors	encountered by a Virtual Interface  
        in the current 15-minute interval."
    ::= { virtualIfCurrentEntry 9 }

virtualIfCurrentByteDestuffingViolation OBJECT-TYPE
    SYNTAX  PerfCurrentCount
    MAX-ACCESS  read-only
    STATUS  current
    DESCRIPTION
       "The counter associated with the number of 
        Byte De-stuffing Violations encountered by a Virtual Interface
        in the current 15-minute interval."
    ::= {virtualIfCurrentEntry 10 }
				 

virtualIfCurrentAdressMismatch	 OBJECT-TYPE
    SYNTAX  PerfCurrentCount
    MAX-ACCESS  read-only
    STATUS  current
    DESCRIPTION
       "The counter associated with the number of 
        Adress Mismatch encountered by a Virtual Interface
        in the current 15-minute interval."
    ::= {virtualIfCurrentEntry 11 }
 
virtualIfCurrentControlMismatch OBJECT-TYPE
    SYNTAX  PerfCurrentCount
    MAX-ACCESS  read-only
    STATUS  current
    DESCRIPTION
       "The counter associated with the number of 
        Control Mismatch encountered by a Virtual Interface
        in the current 15-minute interval."
    ::= {virtualIfCurrentEntry 12 }

virtualIfCurrentActiveVC OBJECT-TYPE
     SYNTAX  Integer32 (1..64)
     MAX-ACCESS  read-only
     STATUS  current
     DESCRIPTION
       "This object holds the number of active virtual containers (VCs)  
        of the Virtual Concatenation Group in the current 15-minute interval."
      ::= {virtualIfCurrentEntry 13 }

   

-- the Virtual Interface Interval Table

-- The Virtual Interface Interval Table
-- contains various statistics collected  over a maximum
-- of the previous 24 hours of operation.  
-- The past 24 hours may be broken into 96 
-- completed 15 minute intervals.

virtualIfIntervalTable OBJECT-TYPE
    SYNTAX  SEQUENCE OF VirtualIfIntervalEntry
    MAX-ACCESS  not-accessible
    STATUS  current
    DESCRIPTION
       "The Virtual Interface Interval table."
     ::= { virtualIfStatistics 2 }

virtualIfIntervalEntry OBJECT-TYPE
    SYNTAX  VirtualIfIntervalEntry
    MAX-ACCESS  not-accessible
    STATUS  current
    DESCRIPTION
       "An entry in the Virtual Interface Interval table."
    INDEX   { ifIndex, virtualIfIntervalNumber }
     ::= { virtualIfIntervalTable 1 }

VirtualIfIntervalEntry ::=
    SEQUENCE {
         virtualIfIntervalNumber                   Integer32,
		 virtualIfIntervalMinActiveVC	           Integer32,
		 virtualIfIntervalMaxActiveVC	           Integer32,
         virtualIfIntervalRxFrames                 Counter64,
         virtualIfIntervalTxFrames                 Counter64,
         virtualIfIntervalRxAbortFrames		       PerfIntervalCount,
         virtualIfIntervalTxAbortFrames		       PerfIntervalCount,
         virtualIfIntervalMinLengthViolation       PerfIntervalCount,
         virtualIfIntervalMaxLengthViolation       PerfIntervalCount,
		 virtualIfIntervalFcsError			       PerfIntervalCount,
		 virtualIfIntervalByteDestuffingViolation  PerfIntervalCount,
		 virtualIfIntervalAdressMismatch		   PerfIntervalCount,
		 virtualIfIntervalControlMismatch		   PerfIntervalCount,
		 virtualIfIntervalBelowMinThreshold		   PerfIntervalCount
    }

virtualIfIntervalNumber OBJECT-TYPE
    SYNTAX  Integer32 (1..96)
    MAX-ACCESS  not-accessible
    STATUS  current
    DESCRIPTION
      "A number between 1 and 96, which identifies the
       interval for which the set of statistics is available.
       The interval identified by 1 is the most recently
       completed 15 minute interval,
       and the interval identified
       by N is the interval immediately preceding the
       one identified  by N-1."
     ::= { virtualIfIntervalEntry 1 }

virtualIfIntervalMinActiveVC OBJECT-TYPE
    SYNTAX  Integer32 (1..64)
    MAX-ACCESS  read-only
    STATUS  current
    DESCRIPTION
      "This object holds the minimum number of 
       active virtual containers (VCs) of the Virtual Concatenation Group, in a
       particular 15-minute interval in the past 24 hours."
     ::= { virtualIfIntervalEntry 2 }

virtualIfIntervalMaxActiveVC OBJECT-TYPE
    SYNTAX  Integer32 (1..64)
    MAX-ACCESS  read-only
    STATUS  current
    DESCRIPTION
      "This object holds the maximum number of 
       active virtual containers (VCs) of the Virtual Concatenation Group, in a
       particular 15-minute interval in the past 24 hours."
     ::= { virtualIfIntervalEntry 3 }

virtualIfIntervalRxFrames OBJECT-TYPE
    SYNTAX  Counter64
    MAX-ACCESS  read-only
    STATUS  current
    DESCRIPTION
       "This counter is associated with the number of
        frames received from STS-3/STM-1 by a Virtual Interface in a
        particular 15-minute interval in the past 24 hours."
    ::= { virtualIfIntervalEntry 4 }

virtualIfIntervalTxFrames OBJECT-TYPE
    SYNTAX  Counter64
    MAX-ACCESS  read-only
    STATUS  current
    DESCRIPTION
       "This counter is associated with the number of
        frames transmitted to STS-3/STM-1 by a Virtual Interface in a
        particular 15-minute interval in the past 24 hours."
    ::= { virtualIfIntervalEntry 5 }

  virtualIfIntervalRxAbortFrames OBJECT-TYPE
    SYNTAX  PerfIntervalCount
    MAX-ACCESS  read-only
    STATUS  current
    DESCRIPTION
       "This counter is associated with the number of
        Received Abort frames encountered by a Virtual Interface in a
        particular 15-minute interval in the past 24 hours."
    ::= {virtualIfIntervalEntry 6 }

virtualIfIntervalTxAbortFrames OBJECT-TYPE
    SYNTAX  PerfIntervalCount
    MAX-ACCESS  read-only
    STATUS  current
    DESCRIPTION
       "This counter is associated with the number of
        Transmitted Abort frames encountered by a Virtual Interface in a
        particular 15-minute interval in the past 24 hours."
    ::= { virtualIfIntervalEntry 7 }

virtualIfIntervalMinLengthViolation OBJECT-TYPE
    SYNTAX  PerfIntervalCount
    MAX-ACCESS  read-only
    STATUS  current
    DESCRIPTION
       "This counter is associated with the number of
        Rx payload Min Length Violation frames  
        encountered by a Virtual Interface in a
        particular 15-minute interval in the past 24 hours."
    ::= { virtualIfIntervalEntry 8 }

virtualIfIntervalMaxLengthViolation OBJECT-TYPE
    SYNTAX  PerfIntervalCount
    MAX-ACCESS  read-only
    STATUS  current
    DESCRIPTION
       "This counter is associated with the number of
        Rx payload Max Length Violation frames  
        encountered by a Virtual Interface in a
        particular 15-minute interval in the past 24 hours."
    ::= { virtualIfIntervalEntry 9 }

virtualIfIntervalFcsError OBJECT-TYPE
    SYNTAX  PerfIntervalCount
    MAX-ACCESS  read-only
    STATUS  current
    DESCRIPTION
       "This counter is associated with the number of
        Frame Check Sequence errors encountered by a Virtual Interface in a
        particular 15-minute interval in the past 24 hours."
    ::= { virtualIfIntervalEntry 10 }

virtualIfIntervalByteDestuffingViolation OBJECT-TYPE
    SYNTAX  PerfIntervalCount
    MAX-ACCESS  read-only
    STATUS  current
    DESCRIPTION
       "This counter is associated with the number of 
        Byte De-stuffing Violations
        encountered by a Virtual Interface in a
        particular 15-minute interval in the past 24 hours."
    ::= { virtualIfIntervalEntry 11 }


virtualIfIntervalAdressMismatch	   OBJECT-TYPE 
    SYNTAX  PerfIntervalCount
    MAX-ACCESS  read-only
    STATUS  current
    DESCRIPTION
       "This counter is associated with the number of
        Address Mismatch encountered by a Virtual Interface in a
        particular 15-minute interval in the past 24 hours."
    ::= { virtualIfIntervalEntry 12 }

virtualIfIntervalControlMismatch  OBJECT-TYPE	  
    SYNTAX  PerfIntervalCount
    MAX-ACCESS  read-only
    STATUS  current
    DESCRIPTION
       "This counter is associated with the number of
        Control mismatch encountered by a Virtual Interface in a
        particular 15-minute interval in the past 24 hours."
    ::= { virtualIfIntervalEntry 13 }

virtualIfIntervalBelowMinThreshold	 OBJECT-TYPE		   
    SYNTAX  PerfIntervalCount
    MAX-ACCESS  read-only
    STATUS  current
    DESCRIPTION
       "This counter is associated with the number of
        seconds that number of active VCs was below minimum threshold
		defined by vcGroupCnfgNoOfVCs, 
		encountered by Virtual Interface in a
        particular 15-minute interval in the past 24 hours."
    ::= { virtualIfIntervalEntry 14 }





-- the  Virtual Interface LAPS Current Table

virtualIfLAPSCurrentTable OBJECT-TYPE
    SYNTAX  SEQUENCE OF VcGroupLAPSCurrentEntry
    MAX-ACCESS  not-accessible
    STATUS  current
    DESCRIPTION
       "The Virtual Interface LAPS Current table."
     ::= { virtualIfStatistics 3 }

virtualIfLAPSCurrentEntry OBJECT-TYPE
    SYNTAX  VcGroupLAPSCurrentEntry
    MAX-ACCESS  not-accessible
    STATUS  current
    DESCRIPTION
       "An entry in the Virtual Interface 
        LAPS Current table."
    INDEX   { ifIndex  }
     ::= { virtualIfLAPSCurrentTable 1 }  

VcGroupLAPSCurrentEntry ::=
    SEQUENCE {
           virtualIfLAPSCurrentSapiMismatch            PerfCurrentCount
             }
								

virtualIfLAPSCurrentSapiMismatch OBJECT-TYPE
    SYNTAX  PerfCurrentCount
    MAX-ACCESS  read-only
    STATUS  current
    DESCRIPTION
       "This counter is associated with the number of
        received SAPI field mismatch  
        encountered by a Virtual Interface 
        in the current 15-minute interval."
    ::= { virtualIfLAPSCurrentEntry 1 }

				 

-- the Virtual Interface LAPS Interval Table

-- The Virtual Interface LAPS Interval Table
-- contains various statistics collected  over a maximum
-- of the previous 24 hours of operation.  
-- The past 24 hours may be broken into 96 
-- completed 15 minute intervals.

virtualIfLAPSIntervalTable OBJECT-TYPE
    SYNTAX  SEQUENCE OF VirtualIfLAPSIntervalEntry
    MAX-ACCESS  not-accessible
    STATUS  current
    DESCRIPTION
       "The Virtual Interface LAPS table."
     ::= { virtualIfStatistics 4 }

virtualIfLAPSIntervalEntry OBJECT-TYPE
    SYNTAX  VirtualIfLAPSIntervalEntry
    MAX-ACCESS  not-accessible
    STATUS  current
    DESCRIPTION
       "An entry in the Virtual Interface 
       LAPS Interval table."
    INDEX   { ifIndex, virtualIfIntervalNumber }
     ::= { virtualIfLAPSIntervalTable 1 }

VirtualIfLAPSIntervalEntry ::=
    SEQUENCE {
         virtualIfLAPSIntervalSapiMismatch     PerfIntervalCount
              }

virtualIfLAPSIntervalSapiMismatch OBJECT-TYPE
    SYNTAX  PerfIntervalCount
    MAX-ACCESS  read-only
    STATUS  current
    DESCRIPTION
       "This counter is associated with the number of
        received SAPI field mismatch 
        encountered by a Virtual Interface in a
        particular 15-minute interval in the past 24 hours."
    ::= { virtualIfLAPSIntervalEntry 1 }


-- the Virtual Interface LAPF Current Table

virtualIfLAPFCurrentTable OBJECT-TYPE
    SYNTAX  SEQUENCE OF VirtualIfLAPFCurrentEntry
    MAX-ACCESS  not-accessible
    STATUS  current
    DESCRIPTION
       "The Virtual Interface LAPF Current table."
     ::= { virtualIfStatistics 5 }

virtualIfLAPFCurrentEntry OBJECT-TYPE
    SYNTAX  VirtualIfLAPFCurrentEntry
    MAX-ACCESS  not-accessible
    STATUS  current
    DESCRIPTION
       "An entry in the Virtual Interface 
        LAPF Current table."
    INDEX   { ifIndex  }
     ::= { virtualIfLAPFCurrentTable 1 }

VirtualIfLAPFCurrentEntry ::=
    SEQUENCE {
		 virtualIfLAPFCurrentNlpidMismatch  PerfCurrentCount,
         virtualIfLAPFCurrentOuiMismatch    PerfCurrentCount,
		 virtualIfLAPFCurrentPidMismatch	  PerfCurrentCount,
		 virtualIfLAPFCurrentDlciMismatch	  PerfCurrentCount,
		 virtualIfLAPFCurrentMacRxFrames    PerfCurrentCount,
		 virtualIfLAPFCurrentMacTxFrames    PerfCurrentCount
    }
								

virtualIfLAPFCurrentNlpidMismatch OBJECT-TYPE
    SYNTAX  PerfCurrentCount
    MAX-ACCESS  read-only
    STATUS  current
    DESCRIPTION
       "This counter is associated with the number of
        received NLPID field mismatch  
        encountered by a Virtual Interface 
        in the current 15-minute interval."
    ::= { virtualIfLAPFCurrentEntry 1 }

virtualIfLAPFCurrentOuiMismatch OBJECT-TYPE
    SYNTAX  PerfCurrentCount
    MAX-ACCESS  read-only
    STATUS  current
    DESCRIPTION
       "This counter is associated with the number of
        received OUI field mismatch  
        encountered by a Virtual Interface 
        in the current 15-minute interval."
    ::= { virtualIfLAPFCurrentEntry 2 }


virtualIfLAPFCurrentPidMismatch OBJECT-TYPE
    SYNTAX  PerfCurrentCount
    MAX-ACCESS  read-only
    STATUS  current
    DESCRIPTION
       "This counter is associated with the number of
        received PID field mismatch  
        encountered by a Virtual Interface 
        in the current 15-minute interval."
    ::= { virtualIfLAPFCurrentEntry 3 }


virtualIfLAPFCurrentDlciMismatch OBJECT-TYPE
    SYNTAX  PerfCurrentCount
    MAX-ACCESS  read-only
    STATUS  current
    DESCRIPTION
       "This counter is associated with the number of
        received DLCI field mismatch  
        encountered by a Virtual Interface 
        in the current 15-minute interval."
    ::= { virtualIfLAPFCurrentEntry 4 }


virtualIfLAPFCurrentMacRxFrames OBJECT-TYPE
    SYNTAX  PerfCurrentCount
    MAX-ACCESS  read-only
    STATUS  current
    DESCRIPTION
       "This counter is associated with the number of
        frames received from LAN  
        by a Virtual Interface 
        in the current 15-minute interval."
    ::= { virtualIfLAPFCurrentEntry 5 }


virtualIfLAPFCurrentMacTxFrames OBJECT-TYPE
    SYNTAX  PerfCurrentCount
    MAX-ACCESS  read-only
    STATUS  current
    DESCRIPTION
       "This counter is associated with the number of
        frames transmitted to LAN
        by a Virtual Interface 
        in the current 15-minute interval."
    ::= { virtualIfLAPFCurrentEntry 6 }


-- the Virtual Interface LAPF Interval Table

-- The Virtual Interface LAPF Interval Table
-- contains various statistics collected  over a maximum
-- of the previous 24 hours of operation.  
-- The past 24 hours may be broken into 96 
-- completed 15 minute intervals.

virtualIfLAPFIntervalTable OBJECT-TYPE
    SYNTAX  SEQUENCE OF VirtualIfLAPFIntervalEntry
    MAX-ACCESS  not-accessible
    STATUS  current
    DESCRIPTION
       "The Virtual Interface LAPF Interval table."
     ::= { virtualIfStatistics 6 }

virtualIfLAPFIntervalEntry OBJECT-TYPE
    SYNTAX  VirtualIfLAPFIntervalEntry
    MAX-ACCESS  not-accessible
    STATUS  current
    DESCRIPTION
       "An entry in the Virtual Interface Interval table."
    INDEX   { ifIndex, virtualIfIntervalNumber }
     ::= { virtualIfLAPFIntervalTable 1 }

VirtualIfLAPFIntervalEntry ::=
    SEQUENCE {
         virtualIfLAPFIntervalNlpidMismatch   PerfIntervalCount,
         virtualIfLAPFIntervalOuiMismatch     PerfIntervalCount,
		 virtualIfLAPFIntervalPidMismatch	  PerfIntervalCount,
		 virtualIfLAPFIntervalDlciMismatch    PerfIntervalCount,
		 virtualIfLAPFIntervalMacRxFrames     PerfIntervalCount,
		 virtualIfLAPFIntervalMacTxFrames     PerfIntervalCount
     }


virtualIfLAPFIntervalNlpidMismatch OBJECT-TYPE
    SYNTAX  PerfIntervalCount
    MAX-ACCESS  read-only
    STATUS  current
    DESCRIPTION
       "This counter is associated with the number of
        received NLPID field mismatch 
        encountered by a Virtual Interface in a
        particular 15-minute interval in the past 24 hours."
    ::= { virtualIfLAPFIntervalEntry 1 }


virtualIfLAPFIntervalOuiMismatch OBJECT-TYPE
    SYNTAX  PerfIntervalCount
    MAX-ACCESS  read-only
    STATUS  current
    DESCRIPTION
       "This counter is associated with the number of
        received OUI field mismatch 
        encountered by a Virtual Interface in a
        particular 15-minute interval in the past 24 hours."
    ::= { virtualIfLAPFIntervalEntry 2 }



virtualIfLAPFIntervalPidMismatch OBJECT-TYPE
    SYNTAX  PerfIntervalCount
    MAX-ACCESS  read-only
    STATUS  current
    DESCRIPTION
       "This counter is associated with the number of
        received PID field mismatch 
        encountered by a Virtual Interface in a
        particular 15-minute interval in the past 24 hours."
    ::= { virtualIfLAPFIntervalEntry 3 }


virtualIfLAPFIntervalDlciMismatch OBJECT-TYPE
    SYNTAX  PerfIntervalCount
    MAX-ACCESS  read-only
    STATUS  current
    DESCRIPTION
       "This counter is associated with the number of
        received DLCI field mismatch  
        by a Virtual Interface in a
        particular 15-minute interval in the past 24 hours."
    ::= { virtualIfLAPFIntervalEntry 4 }

virtualIfLAPFIntervalMacRxFrames OBJECT-TYPE
    SYNTAX  PerfIntervalCount
    MAX-ACCESS  read-only
    STATUS  current
    DESCRIPTION
       "This counter is associated with the number of
        frames received from LAN 
        by a Virtual Interface in a
        particular 15-minute interval in the past 24 hours."
    ::= { virtualIfLAPFIntervalEntry 5 }

virtualIfLAPFIntervalMacTxFrames OBJECT-TYPE
    SYNTAX  PerfIntervalCount
    MAX-ACCESS  read-only
    STATUS  current
    DESCRIPTION
       "This counter is associated with the number of
        frames transmitted to LAN 
        encountered by a Virtual Interface in a
        particular 15-minute interval in the past 24 hours."
    ::= { virtualIfLAPFIntervalEntry 6 }


-- the Virtual Interface GFP Current Table

virtualIfGFPCurrentTable OBJECT-TYPE
    SYNTAX  SEQUENCE OF VirtualIfGFPCurrentEntry
    MAX-ACCESS  not-accessible
    STATUS  current
    DESCRIPTION
       "The Virtual Interface GFP Current table."
     ::= { virtualIfStatistics 7 }

virtualIfGFPCurrentEntry OBJECT-TYPE
    SYNTAX  VirtualIfGFPCurrentEntry
    MAX-ACCESS  not-accessible
    STATUS  current
    DESCRIPTION
       "An entry in the Virtual Interface 
       GFP Current table."
    INDEX   { ifIndex  }
     ::= { virtualIfGFPCurrentTable 1 }

VirtualIfGFPCurrentEntry ::=
    SEQUENCE {
		 virtualIfGFPCurrentIdleFrameError  PerfCurrentCount,
		 virtualIfGFPCurrentCHecSbError     PerfCurrentCount,
         virtualIfGFPCurrentPtiMismatch     PerfCurrentCount,
		 virtualIfGFPCurrentExiMismatch     PerfCurrentCount,
		 virtualIfGFPCurrentUpiMismatch     PerfCurrentCount,
		 virtualIfGFPCurrentTHecSbError     PerfCurrentCount,
		 virtualIfGFPCurrentTHecMbError     PerfCurrentCount,
         virtualIfGFPCurrentCidMismatch     PerfCurrentCount,
         virtualIfGFPCurrentEHecSbError     PerfCurrentCount,
         virtualIfGFPCurrentEHecMbError     PerfCurrentCount
    }
								
virtualIfGFPCurrentIdleFrameError OBJECT-TYPE
    SYNTAX  PerfCurrentCount
    MAX-ACCESS  read-only
    STATUS  current
    DESCRIPTION
       "This counter is associated with the number of
        received  GFP IDLE frames that are 
        detected to be in error,
        encountered by a Virtual Interface 
        in the current 15-minute interval."
     ::= { virtualIfGFPCurrentEntry 1}

virtualIfGFPCurrentCHecSbError OBJECT-TYPE
    SYNTAX  PerfCurrentCount
    MAX-ACCESS  read-only
    STATUS  current
    DESCRIPTION
       "This counter is associated with the number of
        received GFP frames that are detected to have 
        single-bit errors in the Core 
        header (i.e. cHEC field) only, 
        encountered by a Virtual Interface 
        in the current 15-minute interval."
    ::= { virtualIfGFPCurrentEntry 2 }

virtualIfGFPCurrentPtiMismatch OBJECT-TYPE
    SYNTAX  PerfCurrentCount
    MAX-ACCESS  read-only
    STATUS  current
    DESCRIPTION
       "This counter is associated with the number of
        rreceived GFP frames that are detected with 
        a mismatch on the PTI field 
        (i.e. value of PTI is not equal to 
        Client Data or Management frame),
        encountered by a Virtual Interface 
        in the current 15-minute interval."
    ::= { virtualIfGFPCurrentEntry 3 }


virtualIfGFPCurrentExiMismatch OBJECT-TYPE
    SYNTAX  PerfCurrentCount
    MAX-ACCESS  read-only
    STATUS  current
    DESCRIPTION
       "This counter is associated with the number of
        received GFP frames that are detected with 
        a mismatch on the EXI field 
        (i.e. value of EXI is not equal 
        to NULL or LINEAR modes), 
        encountered by a Virtual Interface 
        in the current 15-minute interval."
    ::= { virtualIfGFPCurrentEntry 4 }


virtualIfGFPCurrentUpiMismatch OBJECT-TYPE
    SYNTAX  PerfCurrentCount
    MAX-ACCESS  read-only
    STATUS  current
    DESCRIPTION
       "This counter is associated with the number of
        received GFP frames that are detected with a 
        mismatch on the UPI field
        (i.e. value of EXI is not equal to 00000001),
        encountered by a Virtual Interface               
        in the current 15-minute interval."
    ::= { virtualIfGFPCurrentEntry 5 }


virtualIfGFPCurrentTHecSbError OBJECT-TYPE
    SYNTAX  PerfCurrentCount
    MAX-ACCESS  read-only
    STATUS  current
    DESCRIPTION
       "This counter is associated with the number of
        received GFP frames that are detected 
        to only have single-bit errors in the Type header 
        (i.e. tHEC field),
        encountered by a Virtual Interface 
        in the current 15-minute interval."
    ::= { virtualIfGFPCurrentEntry 6 }


virtualIfGFPCurrentTHecMbError OBJECT-TYPE
    SYNTAX  PerfCurrentCount
    MAX-ACCESS  read-only
    STATUS  current
    DESCRIPTION
       "This counter is associated with the number of
       received GFP frames that are detected to 
       only have multi-bit errors in the 
       Type header (i.e. tHEC field),        
       encountered by a Virtual Interface 
        in the current 15-minute interval."
    ::= { virtualIfGFPCurrentEntry 7 }

virtualIfGFPCurrentCidMismatch OBJECT-TYPE
    SYNTAX  PerfCurrentCount
    MAX-ACCESS  read-only
    STATUS  current
    DESCRIPTION
       "This counter is associated with the number of
       received GFP frames that are detected to have a 
       mismatch/unsupported value in the CID field only,  
       encountered by a Virtual Interface 
       in the current 15-minute interval."
    ::= { virtualIfGFPCurrentEntry 8 }

virtualIfGFPCurrentEHecSbError OBJECT-TYPE
    SYNTAX  PerfCurrentCount
    MAX-ACCESS  read-only
    STATUS  current
    DESCRIPTION
       "This counter is associated with the number of
        received  GFP frames that are detected 
        to only have single-bit errors 
        in the Extension header (i.e. eHEC field), 
        encountered by a Virtual Interface 
        in the current 15-minute interval."
    ::= { virtualIfGFPCurrentEntry 9 }

virtualIfGFPCurrentEHecMbError OBJECT-TYPE
    SYNTAX  PerfCurrentCount
    MAX-ACCESS  read-only
    STATUS  current
    DESCRIPTION
       "This counter is associated with the number of
        received GFP frames that are detected to only 
        have single-bit errors in the 
        Extension header (i.e. eHEC field), 
        encountered by a Virtual Interface 
        in the current 15-minute interval."
    ::= { virtualIfGFPCurrentEntry 10 }


-- the Virtual Interface GFP Interval Table

-- The Virtual Interface GFP Interval Table
-- contains various statistics collected  over a maximum
-- of the previous 24 hours of operation.  
-- The past 24 hours may be broken into 96 
-- completed 15 minute intervals.

virtualIfGFPIntervalTable OBJECT-TYPE
    SYNTAX  SEQUENCE OF VirtualIfGFPIntervalEntry
    MAX-ACCESS  not-accessible
    STATUS  current
    DESCRIPTION
       "The Virtual Interface GFP Interval table."
     ::= { virtualIfStatistics 8 }

virtualIfGFPIntervalEntry OBJECT-TYPE
    SYNTAX  VirtualIfGFPIntervalEntry
    MAX-ACCESS  not-accessible
    STATUS  current
    DESCRIPTION
       "An entry in the Virtual Interface 
       GFP Interval table."
    INDEX   { ifIndex, virtualIfIntervalNumber }
     ::= { virtualIfGFPIntervalTable 1 }

VirtualIfGFPIntervalEntry ::=
    SEQUENCE {
     	  virtualIfGFPIntervalIdleFrameError	  PerfIntervalCount,
     	  virtualIfGFPIntervalCHecSbError	      PerfIntervalCount,
     	  virtualIfGFPIntervalPtiMismatch	      PerfIntervalCount,
     	  virtualIfGFPIntervalExiMismatch	      PerfIntervalCount,
     	  virtualIfGFPIntervalUpiMismatch	      PerfIntervalCount,
     	  virtualIfGFPIntervalTHecSbError	      PerfIntervalCount,
     	  virtualIfGFPIntervalTHecMbError	      PerfIntervalCount,
     	  virtualIfGFPIntervalCidMismatch	      PerfIntervalCount,
     	  virtualIfGFPIntervalEHecSbError	      PerfIntervalCount,
     	  virtualIfGFPIntervalEHecMbError	      PerfIntervalCount
     	      }

virtualIfGFPIntervalIdleFrameError OBJECT-TYPE
    SYNTAX  PerfIntervalCount
    MAX-ACCESS  read-only
    STATUS  current
    DESCRIPTION
       "This counter is associated with the number of
        received  GFP IDLE frames that are detected to be in error,
        encountered by a Virtual Interface in a
        particular 15-minute interval in the past 24 hours."
    ::= { virtualIfGFPIntervalEntry 1 }

virtualIfGFPIntervalCHecSbError OBJECT-TYPE
    SYNTAX  PerfIntervalCount
    MAX-ACCESS  read-only
    STATUS  current
    DESCRIPTION
       "This counter is associated with the number of
        received GFP frames that are detected to have 
        single-bit errors in the Core header (i.e. cHEC field) only, 
        encountered by a Virtual Interface in a
        particular 15-minute interval in the past 24 hours."
    ::= { virtualIfGFPIntervalEntry 2 }

virtualIfGFPIntervalPtiMismatch OBJECT-TYPE
    SYNTAX  PerfIntervalCount
    MAX-ACCESS  read-only
    STATUS  current
    DESCRIPTION
       "This counter is associated with the number of
        rreceived GFP frames that are detected with 
        a mismatch on the PTI field (i.e. value of PTI 
        is not equal to Client Data or Management frame),
        encountered by a Virtual Interface in a
        particular 15-minute interval in the past 24 hours."
    ::= { virtualIfGFPIntervalEntry 3 }

virtualIfGFPIntervalExiMismatch OBJECT-TYPE
    SYNTAX  PerfIntervalCount
    MAX-ACCESS  read-only
    STATUS  current
    DESCRIPTION
       "This counter is associated with the number of
        received GFP frames that are detected with 
        a mismatch on the EXI field (i.e. value of EXI is not 
        equal  to NULL or LINEAR modes), 		        
        encountered by a Virtual Interface in a
        particular 15-minute interval in the past 24 hours."
    ::= { virtualIfGFPIntervalEntry 4 }

virtualIfGFPIntervalUpiMismatch OBJECT-TYPE
    SYNTAX  PerfIntervalCount
    MAX-ACCESS  read-only
    STATUS  current
    DESCRIPTION
       "This counter is associated with the number of
        received GFP frames that are detected with a 
        mismatch on the UPI field (i.e. value of EXI 
        is not equal to 00000001),
         encountered by a Virtual Interface in a
        particular 15-minute interval in the past 24 hours."
    ::= { virtualIfGFPIntervalEntry 5 }

virtualIfGFPIntervalTHecSbError OBJECT-TYPE
    SYNTAX  PerfIntervalCount
    MAX-ACCESS  read-only
    STATUS  current
    DESCRIPTION
       "This counter is associated with the number of
        received GFP frames that are detected to only have
         single-bit errors in the Type header (i.e. tHEC field),
        encountered by a Virtual Interface in a
        particular 15-minute interval in the past 24 hours."
    ::= { virtualIfGFPIntervalEntry 6 }

virtualIfGFPIntervalTHecMbError OBJECT-TYPE
    SYNTAX  PerfIntervalCount
    MAX-ACCESS  read-only
    STATUS  current
    DESCRIPTION
       "This counter is associated withthe number of
       received GFP frames that are detected to only have
       multi-bit errors in the Type header (i.e. tHEC field), 
       encountered by a Virtual Interface in a
       particular 15-minute interval in the past 24 hours."
    ::= { virtualIfGFPIntervalEntry 7 }

virtualIfGFPIntervalCidMismatch OBJECT-TYPE
    SYNTAX  PerfIntervalCount
    MAX-ACCESS  read-only
    STATUS  current
    DESCRIPTION
       "This counter is associated with  the number of
       received GFP frames that are detected to have a 
       mismatch/unsupported value in the CID field only,
       encountered by a Virtual Interface in a
       particular 15-minute interval in the past 24 hours."
    ::= { virtualIfGFPIntervalEntry 8 }

virtualIfGFPIntervalEHecSbError OBJECT-TYPE
    SYNTAX  PerfIntervalCount
    MAX-ACCESS  read-only
    STATUS  current
    DESCRIPTION
       "This counter is associated with the number of
        received  GFP frames that are detected 
        to only have single-bit errors 
        in the Extension header (i.e. eHEC field),         
        encountered by a Virtual Interface in a
        particular 15-minute interval in the past 24 hours."
    ::= { virtualIfGFPIntervalEntry 9 }

virtualIfGFPIntervalEHecMbError OBJECT-TYPE
    SYNTAX  PerfIntervalCount
    MAX-ACCESS  read-only
    STATUS  current
    DESCRIPTION
       "This counter is associated with the the number of
        received GFP frames that are detected to only  have
        multi-bit errors in the  Extension header (i.e. eHEC field),
        encountered by a Virtual Interface in a
        particular 15-minute interval in the past 24 hours."
    ::= { virtualIfGFPIntervalEntry 10 }

prtSonetConfig  OBJECT IDENTIFIER  ::=  {sonetInterface 2}

prtSonetGen  	OBJECT IDENTIFIER  ::=  {prtSonetConfig 1}

prtSonetGenTable OBJECT-TYPE
     SYNTAX  SEQUENCE OF PrtSonetGenEntry
     MAX-ACCESS  not-accessible
     STATUS  current
     DESCRIPTION
     "Sonet/SDH general port configuration table."
     ::= { prtSonetGen 1}
   
prtSonetGenEntry   OBJECT-TYPE
     SYNTAX  PrtSonetGenEntry
     MAX-ACCESS  not-accessible
     STATUS  current
     DESCRIPTION
     " An entry in the Sonet/SDH general port configuration table."
     INDEX { prtSonetGenCnfgIdx, prtSonetGenIdx }
     ::= { prtSonetGenTable 1}

PrtSonetGenEntry ::=
     SEQUENCE {
     prtSonetGenCnfgIdx
     Integer32,
     prtSonetGenIdx
     Integer32,
     prtSonetGenSdThreshold
     INTEGER,
     prtSonetGenEedThreshold
     INTEGER,
	 prtSonetGenBerEnable
     INTEGER
          }
 
prtSonetGenCnfgIdx OBJECT-TYPE
     SYNTAX  Integer32 (1..255)
     MAX-ACCESS  read-only
     STATUS  current
     DESCRIPTION
     "This object indicates the Idx of the Config being accessed.
      Idx of 255 relates to the Temporary (Scratch) Config.
      For products that support several configurations, Set can be performed
      only to the Temporary Config (=255). "
     ::= { prtSonetGenEntry 1}

prtSonetGenIdx OBJECT-TYPE
     SYNTAX  Integer32
     MAX-ACCESS  read-only
     STATUS  current
     DESCRIPTION
     "This object indicates a unique  port or interface number.
	 For numbering, see product's spec.
     For some products, the numbering can equal ifIndex."
     ::= { prtSonetGenEntry 2}

prtSonetGenSdThreshold OBJECT-TYPE
     SYNTAX  INTEGER {
     notApplicable(1),
     n3           (3),
     n4           (4),  
     n5           (5),
     n6			  (6),
     n7			  (7),
     n8			  (8),
     n9			  (9)   
     }
     MAX-ACCESS  read-write
     STATUS  current
     DESCRIPTION
     "SD=Signal Degraded Threshold. Units: [10E-].
	  The threshold is 10E-x relative to the frequency of the data flow.
	  x=3, 4, 5, 6, 7, 8, 9.
      n3= 10E-3
      n4= 10E-4
      n5= 10E-5
      n6= 10E-6
      n7= 10E-7
      n8= 10E-8
      n9= 10E-9  ."
     ::= { prtSonetGenEntry 3 }

prtSonetGenEedThreshold OBJECT-TYPE
     SYNTAX  INTEGER {
     notApplicable(1),
	 n3			  (3),
	 n4			  (4),
	 n5			  (5),
     n6           (6),
     n7           (7),  
     n8           (8),
     n9           (9)    
     }
     MAX-ACCESS  read-write
     STATUS  current
     DESCRIPTION
     "EED=Excessive Error Defect Threshold. Units: [10E-].
	  The threshold is 10E-x relative to the frequency of the data flow.
	  x=3, 4, 5, 6, 7, 8, 9.
      n3= 10E-3
      n4= 10E-4
      n5= 10E-5
      n6= 10E-6
      n7= 10E-7
      n8= 10E-8
      n9= 10E-9 ."
     ::= { prtSonetGenEntry 4 }

prtSonetGenBerEnable OBJECT-TYPE
     SYNTAX  INTEGER {
     notApplicable(1),
	 disable      (2),
     enable       (3)    
     }
     MAX-ACCESS  read-write
     STATUS  current
     DESCRIPTION
      "Controls the activation of the Line Ber (Bit Error Rate), means whether 
       SD and EED threshold parameters will be enabled."
      ::= { prtSonetGenEntry 5 }


--STM-1 ports

prtSonetStm1  	OBJECT IDENTIFIER  ::=  {prtSonetConfig 2}


prtSonetStm1Table OBJECT-TYPE
     SYNTAX  SEQUENCE OF PrtSonetStm1Entry
     MAX-ACCESS  not-accessible
     STATUS  current
     DESCRIPTION
     "Sonet/SDH STM-1 port configuration table."
     ::= { prtSonetStm1 1}
   
prtSonetStm1Entry   OBJECT-TYPE
     SYNTAX  PrtSonetStm1Entry
     MAX-ACCESS  not-accessible
     STATUS  current
     DESCRIPTION
     " An entry in the Sonet/SDH STM-1 port configuration table."
     INDEX { prtSonetStm1CnfgIdx, prtSonetStm1Idx }
     ::= { prtSonetStm1Table 1}

PrtSonetStm1Entry ::=
     SEQUENCE {
     prtSonetStm1CnfgIdx
     Integer32,
     prtSonetStm1Idx
     Integer32,
     prtSonetStm1ClockSrc
     INTEGER,
     prtSonetStm1DccMode
     INTEGER,
	 prtSonetStm1RoutingProt
	 INTEGER,
	 prtSonetStm1MngProt
	 INTEGER,
	 prtSonetStm1OperationalMode
	 INTEGER,	  
     prtSonetStm1VoiceChannel 
     INTEGER,
     prtSonetStm1OutputRate
     Integer32,
     prtSonetStm1S1ProtocolClock
     INTEGER,
     prtSonetStm1GatewayRingSubnetAddress
     IpAddress,
     prtSonetStm1GatewayRingSubnetMask	 
	 IpAddress,
	 prtSonetStm1MngProtDeviationType
	 INTEGER,
	 prtSonetStm1MngSameIpAsHost
	 INTEGER,
	 prtSonetStm1MngIpAddress
	 IpAddress,
	 prtSonetStm1MngIpSubnetMask
	 IpAddress,
	 prtSonetStm1MngDefaultGateway
	 IpAddress
	 }
 
prtSonetStm1CnfgIdx OBJECT-TYPE
     SYNTAX  Integer32 (1..255)
     MAX-ACCESS  read-only
     STATUS  current
     DESCRIPTION
     "This object indicates the Idx of the Config being accessed.
      Idx of 255 relates to the Temporary (Scratch) Config.
      For products that support several configurations, Set can be performed
      only to the Temporary Config (=255). "
     ::= { prtSonetStm1Entry 1}

prtSonetStm1Idx OBJECT-TYPE
     SYNTAX  Integer32
     MAX-ACCESS  read-only
     STATUS  current
     DESCRIPTION
     "This object indicates a unique  port or interface number.
	 For numbering, see product's spec.
     For some products, the numbering can equal ifIndex."
     ::= { prtSonetStm1Entry 2}

prtSonetStm1ClockSrc OBJECT-TYPE
     SYNTAX  INTEGER {
     notApplicable(1),
     internal     (2),
     lbt          (3),
	 systemClk    (4)
     }
     MAX-ACCESS  read-write
     STATUS  current
     DESCRIPTION
     "Clock Source of the STM-1 port.
      lbt = Loop Back Timing."
     ::= { prtSonetStm1Entry 3 }

prtSonetStm1DccMode OBJECT-TYPE
     SYNTAX  INTEGER {
     notApplicable(1),
     none         (2),
     d1ToD3       (3),  
     d4ToD12      (4),
     d1           (5),
     d2           (6),
     d3           (7),
     d4           (8),     
     d5           (9),     
     d6           (10),     
     d7           (11),     
     d8           (12),     
     d9           (13),     
     d10          (14),     
     d11          (15),
     d12          (16)        
     }
     MAX-ACCESS  read-write
     STATUS  current
     DESCRIPTION
     "DCC Mode. DCC=Data Communication Channel.
	  d1ToD3 = D1-D3  bytes are used (RS=Regeneration Section).
	  d4ToD12= D4-D12 bytes are used (MS=Multiplexing Section).
	  d1.... d12 enable user to select single DCC byte "
     ::= { prtSonetStm1Entry 4 }

prtSonetStm1RoutingProt OBJECT-TYPE
     SYNTAX  INTEGER {
      notApplicable (1),
      none          (2),  
      proprietary   (3),
	  rip2          (4)
     }
     MAX-ACCESS  read-write
     STATUS  current
     DESCRIPTION
     "Routing Protocol."
     ::= { prtSonetStm1Entry 5 }

prtSonetStm1MngProt OBJECT-TYPE
     SYNTAX  INTEGER {
      notApplicable (1),
      -- none (2)
      proprietary   (3),  
      -- rip2  (4)
      ppp           (5),
	  frameRelay    (6),
	  hdlc          (7),
	  lapdOverHdlc  (8)
     }				
     MAX-ACCESS  read-write
     STATUS  current
     DESCRIPTION
     "Management Protocol over DCC:  Proprietary, PPP, Frame Relay,
     HDLC or LAPD over HDLC .
     ppp = according to STD-51 ( rfc1661/1662)"
     ::= { prtSonetStm1Entry 6 }

prtSonetStm1OperationalMode OBJECT-TYPE
     SYNTAX  INTEGER {
      notApplicable    (1),
      terminal         (2),
      linear           (3),  
      linearProtection (4),
	  dualRing         (5)
     }
     MAX-ACCESS  read-write
     STATUS  current
     DESCRIPTION
     "Operational Mode.
      linear - cannot be selected when there is Redundancy between the
               STM-1 ports."
     ::= { prtSonetStm1Entry 7 }

prtSonetStm1VoiceChannel  OBJECT-TYPE
     SYNTAX  INTEGER {
      notApplicable (1),
      none   (2),
      e1Byte (3),
      e2Byte (4)  
     }
     MAX-ACCESS  read-write
     STATUS  current
     DESCRIPTION
     "This parameter enable user to select whether
      voice channel will be transferred using E1 byte, E2 Byte, or not at all."
     ::= { prtSonetStm1Entry 8 }

prtSonetStm1OutputRate  OBJECT-TYPE
     SYNTAX  Integer32
     MAX-ACCESS  read-write
     STATUS  current
     DESCRIPTION
     "This parameter indicates the output rate in cells/sec, which is 
      supported per port."
     ::= { prtSonetStm1Entry 9 }

prtSonetStm1S1ProtocolClock  OBJECT-TYPE
     SYNTAX  INTEGER {
      notApplicable (1),
      disable       (2),
	  enable        (3),
	  transparent   (4)
     }
     MAX-ACCESS  read-write
     STATUS  current
     DESCRIPTION
     "This parameter allows user to select whether to enable use of
      Remote Side Clock according to the Protocol passed on S1 Bit."
     ::= { prtSonetStm1Entry 10 }

prtSonetStm1GatewayRingSubnetAddress	 OBJECT-TYPE
     SYNTAX  IpAddress
     MAX-ACCESS  read-write
     STATUS  current
     DESCRIPTION
     "This parameter defines subnet for static routing,
      together with prtSonetStm1GatewayRingSubnetMask"     
      ::= { prtSonetStm1Entry 11 }

prtSonetStm1GatewayRingSubnetMask	 OBJECT-TYPE
     SYNTAX  IpAddress
     MAX-ACCESS  read-write
     STATUS  current
     DESCRIPTION
     "This parameter defines subnet for static routing,
      together with prtSonetStm1GatewayRingSubnetAddress"
     ::= { prtSonetStm1Entry 12 }

prtSonetStm1MngProtDeviationType OBJECT-TYPE
     SYNTAX  INTEGER 
     {
	 notApplicable (1),
	 standard      (2),
	 type1         (3)
     }				
     MAX-ACCESS  read-write
     STATUS  current
     DESCRIPTION
     "This parameter is used in conjunction with prtSonetStm1MngProt
      to define management protocol used & type of deviation 
      (if exist) from standard.
      Standard  = no deviation from standard protocol
      Type1     = PPP without sending Address and Control overhead
                  in Link Control Protocol (LCP) packets"
     ::= { prtSonetStm1Entry 13 }

prtSonetStm1MngSameIpAsHost  OBJECT-TYPE
     SYNTAX  INTEGER 
     {
	 notApplicable (1),
	 no            (2),
	 yes           (3)
     }				
     MAX-ACCESS  read-write
     STATUS  current
     DESCRIPTION
     "This parameter indicates whether IP address
      used for management is same as the device IP address"
     ::= { prtSonetStm1Entry 14 }

prtSonetStm1MngIpAddress  OBJECT-TYPE	   
     SYNTAX  IpAddress 
     MAX-ACCESS  read-write
     STATUS  current
     DESCRIPTION
     "This parameter defines IP address for DCC management 
      for this link, together with prtSonetStm1MngIpSubnetMask.		
      This parameter is applicable only if prtSonetStm1MngSameIpAsHost=no."     
      ::= { prtSonetStm1Entry 15 }

prtSonetStm1MngIpSubnetMask	 OBJECT-TYPE
     SYNTAX  IpAddress
     MAX-ACCESS  read-write
     STATUS  current
     DESCRIPTION
     "This parameter defines IP subnet mask for DCC management 
      for this link, together with prtSonetStm1MngIpAddress
      This parameter is applicable only if prtSonetStm1MngSameIp=no"     
      ::= { prtSonetStm1Entry 16 }

prtSonetStm1MngDefaultGateway	 OBJECT-TYPE
     SYNTAX  IpAddress
     MAX-ACCESS  read-write
     STATUS  current
     DESCRIPTION
     "This parameter defines default Gateway address for DCC management 
      for this link. 
      This parameter is applicable only if prtSonetStm1MngSameIp=no"     
      ::= { prtSonetStm1Entry 17 }

--SONET/SDH VC-3, VC-4 and VC-12 ports parameters

prtSonetVc  	OBJECT IDENTIFIER  ::=  {prtSonetConfig 3}


prtSonetVcTable OBJECT-TYPE
     SYNTAX  SEQUENCE OF PrtSonetVcEntry
     MAX-ACCESS  not-accessible
     STATUS  current
     DESCRIPTION
     "Sonet/SDH VC port configuration table."
     ::= { prtSonetVc 1}
   
prtSonetVcEntry   OBJECT-TYPE
     SYNTAX  PrtSonetVcEntry
     MAX-ACCESS  not-accessible
     STATUS  current
     DESCRIPTION
     " An entry in the Sonet/SDH VC port configuration table."
     INDEX { prtSonetVcCnfgIdx, prtSonetVcIdx }
     ::= { prtSonetVcTable 1}

PrtSonetVcEntry ::=
     SEQUENCE {
     prtSonetVcCnfgIdx
     Integer32,
     prtSonetVcIdx
     Integer32,
     prtSonetVcJTxPathTraceEnable
     INTEGER,
     prtSonetVcJRxPathTraceEnable
     INTEGER,
	 prtSonetVcJPathTrace
	 DisplayString,
	 prtSonetVcConnect
	 INTEGER,
	 prtSonetVcSignalLabel
	 OCTET STRING, 
	 prtSonetVcPathTracePadding
     INTEGER,
	 prtSonetVcPayloadBlockOnPathTrace
	 INTEGER,
	 prtSonetVcPayloadType
	 INTEGER,
	 prtSonetVcPathTraceSize
	 INTEGER

     }
 
prtSonetVcCnfgIdx OBJECT-TYPE
     SYNTAX  Integer32 (1..255)
     MAX-ACCESS  read-only
     STATUS  current
     DESCRIPTION
     "This object indicates the Idx of the Config being accessed.
      Idx of 255 relates to the Temporary (Scratch) Config.
      For products that support several configurations, Set can be performed
      only to the Temporary Config (=255). "
     ::= { prtSonetVcEntry 1}

prtSonetVcIdx OBJECT-TYPE
     SYNTAX  Integer32
     MAX-ACCESS  read-only
     STATUS  current
     DESCRIPTION
     "This object indicates a unique  port or interface number.
	 For numbering, see product's spec.
     For some products, the numbering can equal ifIndex."
     ::= { prtSonetVcEntry 2}

prtSonetVcJTxPathTraceEnable OBJECT-TYPE
     SYNTAX  INTEGER {
     notApplicable(1),
     disable      (2),
	 enable       (3)
     }
     MAX-ACCESS  read-write
     STATUS  current
     DESCRIPTION
     "Enable/Disable Transmitting Jy Path Trace. y=1, 2:
      J1 - for VC-4  layer
      J2 - for VC-12 layer."
     ::= { prtSonetVcEntry 3 }

prtSonetVcJRxPathTraceEnable OBJECT-TYPE
     SYNTAX  INTEGER {
     notApplicable(1),
     disable      (2),
	 enable       (3)
     }
     MAX-ACCESS  read-write
     STATUS  current
     DESCRIPTION
     "Enable/Disable checking Jy Path Trace. y=1, 2:
      J1 - for VC-4  layer
      J2 - for VC-12 layer."
     ::= { prtSonetVcEntry 4 }

prtSonetVcJPathTrace OBJECT-TYPE
     SYNTAX  DisplayString (SIZE(0..62))
     MAX-ACCESS  read-write
     STATUS  current
     DESCRIPTION
     "Jy Path Trace. y=1, 2:
      J1 - for VC-4  layer
      J2 - for VC-12 layer.
      This object is applicable only if one of the previous 2 objects is 'enable'."
     ::= { prtSonetVcEntry 5 }

prtSonetVcConnect  OBJECT-TYPE
      SYNTAX  INTEGER
      {
      notApplicable (1),
	  no (2),
	  yes (3)
      }
      MAX-ACCESS  read-write
      STATUS  current
      DESCRIPTION
      "Connect VCn (n - 11,12,2,3,4) port (yes/no)." 
     ::= { prtSonetVcEntry 6 }


prtSonetVcSignalLabel  OBJECT-TYPE
      SYNTAX  OCTET STRING	(SIZE (1))
      MAX-ACCESS  read-write
      STATUS  current
      DESCRIPTION
      "Signal Label. 
       For VC-3:
       The SONET standard defines the C2 byte as
       the path signal label. The purpose of this byte is to
       communicate the payload type being encapsulated by the 
       SONET Framing OverHead. It allows a single interface to
       transport multiple payload types simultaneously.
       
	   For VC-12, VT-1.5:
       VT path overhead V5 byte allocates bits 5-7  for 
       VT Path Signal Label, to indicate the content of the VT SPE.
        000 Unequipped
        001 Equipped : non-specific payload
        010 Asynchronous mapping
        011 Bit synchronous mapping (no longer valid for DS1)
        100 Byte synchronous mapping
        101 Unassigned
        110 Unassigned
        111 Unassigned
        	
       Agents that do not support this feature will send SIZE 0."
     ::= { prtSonetVcEntry 7 } 

prtSonetVcPathTracePadding  OBJECT-TYPE
      SYNTAX  INTEGER
      {
      notApplicable (1),
	  nuls   (2),
	  spaces (3)
      }
      MAX-ACCESS  read-write
      STATUS  current
      DESCRIPTION
      "Padding character will pad prtSonetVcJPathTrace string 
        to fill required number of characters." 
     ::= { prtSonetVcEntry 8 }

prtSonetVcPayloadBlockOnPathTrace  OBJECT-TYPE
      SYNTAX  INTEGER
      {
      notApplicable (1),
	  disable   (2),
	  enable (3)
      }
      MAX-ACCESS  read-write
      STATUS  current
      DESCRIPTION
      "Block payload on this VC upon PathTrace (TIM)." 
     ::= { prtSonetVcEntry 9 }


prtSonetVcPayloadType  OBJECT-TYPE
      SYNTAX  INTEGER
      {
      notApplicable (1),
	  pos           (2),
	  clearchannel  (3),
	  channelized   (4),
	  vc1x     		(5)
       }
      MAX-ACCESS  read-write
      STATUS  current
      DESCRIPTION
      "Payload type, applicable for STS-1/TUG-3 layer.
      vc1x = vc12 or vc11 for SDH, VT1.5, VT2 for SONET.
	  clear channel	 - complete TUG-3 or STS-1 
      For Egate-100:
      POS (Packets over Sonet) configuration is valid per STM1/OC3, 
      change this mode to POS for one TUG3/STS1 change values
      to POS for all TUG3/STS1 under  this STM1/OC3. 
      Clear Channel/channelize/ configuration is valid per TUG3/STS1." 
     ::= { prtSonetVcEntry 10 }


prtSonetVcPathTraceSize  OBJECT-TYPE
      SYNTAX  INTEGER
      {
      notApplicable (1),
	  b16           (2),
	  b64           (3)
       }
      MAX-ACCESS  read-write
      STATUS  current
      DESCRIPTION
      "Path Trace Size in Bytes - 16 or 64." 
     ::= { prtSonetVcEntry 11 }


--TU-12 (within VC-4) Connect Table

prtSonetTuTable  OBJECT-TYPE
     SYNTAX SEQUENCE OF PrtSonetTuEntry
     MAX-ACCESS not-accessible
     STATUS  current
     DESCRIPTION
      "The write operation into the Table's Objects is valid only
       for the TmpCnfg entry (Scratch)."
  ::= { prtSonetVc 2}

prtSonetTuEntry OBJECT-TYPE
      SYNTAX PrtSonetTuEntry
      MAX-ACCESS not-accessible
      STATUS current
	DESCRIPTION  "An entry in table."
	INDEX {prtSonetTuCnfgIdx, prtSonetTuPrtIdx, prtSonetTuIdx, prtSonetTuConPrtIdx }
      ::= { prtSonetTuTable 1}

PrtSonetTuEntry ::=
      SEQUENCE {
      prtSonetTuCnfgIdx        Integer32,
      prtSonetTuPrtIdx         Integer32,
      prtSonetTuIdx            Integer32,
      prtSonetTuConPrtIdx      Integer32,
      prtSonetTuType           INTEGER,
      prtSonetTuMode           INTEGER,
	  prtSonetTuRowStatus      RowStatus
      }

prtSonetTuCnfgIdx OBJECT-TYPE
      SYNTAX  Integer32  (1..255)
      MAX-ACCESS  read-only
      STATUS  current
      DESCRIPTION
      "This object indicates the Idx of the Config being accessed.
      Idx of 255 relates to the Temporary (Scratch) Config.
      For products that support several configurations, Set can be performed
      only to the Temporary Config (=255). "
      ::= { prtSonetTuEntry 1}

prtSonetTuPrtIdx OBJECT-TYPE
      SYNTAX  Integer32
      MAX-ACCESS  read-only
      STATUS  current
      DESCRIPTION
      "This object indicates a unique  port or interface number.
	  For port numbering, see product's spec.
      For some products, the numbering can equal ifIndex."
      ::= { prtSonetTuEntry 2}

prtSonetTuIdx OBJECT-TYPE
      SYNTAX  Integer32
      MAX-ACCESS  read-only
      STATUS  current
      DESCRIPTION
      "This object indicates a unique TU (Tributary Unit) within VC-4.
	   The valid TUs are 1..63."
      ::= { prtSonetTuEntry 3}

prtSonetTuConPrtIdx OBJECT-TYPE
      SYNTAX  Integer32
      MAX-ACCESS  read-only
      STATUS  current
      DESCRIPTION
      "This object indicates the connected port, when prtSonetTuType=connect.
	   For port numbering, see product's spec.
       For some products, the numbering can equal ifIndex.
       notApplicable - will be indicated as 100."
      ::= {prtSonetTuEntry 4}

prtSonetTuType  OBJECT-TYPE
      SYNTAX  INTEGER
      {
      connect (2),
	  bypass  (3)
      }
      MAX-ACCESS  read-create
      STATUS  current
      DESCRIPTION
      "The type of TU (Tributary Unit). 
       connect - connected to one of the E1 ports.
	   bypass  - bypassed to the other VC4 port.
       TUs that are not connected or bypassed, will not exist in this table." 
      ::= { prtSonetTuEntry 5}

prtSonetTuMode  OBJECT-TYPE
      SYNTAX  INTEGER
      {
      notApplicable(1),
      addAndDrop   (2),
      add          (3)
      }
      MAX-ACCESS  read-create
      STATUS  current
      DESCRIPTION
      "TU Mode of connection. 
       addAndDrop    - Add & Drop
       add           - Add (TU receives from the E1 ports)." 
      ::= { prtSonetTuEntry 6}

prtSonetTuRowStatus OBJECT-TYPE
      SYNTAX RowStatus 
      MAX-ACCESS read-create
      STATUS current
      DESCRIPTION
      "Creation/Deletion of rows in the table."
      ::= { prtSonetTuEntry 7}


-- SDH Cross Connect Table
-- May be used also for SONET 

prtSonetXConnect  OBJECT IDENTIFIER  ::= {sonetInterface 3}

prtSonetXConnectTable  OBJECT-TYPE
     SYNTAX SEQUENCE OF PrtSonetXConnectEntry
     MAX-ACCESS not-accessible
     STATUS  current
     DESCRIPTION
      "The write operation into the Table's Objects is valid only
       for the TmpCnfg entry (Scratch)."
     ::= { prtSonetXConnect 1}

prtSonetXConnectEntry OBJECT-TYPE
      SYNTAX PrtSonetXConnectEntry
      MAX-ACCESS not-accessible
      STATUS current
      DESCRIPTION  "An entry in table."
	  INDEX  { 
	         prtSonetXConnectCnfgIdx,
	         prtSonetXConnectPrtIdx,
	         prtSonetXConnectConPrtIdx,
	         prtSonetXConnectAUGIdx,
	         prtSonetXConnectTUG3Idx,
	         prtSonetXConnectTUG2Idx,
	         prtSonetXConnectTUnIdx
	         }
	      ::= { prtSonetXConnectTable 1}

PrtSonetXConnectEntry ::=
      SEQUENCE {
      prtSonetXConnectCnfgIdx        Integer32,
      prtSonetXConnectPrtIdx         Integer32,
	  prtSonetXConnectConPrtIdx      Integer32,
      prtSonetXConnectAUGIdx         Integer32,
      prtSonetXConnectTUG3Idx        Integer32,
      prtSonetXConnectTUG2Idx        Integer32,
      prtSonetXConnectTUnIdx         Integer32,
	  prtSonetXConnectRowStatus      RowStatus,
	  prtSonetXConnectDirection      INTEGER,
      prtSonetXConnectTuNumber       INTEGER,
	  prtSonetXConnectMode			 INTEGER
      }

prtSonetXConnectCnfgIdx OBJECT-TYPE
      SYNTAX  Integer32  (1..255)
      MAX-ACCESS  read-only
      STATUS  current
      DESCRIPTION
      "This object indicates the Idx of the Config being accessed.
       Idx of 255 relates to the Temporary (Scratch) Config.
       For products that support several configurations, Set can be performed
       only to the Temporary Config (=255). "
      ::= { prtSonetXConnectEntry 1}

prtSonetXConnectPrtIdx OBJECT-TYPE
      SYNTAX  Integer32
      MAX-ACCESS  read-only
      STATUS  current
      DESCRIPTION
      "This object indicates a unique  port or interface number.
	   For port numbering, see product's spec.
       For some products, the numbering can equal ifIndex."
      ::= { prtSonetXConnectEntry 2}

prtSonetXConnectConPrtIdx OBJECT-TYPE
      SYNTAX  Integer32
      MAX-ACCESS  read-only
      STATUS  current
      DESCRIPTION
      "This object indicates the connected port. 
	   For port numbering, see product's spec.
       For some products, the numbering can equal ifIndex.
       notApplicable - will be indicated as 255."
      ::= {prtSonetXConnectEntry 3}


prtSonetXConnectAUGIdx OBJECT-TYPE
      SYNTAX  Integer32	
      MAX-ACCESS  read-only
      STATUS  current
      DESCRIPTION
      "This object indicates an  AUG (Administrative Unit Group) within STM-N.
	   The valid AUGs values are:
	   1 for STM-1
	   1...4 for STM-4,
	   1..16 for STM-16  and  
	   1..64 for STM-64  (STM-64)  
	   255 designates NA."
      ::= { prtSonetXConnectEntry 4}

prtSonetXConnectTUG3Idx OBJECT-TYPE
      SYNTAX  Integer32	
      MAX-ACCESS  read-only
      STATUS  current
      DESCRIPTION
      "This object indicates a  TUG-3 (Tributary Unit Group 3) within VC-4.
	   The valid TUG3s are values are 1..3. and 255 which designates NA "
      ::= { prtSonetXConnectEntry 5}

prtSonetXConnectTUG2Idx OBJECT-TYPE
      SYNTAX  Integer32	
      MAX-ACCESS  read-only
      STATUS  current
      DESCRIPTION
      "This object indicates a TUG2 (Tributary Unit Group 2 ) within VC-3.
	   The valid TUG2's values  are 1..7 and 255 which designates NA "
      ::= { prtSonetXConnectEntry 6}

prtSonetXConnectTUnIdx OBJECT-TYPE
      SYNTAX  Integer32
      MAX-ACCESS  read-only
      STATUS  current
      DESCRIPTION
      "This object indicates a TUn within TUG-2 or TUG-3
       (Tributary Unit n, where  n is 2, 12 or 11 within TUG-2,  
       or 3 within TUG-3)
       valid values are
	   1 for TU-2
	   1 for TU-3
	   1..4  for TU-11
	   1..3  for TU-12
	   255 designates NA" 
	   ::= { prtSonetXConnectEntry 7}


prtSonetXConnectRowStatus OBJECT-TYPE
      SYNTAX RowStatus 
      MAX-ACCESS read-create
      STATUS current
      DESCRIPTION
      "Creation/Deletion of rows in the table."
      ::= { prtSonetXConnectEntry 8}


prtSonetXConnectDirection  OBJECT-TYPE
      SYNTAX  INTEGER
      {
      notApplicable(1),
      rx   (2),
      tx   (3),
	  both (4)
      }
      MAX-ACCESS  read-create
      STATUS  current
      DESCRIPTION
      "TU direction of connection. 
      rx=Drop
      tx=Add
      both = Add & Drop"
      ::= { prtSonetXConnectEntry 9}
   
prtSonetXConnectTuNumber OBJECT-TYPE
      SYNTAX  INTEGER
      {
      notApplicable (1),
      tu2			(2),
      tu3           (3),
      tu11          (4),
	  tu12          (5),
	  tuFour4c      (6),
	  sts12c    	(7)
      }
      MAX-ACCESS  read-create
      STATUS  current
      DESCRIPTION
       "This object indicates which TU is used in prtSonetXConnectTUnIdx "
      ::= { prtSonetXConnectEntry 10}

prtSonetXConnectMode  OBJECT-TYPE
      SYNTAX  INTEGER
      {
      notApplicable(1),
      addAndDrop   (2),
      bypass  (3)
      }
      MAX-ACCESS  read-create
      STATUS  current
      DESCRIPTION
      "TU Mode of connection. 
       addAndDrop    - Add & Drop
       bypass  - bypassed to the other VC4 port." 
      ::= {prtSonetXConnectEntry 11}


prtSonetStatus  OBJECT IDENTIFIER  ::= {sonetInterface 4}

prtSonetVcStatTable  OBJECT-TYPE 
    SYNTAX  SEQUENCE OF PrtSonetVcStatEntry
    MAX-ACCESS  not-accessible
    STATUS  current
    DESCRIPTION
       "VC Status Table "
     ::= { prtSonetStatus 1 }

prtSonetVcStatEntry OBJECT-TYPE
    SYNTAX      PrtSonetVcStatEntry
    MAX-ACCESS  not-accessible
    STATUS  current
    DESCRIPTION
       "An entry in the VC status Table."
    INDEX   {prtSonetVcIdx}
     ::= { prtSonetVcStatTable 1 }

PrtSonetVcStatEntry ::=
    SEQUENCE {
	 prtSonetVcRxJPathTrace	   SnmpAdminString,
	 prtSonetVcRxSignalLabel   OCTET STRING,
	 prtSonetVcLcasSourceState INTEGER,
	 prtSonetVcLcasSinkState   INTEGER,
	 prtSonetVcStatus	   	   Integer32,
	 prtSonetVcRxSeqNumber	   Unsigned32,
	 prtSonetVcTxSeqNumber	   Unsigned32,
	 prtSonetVcMfiDiffDelay	   Unsigned32,
	 prtSonetVcLoMF			   INTEGER,
	 prtSonetVcLoopStatus	   INTEGER,
	 prtSonetVcLcasTxStateMachineStatus	 INTEGER,
	 prtSonetVcLcasRxStateMachineStatus	 INTEGER,
	 prtSonetVcMFLengthErrorCounter		Counter32,
	 prtSonetVcCntrlPktCRCErrorCounter	Counter32
	  }

prtSonetVcRxJPathTrace OBJECT-TYPE
     SYNTAX  SnmpAdminString (SIZE(0..62))
     MAX-ACCESS  read-only
     STATUS  current
     DESCRIPTION
     "Jy Path Trace value received from network.
      y=1, 2:
      J1 - for VC-4  layer
      J2 - for VC-12 layer."
     ::= { prtSonetVcStatEntry 1 }

prtSonetVcRxSignalLabel  OBJECT-TYPE
      SYNTAX  OCTET STRING	(SIZE (1))
      MAX-ACCESS  read-only
      STATUS  current
      DESCRIPTION
      "Signal Label received from network. 
       For VC-3:
       The SONET standard defines the C2 byte as
       the path signal label. The purpose of this byte is to
       communicate the payload type being encapsulated by the 
       SONET Framing OverHead. It allows a single interface to
       transport multiple payload types simultaneously.
       
	   For VC-12, VT-1.5:
       VT path overhead V5 byte allocates bits 5-7  for 
       VT Path Signal Label, to indicate the content of the VT SPE.
        000 - Unequipped
        001 - Equipped - non specific payload
        010 - Asynchronous Mapping
        011 - Bit Synchronous Mapping (no longer used)
        100 - Byte Synchronous Mapping (TU11 or TU12)
        101 - Extended Signal Label for Virtual 
              Concatenation Applications (FCD-155 Default)
        110 - Test Signal (0.181) (ITU)
        111 - VC AIS (ITU)"
     ::= { prtSonetVcStatEntry 2 } 
 									   
prtSonetVcLcasSourceState	OBJECT-TYPE
     SYNTAX INTEGER
     {
      notApplicable (1),
      fixed         (2),
      add           (3), 
      norm          (4), 
      eos           (5), 
      idle          (6), 
      dnu           (7)  
      }
     MAX-ACCESS read-only
     STATUS current
     DESCRIPTION
     "Fixed - This is an indication that this end
              uses fixed bandwidth (non-LCAS mode)

      Add -   This member is about to be added to the group 

	  Norm -  Normal transmission.

      EOS  -  End of Sequence indication
              and Normal transmission.

      Idle  - IDLE	This member is not part of 
              the group or about to be removed.

      Dnu   - Do Not use - Do Not Use (the payload) 
              the Sk side reported FAIL status."
     ::= { prtSonetVcStatEntry 3}

prtSonetVcLcasSinkState	OBJECT-TYPE
     SYNTAX INTEGER
     {
      notApplicable (1),
      fixed         (2),
      add           (3), 
      norm          (4), 
      eos           (5), 
      idle          (6), 
      dnu           (7)  
      }
     MAX-ACCESS read-only
     STATUS current
     DESCRIPTION
     "Fixed - This is an indication that this end
              uses fixed bandwidth (non-LCAS mode)

      Add -   This member is about to be added to the group 

	  Norm -  Normal transmission.

      EOS  -  End of Sequence indication
              and Normal transmission.

      Idle  - IDLE	This member is not part of 
              the group or about to be removed.

      Dnu   - Do Not use - Do Not Use (the payload) 
              the Sk side reported FAIL status."
     ::= { prtSonetVcStatEntry 4}

prtSonetVcStatus OBJECT-TYPE
     SYNTAX  Integer32 
     MAX-ACCESS  read-only
     STATUS  current
     DESCRIPTION
     "This variable indicates the Status of the interface.  
     It contains failure state information.  
     The variable is a bit map represented as a sum, therefore, it
     can represent multiple failures simultaneously.  
     The sonetVCNoDefect must be set if and only if no other flag is set.

     The various bit positions are:
            1   sonetVCNoDefect			   	No alarm present
            2   sonetVCLOP				   	Loss Of Pointer
            4   sonetVCPathAIS			   	Alarm Indication Signal
            8   sonetVCPathRDI			   	Remote Defect Indication
           16   sonetVCPathRFI			   	Remote Failure Indication 
           									(RDI lasts for 2.5 (+-0.5) seconds)
           32   sonetVCUnequipped			Signal Label Unequipped
           64   sonetVCSignalLabelMismatch 	Signal Label Mismatch
     	  128   sonetVCEBER  	 			Excessive Bit Error Rate 
      	  256   sonetVCSD    	 			Signal Degradation."
     ::= { prtSonetVcStatEntry 5 }


prtSonetVcRxSeqNumber OBJECT-TYPE
     SYNTAX  Unsigned32 
     MAX-ACCESS  read-only
     STATUS  current
     DESCRIPTION	  
      "This variable indeticates the LCAS Rx
       sequence number of this VC."
     ::= { prtSonetVcStatEntry 6 }

prtSonetVcTxSeqNumber OBJECT-TYPE
     SYNTAX  Unsigned32 
     MAX-ACCESS  read-only
     STATUS  current
     DESCRIPTION
     "This variable indicates the LCAS Tx sequence number of this VC."
     ::= { prtSonetVcStatEntry 7 }

prtSonetVcMfiDiffDelay OBJECT-TYPE
     SYNTAX  Unsigned32 
     MAX-ACCESS  read-only
     STATUS  current
     DESCRIPTION
     "This variable indicates time difference (based on MFI field) from the 
      fastest channel (on which it will be 0), in miliSeconds units"
     ::= { prtSonetVcStatEntry 8 }

prtSonetVcLoMF OBJECT-TYPE
     SYNTAX  INTEGER
	 {
	  notApplicable (1),
	  off (2),  -- OK
	  on  (3)  -- Loss of Multiframe defect
	 }	
     MAX-ACCESS  read-only
     STATUS  current
     DESCRIPTION
     "This variable indicates loss of Multiframe defect."
     ::= { prtSonetVcStatEntry 9 }

prtSonetVcLoopStatus OBJECT-TYPE
     SYNTAX  INTEGER
	 {
	  notApplicable  (1),
	  off            (2),  
	  on             (3) 
	 }	
     MAX-ACCESS  read-only
     STATUS  current
     DESCRIPTION
     "This variable indicates Loop Status."
     ::= { prtSonetVcStatEntry 10 }


prtSonetVcLcasTxStateMachineStatus	OBJECT-TYPE
     SYNTAX INTEGER
     {
      notApplicable (1),
      -- fixed      (2),
      add           (3), 
      norm          (4), 
      -- eos        (5), 
      idle          (6), 
      dnu           (7),
      remove        (8)	   
      }
     MAX-ACCESS read-only
     STATUS current
     DESCRIPTION
     "LCAS State machine status."
     ::= { prtSonetVcStatEntry 11}

prtSonetVcLcasRxStateMachineStatus	OBJECT-TYPE
     SYNTAX INTEGER
     {
      notApplicable (1),
      -- fixed      (2),
      -- add        (3), 
      -- norm       (4), 
      -- eos        (5), 
      idle          (6), 
      -- dnu        (7),
      ok            (9),
      fail          (10)   
      }
     MAX-ACCESS read-only
     STATUS current
     DESCRIPTION
     "LCAS State machine status."
     ::= { prtSonetVcStatEntry 12}

prtSonetVcMFLengthErrorCounter OBJECT-TYPE
     SYNTAX  Counter32 
     MAX-ACCESS  read-only
     STATUS  current
     DESCRIPTION
     "Counts the multi-frames that had wrong length (shorter or longer)"     
     ::= { prtSonetVcStatEntry 13 }

prtSonetVcCntrlPktCRCErrorCounter OBJECT-TYPE
     SYNTAX  Counter32 
     MAX-ACCESS  read-only
     STATUS  current
     DESCRIPTION
     "Counts Number of Control Packet CRC errors"     
     ::= { prtSonetVcStatEntry 14 }


prtSonetPathProtTable  OBJECT-TYPE 
    SYNTAX  SEQUENCE OF PrtSonetPathProtEntry
    MAX-ACCESS  not-accessible
    STATUS  current
    DESCRIPTION
       "Path Protection Monitoring Table "
     ::= { prtSonetStatus 2 }

prtSonetPathProtEntry OBJECT-TYPE
    SYNTAX      PrtSonetPathProtEntry
    MAX-ACCESS  not-accessible
    STATUS  current
    DESCRIPTION
       "An entry in the Path Protection monitoring Table.
        This table indicates for each protected interface
        which VCs are mapped as Working VC, 
        which VCs are mapped as Protection VC, 
        and which of them are currently active."
    INDEX   {prtSonetPathProtProtectedInterface,prtSonetPathProtIdx}
     ::= { prtSonetPathProtTable 1 }

PrtSonetPathProtEntry ::=
    SEQUENCE {
	 prtSonetPathProtProtectedInterface  InterfaceIndex,
	 prtSonetPathProtIdx	             Unsigned32,
	 prtSonetPathProtWorkingVc           Unsigned32,
	 prtSonetPathProtProtectionVc        Unsigned32,
	 prtSonetPathProtActiveVc            INTEGER
	  }

prtSonetPathProtProtectedInterface OBJECT-TYPE
     SYNTAX  InterfaceIndex
     MAX-ACCESS  not-accessible
     STATUS  current
     DESCRIPTION
     "Interface protected by path-protection,
      e.g. PDH (E1/T1/E3/T3) port, VCG (Virtual Concatenation Group)."
     ::= { prtSonetPathProtEntry 1 }

prtSonetPathProtIdx OBJECT-TYPE
     SYNTAX  Unsigned32
     MAX-ACCESS  not-accessible
     STATUS  current
     DESCRIPTION
     "Runing index of entries which are mapped 
     to a specific interface, indicated by PrtSonetPathProtProtectedInterface.
     e.g - multiple working VCs and protection VCs are mapped to single  
           Virtual Concatenation Group (VCG)."
     ::= { prtSonetPathProtEntry 2 }

prtSonetPathProtWorkingVc OBJECT-TYPE
     SYNTAX  Unsigned32
     MAX-ACCESS  read-only
     STATUS  current
     DESCRIPTION
     "A VC mapped to interface indicated by 
     prtSonetPathProtProtectedInterface as 
     working VC. The value of this object may be 
     equal to  the value of ifIndex of working VC "
     ::= { prtSonetPathProtEntry 3 }

prtSonetPathProtProtectionVc OBJECT-TYPE
     SYNTAX  Unsigned32
     MAX-ACCESS  read-only
     STATUS  current
     DESCRIPTION
     "A VC mapped to interface indicated by 
     prtSonetPathProtProtectedInterface 
     as protection VC. The value of this object may be 
     equal to  the value of ifIndex of protection VC "
     ::= { prtSonetPathProtEntry 4 }


prtSonetPathProtActiveVc OBJECT-TYPE
     SYNTAX  INTEGER
                {
	 			 working    (2),
				 protection (3)
	            }
     MAX-ACCESS read-only
     STATUS  current
     DESCRIPTION
     "This object indicates which of the path protection 
      VCs is currently active."
     ::= { prtSonetPathProtEntry 5 }

vcGroupStat OBJECT IDENTIFIER  ::= {sonetInterface 6}

vcGroupStatTable OBJECT-TYPE
     SYNTAX  SEQUENCE OF VcGroupStatEntry 
     MAX-ACCESS  not-accessible
     STATUS  current
     DESCRIPTION
     "Sonet/SDH VCG status table."
     ::= { vcGroupStat 1}
   
vcGroupStatEntry   OBJECT-TYPE
     SYNTAX  VcGroupStatEntry
     MAX-ACCESS  not-accessible
     STATUS  current
     DESCRIPTION
     " An entry in the Sonet/SDH VCG gen staus table."
     INDEX { ifIndex }
     ::= { vcGroupStatTable 1}

VcGroupStatEntry ::=
     SEQUENCE {
     vcGroupStatRemoteChannelStatus  OCTET STRING
     }

vcGroupStatRemoteChannelStatus OBJECT-TYPE
     SYNTAX  OCTET STRING
     MAX-ACCESS  read-only
     STATUS  current
     DESCRIPTION
     "Status of remote VCG channels as received in the local station,
      represented by 1 bit per channel. Refer to product spec for details."
     ::= { vcGroupStatEntry 1}


radAps  OBJECT IDENTIFIER  ::=  { sonetInterface 5 }


radApsEvents  OBJECT IDENTIFIER  ::=  { radAps 0 }

apsActiveChannelTrap  NOTIFICATION-TYPE
     OBJECTS       { radApsStatusCurrentWorkingChannel }
     STATUS	current
     DESCRIPTION     
	 "The trap is sent upon change of Active Channel of APS Group."
     ::= { radApsEvents 1 }


radApsConfigTable OBJECT-TYPE
    SYNTAX  SEQUENCE OF RadApsConfigEntry
    MAX-ACCESS  not-accessible
    STATUS  current
    DESCRIPTION
       "An Augment to the APS Configuration Table
        (apsConfigTable in APS-MIB)."
     ::= { radAps 1 }

radApsConfigEntry OBJECT-TYPE
    SYNTAX  RadApsConfigEntry
    MAX-ACCESS  not-accessible
    STATUS  current
    DESCRIPTION
       "An entry in the table."
    AUGMENTS { apsConfigEntry }
     ::= { radApsConfigTable 1 }

RadApsConfigEntry ::=
    SEQUENCE {
		radApsConfigClearCounters		INTEGER,
		radApsConfigCommandAndStatus	INTEGER,
		radApsConfigFlipOnSD            INTEGER
		}

radApsConfigClearCounters OBJECT-TYPE
     SYNTAX  INTEGER {
     	off(2),
	 	on (3)
	 }
     MAX-ACCESS  read-create
     STATUS  current
     DESCRIPTION
     "Setting this object to on(3) will clear APS Counters.
      Upon performing this operation, the value will be
      automatically changed to off(2)."
     ::= { radApsConfigEntry 1}

radApsConfigCommandAndStatus OBJECT-TYPE
     SYNTAX  INTEGER {
     	noOp			(1),
		clear			(2),
     	forcedSwitch	(3),
		lockout			(4)
	 }
     MAX-ACCESS  read-create
     STATUS  current
     DESCRIPTION
     "noOp			- 	initial state only (cannot be Set by user).
	  
	  clear			-	clearing the last performed command.
						Can be Set only if previous state was other than noOp or clear.

	  forcedSwitch	- 	transferring service from primary channel to the secondary channel.
						Can be Set only if previous state was noOp or clear.
						If the non-Active channel is failed, the command will be rejected.

	  lockout		-	freezing the current state.
						In 1+1 Bidirectional Optimized switching, Lockout is considered
						as a local request which is not signalled across the K-bytes.
						The effect of lockout is to freeze the selector position
						and transmitted	K-bytes until the lockout request is cleared.
						Can be Set only if previous state was noOp or Clear."
     ::= { radApsConfigEntry 2}


radApsConfigFlipOnSD OBJECT-TYPE
     SYNTAX  INTEGER {
     	no  (2),
	 	yes (3)
	 }
     MAX-ACCESS  read-create
     STATUS  current
     DESCRIPTION
     "Flip active channel according to SD (Signal Degradation)."
     ::= { radApsConfigEntry 3}



radApsStatusTable OBJECT-TYPE
    SYNTAX  SEQUENCE OF RadApsStatusEntry
    MAX-ACCESS  not-accessible
    STATUS  current
    DESCRIPTION
       "An Augment to the APS Status Table
        (apsStatusTable in APS-MIB)."
     ::= { radAps 2 }

radApsStatusEntry OBJECT-TYPE
    SYNTAX  RadApsStatusEntry
    MAX-ACCESS  not-accessible
    STATUS  current
    DESCRIPTION
       "An entry in the table."
    AUGMENTS { apsConfigEntry }
     ::= { radApsStatusTable 1 }

RadApsStatusEntry ::=
    SEQUENCE {
		radApsStatusCurrentWorkingChannel		Integer32
		}

radApsStatusCurrentWorkingChannel OBJECT-TYPE
     SYNTAX  Integer32
     MAX-ACCESS  read-only
     STATUS  current
     DESCRIPTION
     "This object indicates the port/interface index of
      the Current Working Channel."
     ::= { radApsStatusEntry 1}

	

prtVcGroupCnfg  OBJECT IDENTIFIER  ::=  {prtSonetConfig 4}

vcGroupCnfgTable OBJECT-TYPE
    SYNTAX  SEQUENCE OF VcGroupCnfgEntry
    MAX-ACCESS  not-accessible
    STATUS  current
    DESCRIPTION
       "The Virtual Concatenation Group configuration table."
     ::= { prtVcGroupCnfg 1 }

vcGroupCnfgEntry OBJECT-TYPE
    SYNTAX  VcGroupCnfgEntry
    MAX-ACCESS  not-accessible
    STATUS  current
    DESCRIPTION
       "An entry in the Virtual Concatenation Group 
        configuration table."
    INDEX   { vcGroupCnfgIdx,vcGroupCnfgNumber}
     ::= { vcGroupCnfgTable 1 }

VcGroupCnfgEntry ::=
    SEQUENCE {
             vcGroupCnfgIdx               Integer32,
             vcGroupCnfgNumber            Integer32,
             vcGroupCnfgRowStatus         RowStatus,
             vcGroupCnfgVcType            INTEGER,
             vcGroupCnfgNoOfVCs           Integer32,
             vcGroupCnfgLCAS              INTEGER,
             vcGroupCnfgEncapsulation     INTEGER,
		     vcGroupCnfgGroupIfIndex      InterfaceIndex,
		     vcGroupCnfgRip2              INTEGER,
			 vcGroupCnfgGfpChId		      Integer32,
			 vcGroupCnfgK4                INTEGER,
			 vcGroupCnfgExSignalLabel     OCTET STRING,
			 vcGroupCnfgLcasMinNoOfVCs    Integer32,
			 vcGroupCnfgLcasStatus		  INTEGER,
			 vcGroupCnfgMappingMode		  INTEGER,
			 vcGroupCnfgTrafficType		  INTEGER,
			 vcGroupCnfgGroupName         SnmpAdminString,
             vcGroupCnfgLoopDetection	  INTEGER,
			 vcGroupCnfgLcasWaitToRestore Unsigned32,
			 vcGroupCnfgLcasHoldOff       Unsigned32			 
			     
		      }

vcGroupCnfgIdx OBJECT-TYPE
     SYNTAX  Integer32 (1..255)
     MAX-ACCESS  not-accessible
     STATUS  current
     DESCRIPTION
     "This object indicates the Idx of the Config being accessed.
      Idx of 255 relates to the Temporary (Scratch) Config.
      For products that support several configurations, Set can be performed
      only to the Temporary Config (=255). "
     ::= { vcGroupCnfgEntry 1}

vcGroupCnfgNumber OBJECT-TYPE
     SYNTAX    Integer32 
      MAX-ACCESS not-accessible
      STATUS current
      DESCRIPTION
      "Virtual Concatenation Group Number.
       For FCD-155 up to eight groups are defined
       valid values are 1..8.
       For MP-4100, group ifIndex is used."
      ::= { vcGroupCnfgEntry 2}

vcGroupCnfgRowStatus OBJECT-TYPE
      SYNTAX RowStatus 
      MAX-ACCESS read-create
      STATUS current
      DESCRIPTION
      "Creation/Deletion of rows in the table."
      ::= { vcGroupCnfgEntry 3}

vcGroupCnfgVcType OBJECT-TYPE
      SYNTAX INTEGER
      {
       notApplicable  (1),
       vc12           (2), --SDH
       vc3            (3), --SDH
       vc4            (4), --SDH
       vt1dot5        (5), --SONET VT1.5
       sts1           (6), --SONET STS1 /SPE 
	   sts12c		  (7),  --STS12c
	   vcFour4c       (8)  --VC4-4c
       }
      MAX-ACCESS read-create
      STATUS current
      DESCRIPTION
      "User may select type of SDH Virtual Containers (VC) 
       (SONET Virtual Tributaries VT ) to be concatenated
       in this Virtual Concatenation Group.
       For SDH,  values 2,3,4 and 8 are valid.
       For SONET, values 5, 6,7 are valid."
      ::= { vcGroupCnfgEntry 4}

vcGroupCnfgNoOfVCs  OBJECT-TYPE
     SYNTAX    Integer32 (0..84)
      MAX-ACCESS read-create
      STATUS current
      DESCRIPTION
      "User may select number of  Virtual Containers (VC) 
       (SONET Virtual Tributaries VT ) to be concatenated
       in this Virtual Concatenation Group.
       Valid range for this number depends on 
       type VC selected by vcGroupCnfgVCType
       For SDH,  up to 63 VC12, or
                 up to 3  VC3,  or
                       1  VC4  are valid
       For SONET, up to 84 VT1.5 without LCAS, 
                  or 64 VT1.5 under  LCAS control.
                  or up tp 3 STS-1/SPE, or
                           1 STS-3"
      ::= { vcGroupCnfgEntry 5}

vcGroupCnfgLCAS OBJECT-TYPE
      SYNTAX INTEGER
      {
       notApplicable (1),
       lcasNotActive (2),
       lcasActive    (3)
       }
      MAX-ACCESS read-create
      STATUS current
      DESCRIPTION
      "This object controls Link Capacity Adjustment 
      Scheme (LCAS)  activation."
      ::= { vcGroupCnfgEntry 6}

vcGroupCnfgEncapsulation OBJECT-TYPE
      SYNTAX INTEGER
      {
       notApplicable (1),
       laps          (2), -- Link access protocol S
       lapf          (3), -- Link access protocol F (Frame relay)
       gfp           (4)  -- Generic Framing Procedure
       }
      MAX-ACCESS read-create
      STATUS current
      DESCRIPTION
      "This object enables user to select encapsulation method."
      ::= { vcGroupCnfgEntry 7}


vcGroupCnfgGroupIfIndex  OBJECT-TYPE
      SYNTAX InterfaceIndex
      MAX-ACCESS read-only
      STATUS current
      DESCRIPTION
      "The ifIndex assigend to this group."                              
      ::= { vcGroupCnfgEntry 8}

vcGroupCnfgRip2 OBJECT-TYPE
      SYNTAX INTEGER
      {
       notApplicable (1),
       no            (2),
       yes           (3)
       }
      MAX-ACCESS read-create
      STATUS current
      DESCRIPTION
      "This object controls RIP 2.
      User may select to send RIP 2 message over 
      selected group or not"
      ::= { vcGroupCnfgEntry 9}


vcGroupCnfgGfpChId	OBJECT-TYPE	   
      SYNTAX    Integer32 (0..255)
      MAX-ACCESS read-create
      STATUS current
      DESCRIPTION
      "Generic Framing Procedure (GFP) Channel ID, 
      Valid only when vcGroupCnfgEncapsulation = gfp (4)
      Valid values are 0x00 - oxFF  (hex) "
      ::= { vcGroupCnfgEntry 10}


vcGroupCnfgK4  OBJECT-TYPE
      SYNTAX INTEGER
      {
       notApplicable (1),
       no            (2),
       yes           (3)
       }
      MAX-ACCESS read-create
      STATUS current
      DESCRIPTION
      "This object controls whether K4 byte
       (of Line Overhead) is used as an indication for
       virtual concatenation (VCAT). 
       This object is applicable, when VCG 
       includes only a single Virtual Container (VC)
       (or SONET VT)  "
      ::= { vcGroupCnfgEntry 11}

vcGroupCnfgExSignalLabel  OBJECT-TYPE
      SYNTAX  OCTET STRING	(SIZE (1))
      MAX-ACCESS  read-create
      STATUS  current
      DESCRIPTION
      "Extended Signal Label. 
 	   Relevant only when vcGroupCnfgK4 = yes(3).
       Agents that do not support this feature will send SIZE 0."
     ::= { vcGroupCnfgEntry 12 }

vcGroupCnfgLcasMinNoOfVCs  OBJECT-TYPE
      SYNTAX    Integer32 (0..83)
      MAX-ACCESS read-create
      STATUS current
      DESCRIPTION
      "Minimum number of VC's to declare alarm, in LCAS mode.
       Applicable only when LCAS is active 
       (vcGroupCnfgLCAS =lcasActive)
       1...63 for SDH, 1...84 for SONET
       0= not applicable. "
      ::= { vcGroupCnfgEntry 13}

vcGroupCnfgLcasStatus  OBJECT-TYPE
      SYNTAX INTEGER
      {
       notApplicable    (1),
       belowMinNoOfVCs  (2),
       withinRange      (3),
	   allNorm          (4) 
       }
      MAX-ACCESS read-only
      STATUS current
      DESCRIPTION
      "This object summarize LCAS states of all VCs in VCG:
                      											 
       belowMinNoOfVCs -  Number of VCs in Norm state is less than 
                          the minimum number of VCs 
                          (indicated by vcGroupCnfgLcasMinNoOfVCs)

      withinRange - Number of VCs in Norm state is higher than 
                    the minimum number of VCs
                    indicated by vcGroupCnfgLcasMinNoOfVCs) 
	                but is lower than Number of VCs mapped 

       allNorm - Number of VCs in Norm state equals 
                 number of mapped VCs. "   
      ::= { vcGroupCnfgEntry 14}
 
vcGroupCnfgMappingMode  OBJECT-TYPE
      SYNTAX INTEGER
      {
       notApplicable    (1),
       off              (2),
       auto             (3),
       manual           (4)
       }
      MAX-ACCESS read-create
      STATUS current
      DESCRIPTION
      "This object define Path Protection mode for VCG.
       Auto -  the entire mapping for Virtual Concatenation Group x 
       is copied  automatically by agent for the protection group 
       to same TUs on the other SONET/SDH link which reside on same slot.. 
       Manual - the user may configure mapping for the protection group 
       on the same link as for other group, or on the other link(s).
       Same type of TUs  should be used for both groups.   
       The TUs selected for each group don't have to be the same."   
      ::= { vcGroupCnfgEntry 15}

vcGroupCnfgTrafficType  OBJECT-TYPE
      SYNTAX INTEGER
      {
       notApplicable  (1),
       managementOnly (2),
       dataOnly       (3),
	   mixed          (4)
       }
      MAX-ACCESS read-create
      STATUS current
      DESCRIPTION
      "This object allows to select traffic type for 
       specific VCG."   
      ::= { vcGroupCnfgEntry 16}

vcGroupCnfgGroupName  OBJECT-TYPE
      SYNTAX     SnmpAdminString
      MAX-ACCESS read-create
      STATUS current
      DESCRIPTION
      "Virtual Concatenation Group (VCG) Name.
       String length is limited to 15 characters."   
      ::= { vcGroupCnfgEntry 17}

vcGroupCnfgLoopDetection  OBJECT-TYPE
      SYNTAX     INTEGER
	  {
	  notApplicable (1),
	  disabled      (2),
	  enabeld       (3)
	  }
      MAX-ACCESS read-create
      STATUS current
      DESCRIPTION
      "VCAT Loop detecetion enabled."   
      ::= { vcGroupCnfgEntry 18}

vcGroupCnfgLcasWaitToRestore OBJECT-TYPE
      SYNTAX     Unsigned32
      MAX-ACCESS read-create
      STATUS current
      DESCRIPTION
      "Time duration (in milliseconds units) waited after 
      errors on channel stopped, before channel is reused."   
      ::= { vcGroupCnfgEntry 19}

vcGroupCnfgLcasHoldOff OBJECT-TYPE
      SYNTAX     Unsigned32
      MAX-ACCESS read-create
      STATUS current
      DESCRIPTION
      "Time duration (in milliseconds units) in which errors on channel
      are disregarded. (Threshold)"   
      ::= { vcGroupCnfgEntry 20}

 

vcgGfpMuxCnfgTable	OBJECT-TYPE
      SYNTAX  SEQUENCE OF VcgGfpMuxCnfgEntry
      MAX-ACCESS  not-accessible
      STATUS  current
      DESCRIPTION
      "The Virtual Concatenation Group GFP Mux configuration table."
       ::= { prtVcGroupCnfg 2 }

-- This table defines multiplexing scheme for GFP mux of 
-- Virtual Concatenation Groups:
-- Primary group, Secondary group/s and bandwidth allocation   
-- to each group.

vcgGfpMuxCnfgEntry OBJECT-TYPE
      SYNTAX  VcgGfpMuxCnfgEntry
      MAX-ACCESS  not-accessible
      STATUS  current
      DESCRIPTION
      "An entry in the Virtual Concatenation Group GFP Mux 
       configuration table."
      INDEX   { vcgGfpMuxCnfgIdx,vcgGfpMuxCnfgMuxNumber}
       ::= { vcgGfpMuxCnfgTable 1 }

VcgGfpMuxCnfgEntry ::=
    SEQUENCE {						 
 		      vcgGfpMuxCnfgIdx     Integer32,
			  vcgGfpMuxCnfgMuxNumber   Integer32,
 		      vcgGfpMuxCnfgRowStatus   RowStatus,
			  vcgGfpMuxCnfgMuxName     SnmpAdminString,
 		      vcgGfpMuxCnfgPrimeGroup  Integer32,
  		      vcgGfpMuxCnfgGrpBwAlloc  OCTET STRING
 		      }

vcgGfpMuxCnfgIdx OBJECT-TYPE
      SYNTAX  Integer32 (1..255)
      MAX-ACCESS  not-accessible
      STATUS  current
      DESCRIPTION
      "This object indicates the Index of the configuration being accessed.
       Index of 255 relates to the Temporary (Scratch) coninguration.
       For products that support several configurations, Set can be performed
       only to the Temporary Config (=255). "
      ::= { vcgGfpMuxCnfgEntry 1}

vcgGfpMuxCnfgMuxNumber OBJECT-TYPE
      SYNTAX    Integer32 
      MAX-ACCESS not-accessible
      STATUS current
      DESCRIPTION
      "Virtual Concatenation Group GFP Mux Number.
       Refer to device specification for definition of 
        - maximum number of GFP-mux.
        - concatenation of Slot and GFP mux number."
      ::= { vcgGfpMuxCnfgEntry 2}
 
vcgGfpMuxCnfgRowStatus OBJECT-TYPE
      SYNTAX RowStatus 
      MAX-ACCESS read-create
      STATUS current
      DESCRIPTION
      "Creation/Deletion of rows in the table."
      ::= { vcgGfpMuxCnfgEntry 3}

vcgGfpMuxCnfgMuxName  OBJECT-TYPE
      SYNTAX    SnmpAdminString 
      MAX-ACCESS read-create
      STATUS current
      DESCRIPTION
      "Virtual Concatenation Group, GFP Mux name."
      ::= { vcgGfpMuxCnfgEntry 4}

vcgGfpMuxCnfgPrimeGroup OBJECT-TYPE
     SYNTAX  Integer32 
     MAX-ACCESS  read-create
     STATUS  current
     DESCRIPTION
     "Index of Virtual Concatenation Group used as 
      Primary for the GFP mux created 
      for FCD 155 up to 8 Virtual Concatenation Group are defined:
      1 -> Virtual Concatenation Group 1
	  2 -> Virtual Concatenation Group 2
      3 -> Virtual Concatenation Group 3
      4 -> Virtual Concatenation Group 4
      5 -> Virtual Concatenation Group 5
	  6 -> Virtual Concatenation Group 6
      7 -> Virtual Concatenation Group 7
      8 -> Virtual Concatenation Group 8
      "
     ::= { vcgGfpMuxCnfgEntry 5}

vcgGfpMuxCnfgGrpBwAlloc OBJECT-TYPE
     SYNTAX  OCTET STRING 
     MAX-ACCESS  read-create
     STATUS  current
     DESCRIPTION
     "This object indicates the  allocated bandwidth (BW) to each 
     Virtual Concatenation Group (VCG).
     Each nibble indicates BW percentage, in 12.5% steps, 
     assigned to a group. 
     
     For FCD-155, there may be 4 or 8 VCGs. When only 4 VCG exists,
	 only two octets are used.
     In current GFP Mux,one VCG is identified as primary group  
     by vcGfpMuxConfPrimeGroup.
	 Other VCGs may be secondaries.
	 VCG with allocated BW value of zero does not belong to the GFPmux
	 defined by GFP Mux number.
	          ________________________________________
	         |     Octet 0       |     Octet 1       |  
             |Nibble 4 | Nibble 3| Nibble 2| Nibble 1|
	   MSB   | 7 6 5 4 | 3 2 1 0 | 7 6 5 4 | 3 2 1 0 | 
			 +___________________+___________________+
	           VCG1        VCG2     VCG 3    VCG4

	          ________________________________________
	         |     Octet 3       |     Octet 4       |  
             |Nibble 4 | Nibble 3| Nibble 2| Nibble 1|
	         | 7 6 5 4 | 3 2 1 0 | 7 6 5 4 | 3 2 1 0 | LSB
			 +___________________+___________________+
	           VCG5        VCG6     VCG 7    VCG8


       Nibble value - BW Percentage
       (0...7)         (0 ...87.5%) 
      1   0001            12.5 %
      2   0010 		      25%
	  3   0011            37.5
	  .....
	  7   0111            87.5%
        
	  at least one nibble must be greater that zero. 
	  Sum of alloacted BW must be 100%.
	  Primary VCG BW must be greater than zero."
     ::= { vcgGfpMuxCnfgEntry 6}


virtualIfConfiguration  OBJECT IDENTIFIER  ::=  { prtSonetConfig 5}

virtualIfGenTable OBJECT-TYPE
     SYNTAX  SEQUENCE OF VirtualIfGenEntry
     MAX-ACCESS  not-accessible
     STATUS  current
     DESCRIPTION
     "Sonet/SDH general port configuration table."
     ::= { virtualIfConfiguration 1}
   
virtualIfGenEntry   OBJECT-TYPE
     SYNTAX  VirtualIfGenEntry
     MAX-ACCESS  not-accessible
     STATUS  current
     DESCRIPTION
     " An entry in the Sonet/SDH general port configuration table."
     INDEX { virtualIfGenCnfgIdx, virtualIfGenIdx }
     ::= { virtualIfGenTable 1}

VirtualIfGenEntry ::=
     SEQUENCE {
     virtualIfGenCnfgIdx
     Integer32,
     virtualIfGenIdx
     Integer32,
     virtualIfGenFrameFormat
     INTEGER
      }
 
virtualIfGenCnfgIdx OBJECT-TYPE
     SYNTAX  Integer32 (1..255)
     MAX-ACCESS  read-only
     STATUS  current
     DESCRIPTION
     "This object indicates the Idx of the Config being accessed.
      Idx of 255 relates to the Temporary (Scratch) Config.
      For products that support several configurations, Set can be performed
      only to the Temporary Config (=255). "
     ::= { virtualIfGenEntry 1}

virtualIfGenIdx OBJECT-TYPE
     SYNTAX  Integer32
     MAX-ACCESS  read-only
     STATUS  current
     DESCRIPTION
     "This object indicates a unique  port or interface number.
	 For numbering, see product's spec.
     For some products, the numbering can equal ifIndex."
     ::= { virtualIfGenEntry 2}

virtualIfGenFrameFormat OBJECT-TYPE
     SYNTAX  INTEGER {
     notApplicable(1),
     fcsEnable     (2),
     fcsDisable   (3)
      
     }
     MAX-ACCESS  read-write
     STATUS  current
     DESCRIPTION
     "The frame format.
      fcsEnabe = Frame will be sent with the FCS bits.
      fcsDisable = Frame will be sent without the FCS bits ."
     ::= { virtualIfGenEntry 3 }





-- NOTIFICATIONs 

-- ALARM TRAPS

sonetAlarmLOS  NOTIFICATION-TYPE
	OBJECTS  {alarmSeverity, alarmState, ifAlias}  
	STATUS  current
	DESCRIPTION
	"This trap indicates Loss Of Signal." 
	::= { prtSonetEvents 1 }

sonetAlarmLOF  NOTIFICATION-TYPE
	OBJECTS  {alarmSeverity, alarmState, ifAlias}  
	STATUS  current
	DESCRIPTION
	"This trap indicates Loss Of Frame." 
	::= { prtSonetEvents 2 }

sonetAlarmOOF  NOTIFICATION-TYPE
	OBJECTS  {alarmSeverity, alarmState, ifAlias}  
	STATUS  current
	DESCRIPTION
	"This trap indicates Out Of Frame." 
	::= { prtSonetEvents 3 }

sonetAlarmLineAIS  NOTIFICATION-TYPE
	OBJECTS  {alarmSeverity, alarmState, ifAlias}  
	STATUS  current
	DESCRIPTION
	"This trap indicates Line Alarm Indication Signal." 
	::= { prtSonetEvents 4 }

sonetAlarmLineEED  NOTIFICATION-TYPE
	OBJECTS  {alarmSeverity, alarmState, ifAlias}  
	STATUS  current
	DESCRIPTION
	"This trap indicates Line Excessive Error Detect." 
	::= { prtSonetEvents 5 }

sonetAlarmLineRDI  NOTIFICATION-TYPE
	OBJECTS  {alarmSeverity, alarmState, ifAlias}  
	STATUS  current
	DESCRIPTION
	"This trap indicates Line Remote Defect Indication." 
	::= { prtSonetEvents 6 }

sonetAlarmLineSD  NOTIFICATION-TYPE
	OBJECTS  {alarmSeverity, alarmState, ifAlias}  
	STATUS  current
	DESCRIPTION
	"This trap indicates Line Signal Degrade." 
	::= { prtSonetEvents 7 }

sonetAlarmPathLOP  NOTIFICATION-TYPE
	OBJECTS  {alarmSeverity, alarmState, ifAlias}  
	STATUS  current
	DESCRIPTION
	"This trap indicates Path Loss of Pointer." 
	::= { prtSonetEvents 8 }

sonetAlarmPathAIS  NOTIFICATION-TYPE
	OBJECTS  {alarmSeverity, alarmState, ifAlias}  
	STATUS  current
	DESCRIPTION
	"This trap indicates Path Alarm Indication Signal." 
	::= { prtSonetEvents 9 }

sonetAlarmPathEED  NOTIFICATION-TYPE
	OBJECTS  {alarmSeverity, alarmState, ifAlias}  
	STATUS  current
	DESCRIPTION
	"This trap indicates Path Excessive Error Detect." 
	::= { prtSonetEvents 10 }

sonetAlarmPathSLM  NOTIFICATION-TYPE
	OBJECTS  {alarmSeverity, alarmState, ifAlias}  
	STATUS  current
	DESCRIPTION
	"This trap indicates Path Signal Label Mismatch." 
	::= { prtSonetEvents 11 }

sonetAlarmPathLOMF  NOTIFICATION-TYPE
	OBJECTS  {alarmSeverity, alarmState, ifAlias}  
	STATUS  current
	DESCRIPTION
	"This trap indicates Path Loss of Multi-Frame." 
	::= { prtSonetEvents 12 }

sonetAlarmPathRDI  NOTIFICATION-TYPE
	OBJECTS  {alarmSeverity, alarmState, ifAlias}  
	STATUS  current
	DESCRIPTION
	"This trap indicates Path Remote Defect Indication." 
	::= { prtSonetEvents 13 }

sonetAlarmPathSD  NOTIFICATION-TYPE
	OBJECTS  {alarmSeverity, alarmState, ifAlias}  
	STATUS  current
	DESCRIPTION
	"This trap indicates Path Signal Degrade." 
	::= { prtSonetEvents 14 }

sonetAlarmVtLOP  NOTIFICATION-TYPE
	OBJECTS  {alarmSeverity, alarmState, ifAlias}  
	STATUS  current
	DESCRIPTION
	"This trap indicates VT Loss of Pointer." 
	::= { prtSonetEvents 15 }

sonetAlarmVtAIS  NOTIFICATION-TYPE
	OBJECTS  {alarmSeverity, alarmState, ifAlias}  
	STATUS  current
	DESCRIPTION
	"This trap indicates VT Alarm Indication Signal." 
	::= { prtSonetEvents 16 }

sonetAlarmVtEED  NOTIFICATION-TYPE
	OBJECTS  {alarmSeverity, alarmState, ifAlias}  
	STATUS  current
	DESCRIPTION
	"This trap indicates VT Excessive Error Detect." 
	::= { prtSonetEvents 17 }

sonetAlarmVtSLM  NOTIFICATION-TYPE
	OBJECTS  {alarmSeverity, alarmState, ifAlias}  
	STATUS  current
	DESCRIPTION
	"This trap indicates VT Signal Label Mismatch." 
	::= { prtSonetEvents 18 }

sonetAlarmVtRDI  NOTIFICATION-TYPE
	OBJECTS  {alarmSeverity, alarmState, ifAlias}  
	STATUS  current
	DESCRIPTION
	"This trap indicates VT Remote Defect Indication." 
	::= { prtSonetEvents 19 }

sonetAlarmVtSD  NOTIFICATION-TYPE
	OBJECTS  {alarmSeverity, alarmState, ifAlias}  
	STATUS  current
	DESCRIPTION
	"This trap indicates VT Signal Degrade."
	::= { prtSonetEvents 20 } 

-- END-- 
-- file :D:\Synergy\WorkArea\545\mib_rad\txt\radds1.txt
-- 
-- RAD-DS1-MIB DEFINITIONS ::= BEGIN

--Title:    RAD-DS1   MIB
--
-- Copyright 1998 RAD Data Communications, Ltd.
-- All Rights Reserved.  

-- IMPORTS
-- PerfCurrentCount, PerfIntervalCount	FROM PerfHist-TC-MIB;

--      OBJECT-TYPE                     FROM RFC-1212
 --     radWan                          FROM RAD-GEN-MIB;
--                RAD-DS1 MIB   

--Title:     RAD's DS1 INTERFACE MIB
--Date:      03.02.98
--By:        Ilana Schvetz
--File:      radds1.mib

-- Last updated by Yig'al Hachmon 12-May-2008

ds1Interface  OBJECT IDENTIFIER  ::=  {diverseIfWanGen 4}

prtDS1Events OBJECT IDENTIFIER       ::= {ds1Interface 0}

prtDs1PerfHistory  OBJECT IDENTIFIER  ::=  {ds1Interface 1}

  --   Extension to the dsx1 current table
  
dsx1XCurrentTable  OBJECT-TYPE
       SYNTAX      SEQUENCE OF Dsx1XCurrentEntry
       MAX-ACCESS  not-accessible
       STATUS      current
       DESCRIPTION
       "A list of current statistics entries.  This table
        contains additional objects for the current table."
       ::= { prtDs1PerfHistory 2 }

dsx1XCurrentEntry OBJECT-TYPE
       SYNTAX  Dsx1XCurrentEntry 
       MAX-ACCESS  not-accessible
       STATUS      current
       DESCRIPTION
       "An entry containing additional statistical counters
        applicable to a particular current table."
 --      AUGMENTS    { dsx1CurrentEntry }
         INDEX   { dsx1CurrentIndex }
       ::= { dsx1XCurrentTable 1 }

Dsx1XCurrentEntry     ::=
      SEQUENCE {
        dsx1CurrentLOS		    PerfCurrentCount,
        dsx1CurrentLOF		    PerfCurrentCount,
        dsx1CurrentLOC			PerfCurrentCount,
        dsx1CurrentAIS		    PerfCurrentCount,
        dsx1CurrentRAI			PerfCurrentCount,
        dsx1CurrentLOMF			PerfCurrentCount,
        dsx1CurrentFEBE			PerfCurrentCount,
        dsx1CurrentStatus		OCTET STRING,
		dsx1CurrentBPV			PerfCurrentCount,
		dsx1CurrentLOCRCMF	    PerfCurrentCount,
		dsx1CurrentLOFC			PerfCurrentCount,
		dsx1CurrentCRCErrors	PerfCurrentCount


}

dsx1CurrentLOS OBJECT-TYPE
        SYNTAX PerfCurrentCount
        MAX-ACCESS  read-only
        STATUS  current
        DESCRIPTION
        "The counter associated with the number of LOS
         seconds, encountered by a DS1 interface in
         the current 15 minute interval."
        ::= { dsx1XCurrentEntry 1 }

dsx1CurrentLOF OBJECT-TYPE
        SYNTAX PerfCurrentCount
        MAX-ACCESS  read-only
        STATUS  current
        DESCRIPTION
        "The counter associated with the number of LOF
         seconds, encountered by a DS1
         interface in the current 15 minute interval."
        ::= { dsx1XCurrentEntry 2 }


dsx1CurrentLOC OBJECT-TYPE
         SYNTAX PerfCurrentCount
         MAX-ACCESS  read-only
         STATUS  current
         DESCRIPTION
         " Loss Of Cell delineation. Counts number of cells the ATM UNI cells receiver
           lost cells delineation ."
         ::= { dsx1XCurrentEntry 3 }

dsx1CurrentAIS OBJECT-TYPE
        SYNTAX PerfCurrentCount
        MAX-ACCESS  read-only
        STATUS  current
        DESCRIPTION
        "The counter associated with the number of AIS
         seconds, encountered by a DS1
         interface in the current 15 minute interval."
        ::= { dsx1XCurrentEntry 4 }

dsx1CurrentRAI OBJECT-TYPE
         SYNTAX PerfCurrentCount
         MAX-ACCESS  read-only
         STATUS  current
         DESCRIPTION
         "Remote Alarm Indication: Transmitted  in the outgoing direction
	      (toward the PABX) over FDL bits when the DS1 device detected 
          an incoming Loss Of Frame. Received from the far end (PABX) 
          over FDL when it detects a Loss of frame."
         ::= { dsx1XCurrentEntry 5 }

dsx1CurrentLOMF OBJECT-TYPE
         SYNTAX PerfCurrentCount
         MAX-ACCESS  read-only
         STATUS  current
         DESCRIPTION
         "Loss of Multi-Frame sequence  in E1 time slot 16."
         ::= { dsx1XCurrentEntry 6 }

dsx1CurrentFEBE OBJECT-TYPE
         SYNTAX PerfCurrentCount
         MAX-ACCESS  read-only
         STATUS  current
         DESCRIPTION
         "Far End Block Errors, as reported in the first bit
          of frames 13 and 15, on multiframe E1 lines with CRC4,
          in the current 15 minute interval."
         ::= { dsx1XCurrentEntry 7 }


dsx1CurrentStatus OBJECT-TYPE
	SYNTAX OCTET STRING  (SIZE (4))
         MAX-ACCESS  read-only
         STATUS  current
         DESCRIPTION
         "The statuses of the current interval:
           0 - Valid.
           1 - redundantLinkSwitch - the link has been switched 
               by a redundancy mechanism.
           2 - discontinuity - module was partialy out.
           4 - notValid - module is out."
         ::= { dsx1XCurrentEntry 8 }

dsx1CurrentBPV OBJECT-TYPE
         SYNTAX PerfCurrentCount
         MAX-ACCESS  read-only
         STATUS  current
         DESCRIPTION
         "The counter associated with the number of BPVs (Bi-Polar Violations)
          encountered by a DS1	interface in the current 15 minute interval."
         ::= { dsx1XCurrentEntry 9 }

dsx1CurrentLOCRCMF OBJECT-TYPE
         SYNTAX PerfCurrentCount
         MAX-ACCESS  read-only
         STATUS  current
         DESCRIPTION
         "Loss of CRC4 Multi-Frame sequence in E1.
          encountered in the current 15 minute interval"
         ::= { dsx1XCurrentEntry 10 }

dsx1CurrentLOFC	OBJECT-TYPE
         SYNTAX PerfCurrentCount 
         MAX-ACCESS  read-only
         STATUS  current
         DESCRIPTION
         "Counts the number of loss of frame events measured.
          encountered in the current 15 minute interval"
         ::= { dsx1XCurrentEntry 11 }

dsx1CurrentCRCErrors  OBJECT-TYPE
         SYNTAX PerfCurrentCount
         MAX-ACCESS  read-only
         STATUS  current
         DESCRIPTION
         "Counts the number of CRC error events,
          encountered in the current 15 minute interval."
         ::= { dsx1XCurrentEntry 12 }



-- Interval table

dsx1XIntervalTable OBJECT-TYPE
         SYNTAX  SEQUENCE OF Dsx1XIntervalEntry
         MAX-ACCESS  not-accessible
         STATUS  current
         DESCRIPTION
         " A list of Interval entries.  This table
           contains additional objects for the interval table."
         ::= { prtDs1PerfHistory 3 }

dsx1XIntervalEntry OBJECT-TYPE
         SYNTAX  Dsx1XIntervalEntry
         MAX-ACCESS  not-accessible
         STATUS  current
         DESCRIPTION
         "An entry containing additional statistical counters
          applicable to a particular interval table."
      -- AUGMENTS    { dsx1IntervalEntry }
         INDEX   { dsx1IntervalIndex, dsx1IntervalNumber }
         ::= { dsx1XIntervalTable 1 }

Dsx1XIntervalEntry     ::=
         SEQUENCE {
         dsx1IntervalLOS	   PerfIntervalCount,
         dsx1IntervalLOF	   PerfIntervalCount,
	     dsx1IntervalLOC       PerfIntervalCount,
         dsx1IntervalAIS	   PerfIntervalCount,
	     dsx1IntervalRAI	   PerfIntervalCount,
	     dsx1IntervalLOMF	   PerfIntervalCount,
		 dsx1IntervalFEBE	   PerfIntervalCount,
         dsx1IntervalStatus	   OCTET STRING,
         dsx1IntervalBPV	   PerfIntervalCount,
		 dsx1IntervalLOCRCMF   PerfIntervalCount,
		 dsx1IntervalLOFC	   PerfIntervalCount
}


dsx1IntervalLOS OBJECT-TYPE
         SYNTAX PerfIntervalCount
         MAX-ACCESS  read-only
         STATUS  current
         DESCRIPTION
          "The counter associated with the number of LOS
           seconds , encountered by a DS1 interface in
           one of the previous 96, individual 15 minute,
           intervals."
         ::= { dsx1XIntervalEntry 1 }

dsx1IntervalLOF OBJECT-TYPE
          SYNTAX PerfIntervalCount
          MAX-ACCESS  read-only
          STATUS  current
          DESCRIPTION
           "The counter associated with the number of OOF
            seconds, encountered by a DS1
            interface in one of the previous 96, individual 15
            minute, intervals."
          ::= { dsx1XIntervalEntry 2 }

dsx1IntervalLOC OBJECT-TYPE
         SYNTAX PerfIntervalCount
         MAX-ACCESS  read-only
         STATUS  current
         DESCRIPTION
          " Loss Of Cell delineation. Counts number of cells the ATM UNI cells receiver
            lost cells delineation ."
         ::= { dsx1XIntervalEntry 3 }

dsx1IntervalAIS OBJECT-TYPE
          SYNTAX PerfIntervalCount
          MAX-ACCESS  read-only
          STATUS  current
          DESCRIPTION
           "The counter associated with the number of AIS
            seconds, encountered by a SONET
            interface in one of the previous 96, individual 15
            minute, intervals."
          ::= { dsx1XIntervalEntry 4 }

dsx1IntervalRAI OBJECT-TYPE
           SYNTAX PerfIntervalCount
           MAX-ACCESS  read-only
           STATUS  current
           DESCRIPTION
           "Remote Alarm Indication: Transmitted  in the outgoing direction
	        (toward the PABX) over FDL bits when the DS1 device detected 
            an incoming Loss Of Frame. Received from the far end (PABX) 
            over FDL when it detects a Loss of frame."
           ::= { dsx1XIntervalEntry 5 }

dsx1IntervalLOMF OBJECT-TYPE
           SYNTAX PerfIntervalCount
           MAX-ACCESS  read-only
           STATUS  current
           DESCRIPTION
           "Loss of Multi-Frame sequence  in E1 time slot 16."
           ::= { dsx1XIntervalEntry 6 }

dsx1IntervalFEBE OBJECT-TYPE
          SYNTAX PerfIntervalCount
          MAX-ACCESS  read-only
          STATUS  current
          DESCRIPTION
          "Far End Block Errors, as reported in the first bit
           of frames 13 and 15, on multiframe E1 lines with CRC4,
           in one of the previous 96, individual, 15 minute intervals."
          ::= { dsx1XIntervalEntry 7 }

dsx1IntervalStatus OBJECT-TYPE
	SYNTAX OCTET STRING  (SIZE (4))
           MAX-ACCESS  read-only
           STATUS  current
           DESCRIPTION
            "The statuses of the current interval:
              0 - Valid.
              1 - redundantLinkSwitch - the link has been switched 
                  by a redundancy mechanism.
              2 - discontinuity - module was partialy out.
              4 - notValid - module is out."
           ::= { dsx1XIntervalEntry 8 }

dsx1IntervalBPV OBJECT-TYPE
         SYNTAX PerfIntervalCount
         MAX-ACCESS  read-only
         STATUS  current
         DESCRIPTION
         "The counter associated with the number of BPV (Bi-Polar Violations)
          encountered by a DS1	interface in one of the previous 96, 
          individual 15 minute, intervals."
         ::= { dsx1XIntervalEntry 9 }

dsx1IntervalLOCRCMF OBJECT-TYPE
         SYNTAX PerfIntervalCount
         MAX-ACCESS  read-only
         STATUS  current
         DESCRIPTION
         "Loss of CRC4 Multi-Frame sequence in E1."
         ::= { dsx1XIntervalEntry 10 }

dsx1IntervalLOFC OBJECT-TYPE
          SYNTAX PerfIntervalCount
          MAX-ACCESS  read-only
          STATUS  current
          DESCRIPTION
          "Counts the number of loss of frame events measured
          in one of the previous 96, individual 15 minute, intervals."
          ::= { dsx1XIntervalEntry 11 }


--   Extension to the dsx1 Total table
  
dsx1XTotalTable  OBJECT-TYPE
       SYNTAX      SEQUENCE OF Dsx1XTotalEntry
       MAX-ACCESS  not-accessible
       STATUS      current
       DESCRIPTION
       "A list of Total statistics entries.  This table
        contains additional objects for the Total table."
       ::= { prtDs1PerfHistory 4 }

dsx1XTotalEntry OBJECT-TYPE
       SYNTAX  Dsx1XTotalEntry 
       MAX-ACCESS  not-accessible
       STATUS      current
       DESCRIPTION
       "An entry containing additional statistical counters
        applicable to a particular current table."
 --     AUGMENTS    { dsx1CurrentEntry }
        INDEX   { dsx1TotalIndex }
       ::= { dsx1XTotalTable 1 }

Dsx1XTotalEntry     ::=
      SEQUENCE {
	  dsx1TotalLOS 			PerfTotalCount,
	  dsx1TotalBPV			PerfTotalCount,
      dsx1TotalLOFC			PerfTotalCount
      }

 dsx1TotalLOS OBJECT-TYPE
      SYNTAX PerfTotalCount
      MAX-ACCESS  read-only
      STATUS  current
      DESCRIPTION
      "The counter associated with the number of LOS (Loss of Signal) 
      seconds encountered by a DS1 interface in the previous 
      24 hour interval.
      Invalid 15 minute intervals count as 0."
      ::= { dsx1XTotalEntry 1 }

dsx1TotalBPV OBJECT-TYPE
      SYNTAX PerfTotalCount
      MAX-ACCESS  read-only
      STATUS  current
      DESCRIPTION
      "The counter associated with the number of BPV (Bi-Polar Violations)
       encountered by a DS1	interface in the previous 24 hour interval.
       Invalid 15 minute intervals count as 0."
      ::= { dsx1XTotalEntry 9 }

dsx1TotalLOFC OBJECT-TYPE
      SYNTAX PerfTotalCount
      MAX-ACCESS  read-only
      STATUS  current
      DESCRIPTION
      "The counter associated with the number loss of frames
       encountered by a DS1	interface in the previous 24 hour interval.
       Invalid 15 minute intervals count as 0."
      ::= { dsx1XTotalEntry 11 }


-- DS1 Data Stream Statistics Table

dsx1DataStreamStatTable OBJECT-TYPE
      SYNTAX  SEQUENCE OF Dsx1DataStreamStatEntry
      MAX-ACCESS   not-accessible
      STATUS  current
      DESCRIPTION
      "The DS1 Data Stream Statistics table."
      ::= { prtDs1PerfHistory 5 }

dsx1DataStreamStatEntry OBJECT-TYPE
      SYNTAX  Dsx1DataStreamStatEntry
      MAX-ACCESS  not-accessible
      STATUS  current
      DESCRIPTION
      "An entry in the DS1 Data Stream Statistics table."
      INDEX   { dsx1DataStreamStatIfIndex, dsx1DataStreamStatIndex }
      ::= { dsx1DataStreamStatTable 1 }

Dsx1DataStreamStatEntry ::=
      SEQUENCE {
      dsx1DataStreamStatIfIndex			Integer32,
      dsx1DataStreamStatIndex			Integer32,
	  dsx1DataStreamStatValid			TruthValue,
      dsx1DataStreamStatInFrames		Counter32,
      dsx1DataStreamStatInBytes			Counter32,
      dsx1DataStreamStatInDiscards		Counter32,
      dsx1DataStreamStatInErrors		Counter32,
      dsx1DataStreamStatOutFrames		Counter32,
      dsx1DataStreamStatOutBytes		Counter32,
      dsx1DataStreamStatOutDiscards		Counter32,
	  dsx1DataStreamStatOutErrors		Counter32
      }

dsx1DataStreamStatIfIndex OBJECT-TYPE
    SYNTAX      Integer32
    MAX-ACCESS  not-accessible
    STATUS      current
    DESCRIPTION
    "The index of the DS1 interface.
     It may be ifIndex."
    ::= { dsx1DataStreamStatEntry 1 }

dsx1DataStreamStatIndex OBJECT-TYPE
    SYNTAX      Integer32
    MAX-ACCESS  not-accessible
    STATUS      current
    DESCRIPTION
    "The DS1 Data Stream Index.
     For Vmux - the following indices are used:
       1  for Transparent
	 2-3  for SS71-SS72 (respectively)
	 4-7  for Data1-Data4 (respectively)
	   8  for HDLC Ph2 Compatible
	9-16  for Sub-CH1-1...Sub-CH1-8 (respectively)."
    ::= { dsx1DataStreamStatEntry 2 }

dsx1DataStreamStatValid OBJECT-TYPE
    SYNTAX  TruthValue
    MAX-ACCESS  read-only
    STATUS      current
    DESCRIPTION
    "Indicates whether this Data Stream is valid or not.
     When invalid - all counters are irrelevant."
    ::= { dsx1DataStreamStatEntry 3 }

dsx1DataStreamStatInFrames OBJECT-TYPE
      SYNTAX  Counter32  
      MAX-ACCESS  read-only
      STATUS  current
      DESCRIPTION
	  "The counter associated with the number of received frames,
	   encountered by the DS1 Data Stream."
      ::= { dsx1DataStreamStatEntry 4 }

dsx1DataStreamStatInBytes OBJECT-TYPE
      SYNTAX  Counter32  
      MAX-ACCESS  read-only
      STATUS  current
      DESCRIPTION
	  "The counter associated with the number of received bytes,
	   encountered by the DS1 Data Stream."
      ::= { dsx1DataStreamStatEntry 5 }

dsx1DataStreamStatInDiscards OBJECT-TYPE
      SYNTAX  Counter32  
      MAX-ACCESS  read-only
      STATUS  current
      DESCRIPTION
	  "The counter associated with the number of Discarded incoming frames,
	   encountered by the DS1 Data Stream."
      ::= { dsx1DataStreamStatEntry 6 }

dsx1DataStreamStatInErrors OBJECT-TYPE
      SYNTAX  Counter32  
      MAX-ACCESS  read-only
      STATUS  current
      DESCRIPTION
	  "The counter associated with the number of received Errored frames,
	   encountered by the DS1 Data Stream."
      ::= { dsx1DataStreamStatEntry 7 }

dsx1DataStreamStatOutFrames OBJECT-TYPE
      SYNTAX  Counter32  
      MAX-ACCESS  read-only
      STATUS  current
      DESCRIPTION
	  "The counter associated with the number of transmitted frames,
	   encountered by the DS1 Data Stream."
      ::= { dsx1DataStreamStatEntry 8 }

dsx1DataStreamStatOutBytes OBJECT-TYPE
      SYNTAX  Counter32  
      MAX-ACCESS  read-only
      STATUS  current
      DESCRIPTION
	  "The counter associated with the number of transmitted bytes,
	   encountered by the DS1 Data Stream."
      ::= { dsx1DataStreamStatEntry 9 }

dsx1DataStreamStatOutDiscards OBJECT-TYPE
      SYNTAX  Counter32  
      MAX-ACCESS  read-only
      STATUS  current
      DESCRIPTION
	  "The counter associated with the number of Discarded outgoing frames,
	   encountered by the DS1 Data Stream."
      ::= { dsx1DataStreamStatEntry 10 }

dsx1DataStreamStatOutErrors OBJECT-TYPE
      SYNTAX  Counter32  
      MAX-ACCESS  read-only
      STATUS  current
      DESCRIPTION
	  "The counter associated with the number of errored transmitted frames, 
	   encountered by the DS1 Data Stream."
      ::= { dsx1DataStreamStatEntry 11 }


--   Extension to the DS1 Configuration Table
  
dsx1XConfigTable  OBJECT-TYPE
       SYNTAX      SEQUENCE OF Dsx1XConfigEntry
       MAX-ACCESS  not-accessible
       STATUS      current
       DESCRIPTION
               " An extension to the DS1 Configuration table."
       ::= { ds1Interface 2 }

dsx1XConfigEntry OBJECT-TYPE
       SYNTAX  Dsx1XConfigEntry 
       MAX-ACCESS  not-accessible
       STATUS      current
       DESCRIPTION
           "An entry containing additional configuration
           parameters."
 --      AUGMENTS    { dsx1ConfigTable }
         INDEX   { dsx1LineIndex }
       ::= { dsx1XConfigTable 1 }

Dsx1XConfigEntry      ::=
       SEQUENCE {
         dsx1IdleCode		    	Integer32,
         dsx1LineMode		    	INTEGER,
         dsx1dBTxGain     			INTEGER,
         dsx1RxSensitivity			INTEGER,
         dsx1RestoreTime			INTEGER,
         dsx1TcFirstSignal			Integer32,
         dsx1TcSignal   			Integer32,
         dsx1TcPattern     			Integer32,
         dsx1Scramble     			INTEGER,
         dsx1LineAdaptiveTimingMode INTEGER,
		 dsx1TxClockSource          INTEGER,
		 dsx1AisEnable				INTEGER,
		 dsx1TsEchoCancel			OCTET STRING,
		 dsx1EchoCancelerModule     INTEGER,
         dsx1PortFunction 		    INTEGER,
		 dsx1PortMultiplier			INTEGER,
		 dsx1LeasedLine				INTEGER,	
		 dsx1CsuLoop				INTEGER,
		 dsx1ClockSource			Integer32,
		 dsx1OosSignal				INTEGER,
		 dsx1BundleNextIndex		Integer32,
		 dsx1CRC6CalcMode           INTEGER,
		 dsx1SendUponFail           INTEGER
		        }

dsx1IdleCode OBJECT-TYPE
         SYNTAX  Integer32
         MAX-ACCESS   read-write
         STATUS  current
         DESCRIPTION
	     "Byte pattern of the data received/transmitted in the 
	      E1T1 framer idle timeslots.
	      Valid range: (0 - FF HEX)."
         ::= { dsx1XConfigEntry 1 }

dsx1LineMode OBJECT-TYPE
          SYNTAX  INTEGER { 
          csu(1),
          dsu(2)
          }
          MAX-ACCESS  read-write
          STATUS  current
          DESCRIPTION
                  "T1 device operation mode. 
                   Valid for T1 only."
          ::= { dsx1XConfigEntry 2 }

dsx1dBTxGain OBJECT-TYPE
         SYNTAX  INTEGER { 
         notApplicable (1),
         neg75dB       (2),
         neg15dB       (3),
         neg225dB      (4),
		 zerodB	       (5)
         }
         MAX-ACCESS  read-write
         STATUS  current
         DESCRIPTION
                 "Transmit line Gain for T1 CSU line mode."
         ::= { dsx1XConfigEntry 3 }

dsx1RxSensitivity OBJECT-TYPE
        SYNTAX  INTEGER { 
		notApplicable  (1),
        longHaul       (2),	
        shortHaul      (3)	
        }
        MAX-ACCESS  read-write
        STATUS  current
        DESCRIPTION
        "Low Sensitivity is considered Short Haul while High Sensitivity 
		 is considered Long Haul. The actual values depend on the LIU.
		 Examples:
		 - E1: -12dB is considered Short Haul ; -43dB is considered Long Haul
		 - T1: -12dB is considered Short Haul ; -36dB is considered Long Haul."
        ::= { dsx1XConfigEntry 4 }

dsx1RestoreTime OBJECT-TYPE
        SYNTAX  INTEGER { 
        other(1),
        sec1(2),
        sec10(3),
		immediate(4)
        }
        MAX-ACCESS  read-write
        STATUS  current
        DESCRIPTION
        "Used to change the sync. algorithms to reduce the time 
         required for the port to return to normal operation after 
         a RED alarm.
         'sec1' = Fast,
         'sec10' = TR-6211,
		 'immediate' = CCITT"
        ::= { dsx1XConfigEntry 5 }

dsx1TcFirstSignal OBJECT-TYPE
        SYNTAX  Integer32
        MAX-ACCESS  read-write
        STATUS  current
        DESCRIPTION
        "Trunk conditioning signal - value to be sent as a signal
         during the first 2.5 seconds after alarm detection.
		 Range is 0x0..0xF. 0xFF is a NULL value. 
		 This variable is used also for Space Signaling Code (in this case 
		 0xFF is not NULL)."
        ::= { dsx1XConfigEntry 6 }

dsx1TcSignal OBJECT-TYPE
        SYNTAX  Integer32 
        MAX-ACCESS  read-write
        STATUS  current
        DESCRIPTION
        "Trunk conditioning signal value after alarm detection. 
         Range is 0x1..0xF for E1, and 0x0..0xF for T1.
         This variable is used also for Space Signaling Code (E1 and T1)."
        ::= { dsx1XConfigEntry 7 }

dsx1TcPattern OBJECT-TYPE
       SYNTAX  Integer32
       MAX-ACCESS  read-write
       STATUS  current
       DESCRIPTION
       "Trunk conditioning data pattern to be sent upon a DS0 fail.
	  	Range is 0x0..0xFF. 
	  	This variable used also for Out of Service Code."
       ::= { dsx1XConfigEntry 8 }

dsx1Scramble  OBJECT-TYPE
       SYNTAX  INTEGER { 
       notApplicable (1),
       notActive     (2),
       active        (3)
       }
       MAX-ACCESS  read-write
       STATUS  current
       DESCRIPTION
       "Scrambling is an operation that randomizes the bits 
        of the payload of the ATM cell by a polynom.
        This operation helps with the error detection mechanism
        of the HEC. Not applicable for E1.
        active - will scramble/descramble the payload ATM cell
        notActive - will not scramble/descramble. "
       ::= { dsx1XConfigEntry 9 }

dsx1LineAdaptiveTimingMode OBJECT-TYPE
       SYNTAX  INTEGER {
       off(1),
       on(2)
       }
       MAX-ACCESS  read-write
       STATUS  current
       DESCRIPTION
       "Enables end to end clock synchronization.
        Default value - off."
       ::= { dsx1XConfigEntry 10 }

dsx1TxClockSource OBJECT-TYPE
       SYNTAX  INTEGER {
       loopTiming(1),
       localTiming(2),
       throughTiming(3),
	   adaptive(4),
	   system(5)
       }
       MAX-ACCESS  read-write
       STATUS  current
       DESCRIPTION
       "The source of Transmit Clock.
        'loopTiming' indicates that the recovered receive clock 
         is used as the transmit clock.

        'localTiming' indicates that a local clock
         source is used or when an external clock is
         attached to the box containing the interface.

        'throughTiming' indicates that recovered receive clock 
         from another interface is used as the transmit clock.
         
        'adaptive' indicates that the clock is recovered according
         to the received data flow rate.

        'system' indicates that the system clock 
         is used as the transmit clock."
       ::= { dsx1XConfigEntry 11 }

dsx1AisEnable  OBJECT-TYPE
       SYNTAX  INTEGER {
       notApplicable(1),
       disable(2),
       enable(3)
       }
       MAX-ACCESS  read-write
       STATUS  current
       DESCRIPTION
       "Enable/ disable AIS transmit when Ethernet cable (for TDMoIP) is out (disconnected)."
       ::= { dsx1XConfigEntry 12 }

dsx1TsEchoCancel OBJECT-TYPE
       SYNTAX OCTET STRING  (SIZE (4))
       MAX-ACCESS  read-write
       STATUS  current
       DESCRIPTION
       "This parameter defines for each TS whether Echo-Cancellation is on.
	  	Each bit represents one TS as follow:
		First octet bit'0' = TS#1, bit'7' = TS#8, .. 2nd octet bit'0' = TS#9,.., 
		4th octet bit'7' = TS#32.
		Octets and bits order is from left to right:
		[31,30,..24]      [23..16]    [15..8]      [7..0]
		MSB       LSB 	 MSB	LSB	 MSB   LSB	  MSB	LSB
	  	
	  	For each bit values are:
         0 - Echo-Cancellation off.
         1 - Echo-Cancellation on."
       ::= { dsx1XConfigEntry 13 }

dsx1EchoCancelerModule OBJECT-TYPE
       SYNTAX  INTEGER { 
       notExist(2),
       exist(3)
       }
       MAX-ACCESS  read-only
       STATUS  current
       DESCRIPTION
       "This parameter indicates whether echo-cancellation module
        exists for this line."
       ::= { dsx1XConfigEntry 14 }

dsx1PortFunction OBJECT-TYPE
       SYNTAX  INTEGER { 
	    notApplicable	(1),	
	  	uni				(2),
	  	ces				(3),
	  	ima				(4),
		cesPsn			(5),
		abis			(6)
	    }
       MAX-ACCESS  read-write
       STATUS  current
       DESCRIPTION
       "This object determines the ATM Mode over the 
        physical port.
        uni  	- The port will function as an ATM UNI.  
        ces  	- The port will function as a CES.
        ima  	- The port will function as an IMA-ATM.
        cesPsn  - The port will function as a CES-PSN.
		abis 	- The port will function as an Abis."
       ::= { dsx1XConfigEntry 15 }

dsx1PortMultiplier OBJECT-TYPE
       SYNTAX  INTEGER { 
	    notApplicable (1),	
	  	r56 (2),
	  	r64 (3)
	    }
       MAX-ACCESS  read-write
       STATUS  current
       DESCRIPTION
       "This object determines the data rate of each TS 
        (Kbps units). 
        This parameter is applicable for T1 only."
       ::= { dsx1XConfigEntry 16 }

dsx1LeasedLine OBJECT-TYPE
       SYNTAX  INTEGER { 
	    notApplicable (1),	
	  	disable (2),
	  	enable (3)
	    }
       MAX-ACCESS  read-write
       STATUS  current
       DESCRIPTION
       "This parameter defines whether Line mode is regular (non Leased Line mode) 
       or transparent (Leased Line mode)."
       ::= { dsx1XConfigEntry 17 }

dsx1CsuLoop OBJECT-TYPE
       SYNTAX  INTEGER { 
	   notApplicable	(1),
       local	  	    (2),
	   transparent		(3),
	   remote           (4)	    }
       MAX-ACCESS  read-write
       STATUS  current
       DESCRIPTION
       "This parameter defines where the CSU loop will be done: 
        local - locally (by IPmux) towards the TDM device
        transparent - transferred to Remote Device that will send it to its
                      connected TDM device.
        remote - Remote Device will close the loop towards the Local Device."
       ::= { dsx1XConfigEntry 18 }

dsx1ClockSource OBJECT-TYPE
    SYNTAX  Integer32
    MAX-ACCESS  read-write
    STATUS  current
    DESCRIPTION
    "This entry specifies the source from which the clock will be taken.
	 Refer to device specification for source Index"      
      ::= { dsx1XConfigEntry 19 }

dsx1OosSignal OBJECT-TYPE
       SYNTAX  INTEGER { 
	    notApplicable	(1),
        space    		(2),
	    mark	 		(3),
	    spaceMark		(4),
	    markSpace		(5)	   
	   					 }
       MAX-ACCESS  read-write
       STATUS  current
       DESCRIPTION
       " This parameter defines the value to be sent as a signal
         after alarm detection:
         'Space' = both A and B signaling bits are forced
                      to '0' during out-of-service periods.
		 'Mark' = both A and B signaling bits are forced
                      to '1' during out-of-service periods.
         'spaceMark' = A and B bits are forced to '0' for
                      2.5 seconds; then they are switched to '1'
                      until out-of-service condition disappears.
         'markSpace' = A and B bits are forced to '1' for
                      2.5 seconds; then they are switched to '0'
                      until out-of-service condition disappears.
       - '0'= 0 for T1, 1 for E1, or user defined value for Space                         
       - '1'= 1 for T1, 0 for E1, or user defined value for Mark."
       ::= { dsx1XConfigEntry 20 }

dsx1BundleNextIndex OBJECT-TYPE
       SYNTAX  Integer32
       MAX-ACCESS  read-only
       STATUS  current
       DESCRIPTION
       "This parameter indicates the Next free Bundle Index for this DS1 port."
       ::= { dsx1XConfigEntry 21 }

dsx1CRC6CalcMode OBJECT-TYPE
       SYNTAX  INTEGER { 
	    jtG704 (1),	
	  	ituG704(2)
	    }
       MAX-ACCESS  read-write
       STATUS  current
       DESCRIPTION
       "This object determines the CRC6 Calculation mode.
        jtG704 =JT-G704  = the Japanese standard
        ituG704=ITU-G704 = the International standard 
        This parameter is applicable for J1 only."
       ::= { dsx1XConfigEntry 22 }

dsx1SendUponFail   OBJECT-TYPE
       SYNTAX      INTEGER
	   {
	       oosCode (2),
		   ais (3)
	   }
       MAX-ACCESS  read-write
       STATUS  current
       DESCRIPTION
       "This object determines which notification will be sent to the other side 
       upon fail of another interface.
       In Ipmux14 the notification is sent upon failure of the Ethernet link."
       ::= { dsx1XConfigEntry 23 }

--NOTIFICATIONs 

-- ALARM TRAPS

-- USER E1 LOCAL MULTIFRAME ALARM
ds1LocalMultiframeAlarmTrap  NOTIFICATION-TYPE
      OBJECTS  {alarmSeverity, ifAlias}  
      STATUS  current
      DESCRIPTION
	    "This trap indicates near end (Local) Loss of 
      Multiframe Alignment, of the user E1 interface." 
      ::= { prtDS1Events  1 }

-- USER E1 REMOTE MULTIFRAME ALARM
ds1RemoteMultiframeAlarmTrap	  NOTIFICATION-TYPE
      OBJECTS  {alarmSeverity, ifAlias}  
      STATUS  current
      DESCRIPTION
	    "This trap indicates that the far end (remote) unit, 
      connected to the user E1 interface, reports
      Loss of Multiframe Alignment."
      ::= { prtDS1Events  2 }

-- USER DS1 LINK FRAME SLIP
ds1LinkFrameSlipTrap	  NOTIFICATION-TYPE
      OBJECTS  {alarmSeverity, ifAlias}  
      STATUS  current
      DESCRIPTION
	  "This trap indicates that a Frame Slip occurred at the user 
      DS1 interface. This usually indicates timing problems 
      (incorrect selection of timing reference), 
       on the user DS1 link."
      ::= { prtDS1Events  3 }

-- USER DS1 BPV ERROR
ds1BpvErrorTrap	NOTIFICATION-TYPE
      OBJECTS  {alarmSeverity, ifAlias}  
      STATUS  current
      DESCRIPTION
	  "This trap indicates a Bipolar Violation (BPV)
      error has been detected at the user DS1 interface."
      ::= { prtDS1Events  4 }

-- USER DS1 EXCESSIVE BPV
ds1ExcessiveBpvTrap	NOTIFICATION-TYPE
      OBJECTS  {alarmSeverity, alarmState, ifAlias}  
      STATUS  current
      DESCRIPTION
	  "This trap indicates excessive number of 
      Bipolar Violation errors  (BPV)
      detected by the user DS1 interface"
      ::= { prtDS1Events  5 }

-- USER DS1 CRC-4 ERROR
ds1Crc4ErrorTrap	 NOTIFICATION-TYPE
      OBJECTS  {alarmSeverity, ifAlias}  
      STATUS  current
      DESCRIPTION
	    "This trap indicates that a frame with CRC-4 error has been
      detected at the user DS1 interface."
      ::= { prtDS1Events  6 }

-- USER DS1 EXCESSIVE ERROR RATIO
ds1ExcessiveErrorRatioTrap  NOTIFICATION-TYPE
      OBJECTS  {alarmSeverity, alarmState, ifAlias}  
      STATUS  current
      DESCRIPTION
	    "This trap indicates that the error rate, detected 
      at the user DS1 interface, on the frame synchronization bits
      is high, as defined by ITU-T Rec. G.732."
     ::= { prtDS1Events  7 }

-- USER DS1 REMOTE SYNC LOSS
ds1RemoteSyncLossTrap  NOTIFICATION-TYPE
      OBJECTS  {alarmSeverity, alarmState, ifAlias}  
      STATUS  current
      DESCRIPTION
	  "This trap indicates that the far-end (remote)
      unit, connected to user DS1 interface,
      reports Loss of Frame Alignment (Sync Loss)."
      ::= { prtDS1Events  8 }

-- USER DS1 LOCAL SYNC LOSS
ds1LocalSyncLossTrap NOTIFICATION-TYPE
      OBJECTS  {alarmSeverity, alarmState, ifAlias}  
      STATUS  current
      DESCRIPTION
	  "This trap indicates near end (Local) 
      Loss of Frame Alignment failure (Sync Loss), 
      of the user DS1 interface"
      ::= { prtDS1Events  9 }

-- USER DS1 AIS SYNC LOSS
ds1AisSyncLossTrap  NOTIFICATION-TYPE
      OBJECTS  {alarmSeverity, ifAlias}  
      STATUS  current
      DESCRIPTION
      "This trap indicates near end (Local) 
      Loss of Frame Alignment (Sync Loss), caused by the reception
      of AIS at the user DS1 interface."
      ::= { prtDS1Events  10 }

-- USER DS1 AIS
ds1AisTrap  NOTIFICATION-TYPE
      OBJECTS  {alarmSeverity, alarmState, ifAlias}  
      STATUS  current
      DESCRIPTION
	  "This trap indicates AIS  being received
      at the user DS1 interface."
      ::= { prtDS1Events  11 }

-- NETWORK REMOTE LOOP
 ds1NetworkRemoteLoopTrap NOTIFICATION-TYPE
       OBJECTS  {alarmSeverity, alarmState, ifAlias}  
       STATUS  current
       DESCRIPTION
       "This trap indicates that a remote loopback
       has been activated, on the local uplink interface."
       ::= { prtDS1Events  12 }

-- USER SIDE REMOTE LOOP
ds1RemoteLoopTrap  NOTIFICATION-TYPE
      OBJECTS  {alarmSeverity, alarmState, ifAlias}  
      STATUS  current
      DESCRIPTION
	  "This trap indicates that a remote loopback 
      has been activated, on the local user port."
      ::= { prtDS1Events  13 }
								
-- USER SIDE LOCAL LOOP
ds1LocalLoopTrap	NOTIFICATION-TYPE
      OBJECTS  {alarmSeverity, alarmState, ifAlias}  
      STATUS  current
      DESCRIPTION
	  "This trap indicates that a local loopback 
      has been activated on the user port."
      ::= { prtDS1Events  14 }	

-- DS1 EXCESSIVE FRAME SLIP
ds1ExcessiveFrameSlipTrap  NOTIFICATION-TYPE
      OBJECTS  {alarmSeverity, alarmState, ifAlias}  
      STATUS  current
      DESCRIPTION
	  "This trap indicates that the number of Frame Slips
      detected at the user DS1 interface, during the last minute
      exceeds threshold. For LA-110, threshold value is 10.
      This usually indicates timing problems 
      (incorrect selection of timing reference) on the user DS1."
      ::= { prtDS1Events  15 }

-- USER DS1 EXCESSIVE CRC 4 ERROR
ds1ExcessiveCrc4ErrorTrap  NOTIFICATION-TYPE
      OBJECTS  {alarmSeverity, alarmState, ifAlias}  
      STATUS  current
      DESCRIPTION
	  "This trap indicates that the error rate 
      detected on the CRC-4 bits at the
      user DS1 interface, is high."
      ::= { prtDS1Events  16 }

-- USER E1 EXCESSIVE LOCAL MULTIFRAME ALARM
ds1ExcessiveLocalMfAlarmTrap	 NOTIFICATION-TYPE
      OBJECTS  {alarmSeverity, alarmState, ifAlias}  
      STATUS  current
      DESCRIPTION
	     "This trap indicates that the number of local
      Loss of Multiframe Alignment events, detected at
      the user E1 interface during the last minute exceeds threshold. 
      For LA-110, threshold value is 10."
      ::= { prtDS1Events  17 }

-- USER E1 EXCESSIVE REMOTE MULTIFRAME ALARM
ds1ExcessiveRemoteMfAlarmTrap  NOTIFICATION-TYPE
      OBJECTS  {alarmSeverity, alarmState, ifAlias}  
      STATUS  current
      DESCRIPTION
	  "This trap indicates that the number of 
      Loss of multiframe alignment events reported
      by the remote unit connected to the user 
      E1 interface during the last minute exceeds threshold. 
      For LA-110, threshold value is 10."
      ::= { prtDS1Events  18 }

-- USER DS1 EXCESSIVE REMOTE SYNC LOSS
ds1ExcessiveRemoteSyncLossTrap	  NOTIFICATION-TYPE
      OBJECTS  {alarmSeverity, alarmState, ifAlias}  
      STATUS  current
      DESCRIPTION
	  "This trap indicates that the number of far end 
      (remote) Loss of Synchronization alarms,
      reported by the user DS1 interface 
      during the last minute, exceeds threshold. 
      For LA-110, threshold value is 10."
      ::= { prtDS1Events  19 }

-- USER DS1 EXCESSIVE LOCAL SYNC LOSS
ds1ExcessiveLocalSyncLossTrap	 NOTIFICATION-TYPE
      OBJECTS  {alarmSeverity, alarmState, ifAlias}  
      STATUS  current
      DESCRIPTION
	  "This trap indicates that the number of 
      Loss of local Synchronization alarms  
      reported by the user DS1 interface 
      during the last minute, exceeds threshold. 
      For LA-110, threshold value is 10."
      ::= { prtDS1Events  20 }

-- USER DS1 SIGNAL LOSS
ds1SignalLossTrap	 NOTIFICATION-TYPE
      OBJECTS  {alarmSeverity, alarmState, ifAlias}  
      STATUS  current
      DESCRIPTION
	  "This trap indicates Signal Loss.
	  (possible reason -  cable disconnection. etc.)"
      ::= { prtDS1Events  21 }

--END
-- 
-- file :D:\Synergy\WorkArea\545\mib_rad\txt\radds3.txt
-- 
-- RAD-DS3-MIB DEFINITIONS ::= BEGIN

--Title:    RAD-DS3   MIB
--
-- Copyright 1993 RAD Data Communications, Ltd.
-- All Rights Reserved.  

-- It is RAD's intent to encourage the widespread use of
-- this Specification in connection with the management of
-- RAD products. RAD grants vendors, end-users,
-- and other interested parties a non-exclusive license to
-- use this Specification in connection with the management
-- of RAD products.
-- This Specification is supplied "as is," and RAD makes
-- no warranty, either express or implied, as to the use,
-- operation, condition, or performance of the Specification.

-- IMPORTS
--      Gauge32                           FROM SNMPv2-SMI
--      ifIndex                         FROM SNMPv2-TC
--      OBJECT-TYPE                     FROM SNMPv2-SMI
 --     radWan                          FROM RAD-GEN-MIB;



--                RAD-DS3 MIB   

--Title:     RAD's DS3 INTERFACE MIB
--Version:   1.0
--Date:      13.10.96
--By:        Yair Arian
--File:      ds3.mib
--
--Last update: 12 May 08 by Yig'al Hachmon


ds3Interface  OBJECT IDENTIFIER  ::=  {diverseIfWanGen 3}

prtDs3PerfHistory  OBJECT IDENTIFIER  ::=  {ds3Interface 1}


          -- The DS3 Interface Table

          prtSDs3IfTable OBJECT-TYPE
              SYNTAX  SEQUENCE OF PrtDs3IfEntry
              MAX-ACCESS  not-accessible
              STATUS  current
              DESCRIPTION
                      "The DS3 interface table."
              ::= { prtDs3PerfHistory 1 }

          prtDs3IfEntry OBJECT-TYPE
              SYNTAX  PrtDs3IfEntry
              MAX-ACCESS  not-accessible
              STATUS  current
              DESCRIPTION
                      "An entry in the DS3 interface table."
              INDEX   { ifIndex }
              ::= { prtSDs3IfTable 1 }

          PrtDs3IfEntry ::=
              SEQUENCE {
                  prtDs3IfTimeElapsed
                      Integer32,
                  prtDs3IfValidIntervals
                      Integer32
                                           }

           prtDs3IfTimeElapsed OBJECT-TYPE
               SYNTAX  Integer32 (0..899)
               MAX-ACCESS  read-only
               STATUS  current
               DESCRIPTION
                       "The number of seconds that have elapsed since
                       the beginning of the near end current error-
                       measurement period."
              ::= { prtDs3IfEntry 1 }

          prtDs3IfValidIntervals OBJECT-TYPE
              SYNTAX  Integer32 (0..96)
              MAX-ACCESS  read-only
              STATUS  current
              DESCRIPTION
                      "The number of previous near end intervals for
                      which valid data was collected.  The value will be
                      96 unless the interface was brought online within
                      the last 24 hours, in which case the value will be
                      the number of complete 15 minute near end
                      intervals since the interface has been online."
              ::= { prtDs3IfEntry 2 }

        

          -- The DS3 Current Table

          -- The DS3 Current table contains various statistics being
          -- collected for the current 15 minute interval.

          prtDs3CurrentTable OBJECT-TYPE
              SYNTAX  SEQUENCE OF PrtDs3CurrentEntry
              MAX-ACCESS  not-accessible
              STATUS  current
              DESCRIPTION
                      "The DS3 Current table."
              ::= { prtDs3PerfHistory 2 }

          prtDs3CurrentEntry OBJECT-TYPE
              SYNTAX  PrtDs3CurrentEntry
              MAX-ACCESS  not-accessible
              STATUS  current
              DESCRIPTION
                      "An entry in the DS3 Current table."
              INDEX   { ifIndex }
              ::= { prtDs3CurrentTable 1 }

          PrtDs3CurrentEntry ::=
              SEQUENCE {
                  prtDs3CurrentLOS
                      Gauge32,
                  prtDs3CurrentOOF
                      Gauge32,
                  prtDs3CurrentLOC
                      Gauge32,
                  prtDs3CurrentAIS
                      Gauge32,
                  prtDs3CurrentRDI
                      Gauge32,
                  prtDs3CurrentUAS
                      Gauge32,
	              prtDs3CurrentBIP
                      Gauge32,
                  prtDs3CurrentFEBE
	                  Gauge32,
	              prtDs3CurrentSLM
	                  Gauge32,
                  prtDs3CurrentSES
                      Gauge32,
                  prtDs3CurrentES 
                      Gauge32,
                  prtDs3CurrentBitParity
                      Gauge32,
                  prtDs3CurrentPlcpLOF
                      Gauge32,
                  prtDs3CurrentPlcpRAI
                       Gauge32,
	              prtDs3CurrentPlcpBIP
                       Gauge32,
                  prtDs3CurrentPlcpFEBE
	                   Gauge32,
				 prtDs3CurrentBPV
				       Gauge32,
				 prtDs3CurrentLCE
				       Gauge32,
				  prtDs3CurrentStatus
				       OCTET STRING
}

          prtDs3CurrentLOS OBJECT-TYPE
              SYNTAX  Gauge32
              MAX-ACCESS  read-only
              STATUS  current
              DESCRIPTION
                      "The counter associated with the number of LOS
                       seconds, encountered by a DS3 interface in
                      the current 15 minute interval."
              ::= { prtDs3CurrentEntry 1 }

          prtDs3CurrentOOF OBJECT-TYPE
              SYNTAX  Gauge32
              MAX-ACCESS  read-only
              STATUS  current
              DESCRIPTION
                      "The counter associated with the number of OOF
                       seconds, encountered by a DS3
                       interface in the current 15 minute interval."
              ::= { prtDs3CurrentEntry 2 }

          prtDs3CurrentLOC OBJECT-TYPE
              SYNTAX  Gauge32
              MAX-ACCESS  read-only
              STATUS  current
              DESCRIPTION
                      "The counter associated with the number of LOC
                      seconds, encountered by a DS3
                      interface in the current 15 minute interval."
              ::= { prtDs3CurrentEntry 3 }

          prtDs3CurrentAIS OBJECT-TYPE
              SYNTAX  Gauge32
              MAX-ACCESS  read-only
              STATUS  current
              DESCRIPTION
                      "The counter associated with the number of AIS
                      seconds, encountered by a DS3
                      interface in the current 15 minute interval."
              ::= { prtDs3CurrentEntry 4 }

          prtDs3CurrentRDI OBJECT-TYPE
              SYNTAX  Gauge32
              MAX-ACCESS  read-only
              STATUS  current
              DESCRIPTION
                      "The counter associated with the number of RDI
                      seconds, encountered by a DS3
                      interface."
              ::= { prtDs3CurrentEntry 5 }

          prtDs3CurrentUAS OBJECT-TYPE
              SYNTAX  Gauge32
              MAX-ACCESS  read-only
              STATUS  current
              DESCRIPTION
                      "The counter associated with the number of UAS, 
                      encountered by a SONET interface."
              ::= { prtDs3CurrentEntry 6 }

        prtDs3CurrentBIP OBJECT-TYPE
              SYNTAX  Gauge32
              MAX-ACCESS  read-only
              STATUS  current
              DESCRIPTION
                      "The counter associated with the number of 
                      BIP errors, encountered by a DS3
                      interface in the current 15 minute interval."
              ::= { prtDs3CurrentEntry 7 }

          prtDs3CurrentFEBE OBJECT-TYPE
              SYNTAX  Gauge32
              MAX-ACCESS  read-only
              STATUS  current
              DESCRIPTION
                      "The counter associated with the number of 
                      FEBE errors, encountered by a DS3
                      interface in the current 15 minute interval."
              ::= { prtDs3CurrentEntry 8 }

          prtDs3CurrentSLM OBJECT-TYPE
              SYNTAX  Gauge32
              MAX-ACCESS  read-only
              STATUS  current
              DESCRIPTION
                      "The counter associated with the number of SLM
                       seconds, encountered by an E3 (only )
                       interface in the current 15 minute interval."
              ::= { prtDs3CurrentEntry 9 }

        prtDs3CurrentSES OBJECT-TYPE
              SYNTAX  Gauge32
              MAX-ACCESS  read-only
              STATUS  current
              DESCRIPTION
                      "The counter associated with the number of SES
                       encountered by a E3
                       interface in the current 15 minute interval."
	     ::= { prtDs3CurrentEntry 10 }

	  prtDs3CurrentES OBJECT-TYPE
	SYNTAX Gauge32 
              MAX-ACCESS  read-only
              STATUS  current
              DESCRIPTION
                      " The number of Errored Seconds, encountered  by a
                      DS3 interface in the current 15 minute interval."
	::= { prtDs3CurrentEntry 11 }

     prtDs3CurrentBitParity OBJECT-TYPE
              SYNTAX  Gauge32
              MAX-ACCESS  read-only
              STATUS  current
              DESCRIPTION
                      "Bit Parity Error counter. Relevant to T3 only."
              ::= { prtDs3CurrentEntry 12 }

        prtDs3CurrentPlcpLOF OBJECT-TYPE
              SYNTAX  Gauge32
              MAX-ACCESS  read-only
              STATUS  current
              DESCRIPTION
                      "The counter associated with the number of LOF
                      seconds, encountered by a DS3
                      interface in one of the previous 96, individual 15
                      minute, intervals. This counter is relevant for plcpInternal(5)
                       or plcpExternal(6) configuration If frame types only."
              ::= { prtDs3CurrentEntry 13 }

prtDs3CurrentPlcpRAI OBJECT-TYPE
              SYNTAX  Gauge32
              MAX-ACCESS  read-only
              STATUS  current
              DESCRIPTION
                    "Receiving Yellow/Remote Alarm Indication. This counter is 
                      relevant for PLCP (external/internal) frame types only."
              ::= { prtDs3CurrentEntry 14 }

      prtDs3CurrentPlcpBIP OBJECT-TYPE
              SYNTAX  Gauge32
              MAX-ACCESS  read-only
              STATUS  current
              DESCRIPTION
                    " The counter associated with the number of BIP errors, 
                      encountered by a DS3 interface in the current 15 minute 
                      interval. This counter is relevant for PLCP (external/internal) 
                      frame types only."
              ::= { prtDs3CurrentEntry 15 }

      prtDs3CurrentPlcpFEBE OBJECT-TYPE
              SYNTAX  Gauge32
              MAX-ACCESS  read-only
              STATUS  current
              DESCRIPTION
                    " The counter associated with the number of FEBE
                      errors, encountered by a DS3 interface in the current
                      15 minute interval. This counter is relevant for PLCP
                      (external/internal) frame types only."
              ::= { prtDs3CurrentEntry 16 }

      prtDs3CurrentBPV OBJECT-TYPE
              SYNTAX  Gauge32
              MAX-ACCESS  read-only
              STATUS  current
              DESCRIPTION
                    " Number of BPVs (Bi-Polar Violations) , encountered by a 
                      DS3 interface in the current 15 minute interval. 
                      This object is relevant only for Electrical Line
                      of Fomi-E3/T3."
              ::= { prtDs3CurrentEntry 17 }

      prtDs3CurrentLCE OBJECT-TYPE
              SYNTAX  Gauge32
              MAX-ACCESS  read-only
              STATUS  current
              DESCRIPTION
                    " Number of LCE (Link Code Errors)  encountered 
                      by a DS3 interface in the current 15 minute interval. 
                      This object is relevant only for Optical Links
                      of Fomi-E3/T3."
              ::= { prtDs3CurrentEntry 18 }

     prtDs3CurrentStatus OBJECT-TYPE
	          SYNTAX OCTET STRING  (SIZE (4))
              MAX-ACCESS  read-only
              STATUS  current
              DESCRIPTION
                      "The statuses of the current interval:
                        0 - Valid.
                        1 - redundantLinkSwitch - the link has been switched 
                            by a redundancy mechanism.
                        2 - discontinuity - module was partialy out.
                        4 - notValid - module is out."
              ::= { prtDs3CurrentEntry 19 }

         -- The DS3 interface Interval

          -- The DS3 Interval Table contains various statistics
          -- collected by the Interface over the previous 24
          -- hours of operation.  The past 24 hours are broken into 96
          -- completed 15 minute intervals.

          prtDs3IntervalTable OBJECT-TYPE
              SYNTAX  SEQUENCE OF PrtDs3IntervalEntry
              MAX-ACCESS  not-accessible
              STATUS  current
              DESCRIPTION
                      "The DS3 Interval table."
              ::= { prtDs3PerfHistory 3 }

          prtDs3IntervalEntry OBJECT-TYPE
              SYNTAX  PrtDs3IntervalEntry
              MAX-ACCESS  not-accessible
              STATUS  current
              DESCRIPTION
                      "An entry in the DS3 Interval table."
              INDEX   { ifIndex, prtDs3IntervalNumber }
              ::= { prtDs3IntervalTable 1 }

          PrtDs3IntervalEntry ::=
              SEQUENCE {
                  prtDs3IntervalNumber
                      Integer32,
                  prtDs3IntervalLOS
                      Gauge32,
                  prtDs3IntervalOOF
                      Gauge32,
                  prtDs3IntervalLOC
                      Gauge32,
                  prtDs3IntervalAIS
                      Gauge32,
                  prtDs3IntervalRDI
                      Gauge32,
                  prtDs3IntervalUAS
                      Gauge32,
	              prtDs3IntervalBIP
                      Gauge32,
                  prtDs3IntervalFEBE
                      Gauge32,
	              prtDs3IntervalSLM
                      Gauge32,
                  prtDs3IntervalSES 
                      Gauge32,
	              prtDs3IntervalES
                      Gauge32,
                  prtDs3IntervalBitParity
                      Gauge32,
                  prtDs3IntervalPlcpLOF
                      Gauge32,
                  prtDs3IntervalPlcpRAI
                      Gauge32,
	              prtDs3IntervalPlcpBIP
                      Gauge32,
                  prtDs3IntervalPlcpFEBE
	                  Gauge32,
				  prtDs3IntervalBPV
				       Gauge32,
				  prtDs3IntervalLCE
				       Gauge32,
				  prtDs3IntervalStatus 
	                  OCTET STRING
}

          prtDs3IntervalNumber OBJECT-TYPE
              SYNTAX  Integer32 (1..96)
              MAX-ACCESS  read-only
              STATUS  current
              DESCRIPTION
                      "A number between 1 and 96, where 1 is the most
                      recently completed 15 minute interval and 96 is
                      the least recently completed 15 minutes interval
                      (assuming that all 96 intervals are valid)."
              ::= { prtDs3IntervalEntry 1 }

          prtDs3IntervalLOS OBJECT-TYPE
              SYNTAX  Gauge32
              MAX-ACCESS  read-only
              STATUS  current
              DESCRIPTION
                      "The counter associated with the number of LOS
                      seconds , encountered by a DS3 interface in
                      one of the previous 96, individual 15 minute,
                      intervals."
              ::= { prtDs3IntervalEntry 2 }

          prtDs3IntervalOOF OBJECT-TYPE
              SYNTAX  Gauge32
              MAX-ACCESS  read-only
              STATUS  current
              DESCRIPTION
                      "The counter associated with the number of OOF
                      seconds, encountered by a DS3
                      interface in one of the previous 96, individual 15
                      minute, intervals."
              ::= { prtDs3IntervalEntry 3 }

          prtDs3IntervalLOC OBJECT-TYPE
              SYNTAX  Gauge32
              MAX-ACCESS  read-only
              STATUS  current
              DESCRIPTION
                      "The counter associated with the number of LOC
                      seconds, encountered by a DS3
                      interface in one of the previous 96,
                      individual 15 minute, intervals."
              ::= { prtDs3IntervalEntry 4 }

          prtDs3IntervalAIS OBJECT-TYPE
              SYNTAX  Gauge32
              MAX-ACCESS  read-only
              STATUS  current
              DESCRIPTION
                      "The counter associated with the number of AIS
                      seconds, encountered by a SONET
                      interface in one of the previous 96, individual 15
                      minute, intervals."
              ::= { prtDs3IntervalEntry 5 }

          prtDs3IntervalRDI OBJECT-TYPE
              SYNTAX  Gauge32
              MAX-ACCESS  read-only
              STATUS  current
              DESCRIPTION
                      "The counter associated with the number of RDI
                      seconds, encountered by a DS3
                      interface in one of the previous 96, individual 15
                      minute, intervals."
              ::= { prtDs3IntervalEntry 6 }

          prtDs3IntervalUAS OBJECT-TYPE
              SYNTAX  Gauge32
              MAX-ACCESS  read-only
              STATUS  current
              DESCRIPTION
                      "The counter associated with the number of UAS,
                      encountered by a DS3
                      interface in one of the previous 96, individual 15
                      minute, intervals."
              ::= { prtDs3IntervalEntry 7 }

          prtDs3IntervalBIP OBJECT-TYPE
              SYNTAX  Gauge32
              MAX-ACCESS  read-only
              STATUS  current
              DESCRIPTION
                      "The counter associated with the number of 
                      BIP errors, encountered by a DS3 
                      interface in one of the previous 96, individual 15
                      minute, intervals."
              ::= { prtDs3IntervalEntry 8 }

          prtDs3IntervalFEBE OBJECT-TYPE
              SYNTAX  Gauge32
              MAX-ACCESS  read-only
              STATUS  current
              DESCRIPTION
                      "The counter associated with the number of 
                      FEBE errors, encountered by a DS3
                      interface in one of the previous 96, individual 15
                      minute, intervals."
              ::= { prtDs3IntervalEntry 9 }

          prtDs3IntervalSLM OBJECT-TYPE
              SYNTAX  Gauge32
              MAX-ACCESS  read-only
              STATUS  current
              DESCRIPTION
                      "The counter associated with the number of SLM
                      seconds, encountered by an E3
                      interface in one of the previous 96, individual 15
                      minute, intervals."
              ::= { prtDs3IntervalEntry 10 }

	 prtDs3IntervalSES OBJECT-TYPE
              SYNTAX  Gauge32
              MAX-ACCESS  read-only
              STATUS  current
              DESCRIPTION
                      "The counter associated with the number of SES
                      encountered by a E3
                      interface in one of the previous 96, individual 15
                      minute, intervals."
	      ::= { prtDs3IntervalEntry 11 }

	 prtDs3IntervalES OBJECT-TYPE
	SYNTAX Gauge32
              MAX-ACCESS  read-only
              STATUS  current
              DESCRIPTION
                      " The number of Errored Seconds, encountered  by a
                      DS3 interface in one of the previous 96, individual 15
                      minute, intervals."
	::= { prtDs3IntervalEntry 12 }

prtDs3IntervalBitParity OBJECT-TYPE
              SYNTAX  Gauge32
              MAX-ACCESS  read-only
              STATUS  current
              DESCRIPTION
                      "Bit Parity Error counter. Relevant to T3 only."
              ::= { prtDs3IntervalEntry 13 }

        prtDs3IntervalPlcpLOF OBJECT-TYPE
              SYNTAX  Gauge32
              MAX-ACCESS  read-only
              STATUS  current
              DESCRIPTION
                      "The counter associated with the number of LOF
                      seconds, encountered by a DS3
                      interface in one of the previous 96, individual 15
                      minute, intervals. This counter is relevant for plcpInternal(5)
                       or plcpExternal(6) configuration If frame types only."
              ::= { prtDs3IntervalEntry 14 }

prtDs3IntervalPlcpRAI OBJECT-TYPE
              SYNTAX  Gauge32
              MAX-ACCESS  read-only
              STATUS  current
              DESCRIPTION
                    "Receiving Yellow/Remote Alarm Indication. This counter is 
                      relevant for PLCP (external/internal) frame types only."
              ::= { prtDs3IntervalEntry 15 }

      prtDs3IntervalPlcpBIP OBJECT-TYPE
              SYNTAX  Gauge32
              MAX-ACCESS  read-only
              STATUS  current
              DESCRIPTION
                    " The counter associated with the number of BIP errors, 
                      encountered by a DS3 interface in the current 15 minute 
                      interval. This counter is relevant for PLCP (external/internal) 
                      frame types only."
              ::= { prtDs3IntervalEntry 16 }

      prtDs3IntervalPlcpFEBE OBJECT-TYPE
              SYNTAX  Gauge32
              MAX-ACCESS  read-only
              STATUS  current
              DESCRIPTION
                    " The counter associated with the number of FEBE
                      errors, encountered by a DS3 interface in the current
                      15 minute interval. This counter is relevant for PLCP
                      (external/internal) frame types only."
              ::= { prtDs3IntervalEntry 17 }

      prtDs3IntervalBPV OBJECT-TYPE
              SYNTAX  Gauge32
              MAX-ACCESS  read-only
              STATUS  current
              DESCRIPTION
                    " Number of BPVs (Bi-Polar Violations) , encountered by a 
                      DS3 interface in the specified 15 minute interval. 
                      This object is relevant only for Electrical Line
                      of Fomi-E3/T3."
              ::= { prtDs3IntervalEntry 18 }

      prtDs3IntervalLCE OBJECT-TYPE
              SYNTAX  Gauge32
              MAX-ACCESS  read-only
              STATUS  current
              DESCRIPTION
                    " Number of LCE (Link Code Errors) encountered 
                      by a DS3 interface in the specified 15 minute interval. 
                      This object is relevant only for Optical Links
                      of Fomi-E3/T3."
              ::= { prtDs3IntervalEntry 19 }


     prtDs3IntervalStatus OBJECT-TYPE
	          SYNTAX OCTET STRING  (SIZE (4))
              MAX-ACCESS  read-only
              STATUS  current
              DESCRIPTION
                      "The statuses of the current interval:
                        0 - Valid.
                        1 - redundantLinkSwitch - the link has been switched 
                            by a redundancy mechanism.
                        2 - discontinuity - module was partialy out.
                        4 - notValid - module is out."
              ::= { prtDs3IntervalEntry 20 }

-- the DS3 Total table

prtDs3TotalTable OBJECT-TYPE
              SYNTAX  SEQUENCE OF PrtDs3TotalEntry
              MAX-ACCESS  not-accessible
              STATUS  current
              DESCRIPTION
              " A list of Total entries."
              ::= { prtDs3PerfHistory 4 }

prtDs3TotalEntry OBJECT-TYPE
              SYNTAX  PrtDs3TotalEntry
              MAX-ACCESS  not-accessible
              STATUS  current
              DESCRIPTION
              "An entry of Total table."
              INDEX   { ifIndex }
              ::= { prtDs3TotalTable 1 }

PrtDs3TotalEntry     ::=
          SEQUENCE {
       	    prtDs3TotalUAS	Gauge32,
        	prtDs3TotalBPV	Gauge32,
            prtDs3TotalLCE  Gauge32,
			prtDs3TotalSES  Gauge32
            }

prtDs3TotalUAS OBJECT-TYPE
              SYNTAX  Gauge32
              MAX-ACCESS  read-only
              STATUS  current
              DESCRIPTION
              "Number of UASs (Unavailable Seconds) , encountered by a 
               DS3 interface in the previous 96 intervals.
               Invalid 15 minute intervals count as 0."
              ::= { prtDs3TotalEntry 6 }

prtDs3TotalBPV OBJECT-TYPE
              SYNTAX  Gauge32
              MAX-ACCESS  read-only
              STATUS  current
              DESCRIPTION
              "Number of BPVs (Bi-Polar Violations) , encountered by a 
               DS3 interface in the previous 96 intervals.
               Invalid 15 minute intervals count as 0."
              ::= { prtDs3TotalEntry 17 }

prtDs3TotalLCE OBJECT-TYPE
              SYNTAX  Gauge32
              MAX-ACCESS  read-only
              STATUS  current
              DESCRIPTION
              "Number of LCE (Link Code Errors) encountered 
               by a DS3 interface in the previous 96 intervals.
               Invalid 15 minute intervals count as 0."
              ::= { prtDs3TotalEntry 18 }
   
prtDs3TotalSES OBJECT-TYPE
              SYNTAX  Gauge32
              MAX-ACCESS  read-only
              STATUS  current
              DESCRIPTION
              "Number of SES (Severely Errored Seconds) encountered 
               by a DS3 interface in the previous 96 intervals.
               Invalid 15 minute intervals count as 0."
              ::= { prtDs3TotalEntry 19 } 


dsx3XConfigTable  OBJECT-TYPE
       SYNTAX      SEQUENCE OF Dsx3XConfigEntry
       MAX-ACCESS  not-accessible
       STATUS      current
       DESCRIPTION
       "An extension to the DS3 Configuration table."
       ::= { ds3Interface 2 }

dsx3XConfigEntry OBJECT-TYPE
       SYNTAX  Dsx3XConfigEntry 
       MAX-ACCESS  not-accessible
       STATUS      current
       DESCRIPTION
       "An entry containing additional configuration
        parameters."
       AUGMENTS    { dsx3ConfigEntry }
      --  INDEX   {dsx3LineIndex }
       ::= { dsx3XConfigTable 1 }

Dsx3XConfigEntry      ::=
       SEQUENCE {
         dsx3AisEnable				INTEGER,
		 dsx3TxClockSource			INTEGER
		        }

dsx3AisEnable  OBJECT-TYPE
       SYNTAX  INTEGER {
	   notApplicable(1),
       disable(2),
	   enable(3)
       }
	   MAX-ACCESS  read-write
	   STATUS  current
	   DESCRIPTION
	   "Enable/ disable AIS transmit when Ethernet (for TDMoIP) line is disconnected."
	   ::= { dsx3XConfigEntry 1 }

dsx3TxClockSource OBJECT-TYPE
     SYNTAX  INTEGER {
                loopTiming(1),
                localTiming(2),
                throughTiming(3),
                system (4)
            }
     MAX-ACCESS  read-write
     STATUS  current
     DESCRIPTION
            "The source of Transmit Clock.

            loopTiming indicates that the recovered receive
            clock is used as the transmit clock.

            localTiming indicates that a local clock source is
            used or that an external clock is attached to the
            box containing the interface.

            throughTiming indicates that transmit clock is
            derived from the recovered receive clock of
            another DS3 interface.

            'system' indicates that the system clock 
            is used as the transmit clock."

     ::= { dsx3XConfigEntry 2}


-- The DS3/E3 Mapping Table

dsx3MappingTable OBJECT-TYPE
    SYNTAX  SEQUENCE OF Dsx3MappingEntry
    MAX-ACCESS  not-accessible
    STATUS  current
    DESCRIPTION
            "The DS3/E3 mapping table associates DS3/E3 channels
             with logical or physical interfaces.

            For example, consider a DS3 device with 16 T1's and 1 VCG.
			There are 28 logical/internal channels, numbered 1 through 28
			but only 17 are actually connected.

			We might describe the allocation of channels, in the dsx3MappingTable, as
            follows:
            dsx3MappingIfIndex.1. 1 = 1001  dsx3MappingIfIndex.1.15 = 1015
            dsx3MappingIfIndex.1. 2 = 1002  dsx3MappingIfIndex.1.16 = 1016
            dsx3MappingIfIndex.1. 3 = 1003  dsx3MappingIfIndex.1.17 = 1017
            dsx3MappingIfIndex.1. 4 = 1004  dsx3MappingIfIndex.1.18 =  0
            dsx3MappingIfIndex.1. 5 = 1005  dsx3MappingIfIndex.1.19 =  0
            dsx3MappingIfIndex.1. 6 = 1006  dsx3MappingIfIndex.1.20 =  0
            dsx3MappingIfIndex.1. 7 = 1007  dsx3MappingIfIndex.1.21 =  0
            dsx3MappingIfIndex.1. 8 = 1008  dsx3MappingIfIndex.1.22 =  0
            dsx3MappingIfIndex.1. 9 = 1009  dsx3MappingIfIndex.1.23 =  0
            dsx3MappingIfIndex.1.10 = 1010  dsx3MappingIfIndex.1.24 =  0
            dsx3MappingIfIndex.1.11 = 1011  dsx3MappingIfIndex.1.25 =  0
            dsx3MappingIfIndex.1.12 = 1012  dsx3MappingIfIndex.1.26 =  0
            dsx3MappingIfIndex.1.13 = 1013  dsx3MappingIfIndex.1.27 =  0
            dsx3MappingIfIndex.1.14 = 1014  dsx3MappingIfIndex.1.28 =  0
            
			Note that in the case above all channels are mapped to one T3 port with ifIndex = 1.
			The Channels 1...28 are represented via the 2nd index.
			The values of 1001...1016 are the T1 interface ifIndexes.
			The value of 1017 is the ifIndex of the VCG.
		    Unconnected channels have a value of 0.			
            "
     ::= { ds3Interface 3 }

dsx3MappingEntry OBJECT-TYPE
     SYNTAX  Dsx3MappingEntry
     MAX-ACCESS  not-accessible
     STATUS  deprecated
     DESCRIPTION
                    "An entry in the DS3 mapping table."
    INDEX   { dsx3MappingDs3Index, dsx3MappingNumber }
    ::= { dsx3MappingTable 1 }

Dsx3MappingEntry ::=
     SEQUENCE {
         dsx3MappingDs3Index     InterfaceIndex,
         dsx3MappingNumber       Unsigned32,
         dsx3MappingIfIndex      InterfaceIndex
    }

dsx3MappingDs3Index OBJECT-TYPE
    SYNTAX  InterfaceIndex
    MAX-ACCESS  not-accessible
    STATUS  current
    DESCRIPTION
            "The index value which uniquely identifies  the
            DS3/E3 interface to which this entry is applicable.
			This value is also equal to dsx3LineIndex used in dsx3ConfigEntry.
                        
            For RICi-16 this is the ifIndex of the T3 interface."
    ::= { dsx3MappingEntry 1 }

dsx3MappingNumber OBJECT-TYPE
    SYNTAX  Unsigned32
    MAX-ACCESS  not-accessible
    STATUS  current
    DESCRIPTION
            "The channel number for this entry.
            
            For RICi-16 this is the channel number 1...28."
   ::= { dsx3MappingEntry 2 }

dsx3MappingIfIndex OBJECT-TYPE
   SYNTAX  InterfaceIndex
   MAX-ACCESS  read-write
   STATUS  current
   DESCRIPTION
           "An index value that uniquely identifies a logical or physical
           interface mapped to a DS3/E3 channel.
           If no interface is currently using a channel, the value should be zero.
           If a single interface occupies more  than one channel,
           that ifIndex value will be found in multiple channels.
           
           For RICi-16 this is the ifIndex of the T1 or VCG interface."
   ::= { dsx3MappingEntry 3 }


-- END
-- 
-- file :D:\Synergy\WorkArea\545\mib_rad\txt\radima.txt
-- 
-- RAD-IMA-MIB DEFINITIONS ::= BEGIN

--Title:    RAD-IMA   MIB
--
-- Copyright 1998 RAD Data Communications, Ltd.
-- All Rights Reserved.  

-- IMPORTS

--      OBJECT-TYPE                     FROM RFC-1212
 --     radWan                          FROM RAD-GEN-MIB;
--                RAD-IMA MIB   

--Title:     RAD's IMA INTERFACE MIB
--Version:   1.0
--Date:      15.09.98
--By:        Ilana Schvetz
--File:      radima.mib

--Last update: 15-Nov-2007 by Shay Harari

radAtmIma  OBJECT IDENTIFIER  ::=  {radAtm 5}

imaPrimaryClk     OBJECT-TYPE
              SYNTAX  INTEGER { 
                             notApplicable(1),           
		                     link1(2),
		                     link2(3),
		                     link3(4),
		                     link4(5),
		                     automatic(6)
              }
              MAX-ACCESS  read-write
              STATUS  current
              DESCRIPTION 
                       "Clock source to be transmitted to the user side, 
                        where user module is in 'External' clock source."
             ::= { radAtmIma 1 }

-- An extension to the Link Table


imaXLinkTable  OBJECT-TYPE
       SYNTAX      SEQUENCE OF ImaXLinkEntry
       MAX-ACCESS  	   not-accessible
       STATUS      current
       DESCRIPTION
               "The IMA Link Status and Configuration table.
                This table contains additional objects for the link table."
       ::= { radAtmIma 2 }

imaXLinkEntry  OBJECT-TYPE
       SYNTAX  	   ImaXLinkEntry 
       MAX-ACCESS  	   not-accessible
       STATUS      current
       DESCRIPTION
               "An entry in the IMA Link table."
 --      AUGMENTS    { imaLinkTable }
         INDEX   { imaLinkIfIndex }
       ::= { imaXLinkTable 1 }

ImaXLinkEntry     ::=
      SEQUENCE {
        imaLinkDirection		    INTEGER,
        imaLinkItcLBClkSrc			INTEGER,
		imaLinkActivation			INTEGER
}



imaLinkDirection  OBJECT-TYPE
              	SYNTAX  INTEGER { 
	                    	rx(1),
							tx(2),
							both(3)
	 			}
              	MAX-ACCESS  read-write
              	STATUS  current
              	DESCRIPTION
                      "the Link direction."
--	        	DEFAULT { both }	
              ::= { imaXLinkEntry 1 }

imaLinkItcLBClkSrc OBJECT-TYPE
              	SYNTAX  INTEGER { 
							link1(1),
							link2(2),
							link3(3),
							link4(4),
							internal (5),
							external (6),
							automatic(7),
							loopback (8)
	 			}
              	MAX-ACCESS  read-write
              	STATUS  current
              	DESCRIPTION
              	 		"Clock source for the current Tx-line."  
              ::= { imaXLinkEntry 2 }


imaLinkActivation OBJECT-TYPE
              	SYNTAX  INTEGER { 
							notApplicable (1),
							down(2),
							up(3)
	 			}
              	MAX-ACCESS  read-write
              	STATUS  current
              	DESCRIPTION
              	 		"IMA Link activation at ATM layer."  
              ::= { imaXLinkEntry 3 }



-- An extension to the Group Table


imaXGroupTable  OBJECT-TYPE
       SYNTAX      SEQUENCE OF ImaXGroupEntry
       MAX-ACCESS  	   not-accessible
       STATUS      current
       DESCRIPTION
               "The IMA group Status and Configuration table.
                This table contains additional objects for the Group table."
       ::= { radAtmIma 3 }

imaXGroupEntry  OBJECT-TYPE
       SYNTAX  	   ImaXGroupEntry 
       MAX-ACCESS  	   not-accessible
       STATUS      current
       DESCRIPTION
               "An entry in the IMA Group table."
 --      AUGMENTS    { imaGroupTable }
         INDEX   { imaGroupIndex }
       ::= { imaXGroupTable 1 }

ImaXGroupEntry     ::=
      SEQUENCE {
		imaGroupVersion				INTEGER,
        imaGroupCtcTxClkSrc			INTEGER,
        imaGroupCtcTxClkSrcPort		Integer32,
		imaGroupRestart				INTEGER,
		imaGroupType				INTEGER
      }


imaGroupVersion     OBJECT-TYPE
              SYNTAX  INTEGER { 
                             ver10(1),           
		                     ver11(2)
              }
              MAX-ACCESS  read-write
              STATUS  current
              DESCRIPTION 
                       "IMA Version."
             ::= { imaXGroupEntry 1 }

imaGroupCtcTxClkSrc OBJECT-TYPE
              	SYNTAX  INTEGER { 
							link1     (1),
							link2     (2),
							link3     (3),
							link4     (4),
							internal  (5),           
							external  (6),
							automatic (7),           
							loopback  (8),           

							notApplicable(255)           
	 			}
              	MAX-ACCESS  read-write
              	STATUS  current
              	DESCRIPTION
              	 		"The source of the transmitted, common, Clock Source.
						 Applicable if imaGroupNeTxClkMode=ctc(1).
                         Automatic - Dynamic source, taken from the currently reference link. 
                         Internal  - taken from the Internal clock on card.
                         Loopback  - Looped back from one of the ports. In this case a specific 
                                     port should be selected for imaGroupCtcTxClkSrcPort parameter.
                         Link N    - Clock will be looped from one of the links."  
               ::= { imaXGroupEntry 2 }

imaGroupCtcTxClkSrcPort OBJECT-TYPE
               SYNTAX  Integer32
               MAX-ACCESS  read-write
               STATUS  current
               DESCRIPTION
                       "This parameter is valid only when imaGroupCtcTxClkSrc=loopback.
                        The value may be any port identifier."
               ::= { imaXGroupEntry 3 }

imaGroupRestart     OBJECT-TYPE
              SYNTAX  INTEGER { 
						off		(1),           
						on		(2)
              }
              MAX-ACCESS  read-write
              STATUS  current
              DESCRIPTION 
                       "off(1)-	default state.
								After on(2) operation ends, value should be automatically
								set to off(1).
                        on(2) - restarts the IMA Group State Machine (GSM)
                       			and the Rx\Tx Link State Machines (Rx/Tx LSM)."
             ::= { imaXGroupEntry 4 }

imaGroupType     OBJECT-TYPE
              SYNTAX  INTEGER { 
						notApplicable	(1),           
						e1t1			(2),
						shdsl			(3)
              }
              MAX-ACCESS  read-write
              STATUS  current
              DESCRIPTION 
				"This parameter defines the Type of IMA Group
				 (which determines its Links Type)."
             ::= { imaXGroupEntry 5 }


-- IMA Traps

--NOTIFICATIONS

atmImaGroupStatusChangeTrap NOTIFICATION-TYPE
      OBJECTS  { imaGroupFailureStatus }  
      STATUS  current
      DESCRIPTION
	  	"This trap indicates IMA Group status change."
	::= { radSysAtmEvents 80 }

-- 
-- file :D:\Synergy\WorkArea\545\mib_rad\txt\radhdlc.txt
-- 
-- RAD-HDLC-MIB DEFINITIONS ::= BEGIN

--Title:    RAD-HDLC   MIB
--
-- Copyright 1998 RAD Data Communications, Ltd.
-- All Rights Reserved.  


--Title:     RAD's HDLC MIB
--Version:   1.0
--Date:      15.09.98
--By:        Ilana Schvetz
--File:      radhdlc.mib
--
-- Last Update: 10-Aug-05 By Shay Harari

hdlcMibObjects  OBJECT IDENTIFIER  ::=  {diverseIfWanGen 5}

hdlcTable  OBJECT-TYPE
       SYNTAX      SEQUENCE OF HdlcEntry
       MAX-ACCESS  	   not-accessible
       STATUS      current
       DESCRIPTION
               	"The HDLC configuration table."
       ::= { hdlcMibObjects 1 }

hdlcEntry  OBJECT-TYPE
       SYNTAX  	   HdlcEntry 
       MAX-ACCESS  	   not-accessible
       STATUS      current
       DESCRIPTION
				"Defines the contents of each line in the RAD HDLC Table."
       INDEX   { ifIndex }
       ::= { hdlcTable 1 }

HdlcEntry     ::=
      SEQUENCE {
        hdlcProtocol				INTEGER,
        hdlcRateResolution			INTEGER,
        hdlcTxClockSource			INTEGER,
        hdlcTerminalMode			INTEGER,
        hdlcLoopbackState			INTEGER,
        hdlcTxClockPolarity			INTEGER,
        hdlcFlowControl				INTEGER,
        hdlcLineRate				Integer32,
        hdlcRxClockMode				INTEGER,
        hdlcLOF						Gauge32,
        hdlcRxClockPolarity			INTEGER,
		hdlcRateCompatibility		INTEGER
}


hdlcProtocol     OBJECT-TYPE
      SYNTAX  INTEGER { 
         notApplicable	(1),           
         v35			(2),
         x21			(3),
         rs530			(4),
 	     cisco 			(5),
 	     lapd			(6), 
		 laps			(7), -- x86
		 proprietary	(8),
		 gfp			(9)
      }
      MAX-ACCESS  read-write
      STATUS  current
      DESCRIPTION 
       "The HDLC protocol type
        V35			- HDLC encapsulated over V35
        X21			- HDLC encapsulated over X21
        RS530		- HDLC encapsulated over RS530
        cisco		- Compatible to Cisco HDLC format.
        lapd		- LAPD over HDLC.
        laps		- LAPS over HDLC.
        proprietary	- HDLC Proprietary.
        gfp			- General Framing Protocol."
      ::= { hdlcEntry 1 }
  
hdlcRateResolution  OBJECT-TYPE
     SYNTAX INTEGER {
     	notApplicable(1),
     	nx56Kbps(2),
     	nx64Kbps(3)
     }
     MAX-ACCESS  read-write
     STATUS  current
     DESCRIPTION
	  "The baud rate of the internal clock."
     ::= { hdlcEntry 2 }

hdlcTxClockSource  OBJECT-TYPE
     SYNTAX INTEGER {
     	internal(1),
     	external(2)
     }
     MAX-ACCESS  read-write
     STATUS  current
     DESCRIPTION
	   "The baud rate of the internal clock."
     ::= { hdlcEntry 3 }

hdlcTerminalMode  OBJECT-TYPE
     SYNTAX INTEGER {
     	 dce(1),
     	 dte(2)
     }
     MAX-ACCESS  read-write
     STATUS  current
     DESCRIPTION
	 	"."
     ::= { hdlcEntry 4 }

hdlcLoopbackState OBJECT-TYPE
      SYNTAX  INTEGER { 
         notApplicable(1),           
      	 internal(2), 
      	 external(3), 
      	 disable(4) 
      }
      MAX-ACCESS  read-write
      STATUS  current
      DESCRIPTION
        "internal - All data coming from the 
        		network port is looped back
         external - All data comming from the line is 
        			looped back."
      ::= { hdlcEntry 5 }

hdlcTxClockPolarity  OBJECT-TYPE
      SYNTAX INTEGER {
      	 normal (1),
      	 inverse(2)
      }
      MAX-ACCESS  read-write
      STATUS  current
      DESCRIPTION
	  	 "normal  - The transmitted data is sampled at the middle of bit time
	  	  inverse - The transmitted data is sampled at the end of the bit time 
	  	   			(high data rate/long cable)."
      ::= { hdlcEntry 6 }

hdlcFlowControl  OBJECT-TYPE
      SYNTAX INTEGER {
      	 disable(1),
      	 enable (2)
      }
      MAX-ACCESS  read-write
      STATUS  current
      DESCRIPTION
	  	 "Enable/Disable the CTS/RTS flow control signals."
      ::= { hdlcEntry 7 }

hdlcLineRate  OBJECT-TYPE
     SYNTAX Integer32     		
     MAX-ACCESS  read-write
     STATUS  current
     DESCRIPTION
	   "The rate values for HDLC are n*56/64Kbps, where 1<=n<=32, 64, 128
	    and the following values: 1544, 3088, 6176.
	    The rate values for HSSI is nMbps, where 1<=n<=52."
     ::= { hdlcEntry 8 }

hdlcRxClockMode  OBJECT-TYPE
     SYNTAX INTEGER {
	 	notApplicable(1),
     	internal     (2),
     	external     (3)
     }
     MAX-ACCESS  read-write
     STATUS  current
     DESCRIPTION
	 	"."
     ::= { hdlcEntry 9 }

hdlcLOF  OBJECT-TYPE
    SYNTAX 	Gauge32
    MAX-ACCESS  read-only
    STATUS  current
    DESCRIPTION
	  "Total number of seconds the port is in Loss Of Frame state."
    ::= { hdlcEntry 10 }

hdlcRxClockPolarity  OBJECT-TYPE
    SYNTAX INTEGER {
      normal (1),
      inverse(2)
    }
    MAX-ACCESS  read-write
    STATUS  current
    DESCRIPTION
	  "normal  - The received data is sampled at the middle of bit time
	   inverse - The received data is sampled at the end of the bit time 
	   			(high data rate/long cable)."
    ::= { hdlcEntry 11 }

hdlcRateCompatibility  OBJECT-TYPE
    SYNTAX INTEGER {
	 	notApplicable(1),
     	disable     (2),
     	enable      (3)
     }
    MAX-ACCESS  read-write
    STATUS  current
    DESCRIPTION
	  "This parameter defines whether limit the port HDLC rate according to the Far-End device.
	   For exaple: limit the HDLC rate from 4000 PPS and 3000 PPS."
    ::= { hdlcEntry 12 }

hdlcPerformance  OBJECT IDENTIFIER  ::=  {hdlcMibObjects 2}


hdlcCurrentTable OBJECT-TYPE
      SYNTAX  SEQUENCE OF HdlcCurrentEntry
      MAX-ACCESS   not-accessible
      STATUS  current
      DESCRIPTION
         "The HDLC Current table."
      ::= { hdlcPerformance 1 }

hdlcCurrentEntry OBJECT-TYPE
      SYNTAX  HdlcCurrentEntry
      MAX-ACCESS  not-accessible
      STATUS  current
      DESCRIPTION
         "An entry in the HDLC Current table."
      INDEX   { hdlcCurrentIfIndex }
      ::= { hdlcCurrentTable 1 }

HdlcCurrentEntry ::=
      SEQUENCE {
      hdlcCurrentIfIndex
           Integer32,
	  hdlcCurrentStatus
	       OCTET STRING,
      hdlcCurrentLOF
      	   Gauge32,
      hdlcCurrentInFrames
           Gauge32,
      hdlcCurrentInErrors
           Gauge32,
      hdlcCurrentOutFrames
           Gauge32,
      hdlcCurrentAbortedFrames
           Gauge32,
      hdlcCurrentLengthError
           Gauge32
      }

hdlcCurrentIfIndex OBJECT-TYPE
      SYNTAX      Integer32
      MAX-ACCESS  read-only
      STATUS      current
      DESCRIPTION
        "The index of the HDLC interface. 
        It may be ifIndex."
    ::= { hdlcCurrentEntry 1 }

hdlcCurrentStatus OBJECT-TYPE
	 SYNTAX OCTET STRING  (SIZE (4))
     MAX-ACCESS  read-only
     STATUS  current
     DESCRIPTION
      "The statuses of the current interval:
         0 - Valid.
         1 - redundantLinkSwitch - the link has been switched 
             by a redundancy mechanism.
         2 - discontinuity - module was partialy out.
         4 - notValid - module is out."
      ::= { hdlcCurrentEntry 2 }

hdlcCurrentLOF OBJECT-TYPE
      SYNTAX  Gauge32  
      MAX-ACCESS  read-only
      STATUS  current
      DESCRIPTION
	  "The counter associated with the number of seconds the 
	   port is in Loss Of Frame state, encountered 
       by the HDLC interface in the current 15 minute interval."
      ::= { hdlcCurrentEntry 3 }

hdlcCurrentInFrames OBJECT-TYPE
      SYNTAX  Gauge32  
      MAX-ACCESS  read-only
      STATUS  current
      DESCRIPTION
	  "The counter associated with the number of received frames, 
	  encountered by the HDLC interface in the current 15 minute 
	  interval."
      ::= { hdlcCurrentEntry 4 }

hdlcCurrentInErrors OBJECT-TYPE
      SYNTAX  Gauge32  
      MAX-ACCESS  read-only
      STATUS  current
      DESCRIPTION
	  "The counter associated with the number of Errored received 
	  frames, encountered by the HDLC interface in the current 15 
	  minute interval."
      ::= { hdlcCurrentEntry 5 }

hdlcCurrentOutFrames OBJECT-TYPE
      SYNTAX  Gauge32  
      MAX-ACCESS  read-only
      STATUS  current
      DESCRIPTION
	  "The counter associated with the number of transmitted frames, 
	  encountered by the HDLC interface in the current 15 minute 
	  interval."
      ::= { hdlcCurrentEntry 6 }

hdlcCurrentAbortedFrames OBJECT-TYPE
      SYNTAX  Gauge32  
      MAX-ACCESS  read-only
      STATUS  current
      DESCRIPTION
	  "The counter associated with the number of frames, in which    
	  at least seven consecutive '1'-s (Abort sequence) were 
	  encountered by the HDLC interface in the current 15 minute 
	  interval."
      ::= { hdlcCurrentEntry 7 }

hdlcCurrentLengthError OBJECT-TYPE
      SYNTAX  Gauge32  
      MAX-ACCESS  read-only
      STATUS  current
      DESCRIPTION
	  "The counter associated with the number of received frames 
	  with length error, encountered by the HDLC interface in the 
	  current 15 minute interval."
      ::= { hdlcCurrentEntry 8 }


--Interval Table


hdlcIntervalTable OBJECT-TYPE
      SYNTAX  SEQUENCE OF HdlcIntervalEntry
      MAX-ACCESS   not-accessible
      STATUS  current
      DESCRIPTION
         "The HDLC Interval table."
      ::= { hdlcPerformance 2 }

hdlcIntervalEntry OBJECT-TYPE
      SYNTAX  HdlcIntervalEntry
      MAX-ACCESS  not-accessible
      STATUS  current
      DESCRIPTION
         "An entry in the HDLC Interval table."
              INDEX   { hdlcIntervalIfIndex, hdlcIntervalNumber }
              ::= { hdlcIntervalTable 1 }

HdlcIntervalEntry ::=
      SEQUENCE {
      hdlcIntervalIfIndex
           Integer32,
      hdlcIntervalNumber
           Integer32,
	  hdlcIntervalStatus
	       OCTET STRING,
      hdlcIntervalLOF
      	   Gauge32,
      hdlcIntervalInFrames
           Gauge32,
      hdlcIntervalInErrors
           Gauge32,
      hdlcIntervalOutFrames
           Gauge32,
      hdlcIntervalAbortedFrames
           Gauge32,
      hdlcIntervalLengthError
           Gauge32
      }

hdlcIntervalIfIndex OBJECT-TYPE
    SYNTAX      Integer32
    MAX-ACCESS  read-only
    STATUS      current
    DESCRIPTION
        "The index of the HDLC interface. 
        It may be ifIndex."
    ::= { hdlcIntervalEntry 1 }

hdlcIntervalNumber OBJECT-TYPE
    SYNTAX  Integer32 (1..96)
    MAX-ACCESS  read-only
    STATUS  current
    DESCRIPTION
        "A number between 1 and 96, where 1 is the most
         recently completed 15 minute interval and 96 is
         the least recently completed 15 minutes interval
         (assuming that all 96 intervals exist)."
    ::= { hdlcIntervalEntry 2 }

hdlcIntervalStatus OBJECT-TYPE
	 SYNTAX OCTET STRING  (SIZE (4))
     MAX-ACCESS  read-only
     STATUS  current
     DESCRIPTION
      "The statuses of the current interval:
         0 - Valid.
         1 - redundantLinkSwitch - the link has been switched 
             by a redundancy mechanism.
         2 - discontinuity - module was partialy out.
         4 - notValid - module is out."
      ::= { hdlcIntervalEntry 3 }

hdlcIntervalLOF OBJECT-TYPE
      SYNTAX  Gauge32  
      MAX-ACCESS  read-only
      STATUS  current
      DESCRIPTION
	  "The counter associated with the number of seconds the 
	  port is in Loss Of Frame state, encountered by an HDLC 
	  interface in one of the previous 96, individual 15 minute, 
	  intervals."
      ::= { hdlcIntervalEntry 4 }

hdlcIntervalInFrames OBJECT-TYPE
      SYNTAX  Gauge32  
      MAX-ACCESS  read-only
      STATUS  current
      DESCRIPTION
	  "The counter associated with the number of received frames,
	   encountered by the HDLC interface in one of the previous 96, 
	   individual 15 minute, intervals."
      ::= { hdlcIntervalEntry 5 }

hdlcIntervalInErrors OBJECT-TYPE
      SYNTAX  Gauge32  
      MAX-ACCESS  read-only
      STATUS  current
      DESCRIPTION
	  "The counter associated with the number of Errored received 
	  frames, encountered by the HDLC interface in one of the 
	  previous 96, individual 15 minute, intervals."
      ::= { hdlcIntervalEntry 6 }

hdlcIntervalOutFrames OBJECT-TYPE
      SYNTAX  Gauge32  
      MAX-ACCESS  read-only
      STATUS  current
      DESCRIPTION
	  "The counter associated with the number of transmitted 
	  frames, encountered by the HDLC interface in one of 
	  the previous 96, individual 15 minute, intervals."
      ::= { hdlcIntervalEntry 7 }
 
hdlcIntervalAbortedFrames OBJECT-TYPE
      SYNTAX  Gauge32  
      MAX-ACCESS  read-only
      STATUS  current
      DESCRIPTION
	  "The counter associated with the number of frames, in which    
	  at least seven consecutive '1'-s (Abort sequence) were 
	  encountered by the HDLC interface in one of the previous 96, 
	  individual 15 minute, intervals."
      ::= { hdlcIntervalEntry 8 }

hdlcIntervalLengthError OBJECT-TYPE
      SYNTAX  Gauge32  
      MAX-ACCESS  read-only
      STATUS  current
      DESCRIPTION
	  "The counter associated with the number of received frames 
	  with length error, encountered by the HDLC interface in 
	  one of the previous 96, individual 15 minute, intervals."
      ::= { hdlcIntervalEntry 9 }

-- 
-- file :D:\Synergy\WorkArea\545\mib_rad\txt\sigmon.txt
-- 

--Version:   1.0
--Date:      2.02.99              
--By:       Ilana Schvetz
--File:     sigmon.txt
--
--Last Update: Ilana Schvetz  19.12.99


radAtmSignalingMonitor  OBJECT IDENTIFIER  ::=  {radAtm 6 }

smSVCOperState  OBJECT-TYPE
              SYNTAX  INTEGER {
                  disable (1),
                  enable  (2)
              }
              MAX-ACCESS  read-only
              STATUS  current
              DESCRIPTION
                  "The SVC monitoring operational state."
--            DEFVAL { disable }
              ::= { radAtmSignalingMonitor 1 } 

smSVCAdminStatus  OBJECT-TYPE
              SYNTAX  INTEGER {
                  disable (1),
                  enable  (2)
              }
              MAX-ACCESS  read-write
              STATUS  current
              DESCRIPTION
                  "The SVC monitoring status."
--            DEFVAL { disable }
              ::= { radAtmSignalingMonitor 2 } 

smILMIMode    OBJECT-TYPE
              SYNTAX  INTEGER {
                  disable       (1),
                  keepAliveOnly (2),
                  enable        (3)
              }
              MAX-ACCESS  read-write
              STATUS  current
              DESCRIPTION
                  "The ILMI operational Mode."
--            DEFVAL { disable }
              ::= { radAtmSignalingMonitor 3 } 


smILMIStatus  OBJECT-TYPE
              SYNTAX  INTEGER {
                  down    (1),
                  up      (2),
                  disable (3)
              }
              MAX-ACCESS  read-only
              STATUS  current
              DESCRIPTION
                  "ILMI protocol status (VCC 0,16)."
              ::= { radAtmSignalingMonitor 4 } 

smUNIVersion  OBJECT-TYPE
              SYNTAX  INTEGER {
                  uni3-0(1),
                  uni3-1(2)
              }
              MAX-ACCESS  read-write
              STATUS  current
              DESCRIPTION
                  "The UNI version that is used by both sides."
--            DEFVAL { UNI3_1 }
              ::= { radAtmSignalingMonitor 5 } 

smPolicing  OBJECT-TYPE
              SYNTAX  INTEGER {
                  none(1),
                  police(2),
                  monitoring(3)
              }
              MAX-ACCESS  read-write
              STATUS  current
              DESCRIPTION
                 "The type of the police action performed on 
                  the cells transmitted from the user side to
                  the network side."
--            DEFVAL { none }
              ::= { radAtmSignalingMonitor 6 } 

smSAALStatus  OBJECT-TYPE
              SYNTAX  INTEGER {
                  down (1),
                  up   (2)
              }
              MAX-ACCESS  read-only
              STATUS  current
              DESCRIPTION
                  "Signaling data link (VCC 0,5) status."
              ::= { radAtmSignalingMonitor 7 } 


-- SM Counters
smOpenedSesssions  OBJECT-TYPE
              SYNTAX  Gauge32
              MAX-ACCESS  read-only
              STATUS  current
              DESCRIPTION
                  "The number of SVC sessions currently opened."
              ::= { radAtmSignalingMonitor 8 }

smUserRejectedSessions  OBJECT-TYPE
              SYNTAX  Gauge32
              MAX-ACCESS  read-only
              STATUS  current
              DESCRIPTION
                  "The number of sessions that the user side rejected
                  to open."
              ::= { radAtmSignalingMonitor 9 }

smNetworkRejectedSessions  OBJECT-TYPE
              SYNTAX  Gauge32
              MAX-ACCESS  read-only
              STATUS  current
              DESCRIPTION
                  "The number of sessions that the Network side rejected."
              ::= { radAtmSignalingMonitor 10 }

smHostRejectedSessions  OBJECT-TYPE
              SYNTAX  Gauge32
              MAX-ACCESS  read-only
              STATUS  current
              DESCRIPTION
                  "The number of sessions that the device rejected
                  to open."
              ::= { radAtmSignalingMonitor 11 }
                                    
smVclILMISessionVpi    OBJECT-TYPE
              SYNTAX    Integer32  (0..255)
              MAX-ACCESS    read-write
              STATUS    current
              DESCRIPTION
                   "ILMI Keep alive session VPI channel.
                   Default: 0. (VCI=16, fixed)."
              ::= { radAtmSignalingMonitor 12 }

-- 
-- file :D:\Synergy\WorkArea\545\mib_rad\txt\sub_rtr.txt
-- 
-- version 5.25
-- file :sub_rtr.txt
-- 
--RTR-MIB  
--
--Last update: 14-Aug-2008 by Shay Harari 

--radRouter         OBJECT IDENTIFIER ::= { rad 11 }  RAD Router

-- ************************************************
-- Interfaces Group
-- Link Layer (layer 2) Configuration MIB
-- ************************************************

-- The following MIB group is used by the Management/Configuration
-- station to configure the device interfaces,
-- physicals as well as virtuals.
-- Each entry in the rtrDynamicIfConfigTable should have one of 
-- the extended rtType.
-- It will also have a corresponding entry in the standard iftable.
-- The implementation uses these inputs to build the interface 
-- layer of the device. The output is reflected in the
-- ifTable and ifStackTable which are implementation dependent.
 

rtrInterfaces  OBJECT IDENTIFIER  ::= { radRouter 1 }

RtrIfConfigTYPE ::= INTEGER
--      STATUS  current
--       DESCRIPTION
--           "This type defines what type of sub-layer is used 
--            in each entr of rtrDynamicIfConfigTable.
--            It should contain values from IANAifType
--            type for standard sub-layer, and values (starting from 999 
--            decimal) for private sub-layers.
--            The values of the ifType field in ifTable should be taken 
--            from IANAifType only."
           {
            other(1),
            ethernetLan(6),          -- From IANAifType
            iso88023Csmacd(7),
            tokenRingLan(9),
            fddi(15),
            basicISDN(20),
            primaryISDN(21),
            propPointToPoint(22),    -- rndWAN
            slip(28),
            ppp(23),                 -- From IANAifType
            frameRelay(32),   
            rs232(33),       
            atm(37),
            x25ple(40),
            v35(45),
			fastEther(62),           -- Fast Ethernet (100BaseT)
			fastEtherFX(69),		 -- Fast Ethernet (100BaseFX)
            virtualNet(500),

            cod(1001),               -- Rad/Rnd private
            backUp(1002),            
            dialUp(1004),
            b1isdn(1010),
            b2isdn(1011),
            ipBcst(1020),
            ipPtp(1021),
            ipxRaw(1022),
            ipxEtType(1023),
            ipxLlcSap(1024),
            ipxLlcSnap(1025),
            ipxPtp(1026),
            brgUnder(1027),
            wanDriver(1060),
            ethernetDriver(1061),
            tokenRingDriver(1062),
			fddiDriver     (1064),   -- RAD private FDDI driver
            virtualLan(1080),
            unknown(1100)
          
           }

rtrConfigIfTable  OBJECT-TYPE     
       SYNTAX  SEQUENCE OF RtrConfigIfEntry
       MAX-ACCESS  not-accessible
       STATUS  current
       DESCRIPTION
           "Table of configured interfaces." 
      ::= { rtrInterfaces 1 }

rtrConfigIfEntry  OBJECT-TYPE     
       SYNTAX  RtrConfigIfEntry
       MAX-ACCESS  not-accessible
       STATUS  current
       DESCRIPTION
           "Each entry defines a configured interface." 
       INDEX { rtrConfigIfIndex }
      ::= { rtrConfigIfTable 1 }


RtrConfigIfEntry ::= SEQUENCE {
       rtrConfigIfIndex
           InterfaceIndex,
       rtrConfigIfType
           RtrIfConfigTYPE,
       rtrConfigIfName
           DisplayString,
       rtrConfigIfStatus
           RowStatus
       }

rtrConfigIfIndex   OBJECT-TYPE
       SYNTAX  InterfaceIndex
       MAX-ACCESS  read-only
       STATUS  current
       DESCRIPTION
           "This variable uniquely identifies the interface. 
            It is used as a cross reference in other system tables"
      ::= { rtrConfigIfEntry 1 }

rtrConfigIfType   OBJECT-TYPE
       SYNTAX  RtrIfConfigTYPE
       MAX-ACCESS  read-create
       STATUS  current
       DESCRIPTION
           "This variable identifies the type of the specific 
            entry in the rtrDynamicIfConfigTable.
            This field is writable only at creation time 
            (i.e., when value of status is underCreation)."
       ::= { rtrConfigIfEntry 2 }

rtrConfigIfName   OBJECT-TYPE
       SYNTAX  DisplayString
       MAX-ACCESS  read-create
       STATUS  current
       DESCRIPTION
           "This variable provides a logical name to a specific entry in     
             rtrConfigIfTable. It is also used in identifying the Driver
             interfaces."
      ::= { rtrConfigIfEntry 3 }

rtrConfigIfStatus  OBJECT-TYPE
       SYNTAX  RowStatus
       MAX-ACCESS  read-create
       STATUS  current
       DESCRIPTION
          "The status of the ConfigEntry.  The choices are those 
           defined in SNMPv2-TC. Only: active, createAndWait, and destroy
           will be used.
           active - The conceptual row is available for use by the managed device.
           createAndWait - A new instance of a conceptual row is desired, but
                           not to have it available for use by the managed device.
           destroy - Delete all instances associated with an existing conceptual row."     
       ::= { rtrConfigIfEntry 4 }


-- Router Interface Configuration Table
 
rtrIfCfgTable  OBJECT-TYPE     
       SYNTAX  SEQUENCE OF RtrIfCfgEntry
       MAX-ACCESS  not-accessible
       STATUS  current
       DESCRIPTION
           "Router Interface Configuration Table." 
      ::= { rtrInterfaces 2 }

rtrIfCfgEntry  OBJECT-TYPE     
       SYNTAX  RtrIfCfgEntry
       MAX-ACCESS  not-accessible
       STATUS  current
       DESCRIPTION
           "An entry in the Router Interface Configuration Table." 
       INDEX { rtrIfCfgIndex, rtrIfCfgIpAddress }
      ::= { rtrIfCfgTable 1 }


RtrIfCfgEntry ::= SEQUENCE {
       rtrIfCfgIndex					Integer32,
       rtrIfCfgIpAddress				IpAddress,
       rtrIfCfgRowStatus				RowStatus,
	   rtrIfCfgIpMask					IpAddress,
	   rtrIfCfgIfIndex					Integer32,
	   rtrIfCfgType						INTEGER,
	   rtrIfCfgVlanId					VlanIndex,
	   rtrIfCfgMtu						Integer32,
	   rtrIfCfgName						SnmpAdminString,
	   rtrIfCfgConnectionPointer		RowPointer,
	   rtrIfCfgVlanTagging				INTEGER,
	   rtrIfCfgVlanPriority				Unsigned32,
	   rtrIfCfgParams					Unsigned32,
	   rtrIfCfgMngAccess				INTEGER,
	   rtrIfCfgLlcSnapEncaps			INTEGER,
	   rtrIfCfgDhcp						INTEGER
       }

rtrIfCfgIndex OBJECT-TYPE
       SYNTAX Integer32
       MAX-ACCESS read-only
       STATUS current
       DESCRIPTION
       "This object indicates the Router Interface Index.
        (In some cases it will be equal to the Router Interface ifIndex)."
       ::= { rtrIfCfgEntry 1 }

rtrIfCfgIpAddress OBJECT-TYPE
       SYNTAX IpAddress
       MAX-ACCESS read-only
       STATUS current
       DESCRIPTION
       "IP Address of the Router Interface."
       ::= { rtrIfCfgEntry 2 }

rtrIfCfgRowStatus OBJECT-TYPE
      SYNTAX  RowStatus
      MAX-ACCESS  read-create
      STATUS  current
      DESCRIPTION
      "This object enables the user to 
       create/delete entries of this table."
      ::= { rtrIfCfgEntry 3 }

rtrIfCfgIpMask OBJECT-TYPE
       SYNTAX IpAddress
       MAX-ACCESS read-create
       STATUS current
       DESCRIPTION
           "IP Mask Address Router Interface."
       ::= { rtrIfCfgEntry 4 }

rtrIfCfgIfIndex OBJECT-TYPE
       SYNTAX Integer32
       MAX-ACCESS read-create
       STATUS current
       DESCRIPTION
       "ifIndex of the device interface connected
        to this Router Interface."
       ::= { rtrIfCfgEntry 5 }

rtrIfCfgType OBJECT-TYPE
       SYNTAX INTEGER { 
           notApplicable(1),
           atm     (2),
           lis     (3),
		   ethernet(4)
       }
       MAX-ACCESS read-create
       STATUS current
       DESCRIPTION
       "The Router Interface Type.
       atm       - ATM router interface
       lis       - Logical IP Subnet router interface. 
       ethernet  - Ethernet router interface. "
       ::= { rtrIfCfgEntry 6 }

rtrIfCfgVlanId OBJECT-TYPE
       SYNTAX      VlanIndex
       MAX-ACCESS  read-create
       STATUS      current
       DESCRIPTION
       "The VLAN ID assigned to Tagged frames transmitted 
        from this Router Interface.
        The value inserted should be a defined VLAN."
       ::= { rtrIfCfgEntry 7 }

rtrIfCfgMtu OBJECT-TYPE
    SYNTAX      Integer32
    MAX-ACCESS  read-create
    STATUS      current
    DESCRIPTION
            "The size of the largest packet which can be sent/received
            on the interface, specified in octets.  For interfaces that
            are used for transmitting network datagrams, this is the
            size of the largest network datagram that can be sent on the
            interface."
    ::= { rtrIfCfgEntry 8}

rtrIfCfgName OBJECT-TYPE
       SYNTAX      SnmpAdminString
       MAX-ACCESS  read-create
       STATUS      current
       DESCRIPTION
       "The Router Interface Name."
       ::= { rtrIfCfgEntry 9 }

rtrIfCfgConnectionPointer OBJECT-TYPE
       SYNTAX      RowPointer
       MAX-ACCESS  read-create
       STATUS      current
       DESCRIPTION
       "This parameter represents the entity that is connected
        to this Router Interface.
		
		The value of this parameter is a pointer to an existing row of a table,
		where the entity connected to this Router Interface is defined.
		
		Examples:

        In case of an interface (from 2863.ifTable):
        	points to 'ifEntry' of corresponding row
        	= <ifEntry OID>.<ifIndex>
        
        In case of a VPI/VCI (from 2515.atmVclTable): 
        	points to 'atmVclEntry' of corresponding row
        	= <atmVclEntry OID>.<ATM>.VPI.VCI

        In case of a Pseudo-Wire (from pwTable): 
        	points to 'pwEntry' of corresponding row
        	= <pwEntry OID>.<pwIndex>

		."
       ::= { rtrIfCfgEntry 10 }

rtrIfCfgVlanTagging OBJECT-TYPE
       SYNTAX      INTEGER
       {
       notApplicable	(1),
       untag			(2),
       tag				(3)
       }
       MAX-ACCESS  read-create
       STATUS      current
       DESCRIPTION
       "The VLAN Tagging."
       ::= { rtrIfCfgEntry 11 }

rtrIfCfgVlanPriority OBJECT-TYPE
       SYNTAX      Unsigned32
       MAX-ACCESS  read-create
       STATUS      current
       DESCRIPTION
       "The VLAN Priority."
       ::= { rtrIfCfgEntry 12 }

rtrIfCfgParams OBJECT-TYPE
       SYNTAX      Unsigned32
       MAX-ACCESS  read-create
       STATUS      current
       DESCRIPTION
	   "This object represents one or more parameters of the Router Interface.
	   Each group of bits (one or more bits) represents a specific parameter
	   and its possible values.
	   This object's mapping and interpretation will be specified in each
	   device's specification documents."
       ::= { rtrIfCfgEntry 13 }

rtrIfCfgMngAccess OBJECT-TYPE
       SYNTAX      INTEGER
       {
       notApplicable	(1),
       disable			(2),
       enable			(3)
       }
       MAX-ACCESS  read-create
       STATUS      current
       DESCRIPTION
       "This object represents whether Management Access is enabled
        via this Router Interface."
       ::= { rtrIfCfgEntry 14 }

rtrIfCfgLlcSnapEncaps OBJECT-TYPE
       SYNTAX      INTEGER
       {
       notApplicable	(1),
       bridgedPdu		(2),
       routedPdu		(3)
       }
       MAX-ACCESS  read-create
       STATUS      current
       DESCRIPTION
       "This object represents the LLC/SNAP Encapsulation."
       ::= { rtrIfCfgEntry 15 }

rtrIfCfgDhcp OBJECT-TYPE
       SYNTAX      INTEGER
       {
       notApplicable	(1),
       disable			(2),
       enable			(3)
       }
       MAX-ACCESS  read-create
       STATUS      current
       DESCRIPTION
       "This object indicates whether DHCP is enabled for this Router Interface."
       ::= { rtrIfCfgEntry 16 }


-- ****************  Interfaces Groups End  *******************
 

-- ****************  IP Groups  ******************

-- IP Group

-- ************************************************
--      IP Interface Configuration MIB
-- ************************************************


ipSpec                 OBJECT IDENTIFIER ::= { radRouter 2 }              

rtrIpAddrTable OBJECT-TYPE
    SYNTAX  SEQUENCE  OF RtrIpAddrEntry 
    MAX-ACCESS  not-accessible
    STATUS  current
    DESCRIPTION
       "This table is parralel to MIB II IpAddrTable, and is used to
        add/delete entries to/from that table. In addition it contains
        private objects."
    ::=  { ipSpec 1 }

rtrIpAddrEntry   OBJECT-TYPE
    SYNTAX  RtrIpAddrEntry 
    MAX-ACCESS  not-accessible
    STATUS  current
    DESCRIPTION
            "The addressing information for one of this
            entity's IP addresses."
    INDEX  {rtrIpAdEntAddr}
    ::=  { rtrIpAddrTable 1 }

RtrIpAddrEntry ::= SEQUENCE {
    rtrIpAdEntAddr                IpAddress,
    rtrIpAdEntIfIndex             Integer32,
    rtrIpAdEntNetMask             IpAddress,
    rtrIpAdEntForwardIpBroadcast  INTEGER,
    rtrIpAdEntBackupAddr          IpAddress,
    rtrIpAdEntStatus              RowStatus
    }

rtrIpAdEntAddr OBJECT-TYPE
    SYNTAX  IpAddress
    MAX-ACCESS  read-only
    STATUS  current
    DESCRIPTION
            "The IP address to which this entry's addressing
            information pertains."
    ::= { rtrIpAddrEntry 1 }

rtrIpAdEntIfIndex OBJECT-TYPE
    SYNTAX  Integer32
    MAX-ACCESS  read-create
    STATUS  current
    DESCRIPTION
            "The index value which uniquely identifies the
            interface to which this entry is applicable.  The
            interface identified by a particular value of this
            index is the same interface as identified by the
            same value of ifIndex."
    ::= { rtrIpAddrEntry 2 }

rtrIpAdEntNetMask OBJECT-TYPE
    SYNTAX  IpAddress
    MAX-ACCESS  read-create
    STATUS  current
    DESCRIPTION
            "The subnet mask associated with the IP address of
            this entry.  The value of the mask is an IP
            address with all the network bits set to 1 and all
            the hosts bits set to 0."
    ::= { rtrIpAddrEntry 3 }

rtrIpAdEntForwardIpBroadcast OBJECT-TYPE
    SYNTAX INTEGER {
       enable(1),
       disable(2)
       }
    MAX-ACCESS  read-create
    STATUS  current
    DESCRIPTION
        " This variable controls forwarding of IP (sub)net-directed 
          broadcasts destined for an attached sub(net). "
    DEFVAL  { enable }
    ::=   { rtrIpAddrEntry 4 }

rtrIpAdEntBackupAddr OBJECT-TYPE
    SYNTAX  IpAddress
    MAX-ACCESS  read-create
    STATUS  current
    DESCRIPTION
            " "
    ::= { rtrIpAddrEntry 5 }

rtrIpAdEntStatus OBJECT-TYPE
    SYNTAX RowStatus
    MAX-ACCESS  read-create
    STATUS  current
    DESCRIPTION
        " The Status variable is used to create and destroy a Ip Addresses."
    ::=   { rtrIpAddrEntry 6 }

icmpSpec               OBJECT IDENTIFIER ::= { ipSpec 2 }
  
rtrIcmpGenErrMsgEnable   OBJECT-TYPE
    SYNTAX INTEGER {
       enable(1),
       disable(2)
   }
    MAX-ACCESS  read-write
    STATUS  current
    DESCRIPTION
           "This variable controlls the ability to generate ICMP error messages"
    DEFVAL  { enable }
    ::= { icmpSpec 1 }

rtrIcmpRdTable OBJECT-TYPE
    SYNTAX  SEQUENCE  OF RtrIcmpRdEntry 
    MAX-ACCESS  not-accessible
    STATUS  current
    DESCRIPTION
       "This table contains ICMP Router Discovery parameters
        configurated per IP interface."
    ::=  {icmpSpec 2}

rtrIcmpRdEntry   OBJECT-TYPE
    SYNTAX  RtrIcmpRdEntry 
    MAX-ACCESS  not-accessible
    STATUS  current
    DESCRIPTION
           "The ICMP parameters configurated for IP interface."
    INDEX  {rtrIcmpRdIpAddr}
    ::=  {rtrIcmpRdTable 1}

RtrIcmpRdEntry ::= SEQUENCE {
    rtrIcmpRdIpAddr             IpAddress,
    rtrIcmpRdIpAdvertAddr       IpAddress,
    rtrIcmpRdMaxAdvertInterval  Integer32,
    rtrIcmpRdMinAdvertInterval  Integer32,
    rtrIcmpRdAdvertLifetime     Integer32,
    rtrIcmpRdAdvertise          INTEGER,
    rtrIcmpRdPreferenceLevel    Integer32,
    rtrIcmpRdEntStatus          Integer32
    }

rtrIcmpRdIpAddr OBJECT-TYPE
    SYNTAX  IpAddress
    MAX-ACCESS  read-only
    STATUS  current
    DESCRIPTION
            "The IP address to which this entry's information pertains."
    ::= {rtrIcmpRdEntry 1}

rtrIcmpRdIpAdvertAddr OBJECT-TYPE
    SYNTAX  IpAddress
    MAX-ACCESS  read-write
    STATUS  current
    DESCRIPTION
            " The IP destination address to be used for multicast
              Router Advertisements sent from the interface. The
              only permissible values are the all-systems multicast
              address, 224.0.0.1, or the limited-broadcast address,
              255.255.255.255."
--    DEFVAL  {224.0.0.1}
    ::= {rtrIcmpRdEntry 2}

rtrIcmpRdMaxAdvertInterval OBJECT-TYPE
    SYNTAX  Integer32 (4..1800)
    MAX-ACCESS  read-write
    STATUS  current
    DESCRIPTION
            "The maximum time allowed between sending multicast
             Router Advertisements from the interface, in seconds.
             Must be no less than 4 seconds and no greater than 1800
             seconds."
    DEFVAL  {600}
    ::= {rtrIcmpRdEntry 3}

rtrIcmpRdMinAdvertInterval OBJECT-TYPE
    SYNTAX  Integer32 (3..1800)
    MAX-ACCESS  read-write
    STATUS  current
    DESCRIPTION
            "The minimum time allowed between sending unsolicited
             multicast Router Advertisements from the interface, in
             seconds.  Must be no less than 3 seconds and no greater
             than rtrIcmpRdMaxAdvertInterval.
             Default: 0.75 * rtrIcmpRdMaxAdvertInterval."
    ::= {rtrIcmpRdEntry 4}

rtrIcmpRdAdvertLifetime OBJECT-TYPE
    SYNTAX  Integer32 (4..9000)
    MAX-ACCESS  read-write
    STATUS  current
    DESCRIPTION
             "The maximum length of time that the advertised addresses
             are to be considered as valid. Must be no less than 
             rtrIcmpRdMaxAdvertInterval and no greater than 9000 seconds.
             Default: 3 * rtrIcmpRdMaxAdvertInterval."
    ::= {rtrIcmpRdEntry 5}

rtrIcmpRdAdvertise OBJECT-TYPE
    SYNTAX  INTEGER {
       enable  (1),
       disable (2)
       }
    MAX-ACCESS  read-write
    STATUS  current
    DESCRIPTION
             "A flag indicating whether or not the address is to be
              advertised."
    DEFVAL  {enable}
    ::= {rtrIcmpRdEntry 6}

rtrIcmpRdPreferenceLevel OBJECT-TYPE
    SYNTAX  Integer32
    MAX-ACCESS  read-write
    STATUS  current
    DESCRIPTION
             "The preferability of the address as a default router
             address, relative to other router addresses on the same
             subnet."
    DEFVAL  {0}
    ::= {rtrIcmpRdEntry 7}

rtrIcmpRdEntStatus  OBJECT-TYPE
    SYNTAX Integer32
    MAX-ACCESS  read-write
    STATUS  current
    DESCRIPTION
            "Setting of any value to this object set values of
             all fields to the default values."
    ::=   {rtrIcmpRdEntry 8}


rip2Spec              OBJECT IDENTIFIER ::= { ipSpec  3 }

rtrRip2IfConfTable OBJECT-TYPE
    SYNTAX  SEQUENCE  OF RtrRip2IfConfEntry 
    MAX-ACCESS  not-accessible
    STATUS  current
    DESCRIPTION
    "This table is an extension of rip2IfConfTable (RFC 1724 ,RIP 2).
     It means that every time somebody creates/destroys a row in the
     rip2IfConfTable, the same row should be automatically created/destroyed  
     in this table."
    ::=  { rip2Spec 1  }

rtrRip2IfConfEntry   OBJECT-TYPE
    SYNTAX  RtrRip2IfConfEntry 
    MAX-ACCESS  not-accessible
    STATUS  current
	DESCRIPTION
	"An entry in table rtrRip2IfConfTable."
    INDEX  { rtrRip2IfConfAddress }
    ::=  {  rtrRip2IfConfTable 1  }

RtrRip2IfConfEntry  ::= SEQUENCE { 
    rtrRip2IfConfAddress          IpAddress,
    rtrRip2IfConfVirtualDis       Integer32,
    rtrRip2IfConfAutoSend         INTEGER,
	rtrRip2IfConfRipEnable        INTEGER 	
 	}

rtrRip2IfConfAddress  OBJECT-TYPE
    SYNTAX IpAddress
    MAX-ACCESS  read-only
    STATUS  current
    DESCRIPTION
      " The IP Address of this system on the indicated subnet.
        For unnumbered interfaces, the value 0.0.0.N,
        where the least significant 24 bits (N) is the ifIndex
        for the IP Interface in network byte order "
    ::=  { rtrRip2IfConfEntry 1 }

rtrRip2IfConfVirtualDis OBJECT-TYPE
    SYNTAX Integer32 
    MAX-ACCESS  read-write 
    STATUS  deprecated
    DESCRIPTION
         "This variable defines the virtual number of hops assigned to 
          the interface specified by rtrIfIpAddrIndex. This enables 
          fine-tuning of the RIP routing algorithm."
    DEFVAL  { 1 }
    ::=   { rtrRip2IfConfEntry  2  }

rtrRip2IfConfAutoSend OBJECT-TYPE
    SYNTAX INTEGER  {
       enable(1),
       disable(2)
    }
    MAX-ACCESS  read-write
    STATUS  deprecated
    DESCRIPTION
         "When set to enable only the default route is sent through
          the interface. When set to disable, regular RIPs are sent."
    DEFVAL  { disable }
    ::=   { rtrRip2IfConfEntry  3  }
 
rtrRip2IfConfRipEnable OBJECT-TYPE
    SYNTAX INTEGER  {
       no  (2),
       yes (3)
    }
    MAX-ACCESS  read-write
    STATUS  current
    DESCRIPTION
    "This object shows whether RIP Protocol is enabled on the current interface."   
    ::=   { rtrRip2IfConfEntry  4  }

 

arpSpec                OBJECT IDENTIFIER ::= { ipSpec 4 }

rtrArpDeleteTable OBJECT-TYPE
    SYNTAX  Integer32
    MAX-ACCESS  read-write
    STATUS  current
    DESCRIPTION
         "Setting this object to any not-null value has the effect of deleting 
          all entries of the ARP table."
    ::= { arpSpec 1  }

rtrArpInactiveTimeOut OBJECT-TYPE
    SYNTAX Integer32
    MAX-ACCESS  read-write
    STATUS  current
    DESCRIPTION
         "This variable defines the maximum time period (in second) that can
          pass between ARP requests concerning an entry in the ARP table.
          After this time period, the entry is deleted from the table."
    DEFVAL  { 60000 }
    ::= { arpSpec 2  }

rtrArpProxy OBJECT-TYPE
    SYNTAX INTEGER {
       enable(1),
       disable(2)
    }
    MAX-ACCESS read-write
    STATUS current
    DESCRIPTION
         "When ARP Proxy is enabled, the router can respond to 
          ARP requests for nodes located on a different sub-net, 
          provided they are it its network table. The router responds 
          with its own MAC address. 
          When ARP Proxy is disabled, the router responds only
          to ARP requests for its own IP addresses."
    DEFVAL  { disable }
    ::= { arpSpec 3  }


-- ****************************************
--      NAT    Network Address Translation 
-- *****************************************

rtrNat     OBJECT IDENTIFIER ::= { ipSpec 5 }

rtrNatIfConfTable OBJECT-TYPE
       SYNTAX      SEQUENCE OF RtrNatIfConfEntry
       MAX-ACCESS  not-accessible
       STATUS      current
       DESCRIPTION
       "A list of interfaces which require separate NAT configuration."  
       ::= {rtrNat 1}

rtrNatIfConfEntry OBJECT-TYPE
       SYNTAX      RtrNatIfConfEntry
       MAX-ACCESS  not-accessible
       STATUS      current
       DESCRIPTION
       "A single routing domain in a single subnet."
       INDEX   { ifIndex, rtrNatIfVirtualAddress, rtrNatIfVirtualMask }
       ::= { rtrNatIfConfTable 1 }


RtrNatIfConfEntry ::=
      SEQUENCE {
        rtrNatIfVirtualAddress IpAddress,
        rtrNatIfVirtualMask    IpAddress,
        rtrNatIfConfStatus     RowStatus,
        rtrNatIfRealAddress    IpAddress,
        rtrNatIfRealMask	   IpAddress,
		rtrNatIfType           INTEGER
}


rtrNatIfVirtualAddress OBJECT-TYPE
   SYNTAX  IpAddress
   MAX-ACCESS  read-only
   STATUS  current
   DESCRIPTION
   "The IP Address of the virtual subnet to be translated by the 'NAT box' 
    attached to this interface.
    For some devices/cases, it might represent the Virtual Lowest IP Address."
   ::= { rtrNatIfConfEntry 1 }

rtrNatIfVirtualMask OBJECT-TYPE
   SYNTAX  IpAddress
   MAX-ACCESS  read-only
   STATUS  current
   DESCRIPTION
   "The subnet Mask of the virtual subnet.
    For some devices/cases, it might represent the Virtual Highest IP Address."
   ::= { rtrNatIfConfEntry 2 }

rtrNatIfConfStatus OBJECT-TYPE
   SYNTAX  RowStatus
   MAX-ACCESS read-create
   STATUS  current
   DESCRIPTION
   "Writing 'destroy' has the effect of deleting this interface."
   ::= { rtrNatIfConfEntry 3 }

rtrNatIfRealAddress OBJECT-TYPE
   SYNTAX  IpAddress
   MAX-ACCESS read-create
   STATUS  current
   DESCRIPTION
   " The IP Address of the real subnet which is used by 'NAT box' for translation.
    For some devices/cases, it might represent the Real Lowest IP Address."
   ::= { rtrNatIfConfEntry 4 }

rtrNatIfRealMask OBJECT-TYPE
   SYNTAX  IpAddress
   MAX-ACCESS read-create
   STATUS  current
   DESCRIPTION
   " The subnet Mask of the real subnet.
    For some devices/cases, it might represent the Real Highest IP Address."
   ::= { rtrNatIfConfEntry 5 }

rtrNatIfType OBJECT-TYPE
   SYNTAX INTEGER { 
	              static      (1), 
				  dynamic     (2), 
	              pat         (3),
	              transparent (4) 
				   }
   MAX-ACCESS read-create
   STATUS  current
   DESCRIPTION
   "NAT type.
    
    static - Translate a specific virtual IP network to a specific real IP 
             network. TCP, UDP and ICMP sessions originated both in real and 
             virtual networks will be translated.
	dynamic - (Concurrent) Translate real IP network to larger or equal virtual 
	         IP network. TCP, UDP and ICMP sessions originated in virtual 
	         networks only	can be translated and sessions originated in real 
	         networks will be rejected. A session that starts in the NAT system 
	         will be active until there will be no traffic for aging timeout 
	         period.         
    pat    - (Port Address Translation/ Single IP).
             Translate one real IP address to virtual IP network. TCP, UDP and 
             ICMP sessions originated in virtual network only can be translated, 
             sessions originated in real network will be rejected. A session 
             that starts in the NAT system will be active until there will be no 
             traffic for aging timeout period.
    transparent - In transparent mode all frames belonging to the defined IP 
             network will be forwarded with no translation: virtual = real."     
   ::= { rtrNatIfConfEntry 6 }


-- *************************************
--           Port Address Translation
-- *************************************

rtrPatTable OBJECT-TYPE
       SYNTAX      SEQUENCE OF RtrPatEntry
       MAX-ACCESS  not-accessible
       STATUS      current
       DESCRIPTION
       "Port Address Translation (PAT -  single IP NAT) configuration Table."  
       ::= {rtrNat 2}

rtrPatEntry OBJECT-TYPE
       SYNTAX      RtrPatEntry
       MAX-ACCESS  not-accessible
       STATUS      current
       DESCRIPTION
       "Each entry describe unique mapping between real IP address, 
       range of ports and protocol, to local (virtual) IP address.
       Ports are used in the TCP (rfc793) to name the ends of logical
       connections which carry long term conversations.  
       For the purpose of providing services to unknown callers, 
       a service contact port is defined. "
       INDEX   { rtrPatIdx }
       ::= { rtrPatTable 1 }

RtrPatEntry ::=
      SEQUENCE {
        rtrPatIdx             Integer32,
        rtrPatRealAddress     IpAddress,
        rtrPatVirtualAddress  IpAddress,
        rtrPatLowestPort      Integer32,
        rtrPatHighestPort     Integer32,
		rtrPatProtocol		  Integer32,
		rtrPatStatus		  RowStatus
               }								

rtrPatIdx OBJECT-TYPE
   SYNTAX  Integer32 (1..30)
   MAX-ACCESS  read-only
   STATUS  current
   DESCRIPTION
   "Running index for PAT table."
   ::= { rtrPatEntry 1 }
			  
rtrPatRealAddress OBJECT-TYPE
   SYNTAX      IpAddress
   MAX-ACCESS  read-create
   STATUS  current
   DESCRIPTION
   "The real IP Address used for translation "
   ::= { rtrPatEntry 2 }

rtrPatVirtualAddress OBJECT-TYPE
   SYNTAX      IpAddress
   MAX-ACCESS  read-create
   STATUS  current
   DESCRIPTION
   "The virtual IP Address used for translation"
   ::= { rtrPatEntry 3 }

rtrPatLowestPort OBJECT-TYPE
   SYNTAX      Integer32 (0..65535)
   MAX-ACCESS  read-create
   STATUS  current
   DESCRIPTION
   "Lowest Port number for this PAT entry "
   ::= { rtrPatEntry 4 }

rtrPatHighestPort OBJECT-TYPE
   SYNTAX      Integer32 (0..65535)
   MAX-ACCESS  read-create
   STATUS  current
   DESCRIPTION
   "Highest Port number for this PAT entry "
   ::= { rtrPatEntry 5 }

rtrPatProtocol OBJECT-TYPE
   SYNTAX  Integer32
   MAX-ACCESS read-create
   STATUS  current
   DESCRIPTION
   "Protocol selected.
    This Protocol and port range (lowest port - highest port)
    define the application (FTP, Telnet, SMTP etc.).
    Protocol enumaration numbers correspond to IP header 'protocol' field
	(e.g. 6 means TCP, 17 means UDP)."
   ::= { rtrPatEntry 6 }

rtrPatStatus OBJECT-TYPE
   SYNTAX  RowStatus
   MAX-ACCESS read-create
   STATUS  current
   DESCRIPTION
   "This object enables creating and deleting 
    entries of the table."
   ::= { rtrPatEntry 7 }



-- ************************************************
--                        FACS MIB
-- ************************************************


rtrFACS    OBJECT IDENTIFIER ::=  { radRouter 5 }

rtrFACSDefaultAction OBJECT-TYPE
   SYNTAX  INTEGER {
      block(1),
      forward(2),
      blockAndReport(129)
   }
   MAX-ACCESS  read-write  
   STATUS  current
   DESCRIPTION
         "Used to define the default action for the device, when no
          FACS statements applicable to a given frame are defined."
                
--  DEFVAL  { 1 }
  ::= { rtrFACS 1 }

rtrFACSActTable OBJECT-TYPE
   SYNTAX  SEQUENCE OF RtrFACSActEntry
   MAX-ACCESS  not-accessible
   STATUS  current
   DESCRIPTION
        "The table of  FACS action."
   ::= { rtrFACS 2 }

rtrFACSActEntry OBJECT-TYPE
   SYNTAX  RtrFACSActEntry
   MAX-ACCESS  not-accessible
   STATUS  current
   DESCRIPTION
        "Each rtrFACSActEntry consist of the following parameters"
   INDEX   {rtrFACSActType,
            rtrFACSActIfIndex}
   ::= { rtrFACSActTable 1 }

RtrFACSActEntry ::= SEQUENCE {
   rtrFACSActType    INTEGER,
   rtrFACSActIfIndex Integer32,
   rtrFACSAction     INTEGER,
   rtrFACSActiveDB   INTEGER
}

rtrFACSActType OBJECT-TYPE
   SYNTAX  INTEGER {
      tx(1),
      rx(2)
            }
   MAX-ACCESS  read-only
   STATUS  current
   DESCRIPTION
        "This parameter indicates on which FACS Table the FACS 
        action will preform."
   ::= { rtrFACSActEntry 1 }

rtrFACSActIfIndex OBJECT-TYPE
   SYNTAX  Integer32
   MAX-ACCESS  read-only
   STATUS  current
   DESCRIPTION
         "The interface to which this FACS entry is applicable."
   ::= { rtrFACSActEntry 2 }

rtrFACSAction OBJECT-TYPE
   SYNTAX  INTEGER {
       none(1),
       eraseIP(2),
       eraseDECnet(3),
       eraseIPX(4),
       eraseBrg(5),
       replaceIP(6),
       replaceIPX(8),
       replaceBrg(9),
       backupIP(10),
       backupIPX(12),
       backupBrg(13)
   }
   MAX-ACCESS  read-write
   STATUS  current
   DESCRIPTION
       "The management station that sends a SET request for one of these actions
       with indexes  rtrFACSType and rtrFACSIfIndex defines the type and the
       interface  Id for which all FACS statements are to be erased. 
       If no interface or no type  is specified, all FACS statements for a 
       protocol are erased."
-- DEFVAL  { 1 }
   ::= { rtrFACSActEntry 3 }

rtrFACSActiveDB OBJECT-TYPE
   SYNTAX INTEGER {
      active(1),
      temporary(2)
   }
   MAX-ACCESS  read-write
   STATUS  current
   DESCRIPTION
        "This parameter will point on which Facs DataBase the SNMP agent 
         read. The Active dataBase is Read Only. The user may change FACS 
         statements in the temporary DataBase and then write it to the 
         Active DB."
      ::= { rtrFACSActEntry 4}
     
rtrFACSTable OBJECT-TYPE
  SYNTAX  SEQUENCE OF RtrFACSEntry
  MAX-ACCESS  not-accessible
  STATUS  current
  DESCRIPTION
       "The table of  FACS statment."
  ::= { rtrFACS 3 }

rtrFACSEntry OBJECT-TYPE
  SYNTAX  RtrFACSEntry
  MAX-ACCESS  not-accessible
  STATUS  current
  DESCRIPTION
         "Each FACS statment consists of the following parameters"
  INDEX  {rtrFACSIfIndex,
          rtrFACSProtocolType,
          rtrFACSType,
          rtrFACSIndex } 
  ::= { rtrFACSTable 1 }

RtrFACSEntry ::= SEQUENCE {
   rtrFACSIfIndex      Integer32,
   rtrFACSProtocolType INTEGER,
   rtrFACSType         INTEGER,
   rtrFACSIndex        Integer32,
   rtrFACSSrcAdd       OCTET STRING ,
   rtrFACSSrcAddMask   OCTET STRING,
   rtrFACSDesAdd       OCTET STRING,
   rtrFACSDesAddMask   OCTET STRING,
   rtrFACSOperation    INTEGER,
   rtrFACSNetFiltering INTEGER,
   rtrFACSSocketNum     Integer32,
   rtrFACSMask1Id      Integer32,
   rtrFACSMask2Id      Integer32,
   rtrFACSStatus       INTEGER
  }

rtrFACSIfIndex OBJECT-TYPE
  SYNTAX  Integer32  
  MAX-ACCESS  read-only
  STATUS  current
  DESCRIPTION
         "The interface to which this FACS entry is applicable.
          For applications this variables is always 0."
  ::= { rtrFACSEntry 1 }

rtrFACSProtocolType OBJECT-TYPE
  SYNTAX  INTEGER{
     ip(1),
     ipx(2),
     dec(3),
     bridge(4)
  }
  MAX-ACCESS  read-only
  STATUS  current
  DESCRIPTION
       "This parameter define the protocol the Security  Access Control
       is applicable."
  ::= { rtrFACSEntry 2 }

rtrFACSType OBJECT-TYPE
  SYNTAX  INTEGER {
      tx(1),
      rx(2),
      cod(3)
  }
  MAX-ACCESS  read-only
  STATUS  current
  DESCRIPTION
       " The Mode of in which this FACS statement operates.
         For applications this variable is always rx(2)."
  ::= { rtrFACSEntry 3 }

rtrFACSIndex OBJECT-TYPE
  SYNTAX  Integer32
  MAX-ACCESS  read-only
  STATUS  current
  DESCRIPTION
       "Index to the FACS  Table. "
  ::= { rtrFACSEntry 4 }

rtrFACSSrcAdd OBJECT-TYPE
  SYNTAX  OCTET STRING 
  MAX-ACCESS  read-write
  STATUS  current
  DESCRIPTION
       "The size of the octet string will be according to the protocol type 
        defined in rtrFACSProtocolType."
  ::= { rtrFACSEntry 5 }

rtrFACSSrcAddMask OBJECT-TYPE
  SYNTAX   OCTET STRING 
  MAX-ACCESS  read-write
  STATUS  current
  DESCRIPTION
         "Source-address mask ."
  ::= { rtrFACSEntry 6 }

rtrFACSDesAdd OBJECT-TYPE
  SYNTAX   OCTET STRING
  MAX-ACCESS  read-write
  STATUS  current
  DESCRIPTION
      "Destination-address The size of the octet string will be according to the
      protocol type define in rtrFACSProtocolType ."
  ::= { rtrFACSEntry 7 }


rtrFACSDesAddMask OBJECT-TYPE
   SYNTAX   OCTET STRING
   MAX-ACCESS  read-write
   STATUS  current
   DESCRIPTION
       "Destination-address mask ."
   ::= { rtrFACSEntry 8 }


rtrFACSOperation OBJECT-TYPE
   SYNTAX  INTEGER {
       block(1),
       forward(2),
       permit(3),        -- For Connect On demand Only
       deny(4),          -- For Connect On demand Only
       blockAndReport(129)
   }
   MAX-ACCESS  read-write
   STATUS  current
   DESCRIPTION
               "... ."
   ::= { rtrFACSEntry 9 }

rtrFACSNetFiltering OBJECT-TYPE
   SYNTAX  INTEGER {
       none(1), 
       l2multicast(2), --applicable for Bridge protocol 
       arp(3),      --applicable for ip protocol 
       icmp(4),     --applicable for ip protocol 
       ip(5),       --applicable for ip protocol 
       udp(6),      --applicable for ip protocol 
       tcp(7),      --applicable for ip protocol 
       decnet(8),   --applicable for decnet protocol 
       ipx(9)      --applicable for ipx protocol 
   }
   MAX-ACCESS  read-write
   STATUS  current
   DESCRIPTION
      "... ."
   ::= { rtrFACSEntry 10 }


rtrFACSSocketNum OBJECT-TYPE   --applicable for ip,ipx protocol 
   SYNTAX  Integer32 
   MAX-ACCESS  read-write
   STATUS  current
   DESCRIPTION
       " Port/socket  number for different applications
       0 is default meaning not applicable.
       none(1),
       ftp(21),
       telnet(23),
       smtp(25),
       tftp(69),
       snmp(161),
       snmpTrap(162),
       rip(520),
       sapIPX(1106),
       ripIPX(1107)    "
   ::= { rtrFACSEntry 11}

rtrFACSMask1Id OBJECT-TYPE
   SYNTAX  Integer32
   MAX-ACCESS  read-write
   STATUS  current
   DESCRIPTION
       " Index into RND mask table FACS/COD Type) ."
   ::= { rtrFACSEntry 12}

rtrFACSMask2Id OBJECT-TYPE
   SYNTAX  Integer32
   MAX-ACCESS  read-write
   STATUS  current
   DESCRIPTION
       " Index into RND mask table FACS/COD according to
       the value of rtrFACSType ."
   ::= { rtrFACSEntry 13}

rtrFACSStatus OBJECT-TYPE
   SYNTAX  INTEGER {
      valid(1),
      createRequest(2),  
      underCreation(3), 
      invalid(4)          -- logically deleted
   }

   MAX-ACCESS  read-write
   STATUS  current
   DESCRIPTION
       "The status of a table entry."
   ::= { rtrFACSEntry 14}


rtrFACSFrameData OBJECT-TYPE
   SYNTAX  OCTET STRING (SIZE(0..256))
   MAX-ACCESS  read-only
   STATUS  current
   DESCRIPTION
         "Data from the frame that violated a FACS Filter."
  ::= { rtrFACS 4 }

-- ****************  FACS Group Ends  *******************


-- ************************************************
-- Bridge ports Configuration MIB
-- ************************************************

-- rtrBridge    OBJECT IDENTIFIER ::= { radRouter 7 }

        
rtrBridgePortConfigTable  OBJECT-TYPE     
       SYNTAX  SEQUENCE OF RtrBridgePortConfigEntry
       MAX-ACCESS  not-accessible
       STATUS  current
       DESCRIPTION
           "Table of the bridge ports" 
      ::= { rtrBridge 1 }

rtrBridgePortConfigEntry  OBJECT-TYPE     
       SYNTAX  RtrBridgePortConfigEntry
       MAX-ACCESS  not-accessible
       STATUS  current
       DESCRIPTION
           "Each entry defines a bridge port " 
       INDEX { rtrBridgePortCIndex }
      ::= { rtrBridgePortConfigTable 1 }

RtrBridgePortConfigEntry ::= SEQUENCE {
        rtrBridgePortCIndex
                Integer32,
        rtrBridgePortCIf
                Integer32,
        rtrBridgePortCStatus
                RowStatus
        }



rtrBridgePortCIndex OBJECT-TYPE
        SYNTAX  Integer32
        MAX-ACCESS  read-only
        STATUS  current
        DESCRIPTION
                "This is the index of the bridge port. It is the same
                 as 'dot1dBasePort' of the Bridge MIB."
        ::= {rtrBridgePortConfigEntry 1}

rtrBridgePortCIf OBJECT-TYPE
        SYNTAX  Integer32
        MAX-ACCESS  read-create
        STATUS  current
        DESCRIPTION
                "The config ifIndex the bridge port is sitting on. "
        ::= {rtrBridgePortConfigEntry 2}

rtrBridgePortCStatus OBJECT-TYPE
        SYNTAX  RowStatus
        MAX-ACCESS  read-create
        STATUS  current
        DESCRIPTION
          "The status of the RtrBridgePortConfigEntry.  
           Creating and destroying the bridge port is done by this
           variable."
        ::= {rtrBridgePortConfigEntry 3}

 
radRouterConfig  OBJECT IDENTIFIER  ::= { radRouter 9 }


-- The Router's Configuration Table

rtrConfigTable OBJECT-TYPE
    SYNTAX      SEQUENCE OF RtrConfigEntry
    MAX-ACCESS  not-accessible
    STATUS      current
    DESCRIPTION
    "The Router's Configuration table."
    ::= {  radRouterConfig 1 }

rtrConfigEntry  OBJECT-TYPE
    SYNTAX      RtrConfigEntry
    MAX-ACCESS  not-accessible
    STATUS      current
    DESCRIPTION
    "An entry in the Router's Configuration table."
    INDEX   { rtrConfigIndex }
    ::= { rtrConfigTable 1 }

RtrConfigEntry ::=
	SEQUENCE { 
        rtrConfigIndex           		Integer32,
		rtrConfigDefaultGateway         IpAddress,
		rtrConfigArpAgingTime			Integer32,
		-- 4 is NOT used
		rtrConfigClassifierTosMask		Integer32,
		rtrConfigRIPMode				INTEGER
    	}

rtrConfigIndex OBJECT-TYPE
    SYNTAX  Integer32
    MAX-ACCESS  read-only
    STATUS  current
    DESCRIPTION
    "This object indicates the Router's Index."
    ::= { rtrConfigEntry 1 }

rtrConfigDefaultGateway	 OBJECT-TYPE
       SYNTAX  IpAddress
       MAX-ACCESS  read-write
       STATUS  current
       DESCRIPTION
       "Router Default Gateway."     
      ::= { rtrConfigEntry 2 }

rtrConfigArpAgingTime OBJECT-TYPE
    SYNTAX  Integer32
    MAX-ACCESS  read-write
    STATUS  current
    DESCRIPTION
    "ARP Aging Time."
    ::= { rtrConfigEntry 3 }

-- { rtrConfigEntry 4 } is NOT used

rtrConfigClassifierTosMask OBJECT-TYPE
    SYNTAX Integer32
    MAX-ACCESS  read-write
    STATUS  current
    DESCRIPTION
    "This object indicates the Classifier's TOS Mask,
	 as follows:
	 0x1C for DTR			-- rfc795
     0x1E for Cisco
     0xE0 for Precedence	-- rfc795
     0xFC for Diffserv
     Else for Manual
	 ."
    ::= { rtrConfigEntry 5 }

rtrConfigRIPMode OBJECT-TYPE
    SYNTAX INTEGER {
		notApplicable(1),
		rip1(2),
		rip2(3),
		rip1And2(4)
    }
    MAX-ACCESS  read-write
    STATUS  current
    DESCRIPTION
    "This object determines the Router Information Protocol
     to measure the shortest path between 2 positions 
     on the network."
    ::= { rtrConfigEntry 6 }


rtrSystemAddress OBJECT-TYPE
	SYNTAX      IpAddress
	MAX-ACCESS  read-write
	STATUS      current
	DESCRIPTION
	"This object represents the System Address."
    ::= { radRouterConfig 2 }


-- The Router's Forwarding Table

rtrFwdTable OBJECT-TYPE
    SYNTAX      SEQUENCE OF RtrFwdEntry
    MAX-ACCESS  not-accessible
    STATUS      current
    DESCRIPTION
    "The Router's Forwarding Table."
    ::= {  radRouterConfig 3 }

rtrFwdEntry  OBJECT-TYPE
    SYNTAX      RtrFwdEntry
    MAX-ACCESS  not-accessible
    STATUS      current
    DESCRIPTION
    "An entry in the Router's Forwarding table."
    INDEX   { rtrFwdIdx, rtrFwdIpAddress, 
    			rtrFwdIpMask, rtrFwdRuleIdx }
    ::= { rtrFwdTable 1 }

RtrFwdEntry ::=
	SEQUENCE { 
        rtrFwdIdx				Integer32,
        rtrFwdIpAddress			IpAddress,
		rtrFwdIpMask			IpAddress,
		rtrFwdRuleIdx			Integer32,
		rtrFwdRowStatus	  		RowStatus,
		rtrFwdNextHop			IpAddress,			
		rtrFwdIfIndex			Integer32,
		rtrFwdType				INTEGER,
		rtrFwdProto				INTEGER,
		rtrFwdEthQueue			Integer32,
		rtrFwdMetric1			Integer32
    	}

rtrFwdIdx OBJECT-TYPE
    SYNTAX  Integer32
    MAX-ACCESS  read-only
    STATUS  current
    DESCRIPTION
    "This object indicates the Router Index."
    ::= { rtrFwdEntry 1 }

rtrFwdIpAddress OBJECT-TYPE
    SYNTAX  IpAddress
    MAX-ACCESS  read-only
    STATUS  current
    DESCRIPTION
    "This object indicates the Destination IP Address."
    ::= { rtrFwdEntry 2 }

rtrFwdIpMask OBJECT-TYPE
    SYNTAX  IpAddress
    MAX-ACCESS  read-only
    STATUS  current
    DESCRIPTION
    "This object indicates the Mask IP address."
    ::= { rtrFwdEntry 3 }

rtrFwdRuleIdx OBJECT-TYPE
    SYNTAX  Integer32
    MAX-ACCESS  read-only
    STATUS  current
    DESCRIPTION
    "This object indicates the Rule's Number."
    ::= { rtrFwdEntry 4 }

rtrFwdRowStatus OBJECT-TYPE
    SYNTAX      RowStatus
    MAX-ACCESS  read-create
    STATUS      current
    DESCRIPTION
    "This object enables the user to 
     create/delete entries in this table.
     
     Entry of Type rtrFwdType = staticRouting(3)
	 are created by the user.
	 Only this type of entries can be deleted by the user.

	 Entry of Type rtrFwdType = interface(2)
	 are created/deleted automatically by the Agent
	 when the user creates/deletes an interface of the Router."
    ::= { rtrFwdEntry 5 }

rtrFwdNextHop OBJECT-TYPE
    SYNTAX  IpAddress
    MAX-ACCESS  read-create
    STATUS  current
    DESCRIPTION
    "This object indicates the IP Address of the Next Hop."
    ::= { rtrFwdEntry 6 }

rtrFwdIfIndex OBJECT-TYPE
    SYNTAX  Integer32
    MAX-ACCESS  read-only
    STATUS  current
    DESCRIPTION
    "This object indicates the Interface Index."
    ::= { rtrFwdEntry 7 }

rtrFwdType OBJECT-TYPE
    SYNTAX  INTEGER {
		other    (1), -- not specified by this MIB
		reject   (2), -- route which discards traffic
		local    (3), -- local interface
		remote   (4)  -- remote destination
		}
    MAX-ACCESS read-create
    STATUS   current
    DESCRIPTION
       "The type of route.  Note that local(3)  refers
       to  a route for which the next hop is the final
       destination; remote(4) refers to  a  route  for
       which  the  next  hop is not the final destina-
       tion.

       Routes which do not result in traffic forwarding or
       rejection should not be displayed even if the
       implementation keeps them stored internally.
	   
       reject (2) refers to a route which, if matched, discards
       the message as unreachable. This is used in some
       protocols as a means of correctly aggregating routes."
    ::= { rtrFwdEntry 8 }

rtrFwdProto OBJECT-TYPE
    SYNTAX   INTEGER {
		other	(1),  -- not specified
		local	(2),  -- local interface
  		netmgmt	(3),  -- static route
 		rip		(8),  -- Berkeley RIP or RIP-II
		lis		(41)  -- Logical IP Subnet
		}
    MAX-ACCESS read-only
    STATUS   current
    DESCRIPTION
	"The routing mechanism via which this route was
	learned.  Inclusion of values for gateway routing 
	protocols is not intended to imply that
	hosts should support those protocols."
    ::= { rtrFwdEntry 9 }

rtrFwdEthQueue OBJECT-TYPE
    SYNTAX  Integer32
    MAX-ACCESS  read-create
    STATUS  current
    DESCRIPTION
    "This object indicates the ETH Queue number."
    ::= { rtrFwdEntry 10 }

rtrFwdMetric1 OBJECT-TYPE
    SYNTAX   Integer32
    MAX-ACCESS read-create
    STATUS   current
    DESCRIPTION
	"The primary routing metric for this route.
	 The semantics of this metric are determined by
	 the routing-protocol specified in the route's
	 rtrFwdProto value. If this metric is not
	 used, its value should be set to -1."
    DEFVAL { -1 }
    ::= { rtrFwdEntry 11 }


rtrPbrTable OBJECT-TYPE
    SYNTAX      SEQUENCE OF RtrPbrEntry
    MAX-ACCESS  not-accessible
    STATUS      current
    DESCRIPTION
    "The Router's Forwarding Table."
    ::= {  radRouterConfig 4 }

rtrPbrEntry  OBJECT-TYPE
    SYNTAX      RtrPbrEntry
    MAX-ACCESS  not-accessible
    STATUS      current
    DESCRIPTION
    "An entry in the Router's Policy Based Routing (PBR) table."
    INDEX   { rtrPbrIdx,rtrPbrInterface, rtrPbrRuleIdx }
    ::= { rtrPbrTable 1 }

RtrPbrEntry ::=
	SEQUENCE { 
        rtrPbrIdx				  Unsigned32,
		rtrPbrInterface			  InterfaceIndex,
		rtrPbrRuleIdx			  Unsigned32,
		rtrPbrRowStatus	  		  RowStatus,
		rtrPbrMatchAllFrames   	  INTEGER,
 		rtrPbrSourceIpAddress     IpAddress,
		rtrPbrSourceIpMask        IpAddress,
		rtrPbrDestIpAddress       IpAddress,
		rtrPbrDestIpMask          IpAddress,
		rtrPbrIpProtocol		  Unsigned32,
		rtrPbrMinFrameLength      Unsigned32,
		rtrPbrMaxFrameLength      Unsigned32,
        rtrPbrDiscardFrame		  INTEGER,	
        rtrPbrForwardingInterface InterfaceIndexOrZero,
		rtrPbrNextHop			  IpAddress
          	}

rtrPbrIdx OBJECT-TYPE
    SYNTAX  Unsigned32
    MAX-ACCESS  not-accessible
    STATUS  current
    DESCRIPTION
    "This object indicates the Router Index."
    ::= { rtrPbrEntry 1 }

rtrPbrInterface OBJECT-TYPE
    SYNTAX InterfaceIndex
    MAX-ACCESS  not-accessible
    STATUS  current
    DESCRIPTION
    "Router interface for which this match-set 
     rule applies."
    ::= { rtrPbrEntry 2 }

rtrPbrRuleIdx OBJECT-TYPE
    SYNTAX Unsigned32
    MAX-ACCESS  not-accessible
    STATUS  current
    DESCRIPTION
    "This object indicates the Policy Based Routing (PBR) 
      match-set rule index."
    ::= { rtrPbrEntry 3 }

rtrPbrRowStatus OBJECT-TYPE
    SYNTAX RowStatus
    MAX-ACCESS  read-create
    STATUS  current
    DESCRIPTION
      "This object enables the user to 
       create/delete entries of this table."
    ::= { rtrPbrEntry 4 }

rtrPbrMatchAllFrames OBJECT-TYPE
    SYNTAX INTEGER
	{
	notApplicable (1),
	no            (2), 
	yes           (3)
	}
    MAX-ACCESS  read-create
    STATUS  current
    DESCRIPTION
    "Forwarding decision is made regardless PBR Rule 
     (as if all conditions are matched)"
    ::= { rtrPbrEntry 5 }

rtrPbrSourceIpAddress OBJECT-TYPE
    SYNTAX IpAddress
    MAX-ACCESS  read-create
    STATUS  current
    DESCRIPTION
    "Received frame source IP Address."
    ::= { rtrPbrEntry 6 }

rtrPbrSourceIpMask  OBJECT-TYPE
    SYNTAX IpAddress
    MAX-ACCESS  read-create
    STATUS  current
    DESCRIPTION
    "The subnet mask of the source IP Address."
    ::= { rtrPbrEntry 7 }

rtrPbrDestIpAddress OBJECT-TYPE
    SYNTAX IpAddress
    MAX-ACCESS  read-create
    STATUS  current
    DESCRIPTION
    "Received frame destination IP Address."
    ::= { rtrPbrEntry 8 }

rtrPbrDestIpMask OBJECT-TYPE
    SYNTAX IpAddress
    MAX-ACCESS  read-create
    STATUS  current
    DESCRIPTION
    "The subnet mask of the destination IP Address."
    ::= { rtrPbrEntry 9 }

rtrPbrIpProtocol OBJECT-TYPE
    SYNTAX Unsigned32
    MAX-ACCESS  read-create
    STATUS  current
    DESCRIPTION
    "Value of Protocol field in IP Frame header."
    ::= { rtrPbrEntry 10 }

rtrPbrMinFrameLength OBJECT-TYPE
    SYNTAX Unsigned32
    MAX-ACCESS  read-create
    STATUS  current
    DESCRIPTION
    "."
    ::= { rtrPbrEntry 11 }

rtrPbrMaxFrameLength OBJECT-TYPE
    SYNTAX Unsigned32
    MAX-ACCESS  read-create
    STATUS  current
    DESCRIPTION
    "."
    ::= { rtrPbrEntry 12 }

rtrPbrDiscardFrame OBJECT-TYPE
    SYNTAX INTEGER
    {
	notApplicable (1),
	no            (2), 
	yes           (3)
    }	
    MAX-ACCESS  read-create
    STATUS  current
    DESCRIPTION
    "Discard a frame when rule is matched ."
    ::= { rtrPbrEntry 13 }

rtrPbrForwardingInterface OBJECT-TYPE
    SYNTAX InterfaceIndexOrZero
    MAX-ACCESS  read-create
    STATUS  current
    DESCRIPTION
    "The router Interface through which the frame 
     should be forwarded, when rule is matched.
     If there's no forwarding interface, 
     then this object has a value of zero"
    ::= { rtrPbrEntry 14 }

rtrPbrNextHop OBJECT-TYPE
    SYNTAX IpAddress
    MAX-ACCESS  read-create
    STATUS  current
    DESCRIPTION
    "IP Address of Next Hop, when Forwarding Interface is LAN, 
     or has BridgePDU (BVI) encapsulation."
    ::= { rtrPbrEntry 15 }

-- ****************  Router Bridge Port Group Ends  *******************



-- Traps

rtrFACSViolation NOTIFICATION-TYPE
      OBJECTS  { rtrFACSFrameData, rtrFACSProtocolType }
      STATUS  current
      DESCRIPTION
	  "The trap is sent for every violation of a FACS filter."
      ::= { radSysRtrEvents 1 }

rtrSwDwnLoadTrap NOTIFICATION-TYPE
      OBJECTS  { fileName }
      STATUS  current
      DESCRIPTION
	  "The trap is sent after the tftp download of the software
	   and before the decompression and reset operations."
      ::= { radSysRtrEvents 2 }


-- 
-- file :D:\Synergy\WorkArea\545\mib_rad\txt\optimux2.txt
-- 
-- OPTIMUX-MIB 	DEFINITIONS ::= BEGIN

--Title:    OPTIMUX   MIB
--
-- Last Update : 19-2-2008 by Yig'al Hachmon
--
-- Copyright 1993 RAD Data Communications, Ltd.
-- All Rights Reserved.  

-- It is RAD's intent to encourage the widespread use of
-- this Specification in connection with the management of
-- RAD products. RAD grants vendors, end-users,
-- and other interested parties a non-exclusive license to
-- use this Specification in connection with the management
-- of RAD products.

-- This Specification is supplied "as is," and RAD makes
-- no warranty, either express or implied, as to the use,
-- operation, condition, or performance of the Specification.

--IMPORTS
--	DisplayString	                    FROM RFC1213-MIB
-- 	enterprises			                FROM RFC1155-SMI
--	OBJECT-TYPE                     	FROM RFC-1212
--	TRAP-TYPE                           FROM RFC-1215
--  ifIndex, InterfaceIndex				FROM IF-MIB
-- 	dsx1LoopbackStatus 					FROM DS1-MIB
--	dsx3LoopbackStatus                  FROM DS3-MIB; 
--	radWan, agnIndication               FROM RAD-GEN-MIB;


--                RAD-OPTIMUX MIB   

--Title:     RAD's   OPTIMUX PRODUCT MIB
--Version:   2.0
--Date:      14/01/97
--By:        Michele Hallak
--File:      optimux2.txt
--
--rad OBJECT IDENTIFIER ::= { enterprises 164 }
--radWan       OBJECT IDENTIFIER ::= { rad 3 }  rad WAN Tree
--radGen        OBJECT IDENTIFIER ::= { rad 6}  General information
--Last update: 26-Oct-2006 by Orly Bachar

optimux OBJECT IDENTIFIER ::= { radWan 5 }

-- One Optimux is sometimes connected to another optimux (or other device)
-- via its link. Therefore, in some cases, the SNMP agent sitting on
-- one device is responsible of the second (remote)
-- device. This table supplies information for both
-- devices, while the first is the local one and the second
-- is the remote one.

optMxConfigTable OBJECT-TYPE
     SYNTAX  SEQUENCE OF OptMxConfigEntry
     MAX-ACCESS  not-accessible
     STATUS  current
     DESCRIPTION
     "This table contains parameters of configuration
	  for each member of the couple of Optimux."
     ::= { optimux 1 }

 optMxConfigEntry OBJECT-TYPE
     SYNTAX OptMxConfigEntry 
     MAX-ACCESS  not-accessible
     STATUS  current
     DESCRIPTION
         "An entry in the Optimux Config  table."
     INDEX   { optIndex }
     ::= { optMxConfigTable 1 }

     OptMxConfigEntry ::=
              SEQUENCE {
         optIndex   		INTEGER,
	     optHWVersion       DisplayString,
 	     optSWVersion       DisplayString,
         optPSPrimary 		INTEGER,
	     optPSSecondary 	INTEGER,
	     optLinkActive     	InterfaceIndex,
	     optSelectLink      INTEGER,
	     optGrpPayLoadLoop  INTEGER,
	     optGrpClockSource  INTEGER,
	     optRedundancyStatus INTEGER,
	     optRedundancyCnf   INTEGER,
	     optFarEndType      INTEGER,
	     optServiceChEnable INTEGER,  
	     optMaskChAlr       Integer32,
	     optAisEnable       INTEGER,
	     optFarMng          INTEGER,
	     optClockDivision   INTEGER,
	     optDteLoopEnable   INTEGER,
	     optGrpClockSourcePrt Integer32,
	     optIncomingAlarm   INTEGER,
	     optDefChannelSet   INTEGER,
	     optWaitToRestore	Integer32,
	     optEnforcedLink	INTEGER,
	     optFlipUponEvent   Integer32,
		 optHwMaskChAlr     Integer32,
		 optServiceChExist  INTEGER,
		 optMaskSystemAlr	INTEGER
	        }

optIndex OBJECT-TYPE
SYNTAX  INTEGER {local(1), remote(2) }
MAX-ACCESS  read-only
STATUS  current
DESCRIPTION
"optIndex = 1 is for local Optimux.
 optIndex = 2 is for remote Optimux."
 ::= { optMxConfigEntry 1 }

optHWVersion OBJECT-TYPE
   SYNTAX  DisplayString
   MAX-ACCESS  read-only
   STATUS  current
   DESCRIPTION
    "HW Version of the device."
    ::= { optMxConfigEntry 2 }

optSWVersion OBJECT-TYPE
    SYNTAX  DisplayString
    MAX-ACCESS  read-only
    STATUS  current
    DESCRIPTION
     "SW Version of the device."
     ::= { optMxConfigEntry 3 }

optPSPrimary OBJECT-TYPE
    SYNTAX  INTEGER {
		unknown(1),
		fault(3),
		active(4),
		none(6)
    }
    MAX-ACCESS  read-only
    STATUS  current
    DESCRIPTION
     "The status of the primary Power Supply Unit."
    DEFVAL { active }
     ::= { optMxConfigEntry 4 }

optPSSecondary OBJECT-TYPE
     SYNTAX  INTEGER {
		unknown(1),
		fault(3),
		active(4),
		none(6)
      }
     MAX-ACCESS  read-only
     STATUS  current
     DESCRIPTION
     "The status of the secondary Power Supply Unit."
     DEFVAL { none }
              ::= { optMxConfigEntry 5 }

optLinkActive OBJECT-TYPE
     SYNTAX  InterfaceIndex
     MAX-ACCESS  read-only
     STATUS  current
     DESCRIPTION
     "This object indicates which link is active. 
      For Optimux-4 it may be: 5, 6 or 105, 106
      For FOMi-E3/T3 it may be: 51, 61 or 151, 161.
      For Optimux-T3 it may be: 51 or 61.
      For Optimux-155/1 refer to product spec." 
      ::= { optMxConfigEntry 6 }

optSelectLink OBJECT-TYPE
     SYNTAX  INTEGER {
		autoredundancy(1),
--		autoWoReturn(4),   not in use for this version of Opt-4-C
		main(5),
		back(6)
     }
     MAX-ACCESS  read-write
     STATUS   current
     DESCRIPTION
     "This object is used by Optimuxes.
	  - For Optimux 4E1/T1 Old Look: 
	    This MIB object enables the user to force the device to use specific link.
        autoredundancy= Main (Link 1) is the default link. When it will fail, the 
                        device will use Backup (Link 2). If Main recovers, it 
                        automatically returns to Main.
        autoWoReturn  = Automatic Without Return. Main (Link 1) is the default link. 
                        When it will fail, the device will use Backup (Link 2). 
                        If Main recovers, it will NOT return to Main. It will 
	                    continue using Backup.
				        This option is supported only by LRS cards.
	    main         =  Forces the device to start immediately use of Main (Link 1),
	                    no matter what is its state and stay there. No Redundancy.
	    back         =  Forces the device to start immediately use of Backup (Link 2),
	                    no matter what is its state and stay there. No Redundancy.
	  - For Optimux-T3, Optimux-155, Optimux-XL and OP-4 (New Look):
	    This MIB object is used to select which Link will be used as MAIN.
		Therefore:
	    autoredundancy - not supported 
	    main = Link A is MAIN (=default).
	    back = Link B is MAIN."
      DEFVAL { autoredundancy }
      ::= { optMxConfigEntry 7 }

optGrpPayLoadLoop OBJECT-TYPE
     SYNTAX  INTEGER {
		off(2), on(3)
     }
     MAX-ACCESS  read-write
     STATUS   current
     DESCRIPTION
    	"Performs payload loop ( remote loop) to 4 E1 channels
         at once."
      DEFVAL { off }
      ::= { optMxConfigEntry 8 }

optGrpClockSource OBJECT-TYPE
     SYNTAX  INTEGER {
	 notApplicable(1), 
	 localInternal(2), 
	 localExternal(3), 
	 loopTiming(4),
	 transparent(5)
     }
     MAX-ACCESS  read-write
     STATUS   current
     DESCRIPTION
     "For Optimux XL:
        If dsx3TransmitClockSource = localTiming(2), then the user
        can configure this field as:
        localInternal(2) = use the internal clock of the device
        localExternal(3) = use the external clock connected to the port
        dedicated to clock.
      For FomiE3/T3 this object is always applicable. 
        localExternal(3) = station clock
        transparent(5)   = the device takes the clock info from the data.
        For FomiE3/T3 with HSSI electrical interface, only the following 
        are valid: localInternal(2) and transparent(5).
      For Optimux-T3 the applicable values are (2), (3), (4).
      For Optimux-155/1 the applicable values are (2), (3), (4), (5)."
      DEFVAL { notApplicable }
      ::= { optMxConfigEntry 9 }

optRedundancyStatus OBJECT-TYPE
     SYNTAX  INTEGER {
	  available(2), notAvailable(3)
     }
     MAX-ACCESS  read-only
     STATUS   current
     DESCRIPTION
     "If there are two modules 'links', then this field
      should be set to available(2). If there is only one
      module 'link', this field should be set to notAvailable(3)."
      DEFVAL { available }
      ::= { optMxConfigEntry 10 }

optRedundancyCnf  OBJECT-TYPE
     SYNTAX  INTEGER {
                      off(2),
                      auto(3),
                      manual(4),
                      forcedBU(6),
                      autoNonRevertive (7) 
                      }
     MAX-ACCESS  read-write
     STATUS   current
     DESCRIPTION
     "This object is used by Optimux-XL, FomiE3/T3, Optimux-T3 and Optimux-155.
      For Optimux-XL:
        If optRedundancyStatus = notAvailable(3), then this field
        can be off(2) or forcedBU(6). 
         - off(2) = forcedMain:	forces the device to start immediately use of 
                    Main (Link 1), no matter what is its state and stay there
	     - forcedBU(6)  =  forces the device to start immediately use of 
	                       Backup (Link 2),	no matter what is its state and stay there.
						   This value is not supported by Optimux-T3.
        Else, user can configure this field as:
        auto(3) = switch back to main link when valid.
        manual(4) = don't switch back to main link = automatic w/o return.
      For FomiE3/T3 all values are applicable unconditioned.
      For Optimux-T3 and OP-4 New Look, values off(2), auto(3), manual(4) 
        are applicable unconditioned.
      For Optimux-155/1 values off (2) = Protection Lockout, auto (3) and manual (4)
      and autoNonRevertive (7)"
      DEFVAL { auto }
      ::= { optMxConfigEntry 11 }

optFarEndType  OBJECT-TYPE
     SYNTAX  INTEGER 
     {
	 unknown     (1), 
	 optimux4Sa  (2), 
	 optimux4Card(3),
	 fomiE3T3Sa  (4),
	 fomiE3T3Card(5),
	 optimuxXL16 (6),
	 optimuxXLE1 (7),
	 optimux4E1L (8),
	 optimux4T1L (9),
	 optimuxXLT1 (10),
	 op16E1L	 (11),	-- 19" box
	 op16E1LS	 (12),	-- half 19" box (single)
	 opXLE1		 (13),	-- Optimux-XL New-Look
	 opXLT1		 (14),	-- Optimux-XL New-Look
	 opXL16E1    (15),	-- Optimux-XL New-Look
	 op4E1		 (16),	-- Op-4E1 SA New-Look
	 op4T1		 (17),	-- Op-4T1 SA New-Look
	 fdsl101     (18),
	 fdsl201     (19),
	 op4E1LNew   (20),	--OP-4E1L - New Low Cost
	 op4T1LNew   (21),	--OP-4T1L - New Low Cost
	 op34E1      (22),
	 op4E1Mar06  (23), 	-- OP-4E1 R5 
	 op4E1NG1    (24),  -- OP-4E1 R6/R6.1
	 op4T1NG1    (25),  -- OP-4T1 R7/R7.1
	 op25        (26),
	 notApplicable(255)
     }
     MAX-ACCESS  read-only
     STATUS   current
     DESCRIPTION
     "Far-End type of product.
      This object is especially relevant for the local optimux.
	  notApplicable - for devices that don't have a far-end unit."
      ::= { optMxConfigEntry 12 }

optServiceChEnable  OBJECT-TYPE
     SYNTAX  INTEGER 
     {
     notApplicable(1),
	 disabled  (2), 
	 enabled   (3)
     }
     MAX-ACCESS   read-write
     STATUS   current
     DESCRIPTION
     "Service Channel Enable/Disable for each Optimux (local/remote)."
      ::= { optMxConfigEntry 13 }

optMaskChAlr  OBJECT-TYPE
     SYNTAX  Integer32 
     MAX-ACCESS   read-write
     STATUS   current
     DESCRIPTION
     "Mask Channel Alarm.
      This object is applicable only for Optimux cards.
      The value of this object is a sum of 2**n, where n is a bit assigned to 
      a certain Channel.  Bit='1' means masked.
	  For Optimux-4:
        Bit0: CH1 ; Bit1: CH2 ; Bit2: CH3 ; Bit3: CH4 (Bit='1' means masked).
        Examples:
        - 15 : means that all Channels are masked.
        -  9 : means that Alarms of CH 1 and CH 4 are masked.
      For Optimux-T3:
        Bit0: CH1 ; Bit1: CH2 ; Bit2: CH3 ;.. Bit20: CH21 OR Bit27: CH28.
      For FDSL:
        Bit0..Bit12 : CH1..CH12; Bit13: ETH ; Bit14..Bit15: Uplink1..Uplink2."
      ::= { optMxConfigEntry 14 }

optAisEnable OBJECT-TYPE
      SYNTAX  INTEGER
      {
       notApplicable (1),
       disable       (2),
       enable        (3)
      }            
      MAX-ACCESS  read-write
      STATUS  current
      DESCRIPTION
      "AIS enable/disable.
       notApplicable - for devices that do not support this feature."
      ::= { optMxConfigEntry 15 }

optFarMng  OBJECT-TYPE
      SYNTAX  INTEGER
	      {
		notApplicable (1),
		no            (2),
		yes           (3)
	      }
      MAX-ACCESS  read-write
      STATUS  current
      DESCRIPTION
      "This object is used by Optimux-XL and FomiE3/T3.
       Is there possibility of Far-End Management (no/yes).
       This object is applicable only for the Local device.
       notApplicable - for Remote device and devices that do not support it.
       no -  far-end device is NOT I-Type so it doesn't have a management 
             link to its pair-device.
       yes - far-end device is I-Type so it has a management link to its 
             pair-device."
      ::= { optMxConfigEntry 16 } 

optClockDivision  OBJECT-TYPE
      SYNTAX  INTEGER
	      {
		notApplicable (1),
		noDivision    (2),
		half          (3),
		quarter       (4)
	      }
      MAX-ACCESS  read-write
      STATUS  current
      DESCRIPTION
      "This object is applicable only for FomiE3/T3 having an HSSI Electrical
       interface.
       It gives the possibility of Clock Division, so that Clock Rate will
       be less than T3/E3.
       notApplicable - for a device that does not support it
       noDivision -  Clock stays as is (Internal or Transparent)
       half       - Clock will be half the original (divided by 2)
       quarter    - Clock will be a quarter of the original (divided by 4)."
      ::= { optMxConfigEntry 17 } 

optDteLoopEnable OBJECT-TYPE
      SYNTAX  INTEGER
      {
       notApplicable (1),
       disable       (2),
       enable        (3)
      }            
      MAX-ACCESS  read-write
      STATUS  current
      DESCRIPTION
      "DTE Loop enable/disable (for example loop command requested 
       by router).
	   This object is applicable only for products having HSSI interface.
       notApplicable - for devices that do not support this feature."
      ::= { optMxConfigEntry 18 }

optGrpClockSourcePrt OBJECT-TYPE
     SYNTAX  Integer32
     MAX-ACCESS  read-write
     STATUS   current
     DESCRIPTION
     "This object is applicable for Optimux-T3, when optGrpClockSource=localExternal.
	       It enables the user to select the Channel or Station Clock from which 
	       the Clock is received.
           Valid values:
           0 = notApplicable
           1..28 (= CH1..CH28).
	       73 = Station Clock.
           Only T1 Channels can be used as Clock Source.
      For Optimux-155/1 refer to product spec for port indexing."
      ::= { optMxConfigEntry 19 }

optIncomingAlarm OBJECT-TYPE
     SYNTAX  INTEGER 
     {
      notApplicable (1),
	  off(2), 
	  on(3)
     }
     MAX-ACCESS  read-only
     STATUS  current
     DESCRIPTION
     "State of the Incoming Alarm (On/Off), via Alarm Relay connector.
      This object is applicable only for Optimux-T3."
      ::= { optMxConfigEntry 20 }

optDefChannelSet OBJECT-TYPE
     SYNTAX  INTEGER 
     {
      notApplicable (1),
	  t1(2), 
	  e1(3)
     }
     MAX-ACCESS  read-write
     STATUS  current
     DESCRIPTION
     "Default configuration for all Optimux Channels: T1 or E1.
      This object is applicable only for Optimux-T3."
      ::= { optMxConfigEntry 21 }

optWaitToRestore OBJECT-TYPE
     SYNTAX  Integer32 
     MAX-ACCESS  read-write
     STATUS  current
     DESCRIPTION
     "This parameter defines the time (sec) device has to wait in the redundant 
      state until it goes back to the default Link."
      ::= { optMxConfigEntry 22 }

optEnforcedLink OBJECT-TYPE
     SYNTAX  INTEGER 
     {
      notApplicable (1),
	  noEnforcement(2), 
	  main(3),			   -- Forced Switch
	  backup(4)		   -- Forced Switch
     }
     MAX-ACCESS  read-write
     STATUS  current
     DESCRIPTION
     "This parameter is not applicable when optRedundancyCnf = off.
      It enables user to enforce a Link in spite of the redundancy mechanism.
      Selecting the noEnforcement(2) value cause return to the usual rules of the 
      redundancy mechanism.
      main (3) and backup (4)  are unconditional (force)."
      ::= { optMxConfigEntry 23 }

optFlipUponEvent  OBJECT-TYPE
     SYNTAX       Integer32
     MAX-ACCESS   read-write
     STATUS       current
     DESCRIPTION
     "This object allows user to define if Flip to the other port will
      be performed (or not), for certain possible events.
      Each event is represented by a bit. The value of the object is a sum
      of 2**n, according to the bits having '1' value.
	  '1' - means that Flip should occur due to this event.
      Bit 0 (LSB) = SD (Signal Degraded)."
     ::= { optMxConfigEntry 24 }

optHwMaskChAlr  OBJECT-TYPE
     SYNTAX  Integer32 
     MAX-ACCESS   read-only
     STATUS   current
     DESCRIPTION
     "Mask Channel Alarm done by the HW dip-switches.
      This object is applicable only for Optimux cards.
      The value of this object is a sum of 2**n, where n is a bit assigned to 
      a certain Channel.
	  For Optimux-16E1:
        Bit0: CH1 ; Bit1: CH2 ; Bit2: CH3 ;.. Bit15: CH16 (Bit='1' means masked).
        Examples:
        -  9 : means that Alarms of CH 1 and CH 4 are masked."
      ::= { optMxConfigEntry 25}

optServiceChExist  OBJECT-TYPE
     SYNTAX  INTEGER 
     {
     notApplicable(1),
	 notExist     (2), 
	 exist        (3)
     }
     MAX-ACCESS   read-only
     STATUS   current
     DESCRIPTION
     "Service Channel Existence indication for each Optimux (local/remote)."
      ::= { optMxConfigEntry 26}

optMaskSystemAlr  OBJECT-TYPE
	SYNTAX	INTEGER 
	{
	off	(2),
	on	(3)
	}
	MAX-ACCESS	 read-write
	STATUS		current
	DESCRIPTION
     "Mask all system alarms for each Optimux (local/remote)."
      ::= {optMxConfigEntry 27}
      
       
-- This table is for XL Optimux, Optimux-T3, FOMi-E3/T3 SA, Optimux-155/1, Optimux 155 DS3
optMxModuleTable OBJECT-TYPE
     SYNTAX  SEQUENCE OF OptMxModuleEntry
     MAX-ACCESS  not-accessible
     STATUS  current
     DESCRIPTION
        "This table defines the type of the module
      enrolled in each slot."
     ::= { optimux 2 }

 optMxModuleEntry OBJECT-TYPE
     SYNTAX OptMxModuleEntry 
     MAX-ACCESS  not-accessible
     STATUS  current
     DESCRIPTION
     "An entry in the Optimux Module  table."
     INDEX   { optMdIdx, optMdSltIdx }
     ::= { optMxModuleTable 1 }

 OptMxModuleEntry ::=
              SEQUENCE {
 		optMdIdx	           INTEGER,
	 	optMdSltIdx 	       Integer32,
 		optMdType 	           INTEGER,
	    optMdHWVersion         DisplayString,
	    optMdModLed 	       OCTET STRING,
	    optMdWaveLength        INTEGER,
	    optMdTimingMode	       INTEGER,
	    optMdStatusIndication  Integer32 
	          }

 optMdIdx OBJECT-TYPE
 SYNTAX  INTEGER {local(1), remote(2) }
 MAX-ACCESS  read-only
 STATUS  current
 DESCRIPTION
 " optMdIdx = 1 is for local Optimux.
   optMdIdx = 2 is for remote Optimux."
  ::= { optMxModuleEntry 1 }

 optMdSltIdx OBJECT-TYPE
    SYNTAX  Integer32
    MAX-ACCESS  read-only
    STATUS  current
    DESCRIPTION
     "For Optimux XL:
        Slot A = 1, Slot B = 2, Slot C = 3, Slot D = 4,
        Slot Link = 5, Slot BU = 6 .
      For FomiE3/R3:
        Slot of Station Clock = 3, Slot of Electrical Link = 4,
        Slot of Optical Main Link = 5, Slot of Optical Backup Link = 6 .
      For Optimux-T3:
        Slot of Station Clock (internal card)= 3, Slot A = 5, Slot B = 6.
      For Optimux-155/1:
        E1/T1 Slot A - 1, E1/T1 Slot B- 2, 
        LINK-A - 5, LINK-B - 6
        Fans moudle - 7
        I/O-1 - 11, I/O-2 -12 ...I/O-6 - 16
      For Optimux-155 DS3:
        Common Logic+E3/T3 Slot A - 1, Common Logic+E3/T3 Slot B- 2, LINK-A - 5, LINK-B - 6"       
     ::= { optMxModuleEntry 2 }

optMdType OBJECT-TYPE
    SYNTAX  INTEGER {
		unknown(1),
		noModule(2),
		e3linkCX34(3),
		e3linkOPT1(4),
		t3linkOPT1(5),
		eth1Port(6),
		e1FourUTP(7),
		e1TwoPort(8),
		e1TwoUB(9),
		t1FourPort(10),
		t1TwoPort(11),
		e1FourRJ45(12),  -- special for XL/16
		e1FourBNC(13),   -- special for XL/16
		e1FourMiniBNC(14),
		sfLink(15),      -- single fiber
		stationClk(16),  -- for E1/E3 products only (not for XL/T1)
		hssi(17),          
		stationClkT3(18),  -- for FOMi-T3 and Optimux-T3 only
		t3linkCX45(19),    -- for FOMi-T3 and Optimux-T3 only
		hs4(20),		   -- for HSM with 4 ports
		hs2(21),		   -- for HSM with 2 ports
		hs1(22),		   -- for HSM with 1 port
		hs1x8M(23),		   -- for HSM with 1 port and 8M
		fastEth(24), 	   -- for fast ethernet with 1 port
		nX64(25),		   -- for N x 64 E1 module
		nX64AndUnbalanced2E1(26), -- N X 64 and unbalanced 2 E1 ports
		nX64AndBalanced2E1(27), -- N X 64 and balanced 2 E1 ports
		nX64T1(28),		   
		nX64T1AndUnbalanced2T1(29), -- N X 64 T1 and unbalanced 2 T1 ports
		nX64T1AndBalanced2T1(30), -- N X 64 T1 and balanced 2 T1 ports
        ds1channels    (31),-- E1/T1 ports of TELCO connector (Balanced)
        op155Fiber   (32),-- OP-155-1 & OP-155-3 Fiber link
        op155SingleFiber(33),-- OP-155-1 Single Fiber Link
        op155coax    (34),-- OP-155-1 & OP-155-3 Coax Link
        op63e1       (35),-- Optimux 155/1 63 E1 main access card
		op84t1       (36),-- Optimux 155/1 84 T1 main access card
 	    op155Ds3Cl   (37),-- Optimux 155/3 Common Logic card with E3 or T3
		ds1channelsUnbalanced (38), -- E1/T1 ports of TELCO connector (Unbalanced)
		fastEthNew (39),  -- for new HW fast ethernet with 1 port
		op2128e1t1 (40), -- Optimux 155/1 21/28 E1/T1 main access card
		op4256e1t1 (41), -- Optimux 155/1 42/56 E1/T1 main access card
		fans       (42), --	Optimux 155/1 fans module
		t1FourRJ45 (43), -- OPTIMUX34 T1
		e1Four2BNC (44)	 -- OPTIMUX34 2BNC E1
	}
    MAX-ACCESS  read-only
    STATUS  current
    DESCRIPTION
     "Module Type and number of connectors."
     ::= { optMxModuleEntry 3 }

optMdHWVersion OBJECT-TYPE
    SYNTAX  DisplayString
    MAX-ACCESS  read-only
    STATUS  current
    DESCRIPTION
     "HW Version of the module."
     ::= { optMxModuleEntry 4 }

optMdModLed OBJECT-TYPE
    SYNTAX  OCTET STRING
    MAX-ACCESS  read-only
    STATUS  current
    DESCRIPTION
     "The meaning of each bit depends on the module type."
     ::= { optMxModuleEntry 5 }

optMdWaveLength OBJECT-TYPE
    SYNTAX  INTEGER {
		notApplicable(1),
		nm850(2),
		nm1300(3),
		nm1300Laser(4),
		nm1550Laser(5)
	}
    MAX-ACCESS  read-only
    STATUS  current
    DESCRIPTION
     "Wave Length of T3/E3 Optical Links in [nm] and specification if Laser or not."
     ::= { optMxModuleEntry 6 }

optMdTimingMode OBJECT-TYPE
    SYNTAX  INTEGER {
		notApplicable(1),
		internal(2),
		external(3),
		lbt(4)		
					}
    MAX-ACCESS  read-write
    STATUS  current
    DESCRIPTION
     "The Module Timing mode."
     ::= { optMxModuleEntry 7 }


optMdStatusIndication OBJECT-TYPE
     SYNTAX  Integer32
     MAX-ACCESS  read-only
     STATUS   current
     DESCRIPTION
     "Indication of Alarm and test status of 
      all interfaces served  by a module.
  
      For Optimux155,  Each interface will be represented by 2 
	  bits  where the 1st  bit (right) will specify alarm status
	  and the 2nd bit will specify test status.
      e.g
      00 - normal
      01 - alarm active
      11 - alarm active + testing
      10 - testing
      
      For bits assignment per interface refer to product spec."
      ::= { optMxModuleEntry 8 }


-- This table is for Optimux T3 that can be in a ring

optimuxRing OBJECT IDENTIFIER  ::=  {optimux 3}

 optFramerPortTable		OBJECT-TYPE
     SYNTAX  SEQUENCE OF OptFramerPortEntry
     MAX-ACCESS  not-accessible
     STATUS  current
     DESCRIPTION
        "This table defines the connection of every ch of the framer."
     ::= {optimuxRing 1}

optFramerPortEntry OBJECT-TYPE
     SYNTAX OptFramerPortEntry 
     MAX-ACCESS  not-accessible
     STATUS  current
     DESCRIPTION
     "An entry in the Optimux Framer port Connections  table."
     INDEX   { optFramerPortIdx }
     ::= { optFramerPortTable 1 }

OptFramerPortEntry ::=
              SEQUENCE {
 		optFramerPortIdx	    Integer32,
	 	optFramerPortConn 		Integer32,
		optFramerPortType		INTEGER,
		optFramerPortFeIpAddr	IpAddress
 	   	    	        }

optFramerPortIdx OBJECT-TYPE
    SYNTAX  Integer32
    MAX-ACCESS  read-only
    STATUS  current
    DESCRIPTION
    " The channel of the Framer. Valid values:1..31."
     ::= { optFramerPortEntry 1 }

optFramerPortConn OBJECT-TYPE
    SYNTAX  Integer32
    MAX-ACCESS  read-write
    STATUS  current
    DESCRIPTION
    "This parameter defines the Framer channel connection.
     The values will be as follows:
     Loop(1),Ch1(2),Ch2(3)....,Ch28(29)."
    ::= { optFramerPortEntry 2 }

optFramerPortType OBJECT-TYPE
    SYNTAX  INTEGER{
	notApplicable (1),
	e1			  (2),
	t1			  (3)
	}			
    MAX-ACCESS  read-write
    STATUS  current
    DESCRIPTION
     "This parameter defines the Framer port (E1 or T1)."
     ::= { optFramerPortEntry 3 }

optFramerPortFeIpAddr	OBJECT-TYPE
   SYNTAX  	IpAddress
   MAX-ACCESS  read-write
   STATUS  current
   DESCRIPTION
   "The IP Address of the opposite optimux in the ring,which this channel connected to."
     ::= { optFramerPortEntry 4 }	

  

optFramerConnChanges 	OBJECT-TYPE
	SYNTAX  			Integer32
	MAX-ACCESS  		read-write
	STATUS 				current
	DESCRIPTION
	"The number of changes in Framer connection table that occured 
	 since last time there was a reset to this parameter"
	::= {optimuxRing 2}

optRing 	OBJECT-TYPE
	SYNTAX  INTEGER {
	pointToPoint(2),
	ring(3),
	drop(4),
	radioRing(5)
	}
	MAX-ACCESS  read-only
	STATUS 		current
	DESCRIPTION
	"Indication about Optimux special behavior:
	pointToPoint(2): regular operation mode (Point to Point).

	ring(3): this optimux is part of a ring.
	operations made on this device may affect other optimuxes in the Ring and vice versa.

	drop(4): enables connection between T3 tributary channel and physical E1/T1 port.
	In this mode there may be no connection between this Optimux and another Optimux
	While working in this mode optimux CANNOT be in PTP or Ring topology.

	radioRing(5): this optimux is part of a ring that may use one or more Radio Links.
	Operations made on this device may affect other optimuxes in the Ring and vice versa."
	::= {optimuxRing 3 }

optRingNeTable OBJECT-TYPE
     SYNTAX  SEQUENCE OF OptRingNeEntry
     MAX-ACCESS  not-accessible
     STATUS  current
     DESCRIPTION
     "This table defines which optimuxes are in the ring and the 
      IP Address of each one."
     ::= { optimuxRing 4}

optRingNeEntry OBJECT-TYPE
     SYNTAX OptRingNeEntry 
     MAX-ACCESS  not-accessible
     STATUS  current
     DESCRIPTION
     "An entry in the Optimux Ring Connections  table."
     INDEX   { optRingNeIdx }
     ::= { optRingNeTable 1 }

OptRingNeEntry ::=
     SEQUENCE {
	 optRingNeIdx	   	Integer32,
     optRingNeIpAddr   	IpAddress
     }

optRingNeIdx 	OBJECT-TYPE
   SYNTAX  Integer32
   MAX-ACCESS  read-only
   STATUS  current
   DESCRIPTION
   "The index of the optimux, starting with next optimux to the current optimux. 
   Valid values:1..28.
   The index is according to the order of optimux connections in the ring.
   Example: 
   1=next optimux to the current, in the ring
   2=next optimux in the ring, after the one having index=1
   etc..
   Last index will be the current optimux, that close the ring. "
   ::= { optRingNeEntry 1 }

optRingNeIpAddr	OBJECT-TYPE
   SYNTAX  	IpAddress
   MAX-ACCESS  read-only
   STATUS  current
   DESCRIPTION
   "The IP Address of each optimux in the ring, according to optRingNeIdx."
   ::= { optRingNeEntry 2 }
   
optRingActiveMode  OBJECT-TYPE
     SYNTAX  INTEGER 
     {
     notApplicable(1),
	 main         (2), 
	 backup       (3)
     }
     MAX-ACCESS   read-only
     STATUS   current
     DESCRIPTION
     "This parameter indicates whether the Ring works in Main or Backup mode."
      ::= { optimuxRing 5}
   	

-- Traps

--NOTIFICATIONS

optimuxEvents OBJECT-IDENTITY
      STATUS  current
	  DESCRIPTION
	  "The events for Optimux."
	  ::= { optimux 0 }

optMxConfigChange NOTIFICATION-TYPE
      OBJECTS  {optIndex,  agnLed }
      STATUS  current
      DESCRIPTION
	  "The trap is sent every time there is a change in
	   the state of one of the PS.."
      ::= { optimuxEvents 1 }

optMxAgentFault NOTIFICATION-TYPE
      OBJECTS  {agnIndication,  agnLed }
      STATUS  current
      DESCRIPTION
	  "The trap is sent every time there is a change in
	   the agnIndication variable.
	   For Optimux XL family, from ver 4.1 and up, this trap should be sent 
	   upon any change in the agnNearFarConnection variable"
      ::= { optimuxEvents 2 }

optLineStatusChange NOTIFICATION-TYPE
      OBJECTS { dsx1LineStatus,
                dsx1LineStatusLastChange }
      STATUS  current
	  DESCRIPTION
      "optLineStatusChange trap is sent when the value of an instance 
       dsx1LineStatus changes. It can be utilized by an NMS to trigger polls.
       When the line status change results from a higher level line status 
       change (i.e. ds3), then no traps for the ds1 are sent."
      ::= { optimuxEvents 3 }

optSlotChange NOTIFICATION-TYPE
        OBJECTS { optMdIdx, optMdSltIdx }
        STATUS  current
        DESCRIPTION
        "This trap alerts the console if there is module
         enrollement/de-enrollement"
        ::= { optimuxEvents 4 }

optLoopbackStatusChange NOTIFICATION-TYPE
      OBJECTS { ifIndex, dsx1LoopbackStatus, dsx3LoopbackStatus }
      STATUS  current
      DESCRIPTION
      "This trap alerts the console if there is changes in the
      loopback status of some of the line."
      ::= { optimuxEvents 5 }

optXlLineStatusChange NOTIFICATION-TYPE
      OBJECTS { ifIndex,  optMdModLed, dsx1LineStatus, dsx3LineStatus }
      STATUS  current
      DESCRIPTION
       "optXlLineStatusChange trap is sent when the value of an instance 
        dsx1LineStatus changes. It can be utilized by an NMS to trigger polls."
      ::= { optimuxEvents 6 }

optRingActiveModeChange NOTIFICATION-TYPE
      OBJECTS { optRingActiveMode}
      STATUS  current
      DESCRIPTION
       "optRingActiveModeChange trap is sent when the value of  
        optRingActiveMode changes."
      ::= { optimuxEvents 7 }


optActiveLinkFlipTrap NOTIFICATION-TYPE
      OBJECTS  { optLinkActive }
      STATUS  current
      DESCRIPTION
      "The trap is sent upon change of Active link module."
      ::= { optimuxEvents 8 }

-- END

-- 
-- file :D:\Synergy\WorkArea\545\mib_rad\txt\webrnger.txt
-- 
--Version:   1.0
--Date:   26.04.98              
--By:       Ilana Schvetz
--File:      webranger.txt
--
--Last update: 14-Aug-2008 by Shay Harari 



--radRouter     OBJECT IDENTIFIER ::= { rad 11 }  
--rtrBridge     OBJECT IDENTIFIER ::= { radRouter 7 }

webranger OBJECT IDENTIFIER ::= { rtrBridge 2 }

wrSysConfig OBJECT IDENTIFIER ::= { webranger 1 }

wrBraodcastCtrlCmd OBJECT-TYPE
       SYNTAX INTEGER {
	   block    (1),
	   forward  (2),
       blockLinkPropagation (3)
	   }
       MAX-ACCESS read-write
       STATUS current
       DESCRIPTION
       "This parameter is a command to the webranger CPU. It
        enables blocking or forwarding broadcast frames, which
        may cause a trigger to a connection.
	  	block (1)   - blocks the broadcast frames.
	  	forward (2) - forwards the broadcast frames.
        blockLinkPropagation (3) - blocks the broadcast frames to the links, tx
        to the LAN. "
       ::= { wrSysConfig 1 }

wrFrSelfLearningMode OBJECT-TYPE
       SYNTAX INTEGER {
	   off (1),
	   on  (2)
	   }
       MAX-ACCESS read-write
       STATUS current
       DESCRIPTION
       "This parameter enables the webranger to learn the DLCi's
        configuration and maintanance protocol. 
        off - will get the configuration by setting it.
        on - disables configuration and start self learning."
       ::= { wrSysConfig 2 }

wrGratuitousArp OBJECT-TYPE
       SYNTAX INTEGER {
	   disable (2),
	   enable  (3)
	   }
       MAX-ACCESS read-write
       STATUS current
       DESCRIPTION
       "This parameter enables/disables the Gratuitous ARP feature.
        When enabled, the feature means: when receiving ARP with sender's 
        Source IP Address that already exists in the ARP table - replace 
        MAC Address with sender's Source MAC Address."
       ::= { wrSysConfig 3 }


wrIpRouterInfo OBJECT IDENTIFIER ::= { webranger 2 }

wrConfigIpDhcp OBJECT IDENTIFIER ::= { wrIpRouterInfo 1 }

wrConfigIpDNS OBJECT IDENTIFIER ::= { wrIpRouterInfo 2 }


wrDhcpAction OBJECT-TYPE
       SYNTAX INTEGER { 
       disable (2),
       enable (3)	   
       }
       MAX-ACCESS read-write
       STATUS current
       DESCRIPTION
       "Activating (disable/enable) DHCP server operation.
        Since DHCP Server and DHCP Relay cannot reside in same device,
        DHCP Relay may be enabled (per interface), only if server action is disabled.

        For some devices, this object is used in order to enable/disable 
        the DHCP Client. See device SDS."
       ::= { wrConfigIpDhcp 1 }

wrDhcpTable OBJECT-TYPE
       SYNTAX SEQUENCE OF WrDhcpEntry
       MAX-ACCESS not-accessible
       STATUS current
       DESCRIPTION
          "A list of DHCP entries. The number of entries is up to
           DHCP current entries, according to the WEBRANger model."
       ::= { wrConfigIpDhcp 2 }

    wrDhcpEntry OBJECT-TYPE
       SYNTAX  WrDhcpEntry
       MAX-ACCESS  not-accessible
       STATUS  current
       DESCRIPTION
           "DHCP parameters per entry of the DHCP table."
       INDEX   { wrDhcpLowIpAddress }
       ::= { wrDhcpTable 1 }

    WrDhcpEntry ::=
       SEQUENCE {
              wrDhcpLowIpAddress
                 IpAddress,
              wrDhcpHighIpAddress
                 IpAddress,
			  wrDhcpIpMaskAddress
                 IpAddress,
			  wrDhcpDefaultGateway
                 IpAddress,
			  wrDhcpPrimaryDNS
                 IpAddress,
			  wrDhcpSecondaryDNS
                 IpAddress,
			  wrDhcpInterface
                 INTEGER,
			  wrDhcpRowStatus
                 RowStatus,
			  wrDhcpIpAddressLeaseTime 
			     Integer32,
			  wrDhcpPoolName 
				  SnmpAdminString,
			  wrDhcpTftpServerIp
                 IpAddress,
			  wrDhcpConfigFileName  
    		     SnmpAdminString
				   }
   
wrDhcpLowIpAddress OBJECT-TYPE
       SYNTAX IpAddress
       MAX-ACCESS read-only
       STATUS current
       DESCRIPTION
           "DHCP Low Ip Address."
       ::= { wrDhcpEntry 1 }


wrDhcpHighIpAddress OBJECT-TYPE
       SYNTAX IpAddress
       MAX-ACCESS read-create
       STATUS current
       DESCRIPTION
           "DHCP High Ip Address."
       ::= { wrDhcpEntry 2 }

wrDhcpIpMaskAddress OBJECT-TYPE
       SYNTAX IpAddress
       MAX-ACCESS read-create
       STATUS current
       DESCRIPTION
           "IP mask Address."
       ::= { wrDhcpEntry 3 }

wrDhcpDefaultGateway OBJECT-TYPE
       SYNTAX IpAddress
       MAX-ACCESS read-create
       STATUS current
       DESCRIPTION
           "Default Gateway's IP Address."
       ::= { wrDhcpEntry 4 }

wrDhcpPrimaryDNS OBJECT-TYPE
       SYNTAX IpAddress
       MAX-ACCESS read-create
       STATUS current
       DESCRIPTION
           "Primary DNS."
       ::= { wrDhcpEntry 5 }

wrDhcpSecondaryDNS OBJECT-TYPE
	   SYNTAX IpAddress  
	   MAX-ACCESS read-create
       STATUS current
       DESCRIPTION
           "Secondary DNS."
       ::= { wrDhcpEntry 6 }

wrDhcpInterface OBJECT-TYPE
       SYNTAX INTEGER { 
       all (1),
       lan1 (2),
       lan2(3),
       anyLan(4),
       wan (5)
       }
       MAX-ACCESS read-create
       STATUS current
       DESCRIPTION
           "The IP addresse allocation is done according to the 
           interface type from which the DHCP request arrives."
       ::= { wrDhcpEntry 7 }


wrDhcpRowStatus OBJECT-TYPE
      SYNTAX  RowStatus
      MAX-ACCESS  read-create
      STATUS  current
      DESCRIPTION
          "This attribute allows to create/delete a row in this table.
          For creating a row, the NMS should set 
          wrDhcpRowStatus.id = active(1).
          For destroying a row, the NMS should set:
          wrDhcpStatus.id = destroy(6).
          Only rows with status active(1) are relevant.
		  The only possible supported RowStatus vaules are
		  active  (1) and destroy (6)."
      ::= { wrDhcpEntry 8 }

wrDhcpIpAddressLeaseTime OBJECT-TYPE 
       SYNTAX   Integer32
       MAX-ACCESS  read-create
       STATUS  current
       DESCRIPTION
          "Allocated IP Address lease time in seconds. 
           A zero  value specifies no time limitation."
     ::= { wrDhcpEntry 9 }
       
wrDhcpPoolName OBJECT-TYPE 
       SYNTAX SnmpAdminString (SIZE (1..10)) 
       MAX-ACCESS  read-create
       STATUS  current
       DESCRIPTION
          "DHCP pool name  - string with max length of 10  characters"
        ::= { wrDhcpEntry 10 }

wrDhcpTftpServerIp OBJECT-TYPE 
       SYNTAX IpAddress  
       MAX-ACCESS  read-create
       STATUS  current
       DESCRIPTION
          "DHCP pool -  TFTP-server IP Address."
        ::= { wrDhcpEntry 11 }

wrDhcpConfigFileName OBJECT-TYPE 
       SYNTAX SnmpAdminString (SIZE (1..50)) 
       MAX-ACCESS  read-create
       STATUS  current
       DESCRIPTION
          "TFTP-name of the configuration File Name for DHCP pool."
        ::= { wrDhcpEntry 12 }


 
-- DHCP (Dynamic Host Configuration Protocol) Pool Allocation Table

dhcpPoolAllocTable OBJECT-TYPE
    SYNTAX SEQUENCE OF DhcpPoolAllocEntry
    MAX-ACCESS not-accessible
    STATUS current
    DESCRIPTION
       "A list of  DHCP  Pool Allocation entries.
       	Each entry (row) consist of a single IP Address belonging to DHCP pool 
       	whose lowest IP address is dhcpPoolAllocLowIpAddress. 
       	This IP address may be offered for leasing, or may already be 
       	leased (in use) by Host it's MacAddress is dhcpPoolAllocMacAddress.
       	Time left for leasing period is indicated by dhcpPoolAllocTimeLeft.
        All posible statuses of IP address are indicated and controlled
        by dhcpPoolAllocFlags"
    ::= { wrConfigIpDhcp 3 }

dhcpPoolAllocEntry OBJECT-TYPE
    SYNTAX  DhcpPoolAllocEntry
    MAX-ACCESS  not-accessible
    STATUS  current
    DESCRIPTION
        "DHCP Pool Allocation parameters per entry of the DHCP Pool Allocation table."
    INDEX   {dhcpPoolAllocLowIpAddress, dhcpPoolAllocLeasingIpAddress}
    ::= { dhcpPoolAllocTable 1 }

DhcpPoolAllocEntry ::=
     SEQUENCE {
            dhcpPoolAllocLowIpAddress
               IpAddress,
            dhcpPoolAllocLeasingIpAddress
               IpAddress,
            dhcpPoolAllocMacAddress
               MacAddress,
            dhcpPoolAllocTimeLeft
              Integer32, 
            dhcpPoolAllocFlags
               INTEGER,
            dhcpPoolAllocFreeCmd
               INTEGER
               }
 

dhcpPoolAllocLowIpAddress  OBJECT-TYPE
     SYNTAX IpAddress
     MAX-ACCESS read-only
     STATUS current
     DESCRIPTION
         "Lowest IP address of this pool, value eqaul to wrDhcpLowIpAddress for 
          the pool."
     ::= { dhcpPoolAllocEntry 1 }

dhcpPoolAllocLeasingIpAddress OBJECT-TYPE
     SYNTAX IpAddress
     MAX-ACCESS read-only
     STATUS current
     DESCRIPTION
         "Single IP Address belonging to dhcp pool whose Lowest Ip Address is 
         dhcpPoolAllocLowIpAddress. This IP address may be offered for leasing
         or may be leased by Host its MacAddress is dhcpPoolAllocMacAddress.
         All posible statuses of IP address are indicated by dhcpPoolAllocFlags     "
     ::= { dhcpPoolAllocEntry 2 }

dhcpPoolAllocMacAddress OBJECT-TYPE
     SYNTAX  MacAddress
     MAX-ACCESS read-only
     STATUS current
	 DESCRIPTION
     "MAC Address to which the IP address has been leased "
     ::= { dhcpPoolAllocEntry 3 }
 
dhcpPoolAllocTimeLeft OBJECT-TYPE
     SYNTAX Integer32 
     MAX-ACCESS read-only
     STATUS current
	 DESCRIPTION
         "IP address leasing time left in seconds "
     ::= { dhcpPoolAllocEntry 4 }



dhcpPoolAllocFlags OBJECT-TYPE
     SYNTAX INTEGER
            {
             notApplicable (1),
			 free (2),
			 inUse (3),
			 offered (4),
			 forbidden (5)         
             } 
     MAX-ACCESS read-only
     STATUS current
     DESCRIPTION
     "These flags indicates status of each IP address. 
     User may change value to free, via dhcpPoolAllocFreeCmd "
     ::= { dhcpPoolAllocEntry 5 }


dhcpPoolAllocFreeCmd OBJECT-TYPE
     SYNTAX INTEGER
            {
             off (2),
			 on (3)
             } 
     MAX-ACCESS read-write
     STATUS current
     DESCRIPTION
	"Setting this attribute to On (3), will enforce the agent to 
	 Free this entry.
	 The Agent will change the value of this MIB object to off(2) 
	 automatically, after performing the command.
	 Setting this object to off(2), will do nothing"
     ::= { dhcpPoolAllocEntry 6 }



--DHCP Relay Table

dhcpRelayTable OBJECT-TYPE
    SYNTAX SEQUENCE OF DhcpRelayEntry
    MAX-ACCESS not-accessible
    STATUS current
    DESCRIPTION
       "A list of DHCP relay entries."
    ::= { wrConfigIpDhcp 4 }

dhcpRelayEntry OBJECT-TYPE
    SYNTAX  DhcpRelayEntry
    MAX-ACCESS  not-accessible
    STATUS  current
    DESCRIPTION
        "DHCP Relay parameters per entry of the DHCP relay table."
    INDEX   { ifIndex }
    ::= { dhcpRelayTable 1 }

DhcpRelayEntry ::=
     SEQUENCE {
			dhcpRelayAction
			   INTEGER, 
            dhcpRelayServerIpAddress
               IpAddress,
            dhcpRelayMaxHop
               Integer32
               }
   
dhcpRelayAction OBJECT-TYPE
     SYNTAX INTEGER
            {
			disable (2),
            enable (3) 
			 } 
     MAX-ACCESS read-write
     STATUS current
     DESCRIPTION
	"Setting this attribute to enable (3), will  
	 enable DHCP Relay action for this interface 
	 (Only if DHCP Server is disabled for device - wrDhcpAction=disable).
	 dhcpRelayServerIpAddressaddress should not be 0.0.0.0 when enable is set"
     ::= { dhcpRelayEntry 1 }


dhcpRelayServerIpAddress OBJECT-TYPE
     SYNTAX IpAddress
     MAX-ACCESS read-write
     STATUS current
     DESCRIPTION
         "DHCP Server IP Address."
     ::= { dhcpRelayEntry 2 }


dhcpRelayMaxHop OBJECT-TYPE
     SYNTAX Integer32 
     MAX-ACCESS read-write
     STATUS current
          DESCRIPTION
         "Maximum number of hops till DHCP Server.
          upper limit is 16 hops"
     DEFVAL {16}
     ::= { dhcpRelayEntry 3 }


wrDhcpPort OBJECT-TYPE
	  SYNTAX  INTEGER
	  { 
       notApplicable	(1),
       all          	(2),
       outOfBand 		(3),
       lan1 			(4),
	   lan2				(5)
       }

      MAX-ACCESS  read-write
      STATUS  current
      DESCRIPTION
          "This parameter defines the port that DHCP flow will be actiavted."
      ::= { wrConfigIpDhcp 5}


--DHCP Client Table

dhcpClientTable OBJECT-TYPE
    SYNTAX SEQUENCE OF DhcpClientEntry
    MAX-ACCESS not-accessible
    STATUS current
    DESCRIPTION
    "A list of DHCP client entries."
    ::= { wrConfigIpDhcp 6 }

dhcpClientEntry OBJECT-TYPE
    SYNTAX  DhcpClientEntry
    MAX-ACCESS  not-accessible
    STATUS  current
    DESCRIPTION
    "DHCP Client parameters per entry of the DHCP Client table."
    INDEX   { ifIndex }
    ::= { dhcpClientTable 1 }

DhcpClientEntry ::=
     SEQUENCE {
	 dhcpClientAction
	 INTEGER, 
     dhcpClientServerIpAddress
     IpAddress,
     dhcpClientLeaseExpirationTime
     Integer32,
	 dhcpClientStatus
	 DisplayString
     }

dhcpClientAction OBJECT-TYPE
     SYNTAX INTEGER
      {
	 	disable (2),
        enable (3) 
	  } 
     MAX-ACCESS read-write
     STATUS current
     DESCRIPTION
	"This parameter default value is enable(3).
	 Setting this attribute to disable (2), will  
	 disable DHCP Client action for this interface.
	 This parameter can be changed to disable (2) only 
	 (it cannot be changed from disable to enable)."
     ::= { dhcpClientEntry 1 }

dhcpClientServerIpAddress OBJECT-TYPE
     SYNTAX IpAddress
     MAX-ACCESS read-write
     STATUS current
     DESCRIPTION
     "DHCP Server IP Address."
     ::= { dhcpClientEntry 2 }

dhcpClientLeaseExpirationTime OBJECT-TYPE
     SYNTAX Integer32 
     MAX-ACCESS read-only
     STATUS current
     DESCRIPTION
     "This parameter holds the time (in minutes) left until lease expiration."
     ::= { dhcpClientEntry 3 }

dhcpClientStatus OBJECT-TYPE
     SYNTAX DisplayString
     MAX-ACCESS read-only
     STATUS current
     DESCRIPTION
     "This parametr displays the DHCP status."
     ::= { dhcpClientEntry 4 }


--DHCP Interface Client Table

dhcpIfClientTable OBJECT-TYPE
    SYNTAX SEQUENCE OF DhcpIfClientEntry
    MAX-ACCESS not-accessible
    STATUS current
    DESCRIPTION
    "DHCP client entries for each Interface."
    ::= { wrConfigIpDhcp 7 }

dhcpIfClientEntry OBJECT-TYPE
    SYNTAX  DhcpIfClientEntry
    MAX-ACCESS  not-accessible
    STATUS  current
    DESCRIPTION
    "DHCP Clients per entry of the DHCP Interface Client table."
    INDEX   { ifIndex, dhcpIfClientIpAddress }
    ::= { dhcpIfClientTable 1 }

DhcpIfClientEntry ::=
     SEQUENCE {
	 dhcpIfClientIpAddress
     IpAddress,
     dhcpIfClientRowStatus
	 RowStatus
     }

dhcpIfClientIpAddress OBJECT-TYPE
     SYNTAX IpAddress
     MAX-ACCESS read-only
     STATUS current
     DESCRIPTION
     "DHCP Client IP Address."
     ::= { dhcpIfClientEntry 2 }

dhcpIfClientRowStatus OBJECT-TYPE
     SYNTAX      RowStatus
     MAX-ACCESS  read-create
     STATUS      current
     DESCRIPTION
     "The row status used for creating, modifying, and deleting instances 
     of the columnar objects in the dhcpIfClientTable.
     
     For Vmux Devices, it will be possible only to Delete instances.
     The addition of Clients will be done automatically by the Server according
     to Network messages that are sent by the Clients; not via SNMP.

     In order to Delete a Client, this MIB object should be set to: destroy (6)."
     ::= { dhcpIfClientEntry 3 }

dhcpServerAction OBJECT-TYPE
    SYNTAX  INTEGER {
       noOp(2),       
       deleteAllClients(3)
     }
    MAX-ACCESS  read-write
    STATUS  current
    DESCRIPTION
	"This variable enables the operator to perform one of the
	specified actions on the Server.
      deleteAllClients (3) is an option that is used for a device functioning as a server.
      It will remove all the clients from all the interfaces of the device.
      When the operation is complete, the agent will return a noOp (2) value."
   ::= { wrConfigIpDhcp 8 }


-- DHCP Client Table (New)

dhcpClientNTable OBJECT-TYPE
	SYNTAX		SEQUENCE OF DhcpClientNEntry
	MAX-ACCESS	not-accessible
	STATUS		current
	DESCRIPTION
		"The DHCP Client table (New)."
	::= { wrConfigIpDhcp 9 }

dhcpClientNEntry OBJECT-TYPE
	SYNTAX		DhcpClientNEntry
	MAX-ACCESS	not-accessible
	STATUS		current
	DESCRIPTION
		"An entry of this table."
	INDEX		{ dhcpClientIndex }
	::= { dhcpClientNTable 1 }

DhcpClientNEntry ::=
	SEQUENCE {
		dhcpClientIndex						Unsigned32,
		dhcpClientAdminStatus				INTEGER,
		dhcpClientOperStatus				INTEGER,
		dhcpClientAddressType				InetAddressType,
		dhcpClientAddress					InetAddress,
		dhcpClientAddressMask				InetAddress,
		dhcpClientNextHop					InetAddress,
		dhcpClientServerAddress				InetAddress,
		dhcpClientActualLeaseTime	  		Unsigned32,
		dhcpClientRemainLeaseTime			Unsigned32,
		dhcpClientCommand					INTEGER,
		dhcpClientOpAdminStatus				BITS,
		dhcpClientOpVendorClassId			SnmpAdminString,  -- option 60
		dhcpClientOpIpAddrLeaseTime  		Unsigned32,       -- option 51
		dhcpClientOpServerId				IpAddress,        -- option 54
		dhcpClientOpClientIdType			Unsigned32,       -- option 61
		dhcpClientOpClientId				SnmpAdminString,  -- option 61
		dhcpClientOpHostName				SnmpAdminString,  -- option 12
		dhcpClientOpDns						OCTET STRING,     -- option 6
		dhcpClientOpTftpServerName			SnmpAdminString,  -- option 66
		dhcpClientOpBootFileName			SnmpAdminString   -- option 67
	}

dhcpClientIndex OBJECT-TYPE
	SYNTAX		Unsigned32
	MAX-ACCESS	not-accessible
	STATUS		current
	DESCRIPTION
		"The DHCP Client index.
		 Index can be ifIndex and/or index of a router interface or host."
	::= { dhcpClientNEntry 1 }

dhcpClientAdminStatus OBJECT-TYPE
	SYNTAX		INTEGER
	{
		down		(2),
		up			(3) 
	} 
	MAX-ACCESS	read-write
	STATUS		current
	DESCRIPTION
		"The Administrative Status of DHCP client."
	::= { dhcpClientNEntry 2 }

dhcpClientOperStatus OBJECT-TYPE
	SYNTAX		INTEGER
	{
		notHoldingLease				(2),
		holdingLease				(3),
		locatingAvailableServer		(4),
		failedToGetLease			(5),
		initializing				(6)
	} 
	MAX-ACCESS	read-only
	STATUS		current
	DESCRIPTION
		"The Operational Status of DHCP client."
	::= { dhcpClientNEntry 3 }

dhcpClientAddressType OBJECT-TYPE
	SYNTAX		InetAddressType
	MAX-ACCESS	read-write
	STATUS		current
	DESCRIPTION
		"The Address Type of all InetAddress objects."
	::= { dhcpClientNEntry 4 }

dhcpClientAddress OBJECT-TYPE
	SYNTAX		InetAddress
	MAX-ACCESS	read-only
	STATUS		current
	DESCRIPTION
		"The DHCP Client Address, which is assigned by the DHCP server."
	::= { dhcpClientNEntry 5 }

dhcpClientAddressMask OBJECT-TYPE
	SYNTAX		InetAddress
	MAX-ACCESS	read-only
	STATUS		current
	DESCRIPTION
		"The DHCP Client Address Mask, which is assigned by the DHCP server."
	::= { dhcpClientNEntry 6 }

dhcpClientNextHop OBJECT-TYPE
	SYNTAX		InetAddress
	MAX-ACCESS	read-only
	STATUS		current
	DESCRIPTION
		"The Next Hop (Default Gateway) of the DHCP client."
	::= { dhcpClientNEntry 7 }

dhcpClientServerAddress OBJECT-TYPE
	SYNTAX		InetAddress
	MAX-ACCESS	read-write
	STATUS		current
	DESCRIPTION
		"The DHCP Server Address.
		 Although object is defined as read-write, current support is read-only."
	::= { dhcpClientNEntry 8 }

dhcpClientActualLeaseTime OBJECT-TYPE
	SYNTAX		Unsigned32
	MAX-ACCESS	read-only
	STATUS		current
	DESCRIPTION
		"The Actual Lease Time (for Address received from the server),
		 measured in seconds.
		 Value=FFFFFFFF represents an infinite actual lease time."
	::= { dhcpClientNEntry 9 }

dhcpClientRemainLeaseTime OBJECT-TYPE
	SYNTAX		Unsigned32
	MAX-ACCESS	read-only
	STATUS		current
	DESCRIPTION
		"The Remaining Lease Time (for Address received from the server),
		 measured in seconds.
		 Value=FFFFFFFF represents an infinite remaining lease time."
	::= { dhcpClientNEntry 10 }

dhcpClientCommand OBJECT-TYPE
	SYNTAX		INTEGER
	{
		off			(2),
		renew		(3),	-- renew current lease
		release		(4)		-- release current lease
	} 
	MAX-ACCESS	read-write
	STATUS		current
	DESCRIPTION
		"The possible commands of DHCP client to DHCP server.
		 Upon performing a command, value should be automatically returned to off(2)."
	::= { dhcpClientNEntry 11 }

dhcpClientOpAdminStatus OBJECT-TYPE
	SYNTAX		BITS
	{
		vendorClassId		(0),  -- Vendor Class Identifier	(option 60) 
		ipAddrLeaseTime		(1),  -- IP Address Lease Time		(option 51) 
		serverId			(2),  -- Server Identifier			(option 54) 
		clientId			(3),  -- Client Identifier			(option 61) 
		hostName			(4),  -- Host Name				 	(option 12) 
		dns					(5),  -- Domain Name Server (DNS) 	(option 6)  
		tftpServerName		(6),  -- TFTP Server Name		 	(option 66) 
		bootFileName		(7)   -- Boot File Name			 	(option 67) 
	}
	MAX-ACCESS	read-write
	STATUS		current
	DESCRIPTION
		"The Administrative Status of the different options.
		 Bit=1 means that respective option is enabled/activated."
	REFERENCE
		"RFC-2132."
	::= { dhcpClientNEntry 12 }

dhcpClientOpVendorClassId OBJECT-TYPE
	SYNTAX		SnmpAdminString
	MAX-ACCESS	read-write
	STATUS		current
	DESCRIPTION
		"The Vendor Class Identifier.
		 Identifier should include at least 1 character."
	REFERENCE
		"RFC-2132, Option 60, Identifier."
	::= { dhcpClientNEntry 13 }

dhcpClientOpIpAddrLeaseTime OBJECT-TYPE
	SYNTAX		Unsigned32
	MAX-ACCESS	read-write
	STATUS		current
	DESCRIPTION
		"The IP Address Lease Time, measured in seconds."
	REFERENCE
		"RFC-2132, Option 51, Time."
	::= { dhcpClientNEntry 14 }

dhcpClientOpServerId OBJECT-TYPE
	SYNTAX		IpAddress
	MAX-ACCESS	read-write
	STATUS		current
	DESCRIPTION
		"The Server Identifier (reported IP Address)."
	REFERENCE
		"RFC-2132, Option 54, IPv4 Address."
	::= { dhcpClientNEntry 15 }

dhcpClientOpClientIdType OBJECT-TYPE
	SYNTAX		Unsigned32
	MAX-ACCESS	read-write
	STATUS		current
	DESCRIPTION
		"The Client Identifier Type.

		 Type=0 indicates that Client Identifier is a string,
		 which is set by dhcpClientOpClientId.

		 Type=1 indicates that Client Identifier represents
		 the Ethernet Hardware Address (MAC)."
	REFERENCE
		"RFC-2132, Option 61, Type."
	::= { dhcpClientNEntry 16 }

dhcpClientOpClientId OBJECT-TYPE
	SYNTAX		SnmpAdminString
	MAX-ACCESS	read-write
	STATUS		current
	DESCRIPTION
		"The Client Identifier.
		 Identifier should include at least 1 character.

		 When Type=1 (dhcpClientOpClientIdType),
		 it means that current object is read-only
		 as it represents the Ethernet Hardware Address (MAC)."
	REFERENCE
		"RFC-2132, Option 61, Identifier."
	::= { dhcpClientNEntry 17 }

dhcpClientOpHostName OBJECT-TYPE
	SYNTAX		SnmpAdminString
	MAX-ACCESS	read-write
	STATUS		current
	DESCRIPTION
		"The Host Name.
		 Name should include at least 1 character."
	REFERENCE
		"RFC-2132, Option 12, Host."
	::= { dhcpClientNEntry 18 }

dhcpClientOpDns OBJECT-TYPE
	SYNTAX		OCTET STRING
	MAX-ACCESS	read-only
	STATUS		current
	DESCRIPTION
		"The Domain Name Server (DNS),
		 which is a list of servers available to the client.
		 This object should include at least 4 octets
		 and must always be a multiple of 4 octets."
	REFERENCE
		"RFC-2132, Option 6, List of Addresses."
	::= { dhcpClientNEntry 19 }

dhcpClientOpTftpServerName OBJECT-TYPE
	SYNTAX		SnmpAdminString
	MAX-ACCESS	read-only
	STATUS		current
	DESCRIPTION
		"The TFTP Server Name.
		 Name should include at least 1 character."
	REFERENCE
		"RFC-2132, Option 66, Server."
	::= { dhcpClientNEntry 20 }

dhcpClientOpBootFileName OBJECT-TYPE
	SYNTAX		SnmpAdminString
	MAX-ACCESS	read-only
	STATUS		current
	DESCRIPTION
		"The Boot File Name.
		 Name should include at least 1 character."
	REFERENCE
		"RFC-2132, Option 67, Name."
	::= { dhcpClientNEntry 21 }


wrDNSRelayAction OBJECT-TYPE
       SYNTAX INTEGER { 
       notApplicable (1),
       disable       (2),
       enable        (3) 
       }
       MAX-ACCESS read-write
       STATUS current
       DESCRIPTION
       "When Enabled, device will act as a DNS Relay:
        whenever the device receives a DNS request from its host,
        it will forward it to the DNS server 
        as if the request was initiated by the  device itself.
        The reply from the DNS server is forwarded by the
        device to the host as if the device 
        was	answering the request."
       ::= { wrConfigIpDNS  1 }

wrConfigIpxRouterInfo OBJECT IDENTIFIER ::= { webranger 3 }

wrAutoLearnLanIpxNets OBJECT-TYPE
       SYNTAX INTEGER { 
       disable (2),
       enable (3)
       }
       MAX-ACCESS read-write
       STATUS current
       DESCRIPTION
           "Activating (disable/enable) the auto-learn operation."
       ::= { wrConfigIpxRouterInfo 1 }

wrLanIpxNetTable OBJECT-TYPE
       SYNTAX SEQUENCE OF WrLanIpxNetEntry
       MAX-ACCESS not-accessible
       STATUS current
       DESCRIPTION
           "Lan IPX nets Table."
       ::= { wrConfigIpxRouterInfo 2 }

wrLanIpxNetEntry OBJECT-TYPE
SYNTAX WrLanIpxNetEntry
MAX-ACCESS not-accessible
       STATUS current
       DESCRIPTION
          "IPX Nets per frame type & LAN port. The table entries 
           will be created by the agent"
INDEX   { wrLanifIndex, wrLanIpxFrameType }
       ::= { wrLanIpxNetTable 1 }

WrLanIpxNetEntry ::=
       SEQUENCE {
         wrLanifIndex
               Integer32,
         wrLanIpxFrameType
               INTEGER,
         wrIpxNetAddress
	           IpAddress
          }

wrLanifIndex OBJECT-TYPE 
          SYNTAX Integer32
          MAX-ACCESS  read-only
          STATUS  current
          DESCRIPTION
             "LAN port ifIndex."
          ::= { wrLanIpxNetEntry 1 }

wrLanIpxFrameType OBJECT-TYPE 
          SYNTAX  INTEGER{ 
          t8023 (1),
          ethernet (2),
          t8022(3),
          snap (4)
          }
          MAX-ACCESS  read-only
          STATUS  current
          DESCRIPTION
             "Frame Type"
          ::= { wrLanIpxNetEntry 2 }

wrIpxNetAddress OBJECT-TYPE 
          SYNTAX IpAddress
          MAX-ACCESS  read-write
          STATUS  current
          DESCRIPTION
             "Net address per Frame Type & LAN port."
          ::= { wrLanIpxNetEntry 3 }

wrDialInIpxNet OBJECT-TYPE
       SYNTAX IpAddress
       MAX-ACCESS read-write
       STATUS current
       DESCRIPTION
           "Net address through a link."
       ::= { wrConfigIpxRouterInfo 3 }

-- The RIP/SAP Interface Configuration Table.

    ripSapIfConfTable OBJECT-TYPE
        SYNTAX   SEQUENCE OF RipSapIfConfEntry
        MAX-ACCESS   not-accessible
        STATUS   current
        DESCRIPTION
           "A list of Interfaces which require separate
           configuration in RIP/SAP."
       ::= { wrConfigIpxRouterInfo 4 }

   ripSapIfConfEntry OBJECT-TYPE
       SYNTAX   RipSapIfConfEntry
       MAX-ACCESS   not-accessible
       STATUS   current
       DESCRIPTION
          "A Single Routing Domain in a single Subnet."
      INDEX { ripSapIfConfIfIndex }
      ::= { ripSapIfConfTable 1 }

    RipSapIfConfEntry ::=
        SEQUENCE {
            ripSapIfConfIfIndex
                Integer32,
            ripSapIfConfMode
                INTEGER,
            ripSapIfConfStatus
                RowStatus
    }

    ripSapIfConfIfIndex OBJECT-TYPE
        SYNTAX   Integer32
        MAX-ACCESS   read-only
        STATUS   current
        DESCRIPTION
           "The interface ifIndex."
       ::= { ripSapIfConfEntry 1 }

    ripSapIfConfMode OBJECT-TYPE
        SYNTAX   INTEGER {
		off(1),
		on (2)
		}
        MAX-ACCESS   read-create
        STATUS   current
        DESCRIPTION
           "The ifIndex RIP/SAP mode."
       ::= { ripSapIfConfEntry 2 }

    ripSapIfConfStatus OBJECT-TYPE
       SYNTAX RowStatus
       MAX-ACCESS read-create
       STATUS current
       DESCRIPTION
           "This attribute allows to create/delete a row in this table.
            For creating a row, the NMS should set 
            ripSapIfConfStatus.id1 = active(1).
            For destroying a row, the NMS should set:
            ripSapIfConfStatus.id1 = destroy(6).
            Only rows with status active(1) are relevant.
		    The only possible supported RowStatus vaules are
		    active  (1) and destroy (6)."
       ::= { ripSapIfConfEntry 3 }

wrInterface OBJECT IDENTIFIER ::= { webranger 4 }

wrIpAddressTable OBJECT-TYPE
       SYNTAX SEQUENCE OF WrIpAddressEntry
       MAX-ACCESS not-accessible
       STATUS current
       DESCRIPTION
           "Link IP addresses Table."
       ::= { wrInterface 1 }

wrIpAddressEntry OBJECT-TYPE
       SYNTAX WrIpAddressEntry
       MAX-ACCESS not-accessible
       STATUS current
       DESCRIPTION
          "Ip Address per Link"
       INDEX   { wrIpIfIndex }
       ::= { wrIpAddressTable 1 }

WrIpAddressEntry ::=
       SEQUENCE {
           wrIpIfIndex
		      Integer32,
           wrIpAddress
              IpAddress,
           wrIpMask
              IpAddress,
		   wrIpRowStatus
		      RowStatus
}

wrIpIfIndex OBJECT-TYPE
       SYNTAX Integer32
       MAX-ACCESS read-only
       STATUS current
       DESCRIPTION
           "Port interface index."
       ::= { wrIpAddressEntry 1 }

wrIpAddress OBJECT-TYPE
       SYNTAX IpAddress
       MAX-ACCESS read-create
       STATUS current
       DESCRIPTION
           "Link IP Address."
       ::= { wrIpAddressEntry 2 }

wrIpMask OBJECT-TYPE
       SYNTAX IpAddress
       MAX-ACCESS read-create
       STATUS current
       DESCRIPTION
           "Link IP mask Address."
       ::= { wrIpAddressEntry 3 }

wrIpRowStatus OBJECT-TYPE
       SYNTAX RowStatus
       MAX-ACCESS read-create
       STATUS current
       DESCRIPTION
           "This attribute allows to create/delete a row in this table.
            For creating a row, the NMS should set 
            wrIpRowStatus.id1 = active(1).
            For destroying a row, the NMS should set:
            wrIpRowStatus.id1 = destroy(6).
            Only rows with status active(1) are relevant.
		    The only possible supported RowStatus vaules are
		    active  (1) and destroy (6)." 
       ::= { wrIpAddressEntry 4 }

wrSpoofingTable OBJECT-TYPE
       SYNTAX SEQUENCE OF WrSpoofingEntry
       MAX-ACCESS not-accessible
       STATUS current
       DESCRIPTION
           "Spoofing Table."
       ::= { wrInterface 2 }

wrSpoofingEntry OBJECT-TYPE
       SYNTAX WrSpoofingEntry
       MAX-ACCESS not-accessible
       STATUS current
       DESCRIPTION
          "Spoofing per Link"
       INDEX   { wrSpoofingIfIndex }
       ::= { wrSpoofingTable 1 }

WrSpoofingEntry ::=
       SEQUENCE {
           wrSpoofingIfIndex
		      Integer32,
           wrSpoofingAction
		      Integer32,
           wrSpoofingAgingStation
              Integer32,
		   wrSpoofingRowStatus
		      RowStatus
}

wrSpoofingIfIndex OBJECT-TYPE
       SYNTAX Integer32
       MAX-ACCESS read-only
       STATUS current
       DESCRIPTION
           "Port interface index."
       ::= { wrSpoofingEntry 1 }


wrSpoofingAction  OBJECT-TYPE
       SYNTAX Integer32 
       MAX-ACCESS read-create
       STATUS current
       DESCRIPTION
	       "Spoofing action is applied by bit code:
            enable        :  bit 0 set (disable: bit 0 is 0)
            keepAlive     :  bit 1
               ...        :  bit 2
            and so on.
            For the above example, to set spoofing to keepAlive action,
            the object's value will be 3 = [ 2**0 + 2**1 ] 
            Only the Remote WEBRANger will accept this object !
                  -------                                  "
       ::= { wrSpoofingEntry 2 }

wrSpoofingAgingStation  OBJECT-TYPE
       SYNTAX Integer32 
       MAX-ACCESS read-create
       STATUS current
       DESCRIPTION
         " Aging time of stations list, in min. The agent 'translates'
           the time entered in minutes, to 10 min. resolution, as
		   follows: 
		   1..10  min - 10 min
		   11..20 min - 20 min
		   and so on...
		   0 is not a valid value.
           Only the Remote WEBRANger will accept this object !
                    ----------------                          "
       ::= { wrSpoofingEntry 3 }

wrSpoofingRowStatus OBJECT-TYPE
       SYNTAX RowStatus
       MAX-ACCESS read-create
       STATUS current
       DESCRIPTION
           "This attribute allows to create/delete a row in this table.
            For creating a row, the NMS should set 
            wrSpoofingRowStatus.id1 = active(1).
            For destroying a row, the NMS should set:
            wrSpoofingRowStatus.id1 = destroy(6).
            Only rows with status active(1) are relevant.
		    The only possible supported RowStatus vaules are
		    active  (1) and destroy (6)."
       ::= { wrSpoofingEntry 4 }


wrLanIfTable OBJECT-TYPE
       SYNTAX SEQUENCE OF WrLanIfEntry
       MAX-ACCESS not-accessible
       STATUS current
       DESCRIPTION
           "Link IP addresses Table."
       ::= { wrInterface 3 }

wrLanIfEntry OBJECT-TYPE
       SYNTAX WrLanIfEntry
       MAX-ACCESS not-accessible
       STATUS current
       DESCRIPTION
          "Ip Address per Link"
       INDEX   { wrLanIfIndex }
       ::= { wrLanIfTable 1 }

WrLanIfEntry ::=
       SEQUENCE {
           wrLanIfIndex
		      Integer32,
           wrLanBridgeRouterMode
              INTEGER,
		   wrLanIfState
		      INTEGER,
		   wrLanIfRdnTimeout
		      Integer32
       }

wrLanIfIndex OBJECT-TYPE
       SYNTAX Integer32
       MAX-ACCESS read-only
       STATUS current
       DESCRIPTION
           "Port interface index."
       ::= { wrLanIfEntry 1 }

wrLanBridgeRouterMode OBJECT-TYPE
     SYNTAX INTEGER {
              unknown         (1),
              bridge          (2),
              ipRouter        (3),
              ipxRouter       (4),
              ipAndIpxRouter  (5),
              bRouter         (6),
			  ipBrouter       (7),
			  ipxBrouter      (8),
			  ipAndIpxBrouter (9),
			  bridgeAndStp    (10)
              }
     MAX-ACCESS read-write
     STATUS current
     DESCRIPTION
         "This parameter indicates whether the link is Bridge 
          or Router	and specifies the Router's type."
     ::= { wrLanIfEntry 2 }

wrLanIfState OBJECT-TYPE
       SYNTAX INTEGER {      
              disable(2),
              enable (3),
			  redundancy(4)
	      }
       MAX-ACCESS read-write
       STATUS current
       DESCRIPTION
	   "The LAN is  disabled or enabled.
	    For LAN 2 it can be also 'redundancy'."
       ::= { wrLanIfEntry 3 }

wrLanIfRdnTimeout OBJECT-TYPE
       SYNTAX Integer32       
       MAX-ACCESS read-write
       STATUS current
       DESCRIPTION
	   "LAN Redundancy Timeout in seconds.
	    Applicable when wrLanIfState=redundancy."
       ::= { wrLanIfEntry 4 }

wrSyncCnfgTable OBJECT-TYPE
       SYNTAX SEQUENCE OF WrSyncCnfgEntry
       MAX-ACCESS not-accessible
       STATUS current
       DESCRIPTION
           "Configuration table for Async interface."
       ::= { wrInterface 4 }

wrSyncCnfgEntry OBJECT-TYPE
       SYNTAX WrSyncCnfgEntry
       MAX-ACCESS not-accessible
       STATUS current
       DESCRIPTION
          "Configuration table"
       INDEX   { wrSyncIfIndex }
       ::= { wrSyncCnfgTable 1 }

WrSyncCnfgEntry ::=
       SEQUENCE {
           wrSyncIfIndex
		      Integer32,
           wrSyncClkMode
              INTEGER,
           wrSyncClkRate
              INTEGER
       }

wrSyncIfIndex OBJECT-TYPE
       SYNTAX Integer32
       MAX-ACCESS read-only
       STATUS current
       DESCRIPTION
           "Sync interface index."
       ::= { wrSyncCnfgEntry 1 }

wrSyncClkMode OBJECT-TYPE
     SYNTAX INTEGER {
              notApplicable   (1),
              manual          (2),
              program         (3)
              }
     MAX-ACCESS read-write
     STATUS current
     DESCRIPTION
         "Clock Mode."
     ::= { wrSyncCnfgEntry 2 }

wrSyncClkRate OBJECT-TYPE
     SYNTAX INTEGER {

              notApplicable   (1),
              r16             (2),
              r32             (3),
              r48             (4),
              r64             (5),
              r96             (6),
              r128            (7),
			  r256            (8),
			  r768            (9)
              }
     MAX-ACCESS read-write
     STATUS current
     DESCRIPTION
         "Clock Rate in. Rate can be changed if Clock Mode is Program only."
     ::= { wrSyncCnfgEntry 3 }



wrFrCnfgTable OBJECT-TYPE
       SYNTAX SEQUENCE OF WrFrCnfgEntry
       MAX-ACCESS not-accessible
       STATUS current
       DESCRIPTION
           "Configuration table for Fr parameters that do not exist in RFC2115."
       ::= { wrInterface 5 }

wrFrCnfgEntry OBJECT-TYPE
       SYNTAX WrFrCnfgEntry
       MAX-ACCESS not-accessible
       STATUS current
       DESCRIPTION
           "Configuration entry for Fr parameters that do not exist in RFC2115."
       INDEX   { ifIndex }
       ::= { wrFrCnfgTable 1 }

WrFrCnfgEntry ::=
       SEQUENCE {
           wrFrDlciLearningMode
		      INTEGER,
		   wrFrCllmMessages
              INTEGER
       }

wrFrDlciLearningMode OBJECT-TYPE
       SYNTAX INTEGER {
	   off (2),
	   on  (3)
	   }
       MAX-ACCESS read-write
       STATUS current
       DESCRIPTION
           "This parameter enables the webranger to learn the DLCi's
            configuration and maintanance protocol for the current interface. 
            off - the WR will read the user's configuration for this interface.
            on -  the WR will begin self learning of the current interface's maintanance
                  protocol and DLCIs."
       ::= { wrFrCnfgEntry 1 }

wrFrCllmMessages OBJECT-TYPE
       SYNTAX INTEGER {
	   disable (2),
	   enable  (3)
	   }
       MAX-ACCESS read-write
       STATUS current
       DESCRIPTION
           "This parameter enables/disables the Webranger to Tx/Rx CLLM
            (Consolidated Link Layer Management) messages via DLCI 1023.
            The CLLM messages are link layer control messages. They can be used for example
		    in cases of congestion. The CLLM message contains a code for cause of congestion
		    and list of all DLCIs that should act to reduce data transmission."
       ::= { wrFrCnfgEntry 2 }


-- 
-- file :D:\Synergy\WorkArea\545\mib_rad\txt\iprouter.txt
-- 
	

--Version:   1.0
--Date:      31.01.99              
--By:        Ilana Schvetz
--File:      ipRouter.txt
--
--Last update: 21-Sep-2006 by Ilana Schvetz 


--radRouter     OBJECT IDENTIFIER ::= { rad 11 }  
--rtrBridge     OBJECT IDENTIFIER ::= { radRouter 7 }

ipRouter OBJECT IDENTIFIER ::= { rtrBridge 3 }



rtrIfIpTable OBJECT-TYPE
       SYNTAX SEQUENCE OF RtrIfIpEntry
       MAX-ACCESS not-accessible
       STATUS current
       DESCRIPTION
          "Router interfaces table."
       ::= { ipRouter 1 }

rtrIfIpEntry OBJECT-TYPE
       SYNTAX  RtrIfIpEntry
       MAX-ACCESS  not-accessible
       STATUS  current
       DESCRIPTION
	   "An entry in table rtrIfIpTable."
       INDEX   { rtrIfIp }
       ::= { rtrIfIpTable 1 }

RtrIfIpEntry ::=
       SEQUENCE {
              rtrIfIp             IpAddress,
			  rtrIfRowStatus      RowStatus,
              rtrIfIpMask         IpAddress,
			  rtrIfIndex          Integer32,
			  rtrIfMng            INTEGER,
			  rtrIfVlanId		  VlanIndex
          }
   
rtrIfIp OBJECT-TYPE
       SYNTAX IpAddress
       MAX-ACCESS read-only
       STATUS current
       DESCRIPTION
           "IP Address."
       ::= { rtrIfIpEntry 1 }

rtrIfRowStatus OBJECT-TYPE
      SYNTAX  RowStatus
      MAX-ACCESS  read-create
      STATUS  current
      DESCRIPTION
          "."
      ::= { rtrIfIpEntry 2 }

rtrIfIpMask OBJECT-TYPE
       SYNTAX IpAddress
       MAX-ACCESS read-create
       STATUS current
       DESCRIPTION
           "IP mask Address."
       ::= { rtrIfIpEntry 3 }

rtrIfIndex OBJECT-TYPE
       SYNTAX Integer32
       MAX-ACCESS read-create
       STATUS current
       DESCRIPTION
           "The ifIndex connection, on which the IP is determined."
       ::= { rtrIfIpEntry 4 }

rtrIfMng OBJECT-TYPE
       SYNTAX INTEGER { 
           no  (1),
           yes (2)
       }
       MAX-ACCESS read-create
       STATUS current
       DESCRIPTION
           "An IP interface might be determined as a management 
           connection (under the product limitations)."
       ::= { rtrIfIpEntry 5 }

rtrIfVlanId OBJECT-TYPE
       SYNTAX      VlanIndex
       MAX-ACCESS  read-create
       STATUS      current
       DESCRIPTION
           "The VLAN ID assigned to Tagged frames transmitted 
            from this port.
            The value inserted should be a defined VLAN."
       ::= { rtrIfIpEntry 6 }


-- Brouter Table

brtrIfTable OBJECT-TYPE
       SYNTAX SEQUENCE OF BrtrIfEntry
       MAX-ACCESS not-accessible
       STATUS current
       DESCRIPTION
          "LAN interface table."
       ::= { ipRouter 2 }

brtrIfEntry OBJECT-TYPE
       SYNTAX  BrtrIfEntry
       MAX-ACCESS  not-accessible
       STATUS  current
       DESCRIPTION
           "The entries of this table will be created by agent."
       INDEX   { brtrIfIndex }
       ::= { brtrIfTable 1 }


BrtrIfEntry ::=
       SEQUENCE {
              brtrIfIndex         Integer32,
			  brtrIfMode          INTEGER,
			  brtrIfMaxFrameSize  Integer32
  	    }
   
brtrIfIndex OBJECT-TYPE
       SYNTAX Integer32
       MAX-ACCESS read-only
       STATUS current
       DESCRIPTION
           "The index of the interface (LAN or ATM)."
       ::= { brtrIfEntry 1 }

brtrIfMode OBJECT-TYPE
       SYNTAX INTEGER { 
           bridge    (1),
           router    (2),
           brouter   (3),
		   off       (4)
       }
       MAX-ACCESS read-write
       STATUS current
       DESCRIPTION
           "Connection Mode."
       ::= { brtrIfEntry 2 }

brtrIfMaxFrameSize OBJECT-TYPE
       SYNTAX Integer32
       MAX-ACCESS read-write
       STATUS current
       DESCRIPTION
           "Frame Max Size."
       ::= { brtrIfEntry 3 }



rtrArpAgingTime OBJECT-TYPE
       SYNTAX Integer32
       MAX-ACCESS read-write
       STATUS current
       DESCRIPTION
           "ARP Aging Time. Applicable for a Router Mode 
           and for a Brouter Mode."
       ::= { ipRouter 3 }

-- Brouter LAN If table


brtrLanIfTable OBJECT-TYPE
       SYNTAX SEQUENCE OF BrtrLanIfEntry
       MAX-ACCESS not-accessible
       STATUS current
       DESCRIPTION
          "LAN interface table."
       ::= { ipRouter 4 }

brtrLanIfEntry OBJECT-TYPE
       SYNTAX  BrtrLanIfEntry
       MAX-ACCESS  not-accessible
       STATUS  current
       DESCRIPTION
           "The entries of this table will be created by agent ."
       INDEX   { brtrLanIfIndex }
       ::= { brtrLanIfTable 1 }


BrtrLanIfEntry ::=
       SEQUENCE {
              brtrLanIfIndex            Integer32,
			  brtrLanIpAddress          IpAddress,
			  brtrLanIpMask             IpAddress,
              brtrLanMaxRateEnable      INTEGER,
              brtrLanMaxRate            Integer32,
              brtrLanMng                INTEGER,
              brtrLanDefaultRouter      IpAddress
       }

brtrLanIfIndex OBJECT-TYPE
       SYNTAX Integer32
       MAX-ACCESS read-only
       STATUS current
       DESCRIPTION
           "The index of the LAN entity (physical interface)."
       ::= { brtrLanIfEntry 1 }

brtrLanIpAddress OBJECT-TYPE
       SYNTAX IpAddress
       MAX-ACCESS read-write
       STATUS current
       DESCRIPTION
           "Host IP address. Applicable for bridge mode connection only."
       ::= { brtrLanIfEntry 2 }

brtrLanIpMask OBJECT-TYPE
       SYNTAX IpAddress
       MAX-ACCESS read-write
       STATUS current
       DESCRIPTION
           "Host IP Mask. Applicable for bridge mode connection only."
       ::= { brtrLanIfEntry 3 }


brtrLanMaxRateEnable OBJECT-TYPE
       SYNTAX INTEGER { 
          disable (1),
          enable  (2)
       }
       MAX-ACCESS read-only
       STATUS current
       DESCRIPTION
           "This parameter determines the HW ability of the LAN 
           card according to HW."
       ::= { brtrLanIfEntry 4 }

brtrLanMaxRate OBJECT-TYPE
       SYNTAX Integer32
       MAX-ACCESS read-write
       STATUS current
       DESCRIPTION
           "Max Rate."
       ::= { brtrLanIfEntry 5 }

brtrLanMng OBJECT-TYPE
       SYNTAX INTEGER { 
           no  (1),
           yes (2)
       }
       MAX-ACCESS read-write
       STATUS current
       DESCRIPTION
           "An IP interface might be determined as a management 
           connection (under the product limitations)."
       ::= { brtrLanIfEntry 6 }

brtrLanDefaultRouter OBJECT-TYPE
       SYNTAX IpAddress
       MAX-ACCESS read-write
       STATUS current
       DESCRIPTION
           "Default Router's (Gateway's) IP Address.
            For each LAN interface there may be a different Default Router."
       ::= { brtrLanIfEntry 7 }



rtrIsdnIfTable OBJECT-TYPE
       SYNTAX SEQUENCE OF RtrIsdnIfEntry
       MAX-ACCESS not-accessible
       STATUS current
       DESCRIPTION
          "This table contains ISDN parameters that do not appear in the standard MIBs."
       ::= { ipRouter 5 }
			  
rtrIsdnIfEntry OBJECT-TYPE
       SYNTAX  RtrIsdnIfEntry
       MAX-ACCESS  not-accessible
       STATUS  current
       DESCRIPTION
           "Entries for ISDN parameters that do not appear in the standard MIBs."
       AUGMENTS    { isdnSignalingEntry }
--        INDEX { isdnSignalingIndex }
       ::= { rtrIsdnIfTable 1 }


RtrIsdnIfEntry ::=
       SEQUENCE {
              rtrIsdnIfMinNumBchans            Integer32,
              rtrIsdnIfMaxNumBchans            Integer32
       }

rtrIsdnIfMinNumBchans OBJECT-TYPE
       SYNTAX Integer32
       MAX-ACCESS read-create
       STATUS current
       DESCRIPTION
           "Minimum number of B channels that the ISDN Dialer of the router will use
            for Dialing out.
            This parameter will be used for the BOD (Bandwidth On Demand) feature.
            Dial up on B channels is according to the need of bandwidth for router 
            data transfer. Voice calls have a higher priority than router data.
            In case of few time slots the voice calls will cause disconnection of
            data channels up to the limit of minimum number of B channels."
       ::= { rtrIsdnIfEntry 1 }

rtrIsdnIfMaxNumBchans OBJECT-TYPE
       SYNTAX Integer32
       MAX-ACCESS read-create
       STATUS current
       DESCRIPTION
           "Maximum number of B channels that the ISDN Dialer of the router will use
            for Dialing out.
            This parameter will be used for the BOD (Bandwidth On Demand) feature.
            Dial up on B channels is according to the need of bandwidth for router 
            data transfer. Voice calls have a higher priority than router data.
            No more than MAX B channels will be used by the ISDN dialer."                     
       ::= {rtrIsdnIfEntry  2 }


rtrLcrTable OBJECT-TYPE
       SYNTAX SEQUENCE OF RtrLcrEntry
       MAX-ACCESS not-accessible
       STATUS current
       DESCRIPTION
          "Least Cost Routing Table.
           The user will be able to set a prefix for an outgoing number
           that arrives with a predefined prefix in order to redirect
           the number for the LCR process to be achieved."
       ::= { ipRouter 6 }
			  
rtrLcrEntry OBJECT-TYPE
       SYNTAX  RtrLcrEntry
       MAX-ACCESS  not-accessible
       STATUS  current
       DESCRIPTION
           "Least Cost Routing Entry."
       INDEX   { ifIndex, rtrLcrOutIfIndex }
       ::= { rtrLcrTable 1 }


RtrLcrEntry ::=
       SEQUENCE {
              rtrLcrOutIfIndex      InterfaceIndex,
			  rtrLcrRowStatus       RowStatus,
              rtrLcrInPrefix        DisplayString,
			  rtrLcrOutPrefix       DisplayString
       }

rtrLcrOutIfIndex OBJECT-TYPE
       SYNTAX InterfaceIndex
       MAX-ACCESS not-accessible
       STATUS current
       DESCRIPTION
           "The outgoing interface Number of the current route.
            The incoming interface number is the value of ifIndex."
       ::= { rtrLcrEntry 1 }

rtrLcrRowStatus OBJECT-TYPE
      SYNTAX  RowStatus
      MAX-ACCESS  read-create
      STATUS  current
      DESCRIPTION
          "Row Status for adding/destroying rows."
      ::= { rtrLcrEntry 2 }

rtrLcrInPrefix OBJECT-TYPE
       SYNTAX DisplayString
       MAX-ACCESS read-create
       STATUS current
       DESCRIPTION
           "This prefix is part of the called number existing in the incoming packet."                     
       ::= {rtrLcrEntry  3 }

rtrLcrOutPrefix OBJECT-TYPE
       SYNTAX DisplayString
       MAX-ACCESS read-create
       STATUS current
       DESCRIPTION
           "This prefix will be inserted into the outgoing packet."
       ::= {rtrLcrEntry  4 }




--radRouter     OBJECT IDENTIFIER ::= { rad 11 }  

multicastGen    OBJECT IDENTIFIER ::= { radRouter 8 } -- General Multicast Parameters

multicastMode  OBJECT-TYPE
      SYNTAX INTEGER {
      disable  (2),        
      wanToLan (3),      
      wanToLanIgmp (4),
	  lanToWan (5),
      bidirectional(6),
      transparent(7)
      }
	  MAX-ACCESS read-write
      STATUS current
      DESCRIPTION
      "According to this mode the packets will be forwarded.
       If disable (2) is selected, there will be no multicast."
      ::= { multicastGen 1 }
-- 
-- file :D:\Synergy\WorkArea\545\mib_rad\txt\v5.txt
-- 

--Title:  RAD's WAN V5.1 Interface MIB
--By:     Smadar Tauber
--Date :  03.11.1998

--Last Update: 27-June-05 
--By: Smadar Tauber
--File:  v:\doc\rdv\mib\ver520\v5.txt

--IMPORTS
--      enterprises                            FROM RFC1155-SMI
--      DisplayString                          FROM RFC1213-MIB
--      IpAddress                              FROM RFC1155-SMI
--      OCTET STRING                           FROM RFC1213-MIB
--      OBJECT-TYPE                            FROM RFC1212;

--wanGen   OBJECT IDENTIFIER ::= {radWan 1}
--diverseIfWanGen OBJECT IDENTIFIER ::= {wanGen 6} (see mpmx.txt)
v51If OBJECT IDENTIFIER ::= {diverseIfWanGen 6}


v51General 	  OBJECT IDENTIFIER ::= {v51If 1}
v51Variant    OBJECT IDENTIFIER ::= {v51If 2}
v51Ml         OBJECT IDENTIFIER ::= {v51If 3}
v51AccessPort OBJECT IDENTIFIER ::= {v51If 4}


--NPL parameters (for most of the manual parameters see TDSoft MIB)

npl OBJECT IDENTIFIER ::= {v51General 1}

nplMode  OBJECT-TYPE
      SYNTAX  INTEGER
       {
          auto  (2),
          manual(3)
       }
      MAX-ACCESS  read-write
      STATUS  current
      DESCRIPTION
      "NPL Mode."
      ::= { npl 1 }

nplCountry  OBJECT-TYPE
      SYNTAX  INTEGER
       {
          none    (1),
          france  (2),
          germany (3)
       }
      MAX-ACCESS  read-write
      STATUS  current
      DESCRIPTION
      "National Protocol Country."
      ::= { npl 2 }

nplVoicePathDuration  OBJECT-TYPE
      SYNTAX  Integer32
      MAX-ACCESS  read-write
      STATUS  current
      DESCRIPTION
      "Maximum time of a voice path, in msec."
      ::= { npl 3 }

--NPL Pulse table

nplPulseTable  OBJECT-TYPE
     SYNTAX SEQUENCE OF NplPulseEntry
     MAX-ACCESS not-accessible
     STATUS  current
     DESCRIPTION
      "NPL Pulse table. This table is written directly to the agent."
     ::= { npl 4 }

nplPulseEntry OBJECT-TYPE
      SYNTAX NplPulseEntry
      MAX-ACCESS not-accessible
      STATUS current
	  DESCRIPTION
	  "An entry in table nplPulseTable."
      INDEX {nplPulseType}
      ::= { nplPulseTable 1}

NplPulseEntry ::=
      SEQUENCE {
      nplPulseType         INTEGER,
	  nplPulseValid        INTEGER,
      nplPulseDurationType Integer32,
      nplPulseOnTime       Integer32,
      nplPulseOffTime      Integer32
      }

nplPulseType OBJECT-TYPE
      SYNTAX  INTEGER
      {
      meteringPulse1   (1),
      meteringPulse2   (2),
      initRinging1     (3),
      initRinging2     (4),
      normalBattery  (237),
      noBattery      (250),
      reducedBattery (251),
      reversePolarity(254),
      normalPolarity (255)
            }
      MAX-ACCESS  read-only
      STATUS  current
      DESCRIPTION
      "Pulse Type"
      ::= {nplPulseEntry 1}

nplPulseValid OBJECT-TYPE
      SYNTAX  INTEGER
      {
      notValid   (2),
      valid      (3)
            }
      MAX-ACCESS  read-write
      STATUS  current
      DESCRIPTION
      "Validity of the Pulse Type."
      ::= {nplPulseEntry 2}

nplPulseDurationType OBJECT-TYPE
      SYNTAX  Integer32  (0..31)
      MAX-ACCESS  read-write
      STATUS  current
      DESCRIPTION
      "Pulse Duration Type.
       - If meteringPulse1 and meteringPulse2 are both 'valid', the value of this 
         object must be different for them.
       - If initRinging1 and initRinging2 are both 'valid', the value of this 
         object must be different for them."
      ::= {nplPulseEntry 3}

nplPulseOnTime OBJECT-TYPE
      SYNTAX  Integer32  (0..990)
      MAX-ACCESS  read-write
      STATUS  current
      DESCRIPTION
      "How much time the pulse is ON, in msec.
       0 is a valid value only when nplPulseValid=notValid."
      ::= {nplPulseEntry 4}

nplPulseOffTime OBJECT-TYPE
      SYNTAX  Integer32  (0..990)
      MAX-ACCESS  read-write
      STATUS  current
      DESCRIPTION
      "How much time the pulse is OFF, in msec."
      ::= {nplPulseEntry 5}


--Variant tables
--
--Variant table - Configuration and Status at Variant Level
--
--Only ONE variant exists per link in the Temporary Configuration

v51VarTable  OBJECT-TYPE
     SYNTAX SEQUENCE OF V51VarEntry
     MAX-ACCESS not-accessible
     STATUS  current
     DESCRIPTION
      "The write operation into the Table Objects is valid only
       to the TmpCnfg entry."
     ::= { v51Variant 1}

v51VarEntry OBJECT-TYPE
      SYNTAX V51VarEntry
      MAX-ACCESS not-accessible
      STATUS current
	  DESCRIPTION
	  "An entry in table v51VarTable."
      INDEX {v51VarCnfgIdx, v51VarSltIdx, v51VarPrtIdx, v51VarIdx }
      ::= { v51VarTable 1}

V51VarEntry ::=
      SEQUENCE {
      v51VarCnfgIdx      Integer32,
      v51VarSltIdx       INTEGER,
      v51VarPrtIdx       Integer32,
      v51VarIdx          Integer32,
	  v51VarPstnCch      INTEGER,
	  v51VarIsdnSTypeCch INTEGER,
	  v51VarDescription  DisplayString,
	  v51VarStatus       INTEGER,
	  v51VarRowStatus    INTEGER
      }

v51VarCnfgIdx OBJECT-TYPE
      SYNTAX  Integer32 (1..255)
      MAX-ACCESS  read-only
      STATUS  current
      DESCRIPTION
      "This attribute indicates the Idx of the Cnfg being accessed.
       255 = TmpCnfg.
       1   = Current Cnfg. 
       Write is allowed only to TmpCnfg."
      ::= {v51VarEntry 1}

v51VarSltIdx OBJECT-TYPE
      SYNTAX  INTEGER
      {
      io1   (5),
      io2   (6),
      io3   (7),
      io4   (8),
      io5   (9),
      io6  (10),
      io7  (11),
      io8  (12),
      io9  (13),
      io10 (14),
      io11 (15),
      io12 (16),
      notApplicable(255)
            }
      MAX-ACCESS  read-only
      STATUS  current
      DESCRIPTION
      "Slot Index.
       For V5.2, this index will be the Slot of the V5.2 Master ML."
      ::= {v51VarEntry 2}

v51VarPrtIdx OBJECT-TYPE
      SYNTAX  Integer32
      MAX-ACCESS  read-only
      STATUS  current
      DESCRIPTION
      "This attribute indicates a unique  port number of the ML having 
       V5 interface.
       Valid values: exPrt1 (1)..exPrt4 (4), inPrt1(101)..inPrt4(104),
       notApplicable(255) - for V5.2 only."
      ::= {v51VarEntry 3}

v51VarIdx OBJECT-TYPE
     SYNTAX  Integer32 (0..255)
     MAX-ACCESS   read-only
     STATUS   current
     DESCRIPTION
     "Variant Id.
      Valid values: 
      - for Current Cnfg: 0..127
      - for Tmp Cnfg: until MP R9 : 255 only.
                      from  MP R10: 0..127."
     ::= {v51VarEntry 4}

v51VarPstnCch OBJECT-TYPE
      SYNTAX  INTEGER 
      { 
      notApplicable (1),
      ts15          (2), 
      ts16          (3),
	  ts31          (4)
      }
      MAX-ACCESS   read-write
      STATUS   current
      DESCRIPTION
      "This object indicates which TS will be used for PSTN C channel.
       For V5.2 - notApplicable."
      ::= {v51VarEntry 5}

v51VarIsdnSTypeCch OBJECT-TYPE
      SYNTAX  INTEGER 
      { 
      notApplicable (1),
      ts15          (2), 
      ts16          (3),
	  ts31          (4)
      }
      MAX-ACCESS   read-write
      STATUS   current
      DESCRIPTION
      "This object indicates which TS will be used for S-Type C channel.
       For V5.2 - notApplicable."
      ::= {v51VarEntry 6}

v51VarDescription OBJECT-TYPE
      SYNTAX  DisplayString 
      MAX-ACCESS  read-write
      STATUS  current
      DESCRIPTION
      "This object describes the Variant."
      ::= {v51VarEntry 7}

v51VarStatus OBJECT-TYPE
      SYNTAX  INTEGER 
      { 
      notApplicable (1), 
      notActive  (2), 
      active     (3),
      activeReq  (4) 
      }
      MAX-ACCESS read-only
      STATUS current
      DESCRIPTION
      "This object reports the status of an existing Variant of a link.
       notActive - the variant exists on this link but is not active
       active    - the variant exists on this link AND is active
       activeReq - the variant exists on this link and it was requested to
                   be active, but the request is still in negotiation
                   (it can be either accepted as active, or not).
       This object is not applicable for v51VarCnfgIdx=255=TmpCnfg."
      ::= {v51VarEntry 8}

v51VarRowStatus OBJECT-TYPE
      SYNTAX  INTEGER 
      { 
      notApplicable(1),
      notValid     (2),
      valid        (3)
      }
      MAX-ACCESS   read-write
      STATUS   current
      DESCRIPTION
      "This object enables to create new entries and delete existing entries
       from the table. It is applicable only from MP R10."
      ::= {v51VarEntry 9}



--Variant Configuration and Status table - TS/Address Level

v51VarCfgTable  OBJECT-TYPE
     SYNTAX SEQUENCE OF V51VarCfgEntry
     MAX-ACCESS not-accessible
     STATUS  current
     DESCRIPTION
      "The write operation into the Table Objects is valid only
       to the TmpCnfg entry."
     ::= { v51Variant 2}

v51VarCfgEntry OBJECT-TYPE
      SYNTAX V51VarCfgEntry
      MAX-ACCESS not-accessible
      STATUS current
	  DESCRIPTION
	  "An entry in table v51VarCfgTable."
      INDEX {v51VarCfgIndex, v51VarCfgSltIdx, v51VarCfgPrtIdx, v51VarCfgIdx, 
             v51VarCfgTsIdx}
      ::= { v51VarCfgTable 1}

V51VarCfgEntry ::=
      SEQUENCE {
      v51VarCfgIndex       Integer32,
      v51VarCfgSltIdx      INTEGER,
      v51VarCfgPrtIdx      Integer32,
      v51VarCfgIdx         Integer32,
      v51VarCfgTsIdx       Integer32,
	  v51VarCfgTsType      INTEGER,
	  v51VarCfgPrtId       Integer32,
	  v51VarCfgEfL3Addr    Integer32,
      v51VarCfgFTypeCch    Integer32,
      v51VarCfgPTypeCch    Integer32,
      v51VarCfgConSlt      INTEGER,
      v51VarCfgConPrt      Integer32,
      v51VarCfgIoState     INTEGER,
	  v51VarCfgBlock       INTEGER,
	  v51VarCfgExtDch      INTEGER,
	  v51VarCfgExtDchSlot  INTEGER,
	  v51VarCfgExtDchPort  Integer32,
	  v51VarCfgExtDchTs    Integer32,
	  v51VarCfgExtDchCmpr     INTEGER,
	  v51VarCfgExtDchRate     INTEGER,
	  v51VarCfgExtDchStartBit Integer32,
      v51VarCfgSTypeCch    Integer32,
	  v51VarCfgStatus      INTEGER,
	  v51VarCfgV52MasterTsa   Integer32
      }

v51VarCfgIndex OBJECT-TYPE
      SYNTAX  Integer32 (1..255)
      MAX-ACCESS  read-only
      STATUS  current
      DESCRIPTION
      "This attribute indicates the Idx of the Cnfg being accessed.
       255 = TmpCnfg.
       1   = Current Cnfg. "
      ::= {v51VarCfgEntry 1}

v51VarCfgSltIdx OBJECT-TYPE
      SYNTAX  INTEGER
      {
      io1   (5),
      io2   (6),
      io3   (7),
      io4   (8),
      io5   (9),
      io6  (10),
      io7  (11),
      io8  (12),
      io9  (13),
      io10 (14),
      io11 (15),
      io12 (16),
      notApplicable(255)
            }
      MAX-ACCESS  read-only
      STATUS  current
      DESCRIPTION
      "Slot Index.
       For V5.2, this index will be the Slot of the V5.2 Master ML."
      ::= {v51VarCfgEntry 2}

v51VarCfgPrtIdx OBJECT-TYPE
      SYNTAX  Integer32
      MAX-ACCESS  read-only
      STATUS  current
      DESCRIPTION
      "This attribute indicates a unique  port number of the ML having 
       V5 interface.
       Valid values: exPrt1 (1)..exPrt4 (4), inPrt1(101)..inPrt4(104)
       notApplicable(255) - for V5.2 only."
      ::= {v51VarCfgEntry 3}

v51VarCfgIdx OBJECT-TYPE
     SYNTAX  Integer32 (0..255)
     MAX-ACCESS   read-only
     STATUS   current
     DESCRIPTION
     "Variant Id.
      Valid values: 
      - for Current Cnfg: 0..127
      - for Tmp Cnfg: until MP R9 : 255 only.
                      from  MP R10: 0..127."
     ::= {v51VarCfgEntry 4}

v51VarCfgTsIdx OBJECT-TYPE
      SYNTAX  Integer32 
      MAX-ACCESS   read-only
      STATUS   current
      DESCRIPTION
      "For V5.1: Time Slot index (1..31).
       For V5.2: Running Index (1..1320) for Address Table."
      ::= {v51VarCfgEntry 5}

v51VarCfgTsType OBJECT-TYPE
      SYNTAX  INTEGER 
      { 
      nc              (1),
      pstn            (2), 
      isdnB1          (3),
	  isdnB2          (4),
	  cChannel        (5),
	  permanentB1     (6),
	  permanentB2     (7),
	  semiPermanentB1 (8),
	  semiPermanentB2 (9)
      }
      MAX-ACCESS   read-write
      STATUS   current
      DESCRIPTION
      "Time Slot Type."
      ::= {v51VarCfgEntry 6}

v51VarCfgPrtId OBJECT-TYPE
      SYNTAX  Integer32 (0..16777215)
      MAX-ACCESS   read-write
      STATUS   current
      DESCRIPTION
      "This object indicates the IO Port Id this TS is connected to.
       For V5.2, the Port Id is a concatenation of SS:PP:TS of the port 
       connected to V5.2 Master.
       SS=IO Slot (1..12)
       PP=Port   (01..16)
       TS = TS   (00 for ports that don't have TSs, 1 ..31).
       Example:  50327  means IO-5, port-3, TS27.
       222222 value is used for a special PSTN case."
      ::= {v51VarCfgEntry 7}

v51VarCfgEfL3Addr OBJECT-TYPE
      SYNTAX  Integer32 (0..65535)
      MAX-ACCESS   read-write
      STATUS   current
      DESCRIPTION
      "This object indicates the Address of the IO port this TS is connected to.
       The IO port is identified according to its Address:
       - for ISDN ports: EF Address. Valid values: 0..8175 
       - for PSTN ports: L3 Address. Valid values: 0..32767
       65535=notApplicable (FFFF)."
      ::= {v51VarCfgEntry 8}

v51VarCfgFTypeCch OBJECT-TYPE
      SYNTAX  Integer32 
      MAX-ACCESS   read-write
      STATUS   current
      DESCRIPTION
      "For V5.1 - this object indicates which TS will be used for F-Type C channel.
           notApplicable (1),
           ts15          (2), 
           ts16          (3),
	       ts31          (4)
	   For V5.2 - this object indicates the Logical C Channel F Type (0..65535).
	              65536=not applicable in this case."
      ::= {v51VarCfgEntry 9}

v51VarCfgPTypeCch OBJECT-TYPE
      SYNTAX  Integer32 
      MAX-ACCESS   read-write
      STATUS   current
      DESCRIPTION
      "For V5.1 - This object indicates which TS will be used for P-Type C channel.
           notApplicable (1),
           ts15          (2), 
           ts16          (3),
	       ts31          (4)
	   For V5.2 - this object indicates the Logical C Channel P Type (0..65535).
	              65536=not applicable in this case."
      ::= {v51VarCfgEntry 10}

v51VarCfgConSlt OBJECT-TYPE
      SYNTAX  INTEGER
      {
      io1   (5),
      io2   (6),
      io3   (7),
      io4   (8),
      io5   (9),
      io6  (10),
      io7  (11),
      io8  (12),
      io9  (13),
      io10 (14),
      io11 (15),
      io12 (16),
      notApplicable(255)
            }
      MAX-ACCESS  read-only
      STATUS  current
      DESCRIPTION
      "The Slot containing the IO port this TS is connected to.
       For V5.2 this object is notApplicable."
      ::= {v51VarCfgEntry 11}

v51VarCfgConPrt OBJECT-TYPE
      SYNTAX  Integer32
      MAX-ACCESS  read-only
      STATUS  current
      DESCRIPTION
      "The IO Port this TS is connected to.
       Valid values: exPrt1 (1)..exPrt12 (12), inPrt1(101)..inPrt4(104).
       100=noConnect
       For V5.2 this object is notApplicable=255."
      ::= {v51VarCfgEntry 12}

v51VarCfgIoState OBJECT-TYPE
      SYNTAX  INTEGER
      {
      notUsed         (1),
	  normal          (2),
	  blockReqDenied  (3),
	  remoteBlocked   (4),
      localBlocked    (5),
      unblockReqDenied(6),
      duringBlock     (7),
      duringUnblock   (8),
      localLoop       (9),
      remoteLoop     (10),
	  localUnblock   (11),
	  remoteUnblock  (12)
             }
      MAX-ACCESS  read-only
      STATUS  current
      DESCRIPTION
      "The State of the IO port this TS is connected to.
       This object is not applicable for v51VarCfgIndex=255=TmpCnfg.
       normal(2) - will be used for operating normally (operate)
       localBlocked(5) - will be used for general Block state"
      ::= {v51VarCfgEntry 13}

v51VarCfgBlock OBJECT-TYPE
      SYNTAX  INTEGER 
      { 
	  notApplicable (1),
      unBlock       (2), 
      block         (3),
	  blockRequest  (4)
      }
      MAX-ACCESS   read-write
      STATUS   current
      DESCRIPTION
      "This object indicates if this TS will be Blocked or not and how:
       block - done locally
       blockRequest - according to external request of the telephone exchange."
      ::= {v51VarCfgEntry 14}

v51VarCfgExtDch OBJECT-TYPE
      SYNTAX  INTEGER 
      { 
	  notApplicable(1),
      no  (2),
      yes (3)
      }
      MAX-ACCESS   read-write
      STATUS   current
      DESCRIPTION
      "For V5.1: This object indicates if this TS is an ISDN D channel that 
                 comes via Bypass from a non-V5.1 ML.
       For V5.2: this object will be notApplicable (not supported)."
      ::= {v51VarCfgEntry 15}

v51VarCfgExtDchSlot OBJECT-TYPE
      SYNTAX  INTEGER
      {
      io1   (5),
      io2   (6),
      io3   (7),
      io4   (8),
      io5   (9),
      io6  (10),
      io7  (11),
      io8  (12),
      io9  (13),
      io10 (14),
      io11 (15),
      io12 (16),
      notApplicable(255)
            }
      MAX-ACCESS  read-write
      STATUS  current
      DESCRIPTION
      "This object is applicable only if v51VarCfgExtDch=yes(3).
       It indicates the Slot of the non-V5.1 ML on which the External D channel
       TS is defined (and is transferred via Bypass between the V5.1 ML and
       the non-V5.1 ML.)
       Not Applicable for V5.2 (it is part of Port Id)."
      ::= {v51VarCfgEntry 16}

v51VarCfgExtDchPort OBJECT-TYPE
      SYNTAX  Integer32
      MAX-ACCESS  read-write
      STATUS  current
      DESCRIPTION
      "This object is applicable only if v51VarCfgExtDch=yes(3).
       It indicates the Port on the Slot of 'v51VarCfgExtDchSlot' of the 
       non-V5.1 ML on which the External D channel TS is defined (and is 
       transferred via Bypass between the V5.1 ML and the non-V5.1 ML.)
	   Valid values: exPrt1 (1)..exPrt4 (4), inPrt1(101)..inPrt4(104).
       100=noConnect.
       Not Applicable for V5.2 (255; it is part of Port Id)."
      ::= {v51VarCfgEntry 17}

v51VarCfgExtDchTs OBJECT-TYPE
      SYNTAX  Integer32 (0..32)
      MAX-ACCESS  read-write
      STATUS  current
      DESCRIPTION
      "This object is applicable only if v51VarCfgExtDch=yes(3).
       It indicates the TS on the non-V5 ML on which the External 
       D channel TS is defined (and is transferred via Bypass between 
       the V5 ML and the non-V5 ML.)
       For V5.1: 0=notApplicable
       For V5.2: 0=None, 32=notApplicable."
      ::= {v51VarCfgEntry 18}

v51VarCfgExtDchCmpr OBJECT-TYPE
      SYNTAX  INTEGER 
      { 
      notApplicable(1),
      no  (2),
      yes (3)
      }
      MAX-ACCESS   read-write
      STATUS   current
      DESCRIPTION
      "For V5.1 - this object is applicable only if v51VarCfgExtDch=yes(3).
       It indicates if this ISDN D channel TS is Compressed or not."
      ::= {v51VarCfgEntry 19}

v51VarCfgExtDchRate OBJECT-TYPE
      SYNTAX  INTEGER 
      { 
      notApplicable(1),
      twoBits      (2),
      fourBits     (3),
	  eightBits    (4)
      }
      MAX-ACCESS   read-write
      STATUS   current
      DESCRIPTION
      "For V5.1 - this object is applicable only if v51VarCfgExtDch=yes(3).
       It indicates the Rate of the ISDN D channel."
      ::= {v51VarCfgEntry 20}

v51VarCfgExtDchStartBit OBJECT-TYPE
      SYNTAX  Integer32 (0..7)
      MAX-ACCESS  read-write
      STATUS  current
      DESCRIPTION
      "For V5.1 - this object is applicable only if v51VarCfgExtDch=yes(3).
       It indicates the Start Bit of the ISDN D channel on the TS of 
       the non-V5.1 ML on which it is defined.
	   Valid values:
	   - for v51VarCfgExtDchRate=twoBits(2):   1, 3, 5, 7
	   - for v51VarCfgExtDchRate=fourBits(3):  1, 5
	   - for v51VarCfgExtDchRate=eightBits(4): 1 
       - 0=notApplicable "
      ::= {v51VarCfgEntry 21}

v51VarCfgSTypeCch OBJECT-TYPE
      SYNTAX  Integer32 
      MAX-ACCESS   read-write 
      STATUS   current
      DESCRIPTION
      "This object is supported only by V5.2. It indicates the Logical 
       C Channel S Type (0..65535). 
	   65536=not applicable."
      ::= {v51VarCfgEntry 22}

v51VarCfgStatus OBJECT-TYPE
      SYNTAX  INTEGER 
      { 
      notApplicable(1),
      notValid     (2),
      valid        (3)
      }
      MAX-ACCESS   read-write
      STATUS   current
      DESCRIPTION
      "This object is supported only by V5.2.
       It enables to create new entries and delete existing entries
       from the table."
      ::= {v51VarCfgEntry 23}

v51VarCfgV52MasterTsa OBJECT-TYPE
      SYNTAX  Integer32 
      MAX-ACCESS   read-only
      STATUS   current
      DESCRIPTION
      "This object is supported only by V5.2.
       This will be the V5.2 Master, Switch Allocated Location. It is
       a concatenation of SS:PP:TS of the V5.2 Master.
	   It indicates which is the exact port and TS allocated by the Local
	   Exchange on the V5.2 Link.
       SS=IO Slot (1..12)
       PP=Port   (01..04)
       TS = TS    (1..31).
       Example: 50323  means IO-5, port-3, TS23."
      ::= {v51VarCfgEntry 24}


--Variant Configuration and Status table - C CH Level (V5.2 only)

v5VarCchTable  OBJECT-TYPE
     SYNTAX SEQUENCE OF V5VarCchEntry
     MAX-ACCESS not-accessible
     STATUS  current
     DESCRIPTION
      "The write operation into the Table Objects is valid only
       to the TmpCnfg entry."
     ::= { v51Variant 3}

v5VarCchEntry OBJECT-TYPE
      SYNTAX V5VarCchEntry
      MAX-ACCESS not-accessible
      STATUS current
	  DESCRIPTION
	  "An entry in table v5VarCchTable."
      INDEX {v5VarCchCfgIndex, v5VarCchVarIdx, v5VarCchIdx}
      ::= { v5VarCchTable 1}

V5VarCchEntry ::=
      SEQUENCE {
      v5VarCchCfgIndex     Integer32,
      v5VarCchVarIdx       Integer32,
      v5VarCchIdx          Integer32,
	  v5VarCchType         INTEGER,
	  v5VarCchPhyLinkNo    Integer32,
	  v5VarCchLogicalId    Integer32,
	  v5VarCchTs           Integer32,
	  v5VarCchPstn         INTEGER,
	  v5VarCchIsdnTypes    Integer32
	  } 

v5VarCchCfgIndex OBJECT-TYPE
      SYNTAX  Integer32 (1..255)
      MAX-ACCESS  read-only
      STATUS  current
      DESCRIPTION
      "This attribute indicates the Idx of the Cnfg being accessed.
       255 = TmpCnfg.
       1   = Current Cnfg. "
      ::= {v5VarCchEntry 1}

v5VarCchVarIdx OBJECT-TYPE
     SYNTAX  Integer32 (0..127)
     MAX-ACCESS   read-only
     STATUS   current
     DESCRIPTION
     "Variant Id.
      Valid values: 0..127."
     ::= {v5VarCchEntry 2}

v5VarCchIdx OBJECT-TYPE
     SYNTAX  Integer32 (1..8)
     MAX-ACCESS   read-only
     STATUS   current
     DESCRIPTION
     "C-CH Id.
      There are only 8 possible C-CHs per Variant."
     ::= {v5VarCchEntry 3}

v5VarCchType OBJECT-TYPE
      SYNTAX  INTEGER 
      { 
      none         (2),
      primary      (3),
	  secondary    (4),
	  regular      (5),
	  standby      (6)
      }
      MAX-ACCESS   read-write
      STATUS   current
      DESCRIPTION
      "C-CH Type."
      ::= {v5VarCchEntry 4}

v5VarCchPhyLinkNo OBJECT-TYPE
     SYNTAX  Integer32 
     MAX-ACCESS   read-write
     STATUS   current
     DESCRIPTION
     "The Physical Link Number of the card (1..4).
      This object is applicable only if v51VarCchType is not 'none'.
      notApplicable=255."
     ::= {v5VarCchEntry 5}

v5VarCchLogicalId OBJECT-TYPE
     SYNTAX  Integer32 (0..65535)
     MAX-ACCESS   read-write
     STATUS   current
     DESCRIPTION
     "The Logical C-CH Id. (0..65535)
      When v51VarCchType is 'none', this object is irrelevant."
     ::= {v5VarCchEntry 6}

v5VarCchTs OBJECT-TYPE
     SYNTAX  Integer32 
     MAX-ACCESS   read-write
     STATUS   current
     DESCRIPTION
     "The C-CH TS. Valid values: 16, 15, 31.
	  If  v51VarCchType=primary or secondary, the value must be 16 (RO).
      This object is applicable only if v51VarCchType is not 'none'.
      notApplicable=0."
     ::= {v5VarCchEntry 7}

v5VarCchPstn OBJECT-TYPE
      SYNTAX  INTEGER 
      { 
	  notApplicable(1),
      no           (2),
      yes          (3)
      }
      MAX-ACCESS   read-write
      STATUS   current
      DESCRIPTION
      "PSTN C-CH.
       Only one entry can have the value 'yes'.
       notApplicable - when v51VarCchType is none, secondary or standby."
      ::= {v5VarCchEntry 8}

v5VarCchIsdnTypes OBJECT-TYPE
     SYNTAX  Integer32 
     MAX-ACCESS   read-write
     STATUS   current
     DESCRIPTION
     "ISDN Types of C-CH.
      This object is a sum of 2**n, where n=Bit No. and Bit is '1':
		   Bit No.     ISDN Type
		      0          P
			  1          F
			  2          S
	  Bit value '1'= Yes
	  Bit value '0'= No
	  Example: P=No, F=Yes, S=Yes  (110H) will have the value 6. 
      Each Type is NA (notApplicable) when v51VarCchType is none, secondary 
      or standby. There is no special value for it, since each type can have
      only 2 values (1 or 0). When this object is NA, Agent will not refer its value
      (don't care)."
     ::= {v5VarCchEntry 9}


--Active Variant - Active Addresses Status table (V5.2 only)

v5VarStatTable  OBJECT-TYPE
     SYNTAX SEQUENCE OF V5VarStatEntry
     MAX-ACCESS not-accessible
     STATUS  current
     DESCRIPTION
      "This is a RO table. It includes only the Active Addresses of
       the Active Variant, their minimal Config data and Status."
     ::= { v51Variant 4}

v5VarStatEntry OBJECT-TYPE
     SYNTAX V5VarStatEntry
     MAX-ACCESS not-accessible
     STATUS current
	 DESCRIPTION
	 "An entry in table v5VarStatTable."
     INDEX {v5VarStatIdx}
     ::= { v5VarStatTable 1}

V5VarStatEntry ::=
      SEQUENCE {
      v5VarStatIdx        Integer32,
	  v5VarStatPrtId      Integer32,
	  v5VarStatPortType   INTEGER,
	  v5VarStatEfL3Addr   Integer32,
      v5VarStatPortState  INTEGER,
	  v5VarStatMasterTsa  Integer32,
	  v5VarStatCallState  INTEGER
      }

v5VarStatIdx OBJECT-TYPE
     SYNTAX  Integer32 
     MAX-ACCESS   not-accessible
     STATUS   current
     DESCRIPTION
     "Running Index (1..120). Up to 120 calls can be active at the same time
      on the Active Variant."
     ::= {v5VarStatEntry 1}

v5VarStatPrtId OBJECT-TYPE
     SYNTAX  Integer32 
     MAX-ACCESS   read-only
     STATUS   current
     DESCRIPTION
     "This object indicates the IO Port Id, the Address is connected to.
      The Port Id is a concatenation of SS:PP:TS of the port connected 
      to an Address of the Active Variant running on the V5.2 Master card.
      SS=IO Slot (1..12)
      PP=Port   (01..04)
      TS = TS   (00 for ports that don't have TSs ..31).
      Example:  50327  means IO-5, port-3, TS27."
     ::= {v5VarStatEntry 2}

v5VarStatPortType OBJECT-TYPE
      SYNTAX  INTEGER 
      { 
      nc              (1),
      pstn            (2), 
      isdnB1          (3),
	  isdnB2          (4),
	  cChannel        (5),
	  permanentB1     (6),
	  permanentB2     (7),
	  semiPermanentB1 (8),
	  semiPermanentB2 (9)
      }
      MAX-ACCESS   read-only
      STATUS   current
      DESCRIPTION
      "Address Port Type."
      ::= {v5VarStatEntry 3}

v5VarStatEfL3Addr OBJECT-TYPE
     SYNTAX  Integer32 (0..65535)
     MAX-ACCESS   read-only
     STATUS   current
     DESCRIPTION
     "This object indicates the EF/L3 Address of the IO port this entry 
      is connected to.
      The IO port is identified according to its EF/L3 Address:
      - for ISDN ports: EF Address. Valid values: 0..8175 
      - for PSTN ports: L3 Address. Valid values: 0..32767
      65535=notApplicable (FFFF)."
     ::= {v5VarStatEntry 4}

v5VarStatPortState OBJECT-TYPE
     SYNTAX  INTEGER
     {
     notUsed         (1),
	 normalOperation (2),
	 block           (5),
	 localUnblock    (11),
	 remoteUnblock   (12)
            }
     MAX-ACCESS  read-only
     STATUS  current
     DESCRIPTION
     "The State of the IO port this Address entry is connected to.
      The values were designed to match the relevant values of v51VarCfgIoState."
     ::= {v5VarStatEntry 5}

v5VarStatMasterTsa OBJECT-TYPE
     SYNTAX  Integer32 
     MAX-ACCESS   read-only
     STATUS   current
     DESCRIPTION
     "This will be the V5.2 Master Switch Allocated TSA Location. It is
      a concatenation of SS:PP:TS of the V5.2 Master card.
	  It indicates which is the exact port and TS allocated by the Local
	  Exchange on the V5.2 Link.
      SS=IO Slot (1..12)
      PP=Port   (01..04)
      TS = TS    (1..31).
      Example: 50323  means IO-5, port-3, TS23."
     ::= {v5VarStatEntry 6}

v5VarStatCallState OBJECT-TYPE
     SYNTAX  INTEGER 
     { 
     empty           (1),
     outOfService    (2), 
     deactive        (3),
	 actInit         (4),
	 accessAct       (5),
	 plActInit       (6),
	 plAct           (7),
	 loopback2       (8),
	 loopback1       (9),
	 loopback1A     (10),
	 null           (11),
	 pathInit       (12),
	 pathAbortReq   (13),
	 lineInfo       (14),
	 pathActive     (15),
	 blocked        (16),
	 disconnectReq  (17)  
     }
     MAX-ACCESS   read-only
     STATUS   current
     DESCRIPTION
     "Call State of the Address."
     ::= {v5VarStatEntry 7}


--V5 ML tables

v51MlCmdAndStatus OBJECT IDENTIFIER ::= {v51Ml 1}
v51MlCnfg   OBJECT IDENTIFIER ::= {v51Ml 2}

--ML command/status table

v51MlTable  OBJECT-TYPE
     SYNTAX SEQUENCE OF V51MlEntry
     MAX-ACCESS not-accessible
     STATUS  current
     DESCRIPTION
      "Variant Command and Status table."
     ::= { v51MlCmdAndStatus 1}

v51MlEntry OBJECT-TYPE
      SYNTAX V51MlEntry
      MAX-ACCESS not-accessible
      STATUS current
	  DESCRIPTION
	  "An entry in table v51MlTable."
      INDEX {v51MlSltIdx, v51MlPrtIdx}
      ::= { v51MlTable 1}

V51MlEntry ::=
      SEQUENCE {
      v51MlSltIdx           INTEGER,
      v51MlPrtIdx           Integer32,
      v51MlCurrActiveVar    Integer32,
      v51MlLeActiveReqVar   Integer32,
	  v51MlProtocolState    INTEGER,
	  v51MlUserActiveVarReq Integer32,
	  v51MlDeleteVarReq     Integer32,
	  v51MlSaveVariant      Integer32,
	  v51MlReadVariant      Integer32,
	  v51MlDeactivateVar    Integer32
	  }

v51MlSltIdx OBJECT-TYPE
      SYNTAX  INTEGER
      {
      io1   (5),
      io2   (6),
      io3   (7),
      io4   (8),
      io5   (9),
      io6  (10),
      io7  (11),
      io8  (12),
      io9  (13),
      io10 (14),
      io11 (15),
      io12 (16),
      notApplicable(255)
            }
      MAX-ACCESS  read-only
      STATUS  current
      DESCRIPTION
      "Slot Index.
       For V5.2 this index is notApplicable."
      ::= {v51MlEntry 1}

v51MlPrtIdx OBJECT-TYPE
      SYNTAX  Integer32
      MAX-ACCESS  read-only
      STATUS  current
      DESCRIPTION
      "This attribute indicates a unique  port number of the ML having 
       V5 interface.
       Valid values: exPrt1 (1)..exPrt4 (4), inPrt1(101)..inPrt4(104),
       notApplicable(255) - for V5.2 only."
      ::= {v51MlEntry 2}

v51MlCurrActiveVar OBJECT-TYPE
      SYNTAX  Integer32  (0..128)
      MAX-ACCESS read-only
      STATUS current
      DESCRIPTION
      "For V5.1: the currently Active Variant Id. on this ML.
	   For V5.2: the currently Active Variant Id.
       128=none."
      ::= {v51MlEntry 3}

v51MlLeActiveReqVar OBJECT-TYPE
      SYNTAX  Integer32  (0..128)
      MAX-ACCESS read-only
      STATUS current
      DESCRIPTION
      "For V5.1: the Variant Id. that the Local Exchange (LE) 
                 requested to be Active on this ML.
       For V5.2: the Variant Id. that the Local Exchange (LE) 
                 requested to be Active.       
       128=none."
      ::= {v51MlEntry 4}

v51MlProtocolState OBJECT-TYPE
      SYNTAX  INTEGER  
      {
	  sysStartUp        (1),
  	  waitForVarId      (2),
  	  activatePstn      (3),
  	  restart1          (4),
 	  inService         (5),
 	  restart2          (6),
 	  restart3          (7),
 	  waitV5Init        (8),
 	  switchOver        (9),
 	  ctrlDataLinkRel1 (10),
 	  ctrlDataLinkRel2 (11),
 	  ctrlDataLinkRel3 (12),
 	  outOfService     (13),
 	  waitE1Reports    (14),
 	  waitL2StartUp    (15),
 	  waitLinkId       (16),
 	  waitRestart      (17),
	  notDefined       (18)
	  }
      MAX-ACCESS read-only
      STATUS current
      DESCRIPTION
      "Protocol State of the ML Active Variant.
       - sysStartUp   - an Establish request arrived to the V5.1 interface.
       - waitForVarId - the variant and the Interface Id were requested 
                        during the system start-up procedure.
       - activatePstn - activation of the PSTN Data Link was requested
                        during the system start-up procedure.
       - restart1     - the PSTN restart procedure is in process.
       - inService    - the V5.1 interface is IN SERVICE.
       - restart2     - the V5.1 is in AN5 state (sends restart complete
                        to all PSTN protocols and changes status to In-Service).
       - restart3     - the V5.1 is in AN6 state (sends restart complete
                        to all PSTN protocols and changes status to In-Service).
       - waitV5Init   - this state is entered when the system's management is in 
                        In-Service state, Switch to a new Variant is received 
                         and V5.1 interface will not be restarted.
       - switchOver   - this state is entered when the system's management is in 
                        In-Service state, Switch to a new Variant is received 
                        and V5.1 interface will be restarted.
       - ctrlDataLinkRel1 - this state is entered when the system's management is in 
                        In-Service state and Release Indication is received.
                        Timer TC1 is running in this state.
       - ctrlDataLinkRel2 - this state is entered on reception of Release-Indication
                        in 'restart3' state.
       - outOfService - the V5.1 interface is Out-of-Service.
       - notDefined   - V5.1 is not defined for this interface."
      ::= {v51MlEntry 5}

v51MlUserActiveVarReq OBJECT-TYPE
      SYNTAX  Integer32 (0..127)
      MAX-ACCESS read-write
      STATUS current
      DESCRIPTION
      "User Request to turn a certain Variant of the ML, to Active.
       This object specifies the Variant Id. requested by user to be Active.
       User's request is not always accepted."
      ::= {v51MlEntry 6}

v51MlDeleteVarReq OBJECT-TYPE
      SYNTAX  Integer32 (0..127)
      MAX-ACCESS read-write
      STATUS current
      DESCRIPTION
      "For V5.1: User Request to Delete a certain Variant of the ML.
	   For V5.2: User Request to Delete a certain Variant
       This object specifies the Variant Id. requested by user to be Delete.
       User's request will not be accepted if the required Variant Id is Active
       or during Reprovision process.
       This object is supported only up to MP R9."
      ::= {v51MlEntry 7}

v51MlSaveVariant OBJECT-TYPE
      SYNTAX  Integer32 (0..127)
      MAX-ACCESS read-write
      STATUS current
      DESCRIPTION
      "User Command to Save the TmpCnfg Variant data to a certain Variant Id of 
       the selected ML, in Current Cnfg. The value of this object specifies
	   the target Variant Id. 
       The data transferred should be: 
       - for V5.1: v51VarTable and v51VarCnfgTable parameters.
       - for V5.2: v51VarTable, v51VarCnfgTable and v51VarCchTable parameters.
       Upon Set command, the MUX will initiate a Sanity-Check process first: 
       - If	successful, the actual transfer will be performed. 
       - If warnings are detected, the user will have to perform the command 
         again to confirm the operation.
       - If errors are detected, transfer will NOT be performed.
       This object is supported only up to MP R9."
      ::= {v51MlEntry 8}

v51MlReadVariant OBJECT-TYPE
      SYNTAX  Integer32 (0..127)
      MAX-ACCESS read-write
      STATUS current
      DESCRIPTION
      "User Command to Read data from a certain Variant Id of the selected ML, 
       (in Current Cnfg) to the TmpCnfg. The value of this object specifies
	   the source Variant Id.
       The data transferred should be: 
       - for V5.1: v51VarTable and v51VarCnfgTable parameters.
       - for V5.2: v51VarTable, v51VarCnfgTable and v51VarCchTable parameters.
       The operation is valid only on existing Variants of the ML.
       This object is supported only up to MP R9."
      ::= {v51MlEntry 9}

v51MlDeactivateVar OBJECT-TYPE
      SYNTAX  Integer32 (0..127)
      MAX-ACCESS read-write
      STATUS current
      DESCRIPTION
      "User Request to Deactivate a certain Variant of the ML.
       This object specifies the Variant Id. requested by user to be Deactivated.
       User can deactivate a variant having Active Request status or Active
       status. Deactivating the variant having Active Status wil stop the V5.1
       operations on this link (for V5.2 it will stop completely the V5 activity)."
      ::= {v51MlEntry 10} 


--ML Cnfg Table

v51MlCnfgTable  OBJECT-TYPE
     SYNTAX SEQUENCE OF V51MlCnfgEntry
     MAX-ACCESS not-accessible
     STATUS  current
     DESCRIPTION
      "The write operation into the Table Objects is valid only
       to the TmpCnfg entry."
     ::= { v51MlCnfg 1}

v51MlCnfgEntry OBJECT-TYPE
      SYNTAX V51MlCnfgEntry
      MAX-ACCESS not-accessible
      STATUS current
	  DESCRIPTION
	  "An entry in table v51MlCnfgTable."
      INDEX {v51MlCnfgIdx, v51MlCnfgSltIdx, v51MlCnfgPrtIdx}
      ::= { v51MlCnfgTable 1}

V51MlCnfgEntry ::=
      SEQUENCE {
      v51MlCnfgIdx             Integer32,
      v51MlCnfgSltIdx          INTEGER,
      v51MlCnfgPrtIdx          Integer32,
      v51MlCnfgIfId            Integer32,
      v51MlCnfgStartupMode     INTEGER,
	  v51MlCnfgReprovision     INTEGER,
	  v51MlCnfgUnblockIoPorts  INTEGER,
	  v51MlCnfgRestartComplete INTEGER,
	  v51MlCnfgV52Application  INTEGER	  
      }

v51MlCnfgIdx OBJECT-TYPE
      SYNTAX  Integer32 (1..255)
      MAX-ACCESS  read-only
      STATUS  current
      DESCRIPTION
      "This attribute indicates the Idx of the Cnfg being accessed.
	   1..10 = Current Cnfg (data will be the same for all Current 
	           Configurations)
       255 = TmpCnfg."
      ::= {v51MlCnfgEntry 1}

v51MlCnfgSltIdx OBJECT-TYPE
      SYNTAX  INTEGER
      {
      io1   (5),
      io2   (6),
      io3   (7),
      io4   (8),
      io5   (9),
      io6  (10),
      io7  (11),
      io8  (12),
      io9  (13),
      io10 (14),
      io11 (15),
      io12 (16),
      notApplicable(255)
            }
      MAX-ACCESS  read-only
      STATUS  current
      DESCRIPTION
      "Slot Index.
       For V5.2 this index will be notApplicable(255)."
      ::= {v51MlCnfgEntry 2}

v51MlCnfgPrtIdx OBJECT-TYPE
      SYNTAX  Integer32
      MAX-ACCESS  read-only
      STATUS  current
      DESCRIPTION
      "This attribute indicates a unique  port number of the ML having 
       V5 interface.
       Valid values: exPrt1 (1)..exPrt4 (4), inPrt1(101)..inPrt4(104)
       NA=255 (for V5.2 only)."
      ::= {v51MlCnfgEntry 3}

v51MlCnfgIfId OBJECT-TYPE
     SYNTAX  Integer32 (0..99999999)
     MAX-ACCESS   read-write
     STATUS   current
     DESCRIPTION
     "V5.1 Interface Id."
     ::= {v51MlCnfgEntry 4}

v51MlCnfgStartupMode OBJECT-TYPE
      SYNTAX  INTEGER 
      { 
      sync  (2),
      async (3)
      }
      MAX-ACCESS   read-write
      STATUS   current
      DESCRIPTION
      "Startup Mode."
      ::= {v51MlCnfgEntry 5}

v51MlCnfgReprovision OBJECT-TYPE
      SYNTAX  INTEGER 
      { 
      no  (2),
      yes (3)
      }
      MAX-ACCESS   read-write
      STATUS   current
      DESCRIPTION
      "Reprovision Support.
       - no : no reprovision support (=default)
       - yes: reprovision is supported."
      ::= {v51MlCnfgEntry 6}

v51MlCnfgUnblockIoPorts OBJECT-TYPE
      SYNTAX  INTEGER 
      { 
      disabled  (2),
      enabled   (3)
      }
      MAX-ACCESS   read-write
      STATUS   current
      DESCRIPTION
      "Unblock IO Ports on Startup.
       - disabled - disable sending Unblock request on restart
       - enabled  - request unblock of all IO ports ON RESTART (=default)."
      ::= {v51MlCnfgEntry 7}

v51MlCnfgRestartComplete OBJECT-TYPE
      SYNTAX  INTEGER 
      { 
      uponLeRestart       (2),
      uponPstnProtocolAck (3)
      }
      MAX-ACCESS   read-write
      STATUS   current
      DESCRIPTION
      "Send Restart Complete.
       - uponLeRestart - after receiving restart from the other side.
       - uponPstnProtocolAck - after receiving restart ack from PSTN 
         protocol (=default)."
      ::= {v51MlCnfgEntry 8}

v51MlCnfgV52Application OBJECT-TYPE
      SYNTAX  INTEGER 
      { 
      notApplicable (1),
      none          (2),
      endPoint      (3),
	  exchangePoint (4)
      }
      MAX-ACCESS   read-write
      STATUS   current
      DESCRIPTION
      "The V5.2 Application of the Mux.
       notApplicable - for Agents that don't support this object.
       none          - V5.2 is not used in the Mux.
       endPoint      - this V5.2 Application transfers voice of Analog Voice 
                       and ISDN cards of the Mux, to/from V5.2 Local Exchange.
       exchangePoint - this V5.2 Application exchanges voice of ML cards (coming
                       from other devices) to/from V5.2 Local Exchange."
      ::= {v51MlCnfgEntry 9}


--V5.1 Access port tables

v51IoCnfgTable  OBJECT-TYPE
     SYNTAX SEQUENCE OF V51IoCnfgEntry
     MAX-ACCESS not-accessible
     STATUS  current
     DESCRIPTION
      "The write operation into the Table Objects is valid only
       to the TmpCnfg entry."
     ::= { v51AccessPort 1}

v51IoCnfgEntry OBJECT-TYPE
      SYNTAX V51IoCnfgEntry
      MAX-ACCESS not-accessible
      STATUS current
	  DESCRIPTION
	  "An entry in table v51IoCnfgTable."
      INDEX {v51IoCnfgIdx, v51IoCnfgSltIdx, v51IoCnfgPrtIdx}
      ::= { v51IoCnfgTable 1}

V51IoCnfgEntry ::=
      SEQUENCE {
      v51IoCnfgIdx         Integer32,
      v51IoCnfgSltIdx      INTEGER,
      v51IoCnfgPrtIdx      Integer32,
      v51IoCnfgSType       INTEGER,
      v51IoCnfgFType       INTEGER,
      v51IoCnfgPType       INTEGER
      }

v51IoCnfgIdx OBJECT-TYPE
      SYNTAX  Integer32 (1..255)
      MAX-ACCESS  read-only
      STATUS  current
      DESCRIPTION
      "This attribute indicates the Idx of the Cnfg being accessed.
	   1..10 = Current Cnfg (data will be the same for all Current 
	           Configurations)
       255 = TmpCnfg."
      ::= {v51IoCnfgEntry 1}

v51IoCnfgSltIdx OBJECT-TYPE
      SYNTAX  INTEGER
      {
      io1   (5),
      io2   (6),
      io3   (7),
      io4   (8),
      io5   (9),
      io6  (10),
      io7  (11),
      io8  (12),
      io9  (13),
      io10 (14),
      io11 (15),
      io12 (16),
      notApplicable(255)
            }
      MAX-ACCESS  read-only
      STATUS  current
      DESCRIPTION
      "Slot Index"
      ::= {v51IoCnfgEntry 2}

v51IoCnfgPrtIdx OBJECT-TYPE
      SYNTAX  Integer32
      MAX-ACCESS  read-only
      STATUS  current
      DESCRIPTION
      "This attribute indicates a unique  port number of the Io having 
       V5 interface.
       Valid values: exPrt1 (1)..exPrt16 (16)"
      ::= {v51IoCnfgEntry 3}

v51IoCnfgSType OBJECT-TYPE
      SYNTAX  INTEGER 
      { 
      notApplicable (1),
      no  (2),
      yes (3)
      }
      MAX-ACCESS   read-write
      STATUS   current
      DESCRIPTION
      "This object indicates if S Type Signaling will be used by this ISDN port
       (yes/no).
       notApplicable - for PSTN ports."
      ::= {v51IoCnfgEntry 4}

v51IoCnfgFType OBJECT-TYPE
      SYNTAX  INTEGER 
      { 
      notApplicable (1),
      no  (2),
      yes (3)
      }
      MAX-ACCESS   read-write
      STATUS   current
      DESCRIPTION
      "This object indicates if F Type Signaling will be used by this ISDN port
       (yes/no).
       notApplicable - for PSTN ports."
      ::= {v51IoCnfgEntry 5}

v51IoCnfgPType OBJECT-TYPE
      SYNTAX  INTEGER 
      { 
      notApplicable (1),
      no  (2),
      yes (3)
      }
      MAX-ACCESS   read-write
      STATUS   current
      DESCRIPTION
      "This object indicates if P Type Signaling will be used by this ISDN port
       (yes/no).
       notApplicable - for PSTN ports."
      ::= {v51IoCnfgEntry 6}


-- Traps

--NOTIFICATIONS

v51IfEvents OBJECT-IDENTITY
   STATUS  current
   DESCRIPTION
   "The events for the V5."
    ::= { v51If 0 }

activeVariantTrap  NOTIFICATION-TYPE
   OBJECTS       { v51MlCurrActiveVar }
   STATUS  current
   DESCRIPTION
   "This trap is sent when the Active Variant of a Link is changed (that
    includes the case when a user performs Save to the Variant that is Active)."
   ::= { v51IfEvents 1 }
-- 
-- file :D:\Synergy\WorkArea\545\mib_rad\txt\voip.txt
-- 

-- --------------------------------------------------------------------------------------
--Title:  RAD's Voice Over IP MIB
--By:     Liora Gafni
--Date :  28-Sep-99
--Description: This MIB contains parameters that were not defined in the ITU H.341 MIB
--             and are required for RAD products.
--
--Last Update:  07/09/2006
--By:  			Shay Harari
--File:  v:\doc\rdv\mib\ver530\voip.txt
-- --------------------------------------------------------------------------------------

--IMPORTS
--      enterprises                            FROM SNMPv2-SMI
--      DisplayString                          FROM SNMPv2-TC
--      IpAddress                              FROM SNMPv2-SMI
--      OCTET STRING                           FROM SNMPv2-TC
--      OBJECT-TYPE                            FROM RFC1212
--      TAddress                               FROM	SNMPv2-TC
--      MmTAddressTag,MmEndpointID,
--      MmAliasAddress,MmH323EndpointType,
--      MmGatekeeperID,MmGlobalIdentifier      FROM MULTI-MEDIA-MIB-TC;


--wanGen   OBJECT IDENTIFIER ::= {radWan 1} (see mpmx.txt)
voipWanGen OBJECT IDENTIFIER ::= {wanGen 7} --(see mpmx.txt)

voipWanGenEvents OBJECT IDENTIFIER ::= {voipWanGen 0}


-- VOIP Card Configuration

voipCardConfig OBJECT-TYPE   
      SYNTAX  Integer32 
      MAX-ACCESS  read-only    
      STATUS  current
      DESCRIPTION
      "The value of this object determines the VOIP card configuration.
       Bit 0 (LSB): if 1 - a GK exists. If 0 - no GK exists in this card.
       The other bits may be used in the future."
      ::= { voipWanGen 1 }


-- GK General Parameters table

gkGenTable  OBJECT-TYPE
     SYNTAX SEQUENCE OF GkGenEntry
     MAX-ACCESS not-accessible
     STATUS  current
     DESCRIPTION
      "General parameters for the VOIP GateKeeper."
     ::= { voipWanGen 2 }

gkGenEntry OBJECT-TYPE
      SYNTAX GkGenEntry
      MAX-ACCESS not-accessible
      STATUS current
	  DESCRIPTION
	  "An entry in table gkGenTable."
      INDEX {ifIndex}
      ::= { gkGenTable 1}

GkGenEntry ::=
      SEQUENCE {
      gkGenCallMode         INTEGER,
      gkGenMaxConnections   Integer32,
	  gkGenDefaultDistance  Integer32,
	  gkGenOutOfZoneDist    Integer32,
	  gkGenCallAcceptPolicy	INTEGER,
	  gkGenIrqInterval      Integer32,
	  gkGenQ931Port         Integer32,
	  gkGenRasPort          Integer32,
      gkGenRegPolicy        INTEGER,
      gkGenZoneId           OCTET STRING      
	  }


gkGenCallMode OBJECT-TYPE
      SYNTAX  INTEGER
      {
      direct           (2),
      routed           (3),
      notApplicable    (255)
            }
      MAX-ACCESS  read-write
      STATUS  current
      DESCRIPTION
      "This parameters shows whether the calls will go through the GK (routed) or
       whether the calls will be direct from Endpoint to Endpoint without involving
       the GK (direct)."
      ::= {gkGenEntry 1}

gkGenMaxConnections OBJECT-TYPE
      SYNTAX  Integer32  
      MAX-ACCESS  read-write
      STATUS  current
      DESCRIPTION
      "MAX no. of connections enabled by the GK to take place simultaneously.
       If the MAX no. of calls is exceeded, a busy signal will be returned."
      ::= {gkGenEntry 2}

gkGenDefaultDistance   OBJECT-TYPE
      SYNTAX  Integer32  
      MAX-ACCESS  read-write
      STATUS  current
      DESCRIPTION
      "The Distance allowed for endpoints that are registered dynamically."
      ::= {gkGenEntry 3}

gkGenOutOfZoneDist   OBJECT-TYPE
      SYNTAX  Integer32  
      MAX-ACCESS  read-write
      STATUS  current
      DESCRIPTION
      "The Distance allowed for an out of zone endpoint that is making a call
       through the gatekeeper."
      ::= {gkGenEntry 4}

gkGenCallAcceptPolicy OBJECT-TYPE
      SYNTAX  INTEGER
      {
      acceptAll      (2),
      registeredOnly (3),
	  predefinedOnly (4)
                  }
      MAX-ACCESS  read-write
      STATUS  current
      DESCRIPTION
      "Defines the policy concerning the incoming phone calls.
       The importance of this parameter is for bidding and security matters.
       Accept All - all the incoming calls are accepted.
       Registered Only - the calls are accepted from the predefined endpoints only,
       which are endpoints that have previously registered with the gatekeeper.
       Predefined Only - with this policy only the calls from the statically
       registered endpoints can be accepted."
      ::= {gkGenEntry 5}

gkGenIrqInterval   OBJECT-TYPE
      SYNTAX  Integer32  
      MAX-ACCESS  read-write
      STATUS  current
      DESCRIPTION
      "In order for the Gatekeeper to determine if an endpoint is turned off,
       or has otherwise entered a failure mode, the Gatekeeper may use the Information
       Request (IRQ) to poll the endpoints at the certain interval (in seconds).
       
       THE IRQ INTERVAL controls the frequency the gk sends IRQ messages.
       This message is sent to all on-line endpoints registered as dynamic in order
       to verify they are really on-line. This is done to detect terminals that
       shut off without sending the required URQ message that notifies the gk that
       they are no longer on-line.
       
       Endpoints failing to respond too many times have their dynamic properties
       unregistered. Choosing the desired interval should take into account the
       following factors : 
       IRQ messages add to the traffic already present over the network and the
       shorter the interval the more IRQ messages will be sent. On the other hand the
       longer the delay the longer it will take for the gk to detect dynamic
       registrations that have ceased to actually be on-line. Note that the
       IRQ interval relates to each endpoint and the actual number of the IRQ messages
       the gk will create should be multiplied by the number of endpoints
       registered dynamically."
      ::= {gkGenEntry 6}

gkGenQ931Port OBJECT-TYPE
      SYNTAX  Integer32
      MAX-ACCESS  read-write
      STATUS  current
      DESCRIPTION
      "Q.931 Port no."
      ::= {gkGenEntry 7}

gkGenRasPort OBJECT-TYPE
      SYNTAX  Integer32
      MAX-ACCESS  read-write
      STATUS  current
      DESCRIPTION
      "RAS Port no."
      ::= {gkGenEntry 8}

gkGenRegPolicy OBJECT-TYPE
      SYNTAX  INTEGER
      {
      acceptAll          (2),
      predefinedOnly     (3),
	  registrationReject (4)
                  }
      MAX-ACCESS  read-write
      STATUS  current
      DESCRIPTION
      "Policy of dynamic registrations in the Gatekeeper.
	   The GK will act according to the following policies:
       Accept All      - The GK will enable all requesting endpoints to register dynamically.
       Predefined Only - The GK will enable registration of endpoints that were registered
                         previously via static registration.
       Registration Reject - No endpoint may register dynamically."
      ::= {gkGenEntry 9}

gkGenZoneId OBJECT-TYPE
      SYNTAX  OCTET STRING
      MAX-ACCESS  read-write
      STATUS  current
      DESCRIPTION
      "Zone Identifier: 1 or 2 digits, (0-9)(1-9)."  
      ::= {gkGenEntry 10}


-- GK Endpoints Table

gkEndpTable  OBJECT-TYPE
     SYNTAX SEQUENCE OF GkEndpEntry
     MAX-ACCESS not-accessible
     STATUS  current
     DESCRIPTION
      "Table containing the Endpoints that are registered (statically & Dynamically)
       with the current GK."
     ::= { voipWanGen 3 }

gkEndpEntry OBJECT-TYPE
      SYNTAX GkEndpEntry
      MAX-ACCESS not-accessible
      STATUS current
	  DESCRIPTION
	  "An entry in table gkEndpTable."
      INDEX {ifIndex,
             gkEndpAliasTag,
             gkEndpAlias}
      ::= { gkEndpTable 1}

GkEndpEntry ::=
      SEQUENCE {
	  gkEndpAliasTag  MmAliasTag,
	  gkEndpAlias     MmAliasAddress,
	  gkEndpRowStatus RowStatus,
      gkEndpAddressTag MmTAddressTag,
	  gkEndpAddress   TAddress,
      gkEndpID        MmEndpointID,
      gkEndpType      MmH323EndpointType,
	  gkEndpQ931Port  Integer32,
	  gkEndpDistance  Integer32,
      gkEndpRegMode   INTEGER,
	  gkEndpSetOnline INTEGER,
	  gkEndpStatus    INTEGER
      }


gkEndpAliasTag OBJECT-TYPE
      SYNTAX   MmAliasTag
      MAX-ACCESS  read-only
      STATUS  current
      DESCRIPTION
      "Alias Tag of the Endpoint."
      ::= {gkEndpEntry 1}

gkEndpAlias OBJECT-TYPE
      SYNTAX   MmAliasAddress
      MAX-ACCESS  read-only
      STATUS  current
      DESCRIPTION
      "Alias of the Endpoint."
      ::= {gkEndpEntry 2}

gkEndpRowStatus OBJECT-TYPE
      SYNTAX  RowStatus
      MAX-ACCESS  read-create
      STATUS  current
      DESCRIPTION
      "The row status of the entry. This object is required to create
       or delete rows remotely by a manager. "
      ::= {gkEndpEntry 3}
						
gkEndpAddressTag  OBJECT-TYPE
      SYNTAX  MmTAddressTag         
      MAX-ACCESS  read-create
      STATUS  current
      DESCRIPTION
      "Address Tag of Endpoint."
      ::= {gkEndpEntry 4}

gkEndpAddress OBJECT-TYPE
      SYNTAX  TAddress
      MAX-ACCESS  read-create
      STATUS  current
      DESCRIPTION
      "Address of Endpoint."
      ::= {gkEndpEntry 5}


gkEndpID OBJECT-TYPE
      SYNTAX   MmEndpointID
      MAX-ACCESS  read-create
      STATUS  current
      DESCRIPTION
      "Endpoint Identifier."
      ::= {gkEndpEntry 6}

gkEndpType OBJECT-TYPE
      SYNTAX  MmH323EndpointType
      MAX-ACCESS  read-create
      STATUS  current
      DESCRIPTION
      "This parameter shows whether the current endpoint is a GW or Terminal or
       any other type of H.323 endpoint."
      ::= {gkEndpEntry 7}

						
gkEndpQ931Port OBJECT-TYPE
      SYNTAX  Integer32
      MAX-ACCESS  read-create
      STATUS  current
      DESCRIPTION
      "Q.931 Port no."
      ::= {gkEndpEntry 8}

gkEndpDistance OBJECT-TYPE
      SYNTAX  Integer32
      MAX-ACCESS  read-create
      STATUS  current
      DESCRIPTION
      "Distance from the current endpoint to the GateKeeper with which it is
       Registered."
      ::= {gkEndpEntry 9}

gkEndpRegMode OBJECT-TYPE
      SYNTAX  INTEGER
	  {
	  dynamic (2),
	  static  (3)
	  }
      MAX-ACCESS  read-only
      STATUS  current
      DESCRIPTION
      "This parameter shows whether the Endpoint Registered Dynamically or Statically."
      ::= {gkEndpEntry 10}

gkEndpSetOnline OBJECT-TYPE
      SYNTAX  INTEGER
	  {
	  uponDynamicReg (2),
	  always (3)
	  }
      MAX-ACCESS  read-create
      STATUS  current
      DESCRIPTION
      "This parameter shows whether the endpoint will always be online or whether it
       will be on line upon Dynamic Registration only."
      ::= {gkEndpEntry 11}

gkEndpStatus OBJECT-TYPE
      SYNTAX  INTEGER
	  {
	  online (2),
	  offline (3)
	  }
      MAX-ACCESS  read-only
      STATUS  current
      DESCRIPTION
      "This parameter shows whether the endpoint is currently online."
      ::= {gkEndpEntry 12}



-- GK Neighbors table

gkNeighbTable  OBJECT-TYPE
     SYNTAX SEQUENCE OF GkNeighbEntry
     MAX-ACCESS not-accessible
     STATUS  current
     DESCRIPTION
      "Table of GateKeepers that are Neighbors of the current Gatekeeper."
     ::= { voipWanGen 4 }

gkNeighbEntry OBJECT-TYPE
      SYNTAX GkNeighbEntry
      MAX-ACCESS not-accessible
      STATUS current
	  DESCRIPTION
	  "An entry in table gkNeighbTable."
      INDEX {ifIndex,
             gkNeighbAddressTag,
             gkNeighbAddress}
      ::= { gkNeighbTable 1}

GkNeighbEntry ::=
      SEQUENCE {
      gkNeighbAddressTag        MmTAddressTag,
	  gkNeighbAddress           TAddress,
	  gkNeighbRowStatus         RowStatus,
      gkNeighbLeadingAlias      MmAliasAddress,
      gkNeighbDistance          Integer32,
	  gkNeighbDescription       MmGatekeeperID
      }

gkNeighbAddressTag  OBJECT-TYPE
      SYNTAX  MmTAddressTag            
      MAX-ACCESS  read-only
      STATUS  current
      DESCRIPTION
      "Tag of GK or GW address."
      ::= {gkNeighbEntry 1}

gkNeighbAddress OBJECT-TYPE
      SYNTAX  TAddress
      MAX-ACCESS  read-only
      STATUS  current
      DESCRIPTION
      "Address of GK or GW."
      ::= {gkNeighbEntry 2}

gkNeighbRowStatus OBJECT-TYPE
      SYNTAX  RowStatus
      MAX-ACCESS  read-create
      STATUS  current
      DESCRIPTION
      "The row status of the entry. This object is required to create
       or delete rows remotely by a manager. "
      ::= {gkNeighbEntry 3}

gkNeighbLeadingAlias  OBJECT-TYPE
      SYNTAX  MmAliasAddress
      MAX-ACCESS  read-create
      STATUS  current
      DESCRIPTION
      "This is the Leading Alias Address (Zone Prefix) that will be dialed in order to reach 
       the specific neighbor."
      ::= {gkNeighbEntry 4}

gkNeighbDistance OBJECT-TYPE
      SYNTAX  Integer32  
      MAX-ACCESS  read-create
      STATUS  current
      DESCRIPTION
      "Distance between the local GateKeeper and the Neighbor GateKeeper."       
      ::= {gkNeighbEntry 5}

gkNeighbDescription OBJECT-TYPE
      SYNTAX  MmGatekeeperID
      MAX-ACCESS  read-create
      STATUS  current
      DESCRIPTION
      "ASCII String Description for identifying the Neighbor."       
      ::= {gkNeighbEntry 6}


-- GW General Parameters table

gwGenTable  OBJECT-TYPE
     SYNTAX SEQUENCE OF GwGenEntry
     MAX-ACCESS not-accessible
     STATUS  current
     DESCRIPTION
      "General parameters for the VOIP GateWay."
     ::= { voipWanGen 5 }

gwGenEntry OBJECT-TYPE
      SYNTAX GwGenEntry
      MAX-ACCESS not-accessible
      STATUS current
	  DESCRIPTION
	  "An entry in table gwGenTable."
      INDEX {ifIndex}
      ::= { gwGenTable 1}

GwGenEntry ::=
      SEQUENCE {
	  gwGenGwId           MmEndpointID,
	  gwGenQ931Port       Integer32,
	  gwGenRasPort        Integer32,
      gwGenMode           INTEGER,
	  gwGenVoipExtension  Integer32,
	  gwGenRemGwAddress   TAddress,
      gwGenMaxConnections Integer32,
	  gwGenTOS            OCTET STRING,
	  gwGenBackupGkAddr   TAddress,
	  gwGenTimeToRegister Integer32        
	  }
	  
gwGenGwId OBJECT-TYPE
      SYNTAX  MmEndpointID
      MAX-ACCESS  read-write
      STATUS  current
      DESCRIPTION
      "A character string of up to 20 characters identifying the gateway."       
      ::= {gwGenEntry 1}

gwGenQ931Port OBJECT-TYPE
      SYNTAX  Integer32
      MAX-ACCESS  read-write
      STATUS  current
      DESCRIPTION
      "The Q.931 port no. of the Gateway."       
      ::= {gwGenEntry 2}

gwGenRasPort OBJECT-TYPE
      SYNTAX  Integer32
      MAX-ACCESS  read-write
      STATUS  current
      DESCRIPTION
      "The RAS port no. of the Gateway."       
      ::= {gwGenEntry 3}

gwGenMode OBJECT-TYPE
      SYNTAX  INTEGER
      {
      disable       (2),
      cvsIp         (3),
	  standard      (4),
      notApplicable (255)
            }
      MAX-ACCESS  read-write
      STATUS  current
      DESCRIPTION
      "GW Mode:
       disable - The GW is not activated.
       cvsIp   - CVS is a Compressed Voice System.
                 The GW will compress voice calls at a ratio of
                 16 to 1. 16 time slots of E1/T1 will be compressed into
                 1 E1/T1 time slot. When this mode is used the Gateway can
                 communicate directly with another Gateway without a Gatekeeper.
       standard - This mode includes a Gateway & a Gatekeeper."
     ::= {gwGenEntry 4}

gwGenVoipExtension OBJECT-TYPE
       SYNTAX  Integer32
       MAX-ACCESS  read-write
       STATUS  current
       DESCRIPTION
      "This is the extension number of the VOIP protocol.
	   It is used for the Voice card to identify the calls made through the VoIP card.
	   The user may choose an arbitrary value for this field, the only restriction is that
	   there must be no other entity registered with the same extension number."
	   ::= {gwGenEntry 5}

gwGenRemGwAddress OBJECT-TYPE
      SYNTAX  TAddress
      MAX-ACCESS  read-write
      STATUS  current
      DESCRIPTION
      "Defines the remote gateway address (IP + port). It is important for gateway
       to gateway connection."       
      ::= {gwGenEntry 6}

gwGenMaxConnections OBJECT-TYPE
      SYNTAX  Integer32  
      MAX-ACCESS  read-write
      STATUS  current
      DESCRIPTION
      "MAX no. of connections enabled by the GW."
      ::= {gwGenEntry 7}

gwGenTOS OBJECT-TYPE
      SYNTAX  OCTET STRING  
      MAX-ACCESS  read-write
      STATUS  current
      DESCRIPTION
      "Type of Service.
       The BIT Format is consistent with the IP standard:
       +-----+-----+-----+-----+-----+-----+-----+-----+
       |                 |                       |     |
       |   PRECEDENCE    |    TYPE OF SERVICE    |  0  |
       |                 |                       |     |
       +-----+-----+-----+-----+-----+-----+-----+-----+
       	  0	   1	  2	    3	  4	    5	  6		7
	   
	   At present, only 1 BYTE will be used, bits 0 (MSB) - 7 (LSB).
	   
	   The precedence consists of 3 BITS (0-2):
       111 - Network Control
       110 - Internetwork Control
       101 - CRITIC/ECP
       100 - Flash Override
       011 - Flash
       010 - Immediate
       001 - Priority
       000 - Routine
	   
       The TOS values BITS (3-5):

       Bit 3 is the Delay:       0 = Normal Delay,       1 = Low Delay.
       Bit 4 is the Throughput:  0 = Normal Throughput,  1 = High Throughput.
       Bit 5:is the Reliability: 0 = Normal Reliability, 1 = High Reliability.

       Bits 6 & 7 are for future use and their current value is 0."
      ::= {gwGenEntry 8}

gwGenBackupGkAddr OBJECT-TYPE
      SYNTAX  TAddress
      MAX-ACCESS  read-write
      STATUS  current
      DESCRIPTION
      "Defines the backup gatekeeper address (IP + port).
       When the backup GK is active, all the calls will be routed to it and it
       will be responsible for their address translation.
       The first GK address is defined in the standard H.341 MIB."
     ::= {gwGenEntry 9}

gwGenTimeToRegister OBJECT-TYPE
      SYNTAX  Integer32  
      MAX-ACCESS  read-write
      STATUS  current
      DESCRIPTION
      "The GW should register every 'Time to Register' seconds with the GK.
       The 'Time to Register' range is from 0 to 900 seconds in intervals of 60 seconds.
	   0 means Never.
       When the GK becomes active the Gateways that are up can register so that
       the GK has an updated list of active Registered Gateways."
     ::= {gwGenEntry 10}



-- RAD's addition to h245ConfigurationTable         

radH245ConfigTable OBJECT-TYPE
      SYNTAX SEQUENCE OF RadH245ConfigEntry
      MAX-ACCESS not-accessible
      STATUS current
      DESCRIPTION
      "This table contains information about H.245 configuration parameters.
       It is a list of configuration parameter entries.
       The number of entries equals to the number of H.245 stacks in a system."
      ::= { voipWanGen 6 }

radH245ConfigEntry OBJECT-TYPE
      SYNTAX RadH245ConfigEntry
      MAX-ACCESS not-accessible
      STATUS current
      DESCRIPTION 
      "It contains objects that describe the H.245 configuration parameters."
      INDEX { ifIndex }
      ::= { radH245ConfigTable 1 }
      
RadH245ConfigEntry ::=
      SEQUENCE {
      h245MaxJitter   Integer32,
	  h245Tunneling   INTEGER
	  } 

h245MaxJitter OBJECT-TYPE
      SYNTAX  Integer32
      MAX-ACCESS  read-write
      STATUS  current
      DESCRIPTION
      "Maximum peak to peak delivery (in miliseconds) of audio packets
       to the transport layer that the transmitter shall cause."
      ::= {radH245ConfigEntry 1}

h245Tunneling OBJECT-TYPE
      SYNTAX  INTEGER
      {
      disable		(2),
      enable	    (3)
 	  }                  
      MAX-ACCESS  read-write
      STATUS  current
      DESCRIPTION
      "This variable enables or disables the usage of Tunneling."
      ::= {radH245ConfigEntry 2}


-- RTP Multiplexing

rtpMultiplexTable  OBJECT-TYPE
     SYNTAX SEQUENCE OF RtpMultiplexEntry
     MAX-ACCESS not-accessible
     STATUS  current
     DESCRIPTION
      "RTP Multiplexing table.
      RTP Multiplexing: In IP telephony system, the addition of packet headers,
      including IP, UDP and RTP headers, increases the header overhead, decreasing
      efficient transmission. Also, because of large numbers of short voice
      packets flowing into the network, Internet load increases, eventually
      resulting in large delay and packet loss. RTP Multiplexing is a way to send
      multiple RTP packets between a pair of Gateways, with a single
      IP frame. This will reduces the header overhead and decreases delay by
      enabling voice transmission with fewer packets."
     ::= { voipWanGen 7 }

rtpMultiplexEntry OBJECT-TYPE
      SYNTAX RtpMultiplexEntry
      MAX-ACCESS not-accessible
      STATUS current
	  DESCRIPTION
	  "An entry in table rtpMultiplexTable."
      INDEX {ifIndex}
      ::= { rtpMultiplexTable 1}

RtpMultiplexEntry ::=
      SEQUENCE {
      rtpMultiplexedRtp     INTEGER,
      rtpMultiplexFrameSize Integer32,
      rtpMultiplexInterval  Integer32,
      rtpMultiplexPcktRedundancy Integer32
      }

rtpMultiplexedRtp  OBJECT-TYPE
      SYNTAX  INTEGER {
	  disable         (2),
	  multiplexType1  (3),
	  multiplexType2  (4)
	  }                  
      MAX-ACCESS  read-write
      STATUS  current
      DESCRIPTION
      "RTP Multiplexing is a way to send multiple RTP packets with a single IP frame.
       This will reduce the header overhead and decrease the delay by enabling
       voice transmission with fewer packets.
       The option of this field are:
       Disable - No RTP Multiplexing.
	   multiplexType1 - medium level  of compression for RTP multiplexing.
   	   multiplexType2 - high level of compression for RTP multiplexing.
       Using the High Compression algorithm is more efficient
       but will cause the loss of some RTP header information.
       If RTP statistics are important, the medium compression must be selected."
      ::= {rtpMultiplexEntry 1}

rtpMultiplexFrameSize  OBJECT-TYPE
      SYNTAX  Integer32 
      MAX-ACCESS  read-write
      STATUS  current
      DESCRIPTION
      "Defines the maximum size in Bytes of the multiplexed frame.
       In some cases this must be limited to avoid IP fragmentation,
       which makes the multiplexing useless, and can also decrease
       the damage in case of the frame loss.
       At present the size is 1500."
      ::= {rtpMultiplexEntry 2}

rtpMultiplexInterval  OBJECT-TYPE
      SYNTAX  Integer32                   
      MAX-ACCESS  read-write
      STATUS  current
      DESCRIPTION
      "Defines the maximum amout of time (msec.) between multiplexed frames 
       that are sent.
       Legal values: 10-90 msec."
       ::= {rtpMultiplexEntry 3}

rtpMultiplexPcktRedundancy  OBJECT-TYPE
      SYNTAX  Integer32 
      MAX-ACCESS  read-write
      STATUS  current
      DESCRIPTION
      "Defines the the number of times each voice frame should be transmitted.
       At present legal values are: 1-4."
      ::= {rtpMultiplexEntry 4}

-- Tariff 

voipTariff OBJECT IDENTIFIER ::= {voipWanGen 8}

voipTariffServerTable  OBJECT-TYPE
     SYNTAX SEQUENCE OF VoipTariffServerEntry
     MAX-ACCESS not-accessible
     STATUS  current
     DESCRIPTION
      "VoIP Tariff Server table."
     ::= { voipTariff 1 }

voipTariffServerEntry OBJECT-TYPE
      SYNTAX VoipTariffServerEntry
      MAX-ACCESS not-accessible
      STATUS current
	  DESCRIPTION
	  "An entry in table voipTariffServerTable."
      INDEX {voipTariffServerCnfgIdx, voipTariffServerIdx}
      ::= { voipTariffServerTable 1}

VoipTariffServerEntry ::=
      SEQUENCE {
      voipTariffServerCnfgIdx   Unsigned32,
	  voipTariffServerIdx       Unsigned32,
	  voipTariffServerIpAddress IpAddress,
	  voipTariffServerPort      Unsigned32
      }

voipTariffServerCnfgIdx OBJECT-TYPE
      SYNTAX Unsigned32
      MAX-ACCESS not-accessible
      STATUS current
      DESCRIPTION
      "This object indicates the Index of the Configuration (1..255) being 
       accessed ; Index=255 relates to the Temporary Configuration.
       Set is allowed only to the Temporary Configuration."
      ::= { voipTariffServerEntry 1}

voipTariffServerIdx OBJECT-TYPE
      SYNTAX Unsigned32
      MAX-ACCESS not-accessible
      STATUS current
      DESCRIPTION
      "This object indicates the Index of the Tariff Server being 
       accessed (1, 2)."
      ::= { voipTariffServerEntry 2} 

voipTariffServerIpAddress OBJECT-TYPE
	SYNTAX  IpAddress 
	MAX-ACCESS  read-write
	STATUS current
	DESCRIPTION
	"This object defines  the  IP Address of the Tariff Server."
	::= { voipTariffServerEntry 3}

voipTariffServerPort  OBJECT-TYPE
      SYNTAX  Unsigned32 
      MAX-ACCESS  read-write
      STATUS  current
      DESCRIPTION
      "This object defines the used TCP/UDP port of the Tariff Server."
      ::= { voipTariffServerEntry 4}

-- VoIP NOTIFICATIONS

voipTariffServerCommFail  NOTIFICATION-TYPE
     OBJECTS       {voipTariffServerIpAddress, voipTariffServerPort}
     STATUS current
     DESCRIPTION     
     "This trap is sent when communication attempt with a Tariff Server failed."
     ::= { voipWanGenEvents 1 }


voipConfig OBJECT IDENTIFIER ::= { voipWanGen 9 }

voipSip OBJECT IDENTIFIER ::= { voipConfig 1 }

-- ----------------------------------
-- SIP (Session Initiation Protocol)
-- ----------------------------------

--
-- SIP Common Objects
--

voipSipCommon		OBJECT IDENTIFIER ::= {voipSip 1}
voipSipCommonCfg	OBJECT IDENTIFIER ::= {voipSipCommon 1}


radSipCommonCfgTable OBJECT-TYPE
	SYNTAX		SEQUENCE OF RadSipCommonCfgEntry
	MAX-ACCESS	not-accessible
	STATUS		current
	DESCRIPTION
	"SIP Common Configuration table.
	 This table contains the common configuration objects
	 applicable to all SIP entities."
	::= { voipSipCommonCfg 1 }

radSipCommonCfgEntry OBJECT-TYPE
	SYNTAX		RadSipCommonCfgEntry
	MAX-ACCESS	not-accessible
	STATUS		current
	DESCRIPTION
	"A row of SIP Common Configuration table."
	INDEX { radSipCommonCfgIdx }
	::= { radSipCommonCfgTable 1 }

RadSipCommonCfgEntry ::=
	SEQUENCE {
		radSipCommonCfgIdx				Unsigned32,
		radSipCommonCfgListenPort		Unsigned32,
		radSipCommonCfgRtpBaseUdpPort	Unsigned32,
		radSipCommonCfgRtpIpTos			Unsigned32
	}

radSipCommonCfgIdx OBJECT-TYPE
	SYNTAX		Unsigned32
	MAX-ACCESS	not-accessible
	STATUS		current
	DESCRIPTION
	"The index of the table.
	 
	 This object might represent the Configuration Index (1..100) being accessed;
	 Index=255 relates to the TmpCnfg.
	 For devices with multiple configurations, Set is permitted to TmpCnfg(255) only.
	 
	 Not-Applicable = 1."
	::= { radSipCommonCfgEntry 1 }

radSipCommonCfgListenPort OBJECT-TYPE
	SYNTAX		Unsigned32
	MAX-ACCESS	read-write
	STATUS		current
	DESCRIPTION
	"This object represents the SIP Listening Port number."
	::= { radSipCommonCfgEntry 2 }

radSipCommonCfgRtpBaseUdpPort OBJECT-TYPE
	SYNTAX		Unsigned32
	MAX-ACCESS	read-write
	STATUS		current
	DESCRIPTION
	"This object represents the RTP Base UDP Port number."
	::= { radSipCommonCfgEntry 3 }

radSipCommonCfgRtpIpTos OBJECT-TYPE
	SYNTAX		Unsigned32
	MAX-ACCESS	read-write
	STATUS		current
	DESCRIPTION
	"This object represents the TOS byte value
	 that will be written in the IP header for RTP packets only."
	::= { radSipCommonCfgEntry 4 }


--
-- SIP Server
--

voipSipServer		OBJECT IDENTIFIER ::= {voipSip 2}
voipSipServerCfg	OBJECT IDENTIFIER ::= {voipSipServer 1}


radSipRegCfgTable OBJECT-TYPE
	SYNTAX		SEQUENCE OF RadSipRegCfgEntry
	MAX-ACCESS	not-accessible
	STATUS		current
	DESCRIPTION
	"SIP Registrar Configuration table."
	::= { voipSipServerCfg 1 }

radSipRegCfgEntry OBJECT-TYPE
	SYNTAX	   	RadSipRegCfgEntry
	MAX-ACCESS	not-accessible
	STATUS		current
	DESCRIPTION
	"A row of SIP Registrar Configuration table."
	INDEX { radSipRegCfgIdx, radSipRegIdx }
	::= { radSipRegCfgTable 1 }

RadSipRegCfgEntry ::=
	SEQUENCE {
		radSipRegCfgIdx					Unsigned32,
		radSipRegIdx					Unsigned32,
		radSipRegActivation				INTEGER,
		radSipRegAddr					SnmpAdminString, -- IP/URL address
		radSipRegUdpPort				Unsigned32,
		radSipRegRenewalTimer			Unsigned32,
		radSipRegDomain					SnmpAdminString,
		radSipRegMode					INTEGER,
		radSipRegUserDefinition			INTEGER,
		radSipRegCallWithoutReg			INTEGER,
		radSipRegUserParams				SnmpAdminString,
		radSipRegRowStatus				RowStatus
		}

radSipRegCfgIdx OBJECT-TYPE
	SYNTAX		Unsigned32
	MAX-ACCESS	not-accessible
	STATUS		current
	DESCRIPTION
	"The first index of the table.
	 
	 This object might represent the Configuration Index (1..100) being accessed;
	 Index=255 relates to the TmpCnfg.
	 For devices with multiple configurations, Set is permitted to TmpCnfg(255) only.
	 
	 Not-Applicable = 1."
	::= { radSipRegCfgEntry 1 }

radSipRegIdx OBJECT-TYPE
	SYNTAX		Unsigned32
	MAX-ACCESS	not-accessible
	STATUS		current
	DESCRIPTION
	"This object represents the Registrar Index."
	::= { radSipRegCfgEntry 2 }

radSipRegActivation OBJECT-TYPE
	SYNTAX		INTEGER
	{
		notApplicable	(1),
		disable			(2),
		enable			(3)
	}
	MAX-ACCESS	read-create
	STATUS		current
	DESCRIPTION
    "This object allows the user to activate the Registrar.
     
     If changed from enable(3) to disable(2) -
        device will be disconnected from server (stop sending renewal messages).
     If changed from disable(2) to enable(3) -
        device will be connected to the server."
	::= { radSipRegCfgEntry 3 }

radSipRegAddr OBJECT-TYPE
	SYNTAX		SnmpAdminString
	MAX-ACCESS	read-create
	STATUS		current
	DESCRIPTION
	"This object represents the Registrar's IP/URL Address."
	::= { radSipRegCfgEntry 4 }

radSipRegUdpPort OBJECT-TYPE
	SYNTAX		Unsigned32
	MAX-ACCESS	read-create
	STATUS		current
	DESCRIPTION
	"This object represents the Registration's Destination UDP Port number."
	::= { radSipRegCfgEntry 5 }

radSipRegRenewalTimer OBJECT-TYPE
	SYNTAX		Unsigned32
	MAX-ACCESS	read-create
	STATUS		current
	DESCRIPTION
	"This object represents the Registration's Renewal Timer, in seconds."
	::= { radSipRegCfgEntry 6 }

radSipRegDomain OBJECT-TYPE
	SYNTAX		SnmpAdminString
	MAX-ACCESS	read-create
	STATUS		current
	DESCRIPTION
	"This object represents the User Agent's Domain Name."
	::= { radSipRegCfgEntry 7 }

radSipRegMode OBJECT-TYPE
	SYNTAX		INTEGER
	{
		gateway			(1),
		localEntries	(2)
	}
	MAX-ACCESS	read-create
	STATUS		current
	DESCRIPTION
	"This object indicates the Registration Mode:
	 gateway(1)      - one registration for the device
	 localEntries(2) - number of registrations are defined according to
	 				   the number of local entries."
	::= { radSipRegCfgEntry 8 }

radSipRegUserDefinition OBJECT-TYPE
	SYNTAX		INTEGER
	{
		gateway			(1),
		localEntries	(2)
	}
	MAX-ACCESS	read-create
	STATUS		current
	DESCRIPTION
	"This object indicates the User configuration:
	 gateway(1)      - single user configuration for the device
	 localEntries(2) - different user configuration for each local entry.
	 
	 This object is irrelevant when radSipRegMode = gateway(1)."
	::= { radSipRegCfgEntry 9 }

radSipRegCallWithoutReg OBJECT-TYPE
	SYNTAX		INTEGER
	{
		no		(2),
		yes		(3)
	}
	MAX-ACCESS	read-create
	STATUS		current
	DESCRIPTION
	"This object indicates whether a call is enabled without registration."
	::= { radSipRegCfgEntry 10 }

radSipRegUserParams OBJECT-TYPE
	SYNTAX		SnmpAdminString
	MAX-ACCESS	read-create
	STATUS		current
	DESCRIPTION
	"This object indicates the User's parameters.
	 This object is irrelevant when radSipRegUserDefinition = localEntries(2)."
	::= { radSipRegCfgEntry 11 }

radSipRegRowStatus OBJECT-TYPE
	SYNTAX		RowStatus
	MAX-ACCESS	read-create
	STATUS		current
	DESCRIPTION
    "This object enables the user to create/delete entries in this table."
	::= { radSipRegCfgEntry 12 }


--
-- Network Routing table
--

voipNetRoutTable OBJECT-TYPE
	SYNTAX		SEQUENCE OF VoipNetRoutEntry
	MAX-ACCESS	not-accessible
	STATUS		current
	DESCRIPTION
	"Network Routing table."
	::= { voipConfig 2 }

voipNetRoutEntry OBJECT-TYPE
	SYNTAX		VoipNetRoutEntry
	MAX-ACCESS	not-accessible
	STATUS		current
	DESCRIPTION
	"A row of Network Routing table."
	INDEX { voipNetRoutCfgIdx, voipNetRoutPrefix }
	::= { voipNetRoutTable 1 }

VoipNetRoutEntry ::=
	SEQUENCE {
		voipNetRoutCfgIdx					Unsigned32,
		voipNetRoutPrefix					SnmpAdminString,
		voipNetRoutRowStatus				RowStatus,
		voipNetRoutMinDigits				Unsigned32,
		voipNetRoutMaxDigits				Unsigned32,
		voipNetRoutAddr						SnmpAdminString, -- IP/URL address
		voipNetRoutUdpPort					Unsigned32,
		voipNetRoutOutboundProxySupport		INTEGER,
		voipNetRoutOutboundProxyAddr		SnmpAdminString, -- IP/URL address
		voipNetRoutOutboundProxyUdpPort		Unsigned32
		}

voipNetRoutCfgIdx OBJECT-TYPE
	SYNTAX		Unsigned32
	MAX-ACCESS	not-accessible
	STATUS		current
	DESCRIPTION
	"The first index of the table.
	 
	 This object might represent the Configuration Index (1..100) being accessed;
	 Index=255 relates to the TmpCnfg.
	 For devices with multiple configurations, Set is permitted to TmpCnfg(255) only.
	 
	 Not-Applicable = 1."
	::= { voipNetRoutEntry 1 }

voipNetRoutPrefix OBJECT-TYPE
	SYNTAX		SnmpAdminString
	MAX-ACCESS	not-accessible
	STATUS		current
	DESCRIPTION
	"This object represents the prefix number.
	 This prefix can include non-decimal digits, such as * or #.
	 
	 The default route will be represented by an empty prefix."
	::= { voipNetRoutEntry 2 }

voipNetRoutRowStatus OBJECT-TYPE
	SYNTAX		RowStatus
	MAX-ACCESS	read-create
	STATUS		current
	DESCRIPTION
    "This object enables the user to create/delete entries in this table."
	::= { voipNetRoutEntry 3 }

voipNetRoutMinDigits OBJECT-TYPE
	SYNTAX		Unsigned32
	MAX-ACCESS	read-create
	STATUS		current
	DESCRIPTION
    "This object indicates the Minimum number of digits."
	::= { voipNetRoutEntry 4 }

voipNetRoutMaxDigits OBJECT-TYPE
	SYNTAX		Unsigned32
	MAX-ACCESS	read-create
	STATUS		current
	DESCRIPTION
    "This object indicates the Maximum number of digits."
	::= { voipNetRoutEntry 5 }

voipNetRoutAddr OBJECT-TYPE
	SYNTAX		SnmpAdminString
	MAX-ACCESS	read-create
	STATUS		current
	DESCRIPTION
    "This object indicates the route's IP/URL Address."
	::= { voipNetRoutEntry 6 }

voipNetRoutUdpPort OBJECT-TYPE
	SYNTAX		Unsigned32
	MAX-ACCESS	read-create
	STATUS		current
	DESCRIPTION
    "This object indicates the route's destination UDP port number."
	::= { voipNetRoutEntry 7 }

voipNetRoutOutboundProxySupport OBJECT-TYPE
	SYNTAX		INTEGER
	{
		notApplicable	(1),
		no				(2),
		yes				(3)
	}
	MAX-ACCESS	read-create
	STATUS		current
	DESCRIPTION
	"This object indicates whether the Outbound Proxy is supported."
	::= { voipNetRoutEntry 8 }

voipNetRoutOutboundProxyAddr OBJECT-TYPE
	SYNTAX		SnmpAdminString
	MAX-ACCESS	read-create
	STATUS		current
	DESCRIPTION
    "This object indicates the Outbound Proxy's IP/URL Address."
	::= { voipNetRoutEntry 9 }

voipNetRoutOutboundProxyUdpPort OBJECT-TYPE
	SYNTAX		Unsigned32
	MAX-ACCESS	read-create
	STATUS		current
	DESCRIPTION
    "This object indicates the Outbound Proxy UDP port number."
	::= { voipNetRoutEntry 10 }


--
-- Numbering Manipulation table
--

voipNumManipTable OBJECT-TYPE
	SYNTAX		SEQUENCE OF VoipNumManipEntry
	MAX-ACCESS	not-accessible
	STATUS		current
	DESCRIPTION
	"Numbering Manipulation table."
	::= { voipConfig 3 }

voipNumManipEntry OBJECT-TYPE
	SYNTAX		VoipNumManipEntry
	MAX-ACCESS 	not-accessible
	STATUS		current
	DESCRIPTION
	"A row of Numbering Manipulation table."
	INDEX { voipNumManipCfgIdx, voipNumManipTypeId, voipNumManipRuleIdx }
	::= { voipNumManipTable 1 }

VoipNumManipEntry ::=
	SEQUENCE {
		voipNumManipCfgIdx					Unsigned32,
		voipNumManipTypeId					Unsigned32,
		voipNumManipRuleIdx					Unsigned32,
		voipNumManipRowStatus				RowStatus,
		voipNumManipOriginalNumber			Unsigned32,
		voipNumManipNewNumber				Unsigned32
		}

voipNumManipCfgIdx OBJECT-TYPE
	SYNTAX		Unsigned32
	MAX-ACCESS 	not-accessible
	STATUS		current
	DESCRIPTION
	"The first index of the table.
	 
	 This object might represent the Configuration Index (1..100) being accessed;
	 Index=255 relates to the TmpCnfg.
	 For devices with multiple configurations, Set is permitted to TmpCnfg(255) only.
	 
	 Not-Applicable = 1."
	::= { voipNumManipEntry 1 }

voipNumManipTypeId OBJECT-TYPE
	SYNTAX		Unsigned32
	MAX-ACCESS	not-accessible
	STATUS		current
	DESCRIPTION
	"This object represents the Numbering Manipulation's Type ID.
	 Type ID represents a unique Type, which can be different for each device.	 

	 For Vmux-300 devices - 

	 Type ID	Manipulated Number		Call direction
	 --------------------------------------------------------------
	 1	=		Dialed (destination)	Incoming (Network to Local)
	 2	=		Dialed (destination)	Outgoing (Local to Network)
	 3	=		Dialing (source)		Incoming (Network to Local)
	 4	=		Dialing (source)		Outgoing (Local to Network)
	 
	 For example:
	 Type ID 1 represents a manipulation on a Dialed number
	 for a call that in its way from the Network towards the Local."
	::= { voipNumManipEntry 2 }

voipNumManipRuleIdx OBJECT-TYPE
	SYNTAX		Unsigned32
	MAX-ACCESS	not-accessible
	STATUS		current
	DESCRIPTION
	"This object represents the Rule index."
	::= { voipNumManipEntry 3 }

voipNumManipRowStatus OBJECT-TYPE
	SYNTAX		RowStatus
	MAX-ACCESS	read-create
	STATUS		current
	DESCRIPTION
    "This object enables the user to create/delete entries in this table."
	::= { voipNumManipEntry 4 }

voipNumManipOriginalNumber OBJECT-TYPE
	SYNTAX		Unsigned32
	MAX-ACCESS	read-create
	STATUS		current
	DESCRIPTION
	"This object represents the original number (before manipulation)."
	::= { voipNumManipEntry 5 }

voipNumManipNewNumber OBJECT-TYPE
	SYNTAX		Unsigned32
	MAX-ACCESS	read-create
	STATUS		current
	DESCRIPTION
	"This object represents the new number (after manipulation)."
	::= { voipNumManipEntry 6 }

--
-- Supplementary Services
--

voipService OBJECT IDENTIFIER ::= { voipConfig 4 }

voipServiceTable OBJECT-TYPE
	SYNTAX		SEQUENCE OF VoipServiceEntry
	MAX-ACCESS	not-accessible
	STATUS		current
	DESCRIPTION
	"Services table."
	::= { voipService 1 }

voipServiceEntry OBJECT-TYPE
	SYNTAX		VoipServiceEntry
	MAX-ACCESS 	not-accessible
	STATUS		current
	DESCRIPTION
	"A row of Service table."
	INDEX { voipServiceCfgIdx, voipServicePrtIdx, voipServiceType }
	::= { voipServiceTable 1 }

VoipServiceEntry ::=
	SEQUENCE {
		voipServiceCfgIdx						Unsigned32,
		voipServicePrtIdx						Unsigned32,
		voipServiceType							INTEGER,
		voipServiceSupport						INTEGER,
		voipServiceCallForwardType				INTEGER,
		voipServiceCallForwardPhoneNo			SnmpAdminString,
		voipServiceCallForwardNoReplyTimeout	Unsigned32,
		voipServiceCallerIdType					INTEGER,
		voipServiceCallerIdDisplayString		SnmpAdminString
		}

voipServiceCfgIdx OBJECT-TYPE
	SYNTAX		Unsigned32
	MAX-ACCESS 	not-accessible
	STATUS		current
	DESCRIPTION
	"The first index of the table.
	 
	 This object might represent the Configuration Index (1..100) being accessed;
	 Index=255 relates to the TmpCnfg.
	 For devices with multiple configurations, Set is permitted to TmpCnfg(255) only.
	 
	 Not-Applicable = 1."
	::= { voipServiceEntry 1 }

voipServicePrtIdx OBJECT-TYPE
	SYNTAX		Unsigned32
	MAX-ACCESS 	not-accessible
	STATUS		current
	DESCRIPTION
	"This object represents the Port Index.
	 When irrelevant, value will be 1."
	::= { voipServiceEntry 2 }

voipServiceType OBJECT-TYPE
	SYNTAX		INTEGER
	{
		callForward				(1),
		callTransfer			(2),
		callerIdRestriction		(3),
		callHold				(4)
	}
	MAX-ACCESS	not-accessible
	STATUS		current
	DESCRIPTION
	"This object represents the Service's Type."
	::= { voipServiceEntry 3 }

voipServiceSupport OBJECT-TYPE
	SYNTAX		INTEGER
	{
		notApplicable	(1),
		disable			(2),
		enable			(3)
	}
	MAX-ACCESS	read-write
	STATUS		current
	DESCRIPTION
	"This object represents the Service's support."
	::= { voipServiceEntry 4 }

voipServiceCallForwardType OBJECT-TYPE
	SYNTAX		INTEGER
	{
		noForward		(1),
		unconditional	(2),
		noReply			(3),
		busy			(4)
	}
	MAX-ACCESS	read-write
	STATUS		current
	DESCRIPTION
	"This object represents the Call Forward Type.
	 It is relevant only for voipServiceType = callForward(1)."
	::= { voipServiceEntry 5 }

voipServiceCallForwardPhoneNo OBJECT-TYPE
	SYNTAX		SnmpAdminString
	MAX-ACCESS	read-write
	STATUS		current
	DESCRIPTION
	"This object represents the Phone Number to be forwarded.
	 It is relevant only for voipServiceType = callForward(1)."
	::= { voipServiceEntry 6 }

voipServiceCallForwardNoReplyTimeout OBJECT-TYPE
	SYNTAX		Unsigned32
	MAX-ACCESS	read-write
	STATUS		current
	DESCRIPTION
	"This object indicates the No Reply Timeout in seconds.
	 It means how many seconds with no reply should pass
	 so that this period of time will be considered as No Reply.
	 It is relevant only for voipServiceType = callForward(1)."
	::= { voipServiceEntry 7 }

voipServiceCallerIdType OBJECT-TYPE
	SYNTAX		INTEGER
	{
		noRestriction		(1),
		restrictAllCalls	(2),
		restrictNextCall	(3)
	}
	MAX-ACCESS	read-write
	STATUS		current
	DESCRIPTION
	"This object represents the Caller ID Type.
	 It is relevant only for voipServiceType = callerIdRestriction(3)."
	::= { voipServiceEntry 8 }

voipServiceCallerIdDisplayString OBJECT-TYPE
	SYNTAX		SnmpAdminString
	MAX-ACCESS	read-write
	STATUS		current
	DESCRIPTION
	"This object represents the string that should be displayed
	 when no restriction is applied.
	 It is relevant only for voipServiceType = callerIdRestriction(3)."
	::= { voipServiceEntry 9 }


voipFeatureTable OBJECT-TYPE
	SYNTAX		SEQUENCE OF VoipFeatureEntry
	MAX-ACCESS	not-accessible
	STATUS		current
	DESCRIPTION
	"Feature table."
	::= { voipService 2 }

voipFeatureEntry OBJECT-TYPE
	SYNTAX		VoipFeatureEntry
	MAX-ACCESS 	not-accessible
	STATUS		current
	DESCRIPTION
	"A row of Feature table."
	INDEX { voipFeatureCfgIdx, voipFeaturePrtIdx, voipFeatureType }
	::= { voipFeatureTable 1 }

VoipFeatureEntry ::=
	SEQUENCE {
		voipFeatureCfgIdx			Unsigned32,
		voipFeaturePrtIdx			Unsigned32,
		voipFeatureType				INTEGER,
		voipFeatureKeypadString		SnmpAdminString
		}

voipFeatureCfgIdx OBJECT-TYPE
	SYNTAX		Unsigned32
	MAX-ACCESS 	not-accessible
	STATUS		current
	DESCRIPTION
	"The first index of the table.
	 
	 This object might represent the Configuration Index (1..100) being accessed;
	 Index=255 relates to the TmpCnfg.
	 For devices with multiple configurations, Set is permitted to TmpCnfg(255) only.
	 
	 Not-Applicable = 1."
	::= { voipFeatureEntry 1 }

voipFeaturePrtIdx OBJECT-TYPE
	SYNTAX		Unsigned32
	MAX-ACCESS 	not-accessible
	STATUS		current
	DESCRIPTION
	"This object represents the Port Index.
	 When irrelevant, value will be 1."
	::= { voipFeatureEntry 2 }

voipFeatureType OBJECT-TYPE
	SYNTAX		INTEGER
	{
		callForwardUnconditional		(1),
		callForwardNoReply				(2),
		callForwardBusy					(3),
		callForwardDeactivation			(4),
		callTransfer					(5),
		callerIdRestrictNextCall		(6),
		callerIdRestrictAllCalls		(7),
		callerIdRestrictDeactivation	(8)
	}
	MAX-ACCESS	not-accessible
	STATUS		current
	DESCRIPTION
	"This object represents the Feature's Type."
	::= { voipFeatureEntry 3 }

voipFeatureKeypadString OBJECT-TYPE
	SYNTAX		SnmpAdminString
	MAX-ACCESS	read-write
	STATUS		current
	DESCRIPTION
	"This object represents the Feature's Keypad string.
	 This string is a combination of digits, * and #."
	::= { voipFeatureEntry 4 }


--
-- NAT Traversal
--

voipNatTraversal OBJECT IDENTIFIER ::= { voipConfig 5 }

voipNatTravIpAddress OBJECT-TYPE
	SYNTAX		IpAddress
	MAX-ACCESS	read-write
	STATUS		current
	DESCRIPTION
    "This object indicates the NAT IP Address, given to the device (e.g. Vmux)
     It is used only in case of static NAT."
	::= { voipNatTraversal 1 }

voipNatTravStun OBJECT IDENTIFIER ::= { voipNatTraversal 2 } -- STUN = Simple Traversal of UDP through NATs

voipNatTravStunServerAddress OBJECT-TYPE
	SYNTAX		SnmpAdminString
	MAX-ACCESS	read-write
	STATUS		current
	DESCRIPTION
    "This object indicates the STUN Server's IP/URL Address."
	::= { voipNatTravStun 1 }

voipNatTravStunBaseUdpPort OBJECT-TYPE
	SYNTAX		Unsigned32
	MAX-ACCESS	read-write
	STATUS		current
	DESCRIPTION
    "This object indicates the STUN Base UDP Port number."
	::= { voipNatTravStun 2 }

voipNatTravStunSipInterval OBJECT-TYPE
	SYNTAX		Unsigned32
	MAX-ACCESS	read-write
	STATUS		current
	DESCRIPTION
    "This object indicates the STUN Keep-Alive time interval (in seconds),
     for maintaining the SIP signaling port and IP address."
	::= { voipNatTravStun 3 }

voipNatTravStunRtpInterval OBJECT-TYPE
	SYNTAX		Unsigned32
	MAX-ACCESS	read-write
	STATUS		current
	DESCRIPTION
    "This object indicates the STUN Keep-Alive time interval (in seconds),
     for maintaining the RTP stream ports and IP addresses."
	::= { voipNatTravStun 4 }
-- 
-- file :D:\Synergy\WorkArea\545\mib_rad\txt\ipmux.txt
-- 
-- File:	Ipmux.txt


ip2If OBJECT IDENTIFIER ::= { diverseIfWanGen 7 }

-- ip2If Configuration table  

ip2IfTable OBJECT-TYPE
       SYNTAX  SEQUENCE OF Ip2IfEntry
       MAX-ACCESS  not-accessible
       STATUS  current
       DESCRIPTION
       "Channels Configuration Table."
       ::= { ip2If 1 }
  
ip2IfEntry OBJECT-TYPE
       SYNTAX Ip2IfEntry
       MAX-ACCESS not-accessible
       STATUS current
       DESCRIPTION
          "Application layer configuration per link"
       INDEX   { ip2IfChannelIndex }
       ::= { ip2IfTable 1 }

Ip2IfEntry ::=
         SEQUENCE {
         ip2IfChannelIndex	    Integer32,
         ip2IfRowStatus	        RowStatus,
         ip2IfOperStatus	    INTEGER,
         ip2IfAdminStatus	    INTEGER,
         ip2IfDestAddr		    IpAddress,
         ip2IfNextHop		    IpAddress,
         ip2IfDestPort		    Integer32,
         ip2IfMacAddr		    MacAddress,
         ip2IfJitterBuffer	    Integer32,
		 ip2IfTos			    Integer32,
		 ip2IfTDMBytesInFrame   Integer32,
		 ip2IfVlanSupport       INTEGER,
		 ip2IfVlanIdentifier    Integer32,
		 ip2IfVlanFramePriority Integer32,
		 ip2IfExitPort          INTEGER,
		 ip2IfVoiceOos			OCTET STRING,
		 ip2IfDataOos			OCTET STRING,
		 ip2IfBundleUsage 		Integer32,
		 ip2IfOAM				OCTET STRING,
		 ip2IfTDMoIpMode		INTEGER,
		 ip2IfTimeElapsed		Integer32,
		 ip2IfValidIntervals    Integer32,
		 ip2IfFarEndType        INTEGER,
		 ip2IfRdnState			INTEGER,
		 ip2IfSourceAddr		IpAddress,
		 ip2IfBandWidth 		Integer32,
		 ip2IfMeasuredSilence   Integer32,
		 ip2IfPayloadType		INTEGER,
		 ip2IfProtocolVersion	INTEGER,
         ip2IfTdmBackUpNextHop  IpAddress,	
		 ip2IfOosTxEnable		INTEGER,		 
		 ip2IfConnCheckPktFrequency Integer32,
         ip2IfConnPktTimeOutCycles  Integer32,
		 ip2IfMfRelay			    INTEGER,
		 ip2IfTxGain			    Integer32,
		 ip2IfSuperTandem			INTEGER,
		 ip2IfSrcPort				Integer32,
     	 ip2IfModemCalls            INTEGER,
         ip2IfMinPulseWidth         Integer32,
		 ip2IfMinPowerLevel         Integer32,
		 ip2IfEchoCanceler          INTEGER,
		 ip2IfCodingLaw             INTEGER,
		 ip2IfCustomToneDetect      INTEGER,
		 ip2IfCallerIdDelay	        Integer32,
		 ip2IfConnectivityMode      INTEGER,
		 ip2IfClockSourceEnable		INTEGER,
		 ip2IfNetworkType			INTEGER,
		 ip2IfMplsRxLabelEnable		INTEGER,
		 ip2IfMplsRxLabel			Integer32,
		 ip2IfMplsTxLabelEnable		INTEGER,
		 ip2IfMplsTxLabel			Integer32,
		 ip2IfMplsTxExpBits			Integer32,
		 ip2IfMfcSpoofing           INTEGER,
		 ip2IfToneAckInterval       Integer32,
		 ip2IfNextHopType 			INTEGER,
 		 ip2IfNoiseLevelForVAD      INTEGER,
		 ip2IfClockPreferences		INTEGER,
		 ip2IfConnectionMode		INTEGER,
		 ip2IfRingBack              INTEGER,
		 ip2IfReversePolarity       INTEGER,
		 ip2IfPulseMeter            INTEGER,
		 ip2IfPulseMeterFreq        INTEGER,
		 ip2IfPulseMeterPeriod      Integer32,
		 ip2IfOnHookDetect          INTEGER,
		 ip2IfComfortNoiseGen       INTEGER,
		 ip2IfExitChannel			Integer32,
		 ip2IfMaxVBDModemCalls		Integer32,
		 ip2IfMaxRelayModemCalls	Integer32,
		 ip2IfCustomToneFrequency	INTEGER,
		 ip2IfVadMethod             INTEGER,
		 ip2IfRxGain                Integer32,
		 ip2IfCallerIDType          INTEGER,
		 ip2IfPeerAddrType 			INTEGER,		 
		 ip2IfVbdRate               INTEGER,
		 ip2IfDtmfDetection         INTEGER,
		 ip2IfNlpCutoffLevel        Unsigned32,
		 ip2IfDtdErlRatioCutoffQ3   Unsigned32,
		 ip2IfCASRedundancy         INTEGER,
		 ip2IfBundleSensitivity     INTEGER,
		 ip2IfOAMBundleIdent        INTEGER,
		 ip2IfMaxTxQueue			Unsigned32,
		 ip2IfMaxGprsTxQueue		Unsigned32,
		 ip2IfV23HD                 INTEGER,
		 ip2IfModemProtocolMode		OCTET STRING,
		 ip2IfCdisCngDetectionTime  Unsigned32,
		 ip2IfSuperTandemBitMask	OCTET STRING,
		 ip2IfVbdSwitchbackTime     Unsigned32,
		 ip2IfCallerIdTxGain		Integer32,
		 ip2IfCallerIdRxGain		Integer32,
		 ip2IfUdpMuxMethod			INTEGER,
		 ip2IfCallerIdDetection		INTEGER,
		 ip2IfWap					INTEGER,
		 ip2IfSignalingOos          INTEGER
	}
  
ip2IfChannelIndex OBJECT-TYPE
    SYNTAX  Integer32 
    MAX-ACCESS  read-only
    STATUS  current
    DESCRIPTION
    "The channel index, which is actualy the bundle ID."
    ::= { ip2IfEntry 1 }

ip2IfRowStatus OBJECT-TYPE
    SYNTAX  RowStatus
    MAX-ACCESS  read-create
    STATUS  current
    DESCRIPTION
    "This parameter allows NMS to create/delete entries of this table."
    ::= { ip2IfEntry 2 }


ip2IfOperStatus OBJECT-TYPE
    SYNTAX       INTEGER {
    down		(2),
    up	        (3),
    disabled    (4),
    remoteFail  (5),
    localFail	(6),
	unavailable (7),
	validationFail  (8),
	standby		(9),
	tdmFail	   (10),
	hwMismatch (11)
    }
    MAX-ACCESS    read-only
    STATUS        current
    DESCRIPTION
    "The actual link status.
    remoteFail - No Rx.
    localFail  - No Tx.
    unavailable - No echo replay or replay with invalid code or when connection is in Test state.
    valiodationFail - Connection is in not valid state.
    standby - offline (can be in pre-sync mode).
    tdmFail - oper status is down cause of failure in the tdm.
    hwMismatch - the bundle exists on a card that is not installed or has a different
                 type than the programmed card."
    ::= { ip2IfEntry 3 }

ip2IfAdminStatus OBJECT-TYPE
    SYNTAX       INTEGER {
    down		(2),
    up	    (3)
    }
    MAX-ACCESS    read-create
    STATUS        current
    DESCRIPTION
    "The desired state of the link."
    ::= { ip2IfEntry 4 }

ip2IfDestAddr OBJECT-TYPE
    SYNTAX  IpAddress 
    MAX-ACCESS  read-create
    STATUS  current
    DESCRIPTION
    "The destination IP address."
    ::= { ip2IfEntry 5 }

ip2IfNextHop OBJECT-TYPE
    SYNTAX  IpAddress 
    MAX-ACCESS  read-create
    STATUS  current
    DESCRIPTION
    "The next hop to which the frame should be sent.
     Default value - 0.0.0.0. 
     Upon setting the default value the frame is sent 
     to the default Gateway."
    ::= { ip2IfEntry 6 }

ip2IfDestPort OBJECT-TYPE
    SYNTAX  Integer32 
    MAX-ACCESS  read-create
    STATUS  current
    DESCRIPTION
    "The destination Bundle at the far-end device."
    ::= { ip2IfEntry 7 }
  
ip2IfMacAddr OBJECT-TYPE
    SYNTAX  MacAddress
    MAX-ACCESS  read-create
    STATUS  current
    DESCRIPTION
    "The Destination MAC address of the next hop or 
     destination station."
    ::= { ip2IfEntry 8 }

ip2IfJitterBuffer OBJECT-TYPE
    SYNTAX  Integer32 
    MAX-ACCESS  read-create
    STATUS  current
    DESCRIPTION
    "The maximum cell arrival jitter in 10 usec that the 
     reassembly process will tolerate in the cell stream, 
     without producing errors on the CBR service interface.
          
     For KM2100:
     KML.11 - The range that will be used is 3...300 msec
     in steps of 1 msec.
     
     For Vmux:
     The range that will be used is 20...100 msec
     in steps of 10 msec."
    ::= { ip2IfEntry 9 }

ip2IfTos OBJECT-TYPE
    SYNTAX  Integer32 
    MAX-ACCESS  read-create
    STATUS  current
    DESCRIPTION
    "The TOS (Type of Service) value: 0..255.

     In Vmux-2100/110 devices versions 3.1 and up, in Vmux-210 and in Vmux-4x0:
     LSB   8 bits - 00 00 00 XX will be used for Signaling packets TOS.                    
     Next  8 bits - 00 00 XX 00 will be used for Media packets TOS.
	 Next 16 bits - will be 0.
				    XX = Hex values: 0..FF
     For mixed packets, TOS of Media Packets will be used.
     Signaling packets are for example: Keep alive packets and ABCD signaling bits.
     Media packets are for example: voice, fax, HDLC, payload packets."
    ::= { ip2IfEntry 10 }

ip2IfTDMBytesInFrame OBJECT-TYPE
    SYNTAX  Integer32 
    MAX-ACCESS  read-create
    STATUS  current
    DESCRIPTION
    "The number of TDM bytes to be placed in a single IP 
     frame payload.
     For ip2IfTDMoIpMode = cesOverPsn this parameter indicates
     the number of IP frames, calculated as: 1440/<Number of Timeslots>."
    ::= { ip2IfEntry 11 }

ip2IfVlanSupport OBJECT-TYPE
    SYNTAX       INTEGER {
    no		(2),
    yes	    (3)
    }
    MAX-ACCESS  read-create
    STATUS  current
    DESCRIPTION
    "VLAN support (Tagging).
     no - No support to VLAN.
     yes - 4 VLAN bytes will be added to the frame."
    ::= { ip2IfEntry 12}

ip2IfVlanIdentifier OBJECT-TYPE
     SYNTAX  Integer32 
     MAX-ACCESS  read-create
     STATUS  current
     DESCRIPTION
     "VLAN ID."
     ::= { ip2IfEntry 13 }
  
ip2IfVlanFramePriority OBJECT-TYPE
     SYNTAX  Integer32 
     MAX-ACCESS  read-create
     STATUS  current
     DESCRIPTION
     "VLAN Frame priority."
     ::= { ip2IfEntry 14 }

ip2IfExitPort  OBJECT-TYPE
     SYNTAX  INTEGER
      {
       notApplicable (1),
       ext1          (2), -- Vmux 2100 slot 1 port 1  or Gmux2000 GbE Slot 6, Port 1
       ext2          (3), -- Vmux 2100 slot 1 port 2  or Gmux2000 GbE Slot 6, Port 2
       auto          (4),
	   card2Ext1	 (5), -- Vmux 2100 slot 2 port 1 or Gmux2000 GbE Slot 8, Port 1
	   card2Ext2	 (6), -- Vmux 2100 slot 2 port 2 or Gmux2000 GbE Slot 6, Port 2
       ext5          (7), -- Vmux-110/210/2100 ETH-NET
       ext7          (8), -- Vmux-110/210 Serial Link
       ext6 		 (9), -- Vmux-110/210 E1/T1 Link, Vmux-2100 E1/T1 Link A   
	   prt17		(10), -- GMUX VMX/Vmux 2100 slot 1 port 3
	   prt18		(11), -- GMUX VMX/Vmux 2100 slot 1 port 4
	   prt19	    (12), -- GMUX VMX/Vmux 2100 slot 2 port 3
	   prt20        (13), -- GMUX VMX/Vmux 2100 slot 2 port 4
	   prtE1T1B     (14), -- Vmux 2100 E1/T1 Link B
       prtEthUser   (15), -- Vmux 2100/110/210 ETH-User
	   card3Ext1    (16), -- Vmux-2100 Slot 3 port 1
       card3Ext2    (17), -- Vmux-2100 Slot 3 port 2 
       card3Ext3    (18), -- Vmux-2100 Slot 3 port 3
       card3Ext4    (19), -- Vmux-2100 Slot 3 port 4
       card4Ext1    (20), -- Vmux-2100 Slot 4 port 1
       card4Ext2    (21), -- Vmux-2100 Slot 4 port 2
       card4Ext3    (22), -- Vmux-2100 Slot 4 port 3
       card4Ext4    (23), -- Vmux-2100 Slot 4 port 4
	   card1Ext3	(24), -- Gmux2000 GbE/8 Slot 6, Port 3
	   card1Ext4	(25), -- Gmux2000 GbE/8 Slot 6, Port 4
	   card1Ext5	(26), -- Gmux2000 GbE/8 Slot 6, Port 5
	   card1Ext6	(27), -- Gmux2000 GbE/8 Slot 6, Port 6
	   card1Ext7	(28), -- Gmux2000 GbE/8 Slot 6, Port 7
	   card1Ext8	(29), -- Gmux2000 GbE/8 Slot 6, Port 8
	   card2Ext3	(30), -- Gmux2000 GbE/8 Slot 8, Port 3
	   card2Ext4	(31), -- Gmux2000 GbE/8 Slot 8, Port 4
	   card2Ext5	(32), -- Gmux2000 GbE/8 Slot 8, Port 5
	   card2Ext6	(33), -- Gmux2000 GbE/8 Slot 8, Port 6
	   card2Ext7	(34), -- Gmux2000 GbE/8 Slot 8, Port 7
	   card2Ext8	(35)  -- Gmux2000 GbE/8 Slot 8, Port 8
     }
     MAX-ACCESS  read-create
     STATUS  current
     DESCRIPTION
     "This object determines to which external port the traffic
      will be sent.
      auto - the device will decide automatically the exit port.
      If there is an option for Tx via more than one ETH card then use ext1 (1) and ext2(2) 
      for ETH card #1 (ex. LAN1 or Ggabit-ETH1) and use card2Ext1(5) and card2Ext2(6) for 
      card #2 (ex. LAN1 or Ggabit-ETH1).
      In Vmux-110/210 ext5 is used for ETH-NET, ext 6 is used for E1/T1 link and ext7 is 
      used for Serial Link.
      In Vmux-2100 Main Board: ext 5 is used for ETH-NET, ext 6 is used for E1/T1 link A, 
      prtE1T1B is used for E1/T1 link B and prtEthUser is used for ETH-User.       
      prt17(10) - prt20(13) values were added in order to support Gmux2000 VMX Card."
      ::= { ip2IfEntry 15 }

ip2IfVoiceOos  OBJECT-TYPE
     SYNTAX  OCTET STRING 
     MAX-ACCESS  read-create
     STATUS  current
     DESCRIPTION
     "Voice Out-Of-Service code. Valid range: (0 - FF HEX).
      For agents that do not support this feature, the value will 
      always be 0."
     ::= { ip2IfEntry 16 }

ip2IfDataOos  OBJECT-TYPE
     SYNTAX  OCTET STRING 
     MAX-ACCESS  read-create
     STATUS  current
     DESCRIPTION
     "Data Out-Of-Service code. Valid range: (0 - FF HEX).
      For agents that do not support this feature, the value will
      always be 0."
     ::= { ip2IfEntry 17 }

ip2IfBundleUsage OBJECT-TYPE
    SYNTAX  Integer32 
    MAX-ACCESS  read-only
    STATUS  current
    DESCRIPTION
    "The Bundle Resource usage in Kbps."
    ::= { ip2IfEntry 18 }

ip2IfOAM  OBJECT-TYPE
     SYNTAX  OCTET STRING 
     MAX-ACCESS  read-create
     STATUS  current
     DESCRIPTION
     "This parameter determine the OAM configuration.
      The LSB (Bit 0 the most right one) is used for OAM connectivity. 
      Values: 0 = disable, 1= enable."
    ::= { ip2IfEntry 19 }

ip2IfTDMoIpMode OBJECT-TYPE
    SYNTAX  INTEGER {
    notApplicable     (1),
    static		      (2),
	dynamicLES        (3),
	dynamicCAS        (4),
	cesOverIp	      (5),
	voiceOverMpls     (6),
	hdlc		      (7),
	voIpComprHeader   (8),
	voMplsComprHeader (9),
	satop             (10),
	cesOverPsn        (11),
	hdlcOverPsn       (12)
    }
    MAX-ACCESS    read-create
    STATUS        current
    DESCRIPTION
    "The TDMoIP Mode configuration. Static- means TS can Tx any time.
     dynamicLES - means TS can Tx only when line is enabled according to LES protocol.
     dynamicCAS - means TS can Tx only when line is enabled according to CAS protocol.
     cesOverIp - use for information that this bundle is used for CES Over IP.
     voiceOverMpls - Voice over Multi Protocol Label Switching.
	 hdlc - High Level Data Link.
	 voIpComprHeader - indicates proprietary compressed IP header packets.
	 voMplsComprHeader - indicates proprietary compressed MPLS header packets."
    ::= { ip2IfEntry 20 }


ip2IfTimeElapsed OBJECT-TYPE
     SYNTAX  Integer32 (0..899)
     MAX-ACCESS  read-only
     STATUS  current
     DESCRIPTION
     "The number of seconds that have elapsed since
      the beginning of the  current error-measurement period.
      If, for some reason, such as an adjustment in the 
      system's time-of-day clock, the current interval exceeds
      the maximum	value, the agent will return the maximum value."
     ::= {ip2IfEntry 21 }

ip2IfValidIntervals OBJECT-TYPE
     SYNTAX  Integer32 (0..96)
     MAX-ACCESS  read-only
     STATUS  current
     DESCRIPTION
     "The number of previous intervals for which data was collected.  
      The value will be	96 unless the interface was brought online within
      the last 24 hours, in which case the value will be
      the number of complete 15 minute intervals since the
      interface has been online. "
     ::= {ip2IfEntry 22 }

ip2IfFarEndType  OBJECT-TYPE
     SYNTAX  INTEGER
      {
       notApplicable (1),
       e1            (2),
       t1Esf         (3),
       t1D4          (4),
       fxs           (5),
	   serialLink 	 (6),
	   t1Unframed	 (7)
      }
     MAX-ACCESS  read-create
     STATUS  current
     DESCRIPTION
     "This object defines the type of the Far-End device.
      This data is important for signaling and DS0 format.
      
      For Vmux: e1  (2) value is used for a PBX in the Far End.
                fxs (5) is used for Phone.
                Other values are not used. "
     ::= { ip2IfEntry 23 }

ip2IfRdnState  OBJECT-TYPE
     SYNTAX  INTEGER
      {
       notApplicable (1),
       none          (2),
       primary       (3),
       secondary     (4)
      }
     MAX-ACCESS  read-only
     STATUS  current
     DESCRIPTION
     "This object defines the role this bundle plays in the redundancy scheme:
     none(2) - means this bundle is not part of redundancy pair.
     primary/ secondary - means this bundle is not part of redundancy pair,
     and that is the primary bundle or the secondary bunle. "
     ::= { ip2IfEntry 24 }

ip2IfSourceAddr OBJECT-TYPE
     SYNTAX  IpAddress 
     MAX-ACCESS  read-create
     STATUS  current
     DESCRIPTION
     "Source IP Address of the bundle."     	  
	  ::= {ip2IfEntry 25 }

ip2IfBandWidth OBJECT-TYPE
    SYNTAX  Integer32 
    MAX-ACCESS  read-create
    STATUS  current
    DESCRIPTION
    "Defines the Bandwidth of the bundle.

     For TDM bundles - it is the Number of Time Slots  in The Bundle.
     - For T1 the value will be: 1..24
     - For E1 the value will be: 1..31
     - For T3 the value will be: 1..84
     - For E3 the value will be: 1..63
     
     This parameter is required for devices like Emux where the bandwidth of
     the bundles is unknown. The bundles that are received should be transmitted
     without any change in the bandwidth. It is the user's responsibility to
     enter the correct bandwidth.
     
     For Ethernet bundles - it is the bandwidth, measured in Kbps."
     ::= {ip2IfEntry 26 }

ip2IfMeasuredSilence  OBJECT-TYPE
     SYNTAX  Integer32     
     MAX-ACCESS  read-only
     STATUS  current
     DESCRIPTION
     "This object shows the percentage of Silence that was measured by the device
      for the current bundle in the transmitted payload.
      Relevant values: 0..100, 255.
      Default value is 50.
      0 means that there is no silence on the line.
      100 means that there is only silence. In this case, there might be no traffic.
      255 - value for not applicable or unknown."      
     ::= { ip2IfEntry 27 }

ip2IfPayloadType  OBJECT-TYPE
     SYNTAX  INTEGER
      {
       notApplicable (1),
       data          (2),
       voice         (3),
       voiceAndCas   (4)
      }
     MAX-ACCESS  read-create
     STATUS  current
     DESCRIPTION
     "This object defines the TDMoIP payload type."
     ::= { ip2IfEntry 28 }

ip2IfProtocolVersion  OBJECT-TYPE
     SYNTAX  INTEGER
      {
       notApplicable (1),
       v1   (2),
       v2   (3)  
      }
     MAX-ACCESS  read-create
     STATUS  current
     DESCRIPTION
     "This object defines the TDMoIP protocol Version."
     ::= { ip2IfEntry 29 }

ip2IfTdmBackUpNextHop OBJECT-TYPE
    SYNTAX  IpAddress 
    MAX-ACCESS  read-create
    STATUS  current
    DESCRIPTION
    "Defines the TDM bundle default router in case there was a switch from the Primary Link
     (for example an ETH port) to a TDM backup Link like E1, T1 or Serial Link.
     This parameter is relevant only when a Backup Link is configured.
     When a Backup Link is not configured the value will be: 0.0.0.0"
    ::= { ip2IfEntry 30 }

ip2IfOosTxEnable  OBJECT-TYPE
     SYNTAX  INTEGER
      {
       notApplicable 	(1),
       disable  		(2),
       enable    		(3)
             }
     MAX-ACCESS  read-create
     STATUS  current
     DESCRIPTION
     "This object defines whether OOS will be Transmitted.
	 Note that for IPmux1000 the Lbit is always sent, 
	 but the OOS will be sent according to user selection in this parameter."
     ::= { ip2IfEntry 31 }

ip2IfConnCheckPktFrequency   OBJECT-TYPE
     SYNTAX  Integer32     
     MAX-ACCESS  read-create
     STATUS  current
     DESCRIPTION
     "Time in sec. between 2 Bundle Connectivity Check packets.
      Valid values: 0..60. 0 = Not Applicable."      
      ::= { ip2IfEntry 32 }

ip2IfConnPktTimeOutCycles      OBJECT-TYPE
     SYNTAX  Integer32     
     MAX-ACCESS  read-create
     STATUS  current
     DESCRIPTION
    "No. of cycles the agent will send Bundle Connectivity packets without receiving
     a response from the remote device before declaring that the bundle connection
     to the remote side is down - Time Out.
     Valid values: 0..5. 0 = Not Applicable."    
     ::= { ip2IfEntry 33 }

ip2IfMfRelay                  OBJECT-TYPE
     SYNTAX  INTEGER
      {
       notApplicable (1),
       disable       (2),
       enable        (3)
      }
     MAX-ACCESS  read-create
     STATUS  current
     DESCRIPTION
    "Multi Frequency Signaling Detection."    
     ::= { ip2IfEntry 34 }

ip2IfTxGain                  OBJECT-TYPE
     SYNTAX  Integer32
     MAX-ACCESS  read-create
     STATUS  current
     DESCRIPTION
    "Transmit gain in dBm."    
     ::= { ip2IfEntry 35 }

ip2IfSuperTandem             OBJECT-TYPE
     SYNTAX  INTEGER
      {
       notApplicable (1),
       disable       (2),
       enable        (3)
      }
     MAX-ACCESS  read-create
     STATUS  current
     DESCRIPTION
    "The Super Tandem feature provides end to end compression over multiple hops,
     solving the double compression problem detected in Voice compressing systems.
     The Super Tandem allows transmission of compressed voice between a few
     Vmux 2100 hubs, and eliminates the need to decompress an recompress it over
     each voice card and PBX, thus improving voice quality and reducing delay."    
     ::= { ip2IfEntry 36 }

ip2IfSrcPort OBJECT-TYPE
    SYNTAX  Integer32 
    MAX-ACCESS  read-create
    STATUS  current
    DESCRIPTION
    "The source Bundle at the local device, 
    this parameter used for cases where there is no match 
    between ip2IfChannelIndex and the Source Bundle ID."
    ::= { ip2IfEntry 37 }

   ip2IfModemCalls             OBJECT-TYPE
     SYNTAX  INTEGER
      {
       disable       (2),
       enable        (3),
	   relay         (4)
      }
     MAX-ACCESS  read-create
     STATUS  current
     DESCRIPTION
     "This MIB object shows whether Modem Calls are enabled via the bundle.
      relay option (3) means that the bundle will send to the network only
      modulated data."
     ::= { ip2IfEntry 38 }
 					 
   ip2IfMinPulseWidth  OBJECT-TYPE
      SYNTAX  Integer32                   
      MAX-ACCESS  read-create
      STATUS  current
      DESCRIPTION
      "Indicates the minimum width in milliseconds of the MF (Multi Frequency)
       tone transmitted by the switch.
       Valid values: 45-300 msec.
       notApplicable=0."
       ::= { ip2IfEntry 39 } 

   ip2IfMinPowerLevel  OBJECT-TYPE
      SYNTAX  Integer32                   
      MAX-ACCESS  read-create
      STATUS  current
      DESCRIPTION
       "Indicates the minimum power level in dBm of the MF (Multi Frequency)
        tone transmitted by the switch.
        Valid values: -1...-35 dBm."
        ::= { ip2IfEntry 40 }

ip2IfEchoCanceler             OBJECT-TYPE
     SYNTAX  INTEGER
        {
          off    (2),
          on     (3)
       }
      MAX-ACCESS  read-create
      STATUS  current
      DESCRIPTION
      "Echo canceler activation."
     ::= { ip2IfEntry 41 }

ip2IfCodingLaw OBJECT-TYPE
      SYNTAX  INTEGER
       {
          aLAW    (1),
          uLAW    (2)
       }
      MAX-ACCESS  read-create
      STATUS  current
      DESCRIPTION
      "This attribute indicates the Method/Law for decoding/encoding the voice
       information.
       aLaw(1) is the standard Law for E1 links.
       uLaw(2) is the standard Law for T1 links."
       ::= { ip2IfEntry 42 }
  
ip2IfCustomToneDetect             OBJECT-TYPE
     SYNTAX  INTEGER
      {
       disable       (2),
       enable        (3)
      }
     MAX-ACCESS  read-create
     STATUS  current
     DESCRIPTION
     "Custom Tone Detection (COT) is a Control operation of a 2Khz tone detector.
	  This tone is sent between PBX devices in order to check that the line status
	  is OK. When the COT is enabled the device will not compress/decompress the tone.
	  In this case, if the tone is initiated by the local PBX, the Device runs
	  a 2Khz detector tone and once detected by the Remote Device, if the COT is enabled
	  in the Remote Device, the Remote Device will generate a 2khz tone to the remote PBX."
	  ::= { ip2IfEntry 43 }

 ip2IfCallerIdDelay      OBJECT-TYPE
     SYNTAX  Integer32
     MAX-ACCESS  read-create
     STATUS  current
     DESCRIPTION
     "Time in msec between CLID (Caller ID) signal detection on the line and CLID
      signal transmission. The CLID must be sent between ringing signals and the value
      of the delay is used for synchronizing the CLID transmission with the ringing
      signals transmission.
      
      Valid values: 0 - 3000 msec."
	  ::= { ip2IfEntry 44 }

 ip2IfConnectivityMode    OBJECT-TYPE
     SYNTAX  INTEGER
      {
       ping       (2),
       oam        (3)
       }
     MAX-ACCESS  read-create
     STATUS  current
     DESCRIPTION
     "This MIB object shows whether to send Pings or OAM frames over the bundle."
      ::= { ip2IfEntry 45 }

ip2IfClockSourceEnable    OBJECT-TYPE
     SYNTAX  INTEGER
      {
       notApplicable 	(1),
       disable  		(2),
       enable    		(3)
       }
     MAX-ACCESS  read-create
     STATUS  current
     DESCRIPTION
     "This MIB object defines whether this bundle can be a clock source."
      ::= { ip2IfEntry 46 }

ip2IfNetworkType   OBJECT-TYPE
      SYNTAX   INTEGER
    {
     notApplicable 	(1),
     ip  			(2),
     mplsEth    	(3),
	 mac			(4),
	 ipComprHeader   (5),
	 mplsComprHeader (6),
	 udp			 (7)
     }
   MAX-ACCESS  read-create
   STATUS  current
   DESCRIPTION
   "This MIB object defines the network over which the 
   Bundle PSN (Packet Switching Network)is transported.
   In Gmux2000:
   ipComprHeader indicates proprietary compressed IP header packets.
   mplsComprHeader indicates proprietary compressed MPLS header packets." 
       ::= { ip2IfEntry 47}

ip2IfMplsRxLabelEnable   OBJECT-TYPE
      SYNTAX   INTEGER
    {
     notApplicable 	(1),
     disable  		(2),
     enable    		(3)
     }
   MAX-ACCESS  read-create
   STATUS  current
   DESCRIPTION
   "This MIB object defines whether there is user defined 
    inner (Rx.) label for this Bundle."
       ::= { ip2IfEntry 48}

ip2IfMplsRxLabel 	  OBJECT-TYPE
   SYNTAX         Integer32
   MAX-ACCESS     read-create
   STATUS         current
   DESCRIPTION
    "This MIB object defines the MPLS Rx. Label for this Bundle."
    ::= { ip2IfEntry 49}

ip2IfMplsTxLabelEnable   OBJECT-TYPE
      SYNTAX   INTEGER
    {
     notApplicable 	(1),
     disable  		(2),
     enable    		(3)
     }
   MAX-ACCESS  read-create
   STATUS  current
   DESCRIPTION
   "This MIB object defines whether there is user defined 
    outer (Tx.) label for this Bundle."
       ::= { ip2IfEntry 50}

ip2IfMplsTxLabel 	  OBJECT-TYPE
   SYNTAX         Integer32
   MAX-ACCESS     read-create
   STATUS         current
   DESCRIPTION
    "This MIB object defines the MPLS Tx. Label for this Bundle."
    ::= { ip2IfEntry 51}

ip2IfMplsTxExpBits	  OBJECT-TYPE
   SYNTAX         Integer32	 (0..7)
   MAX-ACCESS     read-create
   STATUS         current
   DESCRIPTION
    "The MPLS Network priority (EXP bits) used for this bundle."
    ::= { ip2IfEntry 52}

ip2IfMfcSpoofing		 OBJECT-TYPE
      SYNTAX   INTEGER
    {
     notApplicable 	(1),
     disable  		(2),
     enable    		(3)
     }
   MAX-ACCESS  read-create
   STATUS  current
   DESCRIPTION
   "This MIB object defines whether the MFC (Multi Frequency Compelled) protocol
    spoofing will exist in the bundle. When the MFC Spoofing is used, the Local
    and Remote PBXs will send MFC Signaling to each other. The Vmuxes between
    the PBXs will send proprietary signaling to each other. They will however
    create and send MFC tones to their local PBX. The PBXs will not know that
    the actual signaling was not sent from a PBX but from a Vmux."
    ::= { ip2IfEntry 53}

ip2IfToneAckInterval  OBJECT-TYPE
   SYNTAX         Integer32 
   MAX-ACCESS     read-create
   STATUS         current
   DESCRIPTION
   "Time Interval in milli seconds from the time a Vmux sends tone/s to a local PBX until
    it receives an acknowledgement from this PBX.
    Valid values: 60...400 in steps of 20."
    ::= { ip2IfEntry 54}

ip2IfNextHopType   OBJECT-TYPE
      SYNTAX   INTEGER
    {
     notApplicable 	(1),
     ipAddress		(2),
     macAddress    	(3)
     }
   MAX-ACCESS  read-create
   STATUS  current
   DESCRIPTION
   "This MIB object defines the Bundle next Hop Address Type." 
       ::= { ip2IfEntry 55}

ip2IfNoiseLevelForVAD   OBJECT-TYPE
   SYNTAX  INTEGER
   {       
    low          (2),
    high         (3),
	off			 (4)
   }
   MAX-ACCESS  read-create
   STATUS  current
   DESCRIPTION
   "This object defines the Level of Noise on the line,
    the Voice Activation Detector (VAD) will have to handle."
   ::= { ip2IfEntry 56}

ip2IfClockPreferences   OBJECT-TYPE
   SYNTAX  INTEGER
   {       
    accurateness          (2),
    constantDelay         (3)
   }
   MAX-ACCESS  read-create
   STATUS  current
   DESCRIPTION
   "The Clock preferences:
   accurateness (2) = Accurate clock is more important than Constant Delay.
   constantDelay (3)= Constant Delay is more important than Accurate clock ."
   ::= { ip2IfEntry 57}

ip2IfConnectionMode   OBJECT-TYPE
   SYNTAX  INTEGER
   {       
    tdmOIpCe         (2),
    tdmOIpCv         (3)
   }
   MAX-ACCESS  read-create
   STATUS  current
   DESCRIPTION
   "The Connection Mode:
   tdmOIpCe (2) = TDMOiP (CE) = Circuit Emulation.
   tdmOIpCv (3)= TDMOiP (CV) = Compressed Voice."
   ::= {ip2IfEntry 58}

 ip2IfRingBack   OBJECT-TYPE
   SYNTAX  INTEGER
   {       
    disable         (2),
    enable          (3)
   }
   MAX-ACCESS  read-create
   STATUS  current
   DESCRIPTION
   "Enables or disable Ring Back."
   ::= {ip2IfEntry 59}

 ip2IfReversePolarity   OBJECT-TYPE
   SYNTAX  INTEGER
   {       
     disable         (2),
     enable          (3)   
   }
   MAX-ACCESS  read-create
   STATUS  current
   DESCRIPTION
   "Enables or disable Reverse polarity synthesis."
   ::= {ip2IfEntry 60}

 ip2IfPulseMeter   OBJECT-TYPE
   SYNTAX  INTEGER
   {       
    disable         (2),
    enable          (3)
   }
   MAX-ACCESS  read-create
   STATUS  current
   DESCRIPTION
   "Enables or disable Pulse metering synthesis."
   ::= {ip2IfEntry 61}

    ip2IfPulseMeterFreq   OBJECT-TYPE
   SYNTAX  INTEGER
   {       
    rate12Khz        (2),
    rate16Khz        (3)
   }
   MAX-ACCESS  read-create
   STATUS  current
   DESCRIPTION
   "Frequency of synthesized pulse metering for this bundle."
   ::= {ip2IfEntry 62}

    ip2IfPulseMeterPeriod   OBJECT-TYPE
   SYNTAX  Integer32
   MAX-ACCESS  read-create
   STATUS  current
   DESCRIPTION
   "Duration of synthesized pulse metering. current values are: 100-250."
   ::= {ip2IfEntry 63}

    ip2IfOnHookDetect   OBJECT-TYPE
   SYNTAX  INTEGER
   {       
    disable        (2),
    enable       (3)
   }
   MAX-ACCESS  read-create
   STATUS  current
   DESCRIPTION
   "Enables or disable immediate reaction to On-Hook bits from network in Ringing."
   ::= {ip2IfEntry 64}

ip2IfComfortNoiseGen   OBJECT-TYPE  
   SYNTAX  INTEGER
   {       
    disable      (2),
    enable       (3)
   }
   MAX-ACCESS  read-create
   STATUS  current
   DESCRIPTION
   "Enable or disable Comfort Noise Generation (CNG).
    When this parameter is enabled and no voice payload exists on the line for some
    time period during the call (moments of silence), the device will generate a soft   
    background noise which assures the user that the connection is still alive (CNG).
    
    When this parameter is disabled and no voice payload exists on the line,
    absolute silence will be heard (Comfort Noise will not be generated)."
   ::= {ip2IfEntry 65}

ip2IfExitChannel   OBJECT-TYPE
   SYNTAX  Integer32
   MAX-ACCESS  read-create
   STATUS  current
   DESCRIPTION
   "The channelized bundle that the voice bundle exits through.
   In Gmux2000 it is the ifIndex of the Channelized Bundle (sub-channel) 
   that the Voice Bundle exits through. The ifIndex contains 
   the Slot+Prt+Channelized Bundle No."
   ::= {ip2IfEntry 66}

ip2IfMaxVBDModemCalls   OBJECT-TYPE
   SYNTAX  Integer32
   MAX-ACCESS  read-create
   STATUS  current
   DESCRIPTION
   "Maximum VBD modem calls for this bundle."
   ::= {ip2IfEntry 67}

ip2IfMaxRelayModemCalls   OBJECT-TYPE
   SYNTAX  Integer32
   MAX-ACCESS  read-create
   STATUS  current
   DESCRIPTION
   "Maximum Relay modem calls for this bundle."
   ::= {ip2IfEntry 68}

ip2IfCustomToneFrequency          OBJECT-TYPE
     SYNTAX  INTEGER
      {
      notApplicable   (1),
      f1780Hz         (2),
      f2000Hz         (3),
      f1780Plus2000Hz (4)
      }
     MAX-ACCESS  read-create
     STATUS  current
     DESCRIPTION
     "This is the frequency of the Custom Tone that is sent between PBXs in order
      to check that the line status is OK. When the Custom Tone Detection is enabled
      the device will not compress/decompress this tone. The custom tone that is received
      from the local PBX will be sent to the remote PBX with the same frequency it was received.

      When the Custom Tone Frequency is f1780Plus2000Hz (4), the device will not  
      compress/decompress any tone with frequencies of 1780Hz or 2000 Hz."
      ::= { ip2IfEntry 69 }

ip2IfVadMethod   OBJECT-TYPE  
    SYNTAX  INTEGER
    {       
     proprietary      (2),
     internalITUT   (3)
    }
    MAX-ACCESS  read-create
    STATUS  current
    DESCRIPTION
    "Voice Activity Detection (VAD) method.
    proprietary    (2) - non standard VAD based only on power measurement.
                          It is very sensitive to background noise.
    internalITUT (3) - standard ITU-T VAD. It is a robust method."    
    ::= {ip2IfEntry 70}

ip2IfRxGain      OBJECT-TYPE
    SYNTAX  Integer32
    MAX-ACCESS  read-create
    STATUS  current
    DESCRIPTION
    "Receive gain in dBm."    
    ::= { ip2IfEntry 71 }

ip2IfCallerIDType   OBJECT-TYPE  
    SYNTAX  INTEGER
    {       
     bellcoreType1 (2),
     v23           (3)
    }
    MAX-ACCESS  read-create
    STATUS  current
    DESCRIPTION
    "Caller ID Type used by the DSP for this bundle.
     Bellcore type is used by the American method.
     V.23     type is used by the European method."    
    ::= {ip2IfEntry 72}


ip2IfPeerAddrType   OBJECT-TYPE
      SYNTAX   INTEGER
    {
     notApplicable 	(1),
     ipAddress		(2),
     macAddress    	(3)
     }
   MAX-ACCESS  read-create
   STATUS  current
   DESCRIPTION
   "This MIB object defines the peer Address Type." 
       ::= { ip2IfEntry 73}

ip2IfVbdRate   OBJECT-TYPE  
    SYNTAX  INTEGER
    {   
     r64KbpsIn5msecIntervalsG711(2),
     r64KbpsIn10msecIntervalsG711(3),
     r32KbpsG726(4),
     r24KbpsG726(5)     
    }
    MAX-ACCESS  read-create
    STATUS  current
    DESCRIPTION
    "Voice Band Data (VBD) rate for this bundle."    
    ::= {ip2IfEntry 74}

ip2IfDtmfDetection    OBJECT-TYPE
    SYNTAX  INTEGER
    {
     notApplicable 	(1),
     disable  		(2),
     enable    		(3)
    }
    MAX-ACCESS  read-create
    STATUS  current
    DESCRIPTION
    "Enable/Disable DTMF (Dual Tone Multi Frequency) detectors for this bundle."
    ::= { ip2IfEntry 75 }

ip2IfNlpCutoffLevel    OBJECT-TYPE
     SYNTAX  Unsigned32 
     MAX-ACCESS  read-create
     STATUS  current
     DESCRIPTION
     "Non Linear Processor (NLP) Cutoff Level for this bundle.
      This parameter is used by the echo canceller.
      It is the maximum absolute linear PCM amplitude of the near-end signal that will
      cause the NLP module to be active and to mute low level residual echo & noisy
      surroundings."    
   ::= { ip2IfEntry 76 }

ip2IfDtdErlRatioCutoffQ3    OBJECT-TYPE
     SYNTAX  Unsigned32 
     MAX-ACCESS  read-create
     STATUS  current
     DESCRIPTION
     "The DTD ERL cutoff level is used in order to determine whether the near-end is talking
      or not. This parameter is used by the echo canceller when echo exists and there is
      voice with low volume on the line.
      DTD means Double Talk Detection.
      ERL means Echo Return Loss. It  is the power difference [dB] between the far-end signal
      to the echo returned.
      The cutoff level is calculated for the value entering Q.3.
      This value will be divided by 2^3=8 in order to get the linear ratio."       
     ::= { ip2IfEntry 77 }

ip2IfCASRedundancy    OBJECT-TYPE
    SYNTAX  INTEGER
    {
     notApplicable 	(1),
     disable  		(2),
     enable    		(3)
    }
    MAX-ACCESS  read-create
    STATUS  current
    DESCRIPTION
    "Enable/Disable CAS signaling redundancy.
     This parameter is useful when there are problems with the network and applicable
     only for CAS signaling: E1-MF (G.732S) or E1-CRC-MF (G.732SCRC ).
     
     enable (3) - means that each packet containing CAS signaling will be triplicated
                  into 3 packets.
     disable (2)- No redundancy will exist. Only 1 packet containing CAS will be
                  transmitted."
    ::= { ip2IfEntry 78 }

ip2IfBundleSensitivity 	OBJECT-TYPE
    SYNTAX  INTEGER
    {
     delaySensitive	(2),
     dataSensitive	(3)
    }
    MAX-ACCESS  read-create
    STATUS  current
    DESCRIPTION
    "Denotes if the bundle is sensitive to delay in the network,
     or is sensitive to data errors in the network.
	 Voice bundles are sensitive to delay;
	 Non-voice bundles are sensitive to data errors."
    ::= { ip2IfEntry 79 }

ip2IfOAMBundleIdent 	OBJECT-TYPE
    SYNTAX  INTEGER
    {
     bundleNumber  (2),
     vccvCtrlWord  (3)
    }
    MAX-ACCESS  read-create
    STATUS  current
    DESCRIPTION
    "Denotes if an OAM bundle is identified according to the Bundle Number (0x3fff),
     or according to the value of the first nibble in the VCCV control word sent in the frame.
	 controlWord - applicable only when ip2IfProtocolVersion = v2(2).
	 When ip2IfProtocolVersion = v1(1), only bundleNumber is applicable."
    ::= { ip2IfEntry 80 }

ip2IfMaxTxQueue OBJECT-TYPE
	SYNTAX		Unsigned32 
	MAX-ACCESS	read-create
	STATUS		current
	DESCRIPTION
	"Max Tx Queue buffer size, measured in msec (milliseconds).

	 Low buffer size may cause the buffer to overflow and discard packets
	 in case of burst of packets on the network.
	 
	 High buffer size allows to store this burst and not lose packets."
	::= { ip2IfEntry 81 }

ip2IfMaxGprsTxQueue OBJECT-TYPE
	SYNTAX		Unsigned32 
	MAX-ACCESS	read-create
	STATUS		current
	DESCRIPTION
	"Max GPRS Tx Queue buffer size, measured in msec (milliseconds).       

	 Low buffer size may cause the buffer to overflow and discard packets
	 in case of burst of packets on the network.
	 
	 High buffer size allows to store this burst and not lose packets."
	::= { ip2IfEntry 82 }

ip2IfV23HD    OBJECT-TYPE
    SYNTAX  INTEGER
    {
     notApplicable 	(1),
     disable  		(2),
     enable    		(3)
    }
    MAX-ACCESS  read-create
    STATUS  current
    DESCRIPTION
    "This parameter shows whether V.23 Half Duplex Modem Protocol is enabled
     on the bundle."
    ::= { ip2IfEntry 83 }

ip2IfModemProtocolMode  OBJECT-TYPE
    SYNTAX  OCTET STRING
    MAX-ACCESS  read-create
    STATUS  current
    DESCRIPTION
    "This octet string contains the mode of each Modem Protocol used on the bundle.
     For each protocol one octet will be used. 
     
     Octet #1 will be used for V.22 Protocol.
     Octet #2, #3, #4... are reserved for future protocols.

     Octet #1 values:
     0 - Not Applicable
     1 - VBD:   Voice Band Data.
     2 - Relay: Pulse Code Modulated (PCM) data is sent via the bundle.
       
     For V.22: This MIB object is relevant only when ip2IfModemCalls = relay (4)."     
     ::= { ip2IfEntry 84 }

ip2IfCdisCngDetectionTime  OBJECT-TYPE
	SYNTAX	Unsigned32 
	MAX-ACCESS	read-create
	STATUS	current
	DESCRIPTION
	"When working with CDIS (Call DIScrimination method) or CNG (Comfort Noise Generation):
       The time in msec that the device will detect 1100Hz & 2100Hz signals
       on the line before switching to modem or fax.
       For Vmux: the values will be in steps of 10 msec."
	::= { ip2IfEntry 85 }

ip2IfSuperTandemBitMask OBJECT-TYPE
    SYNTAX  OCTET STRING
    MAX-ACCESS  read-create
    STATUS  current
    DESCRIPTION
    "This MIB object enables controlling the Time Slot/Channel rate.
     Valid values: 1 - FF HEX
     Each BIT represents 1/8 of the TS.
     Example:
     7E (0111 1110) means that 6/8 of the TS (the center ones) are masked and data will
     be Tx/Rx only through them.    
     This MIB object is relevant only when Super Tandem is enabled."
    ::= { ip2IfEntry 86 }

ip2IfVbdSwitchbackTime  OBJECT-TYPE
	SYNTAX	Unsigned32 
	MAX-ACCESS	read-create
	STATUS	current
	DESCRIPTION
	"Time in msec required for the DSP to switch back from VBD (Voice Band Data) to Voice.
       For Vmux: the values will be in steps of 30 msec. 
    "
	::= { ip2IfEntry 87 }


ip2IfCallerIdTxGain                  OBJECT-TYPE
     SYNTAX  Integer32
     MAX-ACCESS  read-create
     STATUS  current
     DESCRIPTION
     "The gain value in dBm units used for transmitting the Caller ID signal on the bundle.
     "    
     ::= { ip2IfEntry 88 }


ip2IfCallerIdRxGain      OBJECT-TYPE
    SYNTAX  Integer32
    MAX-ACCESS  read-create
    STATUS  current
    DESCRIPTION
    "The gain value in dBm units of the Caller ID signal received on the bundle."    
    ::= { ip2IfEntry 89 }

ip2IfUdpMuxMethod	  OBJECT-TYPE
    SYNTAX 		INTEGER
	{
	    srcPort  (2),
		destPort (3)
	}
    MAX-ACCESS  read-create
    STATUS  current
    DESCRIPTION
    "This parameter determines according to which field the multiplexing is made:
    srcPort (2) - multiplexing according to the UDP Source Port (Dest=0x085e).
	    This should be the default value, for backwards compatibility.
	destPort (3) - multiplexing according to the UDP Destination Port 
	   (standard multiplexing). 
	   
	 The UDP Source and Destination ports' range is determined according to 
	 ip2IfUdpMuxMethod value:
	 For srcPort (2) the range is 1-7000
	 For destPort (3) the range is 49152-65535."    
    ::= { ip2IfEntry 90 }

ip2IfCallerIdDetection    OBJECT-TYPE
    SYNTAX  INTEGER
    {
     notApplicable 	(1),
     disable  		(2),
     enable    		(3)
    }
    MAX-ACCESS  read-create
    STATUS  current
    DESCRIPTION
    "Enable/Disable Caller ID Detection for this bundle."
    ::= { ip2IfEntry 91 }

ip2IfWap    OBJECT-TYPE
    SYNTAX  INTEGER
    {
     notApplicable 	(1),
     disable  		(2),
     enable    		(3)
    }
    MAX-ACCESS  read-create
    STATUS  current
    DESCRIPTION
    "Enable/Disable WAP (Wireless Application Protocol) for this bundle.
     WAP allows users to access the internet from wireless devices."
    ::= { ip2IfEntry 92 }


ip2IfSignalingOos     OBJECT-TYPE
    SYNTAX  INTEGER
       {
        notApplicable  (1),
        forcedIdle     (3),
        forcedBusy     (4)
       }
      MAX-ACCESS  read-create
      STATUS  current
      DESCRIPTION
      "Out of Service code sent on signaling TimeSlot."
      ::= {ip2IfEntry 93}


ip2IfTDMFrameBytes OBJECT-TYPE
       SYNTAX  Integer32 
       MAX-ACCESS  read-write
       STATUS  current
       DESCRIPTION
       "The number of TDM bytes to be placed in a single IP 
       frame payload."
       ::= { ip2If 2 }

ip2IfTosValue OBJECT-TYPE
       SYNTAX  Integer32 
       MAX-ACCESS  read-write
       STATUS  current
       DESCRIPTION
       "The TOS value to write in the IP frame."
       ::= { ip2If 3 }
  
ip2IfVlanTagging OBJECT-TYPE
       SYNTAX INTEGER {
       no		(1),
       yes	    (2)
       }
       MAX-ACCESS  read-write
       STATUS  current
       DESCRIPTION
       "VLAN support.
       no - No support to VLAN.
       yes - 4 VLAN bytes will be added to the frame."
       ::= { ip2If 4 }

ip2IfVlanID OBJECT-TYPE
       SYNTAX  Integer32 
       MAX-ACCESS  read-write
       STATUS  current
       DESCRIPTION
       "VLAN ID."
       ::= { ip2If 5 }
  
ip2IfVlanPriority OBJECT-TYPE
       SYNTAX  Integer32 
       MAX-ACCESS  read-write
       STATUS  current
       DESCRIPTION
       "Frame priority."
       ::= { ip2If 6 }


-- ip2If Statistics table  

ip2IfStatTable OBJECT-TYPE
       SYNTAX  SEQUENCE OF Ip2IfStatEntry
       MAX-ACCESS  not-accessible
       STATUS  current
       DESCRIPTION
       "Channels (Bundles) Statistics Table."
       ::= { ip2If 7 }
  
ip2IfStatEntry OBJECT-TYPE
       SYNTAX Ip2IfStatEntry
       MAX-ACCESS not-accessible
       STATUS current
       DESCRIPTION
       "IP Statistics per bundle"
       INDEX   { ip2IfStatChIndex }
       ::= { ip2IfStatTable 1 }

Ip2IfStatEntry ::=
         SEQUENCE {
         ip2IfStatChIndex	       Integer32,
         ip2IfStatSeqErrors        Integer32,
         ip2IfStatBufUnderflows    Integer32,
         ip2IfStatBufOverflows     Integer32,
		 ip2IfStatTxOnTimeInterval Counter32,
		 ip2IfStatTxOnMaxSize      Counter32,
		 ip2IfStatRxSignaling      Counter32,
		 ip2IfStatRxVoice          Counter32,
		 ip2IfStatRxHdlc           Counter32,
		 ip2IfStatTxSignaling      Counter32,
		 ip2IfStatTxVoice          Counter32,
		 ip2IfStatTxHdlc           Counter32,
		 ip2IfStatRdnFlip		   Counter32,
		 ip2IfFarEndTdmStatus	   Integer32,
		 ip2IfStatPsnTxFrames		   Counter32,
		 ip2IfStatPsnRxFrames		   Counter32,
		 ip2IfStatMinJittBufLevel	   Unsigned32,
		 ip2IfStatMaxJittBufLevel	   Unsigned32,
		 ip2IfStatRecommendedJittBufSize  Unsigned32,
		 ip2IfStatPsnSeqErrors		  Counter32,
		 ip2IfStatPsnReorderFrames 	  Counter32,
		 ip2IfStatMinRoundTripDelay	  Unsigned32,
		 ip2IfStatMaxRoundTripDelay	  Unsigned32,
		 ip2IfStatAvrRoundTripDelay	  Unsigned32,
		 ip2IfStatFrameTrackDupDrop	   Counter32,
         ip2IfStatFrameTrackMissing	   Counter32,
         ip2IfStatFrameTrackLongSerMiss  Integer32,
		 ip2IfStatTxMeasuredSilence      Integer32,
		 ip2IfStatRxMeasuredSilence      Integer32,
		 ip2IfStatHdlcCrcErr			 Counter32,
		 ip2IfStatHdlcAlignErr			 Counter32,
		 ip2IfStatHdlcOversize			 Counter32,
		 ip2IfStatHdlcUndersize			 Counter32,
		 ip2IfStatHdlcAbort				 Counter32,
		 ip2IfStatRxCorrectFrames        Counter32,
		 ip2IfStatHdlcErroredFrames      Counter32
          }
  
ip2IfStatChIndex OBJECT-TYPE
    SYNTAX  		Integer32 
    MAX-ACCESS  read-only
    STATUS  current
    DESCRIPTION
    "The channel index, which is actualy the bundle ID."
    ::= { ip2IfStatEntry 1 }

ip2IfStatSeqErrors      OBJECT-TYPE
    SYNTAX        Integer32
    MAX-ACCESS        read-only
    STATUS        current
    DESCRIPTION
    "Number of events that the sequence number of an incoming Frame
     causes a transition from the 'sync' state to
     the 'out of sequence' state."
     ::= { ip2IfStatEntry 2 }

ip2IfStatBufUnderflows      OBJECT-TYPE
    SYNTAX        Integer32
    MAX-ACCESS    read-only
    STATUS        current
    DESCRIPTION
    "Number of events that the buffer underflows. This records the count of the
     number of events the Receive (Eth to TDM) buffer underflows. In the
     case of a continuous underflow caused by a loss of Frame
     flow, a single buffer underflow should be counted."
    ::= { ip2IfStatEntry 3 }

ip2IfStatBufOverflows      OBJECT-TYPE
    SYNTAX        Integer32
    MAX-ACCESS        read-only
    STATUS        current
    DESCRIPTION
    "Number of events that the buffer overflows. This records the count of the
     number of events the Receive (Eth to TDM) buffer overflows."
    ::= { ip2IfStatEntry 4 }
  
ip2IfStatTxOnTimeInterval      OBJECT-TYPE
    SYNTAX        Counter32
    MAX-ACCESS    read-only
    STATUS        current
    DESCRIPTION
    "Number of frames that were transmitted due to time interval elapse.
     The user can choose to Tx the Frame when it reaches the Max size
     or when the packetizing time interval elapses.
     The packetizing time interval is the interval in msec that it takes
     to build a Max. size frame."
    ::= { ip2IfStatEntry 5 }

ip2IfStatTxOnMaxSize      OBJECT-TYPE
    SYNTAX        Counter32
    MAX-ACCESS    read-only
    STATUS        current		
    DESCRIPTION
    "Number of frames that were transmitted due to reaching max.
     frame size. The user can choose to Tx the Frame when it reaches the
     Max size or when the packetizing time interval elapses."
    ::= { ip2IfStatEntry 6 }

ip2IfStatRxSignaling      OBJECT-TYPE
    SYNTAX        Counter32
    MAX-ACCESS    read-only
    STATUS        current		
    DESCRIPTION
    "Number of signaling frames that were received."
    ::= { ip2IfStatEntry 7 }

ip2IfStatRxVoice          OBJECT-TYPE
    SYNTAX        Counter32
    MAX-ACCESS    read-only
    STATUS        current		
    DESCRIPTION
    "Number of voice frames that were received."
    ::= { ip2IfStatEntry 8 }

ip2IfStatRxHdlc           OBJECT-TYPE
    SYNTAX        Counter32
    MAX-ACCESS    read-only
    STATUS        current		
    DESCRIPTION
    "Number of HDLC frames that were received."
    ::= { ip2IfStatEntry 9 }

ip2IfStatTxSignaling      OBJECT-TYPE
    SYNTAX        Counter32
    MAX-ACCESS    read-only
    STATUS        current		
    DESCRIPTION
    "Number of signaling frames that were transmitted."
    ::= { ip2IfStatEntry 10 }

ip2IfStatTxVoice          OBJECT-TYPE
    SYNTAX        Counter32
    MAX-ACCESS    read-only
    STATUS        current		
    DESCRIPTION
    "Number of voice frames that were transmitted."
    ::= { ip2IfStatEntry 11 }

ip2IfStatTxHdlc           OBJECT-TYPE
    SYNTAX        Counter32
    MAX-ACCESS    read-only
    STATUS        current		
    DESCRIPTION
    "Number of HDLC frames that were transmitted."
    ::= { ip2IfStatEntry 12 }

ip2IfStatRdnFlip          OBJECT-TYPE
    SYNTAX        Counter32
    MAX-ACCESS    read-only
    STATUS        current		
    DESCRIPTION
    "Number of redundancy flips occured.
    This parameter counts only flips from this bundle to the other bundle
    in the redundancy couple."
    ::= { ip2IfStatEntry 13 }

ip2IfFarEndTdmStatus OBJECT-TYPE
     SYNTAX  Integer32 (1..6)
     MAX-ACCESS  read-only
     STATUS  current
     DESCRIPTION
     "This variable indicates the Status of the Far-End TDM Line.  
     It contains failure state information.  
     The variable is a bit map represented as a sum, therefore, it
     can represent multiple failures simultaneously.  
     The farEndTdmNoDefect must be set if and only if no other flag is set.

     The various bit positions are:
        1   farEndTdmNoDefect
        2   farEndTdmAIS	   Alarm Indication Signal
        4   farEndTdmRDI	   Remote Defect Indication"
    ::= { ip2IfStatEntry 14 }

ip2IfStatPsnTxFrames           OBJECT-TYPE
    SYNTAX        Counter32
    MAX-ACCESS    read-only
    STATUS        current		
    DESCRIPTION
    "Number of frames that were transmitted to PSN."
    ::= { ip2IfStatEntry 15 }

ip2IfStatPsnRxFrames           OBJECT-TYPE
    SYNTAX        Counter32
    MAX-ACCESS    read-only
    STATUS        current		
    DESCRIPTION
    "Number of frames that were recieved from PSN."
    ::= { ip2IfStatEntry 16 }

ip2IfStatMinJittBufLevel      OBJECT-TYPE
    SYNTAX        Unsigned32
    MAX-ACCESS    read-only
    STATUS        current
    DESCRIPTION
    "The Minimum jitter buffer level (in msec)."
    ::= { ip2IfStatEntry 17 }

ip2IfStatMaxJittBufLevel      OBJECT-TYPE
    SYNTAX        Unsigned32
    MAX-ACCESS    read-only
    STATUS        current
    DESCRIPTION
    "The Maximum jitter buffer level (in msec)."
    ::= { ip2IfStatEntry 18 }

ip2IfStatRecommendedJittBufSize      OBJECT-TYPE
    SYNTAX        Unsigned32
    MAX-ACCESS    read-only
    STATUS        current
    DESCRIPTION
    "The Recommended jitter buffer Size (in msec).
     0= not applicable."
    ::= { ip2IfStatEntry 19 }

ip2IfStatPsnSeqErrors      OBJECT-TYPE
    SYNTAX        Counter32
    MAX-ACCESS    read-only
    STATUS        current
    DESCRIPTION
    "Number of times that the sequence number of an incoming Frame
     indicates Loss of Frame or Out of order occured in PSN."
     ::= { ip2IfStatEntry 20 }

ip2IfStatPsnReorderFrames      OBJECT-TYPE
    SYNTAX        Counter32
    MAX-ACCESS    read-only
    STATUS        current
    DESCRIPTION
    "Number of times that Frames had been reordered in PSN."
     ::= { ip2IfStatEntry 21 }

ip2IfStatMinRoundTripDelay      OBJECT-TYPE
    SYNTAX        Unsigned32
    MAX-ACCESS    read-only
    STATUS        current
    DESCRIPTION
    "The minimum Round Trip delay (in msec).
     0= not applicable."
    ::= { ip2IfStatEntry 22}

ip2IfStatMaxRoundTripDelay      OBJECT-TYPE
    SYNTAX        Unsigned32
    MAX-ACCESS    read-only
    STATUS        current
    DESCRIPTION
    "The maximum Round Trip delay (in msec).
     0= not applicable."
    ::= { ip2IfStatEntry 23 }

ip2IfStatAvrRoundTripDelay      OBJECT-TYPE
    SYNTAX        Unsigned32
    MAX-ACCESS    read-only
    STATUS        current
    DESCRIPTION
    "The avarage Round Trip delay (in msec).
     0= not applicable."
    ::= { ip2IfStatEntry 24 }

ip2IfStatFrameTrackDupDrop      OBJECT-TYPE
    SYNTAX        Counter32
    MAX-ACCESS    read-only
    STATUS        current
    DESCRIPTION
    "The number of packets dropped due to being duplicated.
     (duplicated packet means a packet that has the same sequential
      number as a packet being received previously)."
    ::= { ip2IfStatEntry 25 }

ip2IfStatFrameTrackMissing      OBJECT-TYPE
    SYNTAX        Counter32
    MAX-ACCESS    read-only
    STATUS        current
    DESCRIPTION
    "The number of packets that are missing.
     (Missing packet means an expected packet- according to the current sequential
      number - that was not received)."
    ::= { ip2IfStatEntry 26 }

ip2IfStatFrameTrackLongSerMiss   OBJECT-TYPE
    SYNTAX        Integer32
    MAX-ACCESS    read-only
    STATUS        current
    DESCRIPTION
"The longest series of consecutive missing sequential numbers.
    Missing sequential numbers represent missing packets that was
    expected to be received successively."
    ::= { ip2IfStatEntry 27 }


ip2IfStatTxMeasuredSilence  OBJECT-TYPE
     SYNTAX  Integer32     
     MAX-ACCESS  read-only
     STATUS  current
     DESCRIPTION
     "This object shows the percentage of Silence that was measured by the device
      for the current bundle in the transmitted payload.
      Relevant values: 0..100, 255.
      Default value is 50.
      0 means that there is no silence on the line.
      100 means that there is only silence. In this case, there might be no traffic.
      255 - value for not applicable or unknown."      
     ::= { ip2IfStatEntry 28 }
							
ip2IfStatRxMeasuredSilence  OBJECT-TYPE
     SYNTAX  Integer32     
     MAX-ACCESS  read-only
     STATUS  current
     DESCRIPTION
     "This object shows the percentage of Silence that was measured by the device
      for the current bundle in the received payload.
      Relevant values: 0..100, 255.
      Default value is 50.
      0 means that there is no silence on the line.
      100 means that there is only silence. In this case, there might be no traffic.
      255 - value for not applicable or unknown."      
     ::= { ip2IfStatEntry 29 }

ip2IfStatHdlcCrcErr	  OBJECT-TYPE
     SYNTAX  Counter32     
     MAX-ACCESS  read-only
     STATUS  current
     DESCRIPTION
     "This counter indicates the number of received HDLC frames 
     with CRC errors."      
     ::= { ip2IfStatEntry 30 }

ip2IfStatHdlcAlignErr	  OBJECT-TYPE
     SYNTAX  Counter32     
     MAX-ACCESS  read-only
     STATUS  current
     DESCRIPTION
     "This counter indicates the number of received HDLC frames 
     with alignment errors."      
     ::= { ip2IfStatEntry 31 }

ip2IfStatHdlcOversize	  OBJECT-TYPE
     SYNTAX  Counter32     
     MAX-ACCESS  read-only
     STATUS  current
     DESCRIPTION
     "This counter indicates the number of received HDLC frames 
     longer than 1470."      
     ::= { ip2IfStatEntry 32 }

ip2IfStatHdlcUndersize	  OBJECT-TYPE
     SYNTAX  Counter32     
     MAX-ACCESS  read-only
     STATUS  current
     DESCRIPTION
     "This counter indicates the number of received HDLC frames 
     shorter than 4."      
     ::= { ip2IfStatEntry 33 }

ip2IfStatHdlcAbort	  OBJECT-TYPE
     SYNTAX  Counter32     
     MAX-ACCESS  read-only
     STATUS  current
     DESCRIPTION
     "This counter indicates the number of received HDLC frames 
     with abort indication."      
     ::= { ip2IfStatEntry 34 }

ip2IfStatRxCorrectFrames  OBJECT-TYPE
     SYNTAX  Counter32     
     MAX-ACCESS  read-only
     STATUS  current
     DESCRIPTION
     "Number of received correct frames."      
     ::= { ip2IfStatEntry 35 }

ip2IfStatHdlcErroredFrames  OBJECT-TYPE
     SYNTAX  Counter32
     MAX-ACCESS  read-only
     STATUS  current
     DESCRIPTION
     "Number of received errored HDLC frames."      
     ::= { ip2IfStatEntry 36 }


							
ip2IfRateLimit OBJECT-TYPE
       SYNTAX  Integer32 
       MAX-ACCESS  read-write
       STATUS  current
       DESCRIPTION
       "The maximum rate permitted to transfer via the network portin Mbps."
       ::= { ip2If 8 }


-- ip2If Port table  

ip2IfPortTable OBJECT-TYPE
       SYNTAX  SEQUENCE OF Ip2IfPortEntry
       MAX-ACCESS  not-accessible
       STATUS  current
       DESCRIPTION
               "Port  Table."
       ::= { ip2If 9 }
  
ip2IfPortEntry OBJECT-TYPE
       SYNTAX Ip2IfPortEntry
       MAX-ACCESS not-accessible
       STATUS current
       DESCRIPTION
          "Application layer configuration per Port"
       INDEX   { ip2IfPortIndex }
       ::= { ip2IfPortTable 1 }

Ip2IfPortEntry ::=
         SEQUENCE {
         ip2IfPortIndex	    		Integer32,
         ip2IfPortUsage		    	Integer32,
		 ip2IfPortMask				INTEGER,
		 ip2IfPortTotalThroughput	Integer32
         	}
  
ip2IfPortIndex OBJECT-TYPE
    SYNTAX  Integer32 
    MAX-ACCESS  read-only
    STATUS  current
    DESCRIPTION
    "The Port index, which is actualy the ifIndex."
    ::= { ip2IfPortEntry 1 }

ip2IfPortUsage OBJECT-TYPE
    SYNTAX  Integer32 
    MAX-ACCESS  read-only
    STATUS  current
    DESCRIPTION
    "This parameter indicates the usage of the port (percents)."
    ::= { ip2IfPortEntry 2 }


ip2IfPortMask OBJECT-TYPE
       SYNTAX INTEGER {
       notApplicable	(1),
       dontMask  	    (2),
	   mask 			(3)
       }
       MAX-ACCESS  read-write
       STATUS  current
       DESCRIPTION
       "This parameter defines whether Agent will mask port's alarms and statistics or not."
	 ::= {  ip2IfPortEntry 3 }


ip2IfPortTotalThroughput OBJECT-TYPE
    SYNTAX  Integer32 
    MAX-ACCESS  read-only
    STATUS  current
    DESCRIPTION
    "This parameter indicates the total Throughput of the port in bps."
    ::= { ip2IfPortEntry 4 }


-- ip2If Current Statistics table  

ip2IfCurrentStatTable OBJECT-TYPE
       SYNTAX  SEQUENCE OF Ip2IfCurrentStatEntry
       MAX-ACCESS  not-accessible
       STATUS  current
       DESCRIPTION
       "Channels (Bundles) Current Statistics Table."
       ::= { ip2If 10 }
  
ip2IfCurrentStatEntry OBJECT-TYPE
       SYNTAX Ip2IfCurrentStatEntry
       MAX-ACCESS not-accessible
       STATUS current
       DESCRIPTION
       "IP Current Statistics per bundle"
       INDEX   { ip2IfChannelIndex }
       ::= { ip2IfCurrentStatTable 1 }

Ip2IfCurrentStatEntry ::=
         SEQUENCE {
         ip2IfCurrentStatSeqErrors         Counter32,
         ip2IfCurrentStatBufUnderflows     Counter32,
         ip2IfCurrentStatBufOverflows      Counter32,
		 ip2IfCurrentStatMaxDelayVar       Integer32,
		 ip2IfCurrentStatMinJittBufLevel   Unsigned32,
		 ip2IfCurrentStatMaxJittBufLevel   Unsigned32,
		 ip2IfCurrentStatTxErrFrameSec     Counter32
		 		 		 }

ip2IfCurrentStatSeqErrors      OBJECT-TYPE
    SYNTAX        Counter32
    MAX-ACCESS        read-only
    STATUS        current
    DESCRIPTION
    "Number of seconds that the sequence number of an incoming Frame
     causes a transition from the 'sync' state to
     the 'out of sequence' state in the current interval."
     ::= { ip2IfCurrentStatEntry 1 }

ip2IfCurrentStatBufUnderflows      OBJECT-TYPE
    SYNTAX        Counter32
    MAX-ACCESS    read-only
    STATUS        current
    DESCRIPTION
    "Number of seconds that the buffer underflows in the current interval. 
     This records the count of the number of seconds the Receive 
     (Eth to TDM) buffer underflows in the current interval. In the
     case of a continuous underflow caused by a loss of Frame
     flow, a single buffer underflow should be counted."
    ::= { ip2IfCurrentStatEntry 2 }

ip2IfCurrentStatBufOverflows      OBJECT-TYPE
    SYNTAX        Counter32
    MAX-ACCESS        read-only
    STATUS        current
    DESCRIPTION
    "Number of seconds that the buffer overflows in the current interval. 
     This records the count of the number of seonds the Receive 
     (Eth to TDM) buffer overflows in the current interval."
    ::= { ip2IfCurrentStatEntry 3 }

ip2IfCurrentStatMaxDelayVar      OBJECT-TYPE
    SYNTAX        Integer32
    MAX-ACCESS        read-only
    STATUS        current
    DESCRIPTION
    "The maximum deviation from the center of the buffer (in msec) for the current interval."
    ::= { ip2IfCurrentStatEntry 4 }

ip2IfCurrentStatMinJittBufLevel      OBJECT-TYPE
    SYNTAX        Unsigned32
    MAX-ACCESS    read-only
    STATUS        current
    DESCRIPTION
    "The Minimum jitter buffer level (in msec) for the current interval."
    ::= { ip2IfCurrentStatEntry 5 }

ip2IfCurrentStatMaxJittBufLevel      OBJECT-TYPE
    SYNTAX        Unsigned32
    MAX-ACCESS    read-only
    STATUS        current
    DESCRIPTION
    "The Maximum jitter buffer level (in msec) for the current interval."
    ::= { ip2IfCurrentStatEntry 6 }
  
ip2IfCurrentStatTxErrFrameSec    OBJECT-TYPE
    SYNTAX        Counter32
    MAX-ACCESS    read-only
    STATUS        current
    DESCRIPTION
    "The number of seconds in which errored frames were transmitted during the current interval.
     The error may be one of the following:
     CRC error, Alignment error, Oversized frame, Undersized frame, Aborted frame."
    ::= { ip2IfCurrentStatEntry 7 }

-- ip2If Interval Statistics table  

ip2IfIntervalStatTable OBJECT-TYPE
       SYNTAX  SEQUENCE OF Ip2IfIntervalStatEntry
       MAX-ACCESS  not-accessible
       STATUS  current
       DESCRIPTION
       "Channels (Bundles) Interval Statistics Table."
       ::= { ip2If 11 }
  
ip2IfIntervalStatEntry OBJECT-TYPE
       SYNTAX Ip2IfIntervalStatEntry
       MAX-ACCESS not-accessible
       STATUS current
       DESCRIPTION
       "IP Interval Statistics per bundle"
       INDEX   { ip2IfChannelIndex, ip2IfIntervalStatIndex }
       ::= { ip2IfIntervalStatTable 1 }

Ip2IfIntervalStatEntry ::=
         SEQUENCE {
         ip2IfIntervalStatIndex	       	   Integer32,
         ip2IfIntervalStatSeqErrors        Counter32,
         ip2IfIntervalStatBufUnderflows    Counter32,
         ip2IfIntervalStatBufOverflows     Counter32,
		 ip2IfIntervalStatMaxDelayVar      Integer32,
		 ip2IfIntervalStatMinJittBufLevel  Unsigned32,
		 ip2IfIntervalStatMaxJittBufLevel  Unsigned32,
		 ip2IfIntervalStatTxErrFrameSec    Counter32		
		 }

ip2IfIntervalStatIndex OBJECT-TYPE
    SYNTAX  		Integer32 
    MAX-ACCESS  read-only
    STATUS  current
    DESCRIPTION
    "The Interval index, which is actualy the Interval number."
    ::= { ip2IfIntervalStatEntry 1 }

ip2IfIntervalStatSeqErrors      OBJECT-TYPE
    SYNTAX        Counter32
    MAX-ACCESS        read-only
    STATUS        current
    DESCRIPTION
    "Number of seconds that the sequence number of an incoming Frame
     causes a transition from the 'sync' state to
     the 'out of sequence' state in the selected interval."
     ::= { ip2IfIntervalStatEntry 2 }

ip2IfIntervalStatBufUnderflows      OBJECT-TYPE
    SYNTAX        Counter32
    MAX-ACCESS    read-only
    STATUS        current
    DESCRIPTION
    "Number of seconds that the buffer underflows in the selected interval. 
     This records the count of the number of seconds the Receive 
     (Eth to TDM) buffer underflows in the selected interval. In the
     case of a continuous underflow caused by a loss of Frame
     flow, a single buffer underflow should be counted."
    ::= { ip2IfIntervalStatEntry 3 }

ip2IfIntervalStatBufOverflows      OBJECT-TYPE
    SYNTAX        Counter32
    MAX-ACCESS        read-only
    STATUS        current
    DESCRIPTION
    "Number of seconds that the buffer overflows in the selected interval. 
     This records the count of the number of seconds the Receive 
     (Eth to TDM) buffer overflows in the selected interval."
    ::= { ip2IfIntervalStatEntry 4 }

ip2IfIntervalStatMaxDelayVar      OBJECT-TYPE
    SYNTAX        Integer32
    MAX-ACCESS        read-only
    STATUS        current
    DESCRIPTION
    "The maximum size of the buffer (in 10's of usec) in the selected interval.
     For some devices (e.g. MP-4100) units are usec."
    ::= { ip2IfIntervalStatEntry 5 }

ip2IfIntervalStatMinJittBufLevel      OBJECT-TYPE
    SYNTAX        Unsigned32
    MAX-ACCESS    read-only
    STATUS        current
    DESCRIPTION
    "The Minimum jitter buffer level (in msec) for the selected interval.
     For some devices (e.g. MP-4100) units are usec."
    ::= { ip2IfIntervalStatEntry 6 }

ip2IfIntervalStatMaxJittBufLevel      OBJECT-TYPE
    SYNTAX        Unsigned32
    MAX-ACCESS    read-only
    STATUS        current
    DESCRIPTION
    "The Maximum jitter buffer level (in msec) for the selected interval.
     For some devices (e.g. MP-4100) units are usec."
    ::= { ip2IfIntervalStatEntry 7 }
								 
ip2IfIntervalStatTxErrFrameSec   OBJECT-TYPE
    SYNTAX        Counter32		
    MAX-ACCESS    read-only
    STATUS        current
    DESCRIPTION
    "The number of seconds in which errored frames were transmitted during the selected interval.
     The error may be one of the following:
     CRC error, Alignment error, Oversized frame, Undersized frame, Aborted frame."
    ::= { ip2IfIntervalStatEntry 8 }


ip2IfLogEvents			OBJECT-TYPE
     SYNTAX INTEGER {
       notApplicable	(1),
       all		  	    (2),
       oneMinStep		(3)
     }
     MAX-ACCESS  read-write
     STATUS  current
     DESCRIPTION
     "This parameter defines whether all Jitter Buffer and Sequence Number events
      will enter to Log File,
      or enter those events to Log file in one minute steps."
     ::= {  ip2If 12}


ip2IfEthSwitchMode			OBJECT-TYPE
     SYNTAX INTEGER {
       notApplicable	(1),
       unTagged	  	    (2),
       tagged			(3)
     }
     MAX-ACCESS  read-write
     STATUS  current
     DESCRIPTION
     "This parameter defines whether Eth Switch is in VLAN Tagged mode."
     ::= {  ip2If 13}



--Traps
 
--The numbers 1-4 are used by Imx.txt
--The numbers 5-6 are used by IpmuxAtmTraps.txt

alarmLOS NOTIFICATION-TYPE
      OBJECTS  { alarmSeverity, alarmState, ifAlias }  
      STATUS  current
      DESCRIPTION
	  "This trap indicates Loss Of Signal."
      ::= { radSysWanEvents 7 }

alarmLOF NOTIFICATION-TYPE
      OBJECTS  { alarmSeverity, alarmState, ifAlias }  
      STATUS  current
      DESCRIPTION
	  "This trap indicates Loss Of Frame."
      ::= { radSysWanEvents 8 }

channelOperStatusTrap NOTIFICATION-TYPE
      OBJECTS  { ip2IfOperStatus }  
      STATUS  current
      DESCRIPTION
	  "This trap is sent upon any change in one or more channels."
      ::= { radSysWanEvents 9 }

alarmAIS NOTIFICATION-TYPE
      OBJECTS  { alarmSeverity, alarmState, ifAlias }  
      STATUS  current
      DESCRIPTION
	  "This trap indicates AIS."
      ::= { radSysWanEvents 10 }

alarmRDI NOTIFICATION-TYPE
      OBJECTS  { alarmSeverity, alarmState, ifAlias }  
      STATUS  current
      DESCRIPTION
	  "This trap indicates RDI."
      ::= { radSysWanEvents 11 }

alarmFEBE NOTIFICATION-TYPE
      OBJECTS  { alarmSeverity, alarmState, ifAlias }  
      STATUS  current
      DESCRIPTION
	  "This trap indicates FEBE."
      ::= { radSysWanEvents 12 }

localConnStatusTrap NOTIFICATION-TYPE
      OBJECTS  { alarmSeverity, alarmState, ifAlias }  
      STATUS  current
      DESCRIPTION
	  "This trap is sent upon a change in Local connectivity
	   of Bundle connection."
      ::= { radSysWanEvents 13 }

remoteConnStatusTrap NOTIFICATION-TYPE
      OBJECTS  { alarmSeverity, alarmState, ifAlias }  
      STATUS  current
      DESCRIPTION
	  "This trap is sent upon a change in Remote connectivity
	   of Bundle connection."
      ::= { radSysWanEvents 14 }

bundleConnectionStatusTrap NOTIFICATION-TYPE
      OBJECTS  { ifAlias, ip2IfOperStatus }  
      STATUS  current
      DESCRIPTION
	  "This trap is sent upon any change in the connectivity status 
	   of a Bundle (ip2IfOperStatus).
	   The ifAlias index is the ifIndex of the bundle that its status has been changed."
      ::= { radSysWanEvents 15 }



-- 
-- file :D:\Synergy\WorkArea\545\mib_rad\txt\ipmuxAtm.txt
-- 
-- File:	IpmuxAtm.txt


alarmStatusTrap NOTIFICATION-TYPE
      OBJECTS  {atmInterfaceAlarmStatus}
      STATUS  current
      DESCRIPTION
	  "The trap is sent whenever there is a transition from a no alarm
	   state to a state with at least one active alarm."
      ::= { radSysWanEvents 5 }

systemTrap NOTIFICATION-TYPE
      OBJECTS  { atmNteEventType, agnLed, alarmSeverity }  
      STATUS  current
      DESCRIPTION
	  "This trap alerts of major problems in the device."
      ::= { radSysWanEvents 6 }
-- 
-- file :D:\Synergy\WorkArea\545\mib_rad\txt\bdband.txt
-- 
--RAD-BROADBAND-IF-MIB DEFINITIONS ::= BEGIN
--Version:   1.0
--Date:      14-Feb-2000
--By:        Smadar Tauber
--File:      bdband.mib
--
--Last update: 06-Jun-2004 by Shlomo Shoham



broadbandIf  OBJECT IDENTIFIER  ::=  {diverseIfWanGen 8}

bdbandConfig       OBJECT IDENTIFIER  ::=  {broadbandIf 1}
prtPhyPerfHistory  OBJECT IDENTIFIER  ::=  {broadbandIf 2}


-- Indication Signal Table

prtBdbandIndTable OBJECT-TYPE
    SYNTAX  SEQUENCE OF PrtBdbandIndEntry
    MAX-ACCESS  not-accessible
    STATUS  current
    DESCRIPTION
    "The Indication Signal table."
    ::= { bdbandConfig 1 }

prtBdbandIndEntry OBJECT-TYPE
    SYNTAX  PrtBdbandIndEntry
    MAX-ACCESS  not-accessible
    STATUS  current
    DESCRIPTION
    "An entry in the Indication Signal table."
    INDEX {prtBdbandCnfgIdx, prtBdbandIdx, prtBdbandIndSig, prtBdbandIndEvent}
    ::= { prtBdbandIndTable 1 }

PrtBdbandIndEntry ::=
    SEQUENCE {
    prtBdbandCnfgIdx
    Integer32,
    prtBdbandIdx
    Integer32,
	prtBdbandIndSig
	INTEGER,
	prtBdbandIndEvent
	INTEGER,
	prtBdbandIndSigEnable
	INTEGER,
	prtBdbandRowStatus
	RowStatus
    }

prtBdbandCnfgIdx OBJECT-TYPE
    SYNTAX  Integer32 (1..255)
    MAX-ACCESS  read-only
    STATUS  current
    DESCRIPTION
    "This object indicates the Idx of the Agent Cnfg the following 
     objects refer.
     255=Temporary Cnfg (when relevant, Set is done only to this configuration).
     For Agents that support only one configuration, this object will be 
     constant=1. "
    ::= { prtBdbandIndEntry 1 }

prtBdbandIdx OBJECT-TYPE
    SYNTAX  Integer32 
    MAX-ACCESS  read-only
    STATUS  current
    DESCRIPTION
    "This object indicates a unique  port or interface number.
	 For numbering, see product's spec.
     For some products, the numbering can equal ifIndex."    
    ::= { prtBdbandIndEntry 2 }

prtBdbandIndSig OBJECT-TYPE
    SYNTAX  INTEGER
    {
     ais       (1),
	 rdi       (2),
	 aisAndRdi (3)
    }
    MAX-ACCESS  read-only
    STATUS  current
    DESCRIPTION
    "This object indicates a unique Indication Signal.
     ais(1) = AIS = Alarm Indication Signal.
     rdi(2) = RDI = Remote Defect Indication."
    ::= { prtBdbandIndEntry 3 }

prtBdbandIndEvent OBJECT-TYPE
    SYNTAX  INTEGER
    {
     notApplicable(1),
     slm          (2),
	 fail         (3),
	 eed          (4),
	 pathTrace    (5),
	 lom		  (6),
	 lop		  (7),
	 slu		  (8)			
    }
    MAX-ACCESS  read-only
    STATUS  current
    DESCRIPTION
    "This object indicates a unique Event that can cause the Indication Signal.
     slm(2) = SLM = Signal Label Mismatch
     eed(4) = EED = Excessive Error Defect
     pathTrace(5) = the end-to-end source/destination of information is wrong.
     lom(6) = LOM = Loss of Multiframe.
     lop(7) = LOP = Loss of Pointer.
	 slu(8) = SLU = Signal Label Unequipped."
    ::= { prtBdbandIndEntry 4 }

prtBdbandIndSigEnable OBJECT-TYPE
    SYNTAX  INTEGER
    {
     notApplicable(1),
     disable      (2),
	 enable       (3)
    }
    MAX-ACCESS  read-create
    STATUS  current
    DESCRIPTION
    "This object allows user to define if the event specified by prtBdbandIndEvent 
     will cause creation of the Indication Signal specified by prtBdbandIndSig or not.
     disable - will not enable causing the signal
     enable  - will enable causing the signal. "
    ::= { prtBdbandIndEntry 5 }

prtBdbandRowStatus OBJECT-TYPE
    SYNTAX RowStatus 
    MAX-ACCESS read-create
    STATUS current
    DESCRIPTION
    "Creation/Deletion of rows in the table."
    ::= { prtBdbandIndEntry 6 }

-- Port Phy Config Table

prtPhyConfigTable OBJECT-TYPE
    SYNTAX  SEQUENCE OF PrtPhyConfigEntry
    MAX-ACCESS  not-accessible
    STATUS  current
    DESCRIPTION
    "The Phy Config table. Used now for Phy25.6 Mbps."
    ::= { bdbandConfig 2 }

prtPhyConfigEntry OBJECT-TYPE
    SYNTAX  PrtPhyConfigEntry
    MAX-ACCESS  not-accessible
    STATUS  current
    DESCRIPTION
    "An entry in the Phy Config table. "
    INDEX   { ifIndex }
    ::= { prtPhyConfigTable 1 }

PrtPhyConfigEntry ::=
    SEQUENCE {
    prtPhyTimeElapsed
        Integer32,
    prtPhyValidIntervals
        Integer32
       }

prtPhyTimeElapsed OBJECT-TYPE
    SYNTAX  Integer32 (0..899)
    MAX-ACCESS  read-only
    STATUS  current
    DESCRIPTION
    "The number of seconds that have elapsed since
     the beginning of the current error-measurement period."
   ::= { prtPhyConfigEntry 1 }

prtPhyValidIntervals OBJECT-TYPE
     SYNTAX  Integer32 (0..96)
     MAX-ACCESS  read-only
     STATUS  current
     DESCRIPTION
     "The number of previous intervals for which valid data was collected.  
      The value will be	96 unless the interface was brought online within
      the last 24 hours, in which case the value will be the number of complete 
      15 minute since the interface has been online."
     ::= { prtPhyConfigEntry 2 }


--Phy Performance History Tables

-- The PHY Current table contains various statistics being
-- collected for the current 15 minute interval.

prtPhyCurrentTable OBJECT-TYPE
    SYNTAX  SEQUENCE OF PrtPhyCurrentEntry
    MAX-ACCESS  not-accessible
    STATUS  current
    DESCRIPTION
    "The 25.6 Mbps Section/Line Current table."
    ::= { prtPhyPerfHistory 1 }

prtPhyCurrentEntry OBJECT-TYPE
    SYNTAX  PrtPhyCurrentEntry
    MAX-ACCESS  not-accessible
    STATUS  current
    DESCRIPTION
    "An entry in the 25.6 Mbps Line Current table.
     ifIndex of the line 25.6 Mbps layer of type 
     25.6 Mbps."
    INDEX   { ifIndex }
    ::= { prtPhyCurrentTable 1 }

PrtPhyCurrentEntry ::=
    SEQUENCE {
        prtPhyCurrentLOS
            Gauge32,
        prtPhyCurrentLSV
            Gauge32,
        prtPhyCurrentUAS
            Gauge32,
        prtPhyCurrentSES
            Gauge32,
        prtPhyCurrentES 
            Gauge32,
        prtPhyCurrentStatus 
            OCTET STRING,
        prtPhyCurrentLOF 
            Gauge32
    }

prtPhyCurrentLOS OBJECT-TYPE
    SYNTAX  Gauge32
    MAX-ACCESS  read-only
    STATUS  current
    DESCRIPTION
    "The counter associated with the number of Loss Of Sync
     seconds, encountered by a 25.6 Mbps interface in
     the current 15 minute interval."
    ::= { prtPhyCurrentEntry 1 }

prtPhyCurrentLSV OBJECT-TYPE
    SYNTAX  Gauge32
    MAX-ACCESS  read-only
    STATUS  current
    DESCRIPTION
    "The counter associated with the number of Line symbol violation
     seconds, encountered by a 25.6 Mbps
     interface in the current 15 minute interval."
    ::= { prtPhyCurrentEntry 2 }

prtPhyCurrentUAS OBJECT-TYPE
    SYNTAX  Gauge32
    MAX-ACCESS  read-only
    STATUS  current
    DESCRIPTION
    "The counter associated with the number of UAS
     encountered by a 25.6 Mbps
     interface in the current 15 minute interval."
    ::= { prtPhyCurrentEntry 3 }

prtPhyCurrentSES OBJECT-TYPE
     SYNTAX  Gauge32
     MAX-ACCESS  read-only
     STATUS  current
     DESCRIPTION
     "The counter associated with the number of SES
      encountered by a 25.6 Mbps
      interface in the current 15 minute interval."
     ::= { prtPhyCurrentEntry 4 }

prtPhyCurrentES OBJECT-TYPE
     SYNTAX Gauge32 
     MAX-ACCESS  read-only
     STATUS  current
     DESCRIPTION
     "The number of Errored Seconds, encountered  by a
      25.6 Mbps interface in the current 15 minute interval."
     ::= { prtPhyCurrentEntry 5 }
 
prtPhyCurrentStatus OBJECT-TYPE
     SYNTAX OCTET STRING  (SIZE (4))
     MAX-ACCESS  read-only
     STATUS  current
     DESCRIPTION
     "The statuses of the current interval:
       0 - O.K.
       1 - The link has been switched by a redundancy mechanism.
       2 - Module is in/out.
       4 - Empty - card is out."
     ::= { prtPhyCurrentEntry 6 }

prtPhyCurrentLOF OBJECT-TYPE
     SYNTAX Gauge32 
     MAX-ACCESS  read-only
     STATUS  current
     DESCRIPTION
     "The number of Loss of Frames, encountered by an
      interface in the current 15 minute interval."
     ::= { prtPhyCurrentEntry 7 }
 
 
-- The PHY interface Interval

-- The PHY Interval Table contains various statistics
-- collected by the Interface over the previous 24
-- hours of operation.  The past 24 hours are broken into 96
-- completed 15 minute intervals.

prtPhyIntervalTable OBJECT-TYPE
     SYNTAX  SEQUENCE OF PrtPhyIntervalEntry
     MAX-ACCESS  not-accessible
     STATUS  current
     DESCRIPTION
     "The Line Interval table."
     ::= { prtPhyPerfHistory 2 }

prtPhyIntervalEntry OBJECT-TYPE
     SYNTAX  PrtPhyIntervalEntry
     MAX-ACCESS  not-accessible
     STATUS  current
     DESCRIPTION
     "An entry in the 25.6 Mbps Line Interval table.
      ifIndex of the line 25.6 Mbps layer of type 25.6 Mbps."
     INDEX   { ifIndex, prtPhyIntervalNumber }
     ::= { prtPhyIntervalTable 1 }

PrtPhyIntervalEntry ::=
     SEQUENCE {
        prtPhyIntervalNumber
            Integer32,
        prtPhyIntervalLOS
            Gauge32,
        prtPhyIntervalLSV
            Gauge32,
        prtPhyIntervalUAS
            Gauge32,
        prtPhyIntervalSES
            Gauge32,
        prtPhyIntervalES
            Gauge32,
        prtPhyIntervalStatus
            OCTET STRING,
        prtPhyIntervalLOF
            Gauge32
      }

prtPhyIntervalNumber OBJECT-TYPE
     SYNTAX  Integer32 (1..96)
     MAX-ACCESS  read-only
     STATUS  current
     DESCRIPTION
     "A number between 1 and 96, where 1 is the most
      recently completed 15 minute interval and 96 is
      the least recently completed 15 minutes interval
      (assuming that all 96 intervals are valid)."
     ::= { prtPhyIntervalEntry 1 }

prtPhyIntervalLOS OBJECT-TYPE
     SYNTAX  Gauge32
     MAX-ACCESS  read-only
     STATUS  current
     DESCRIPTION
     "The counter associated with the number of Loss Of Sync
      seconds , encountered by a 25.6 Mbps interface in
      one of the previous 96, individual 15 minute intervals."
     ::= { prtPhyIntervalEntry 2 }

prtPhyIntervalLSV OBJECT-TYPE
     SYNTAX  Gauge32
     MAX-ACCESS  read-only
     STATUS  current
     DESCRIPTION
     "The counter associated with the number of line symbol violation
      seconds , encountered by a 25.6 Mbps interface in
      one of the previous 96, individual 15 minute intervals."
     ::= { prtPhyIntervalEntry 3 }

prtPhyIntervalUAS OBJECT-TYPE
     SYNTAX  Gauge32
     MAX-ACCESS  read-only
     STATUS  current
     DESCRIPTION
     "The counter associated with the number of UAS
      encountered by a 25.6 Mbps interface in one of the previous 96, 
      individual 15	minute intervals."
     ::= { prtPhyIntervalEntry 4 }

prtPhyIntervalSES OBJECT-TYPE
     SYNTAX  Gauge32
     MAX-ACCESS  read-only
     STATUS  current
     DESCRIPTION
     "The counter associated with the number of SES
      encountered by a 25.6 Mbps interface in one of the previous 96, 
      individual 15	minute intervals."
    ::= { prtPhyIntervalEntry 5 }

prtPhyIntervalES OBJECT-TYPE
     SYNTAX Gauge32 
     MAX-ACCESS  read-only
     STATUS current 
     DESCRIPTION
     "The number of Errored Seconds, encountered  by a
      25.6 Mbps interface in one of the previous 96, individual 15
      minute intervals."
     ::= { prtPhyIntervalEntry 6 }

prtPhyIntervalStatus OBJECT-TYPE
     SYNTAX OCTET STRING  (SIZE (4))
     MAX-ACCESS  read-only
     STATUS  current
     DESCRIPTION
     " The statuses of the current interval:
       0 - O.K.
       1 - The link has been switched by a redundancy mechanism.
       2 - Module is in/out.
       4 - Empty - card is out."
     ::= { prtPhyIntervalEntry 7 }

prtPhyIntervalLOF OBJECT-TYPE
     SYNTAX Gauge32 
     MAX-ACCESS  read-only
     STATUS current 
     DESCRIPTION
     "The number of Loss of Frames, encountered  by an
      interface in one of the previous 96, individual 15
      minute intervals."
     ::= { prtPhyIntervalEntry 8 }


-- END
-- 
-- file :D:\Synergy\WorkArea\545\mib_rad\txt\r2.txt
-- 

--Title:  RAD's WAN R2 Interface MIB
--By:     Smadar Tauber
--Date :  18.04.2000

--Last Update:  23-June-02
--By: Smadar Tauber
--File:  v:\doc\rdv\mib\ver490\r2.txt


--wanGen   OBJECT IDENTIFIER ::= {radWan 1}
--diverseIfWanGen OBJECT IDENTIFIER ::= {wanGen 6} (see mpmx.txt)
r2If OBJECT IDENTIFIER ::= {diverseIfWanGen 9}


r2ProfileCnfg OBJECT IDENTIFIER ::= {r2If 1}
r2IfStatus    OBJECT IDENTIFIER ::= {r2If 2}


--R2 Profile Configuration tables
--
--Only the profiles that are defined having agnSigProfType=r2Cas will
--exist in these tables. 

--The parameters of the r2CnfgTable are defined per configuration, per Country (RW).

r2CnfgTable  OBJECT-TYPE
     SYNTAX SEQUENCE OF R2CnfgEntry
     MAX-ACCESS not-accessible
     STATUS  current
     DESCRIPTION
      "The write operation into the Table Objects is valid only
       to the TmpCnfg entry."
     ::= { r2ProfileCnfg 1}

r2CnfgEntry OBJECT-TYPE
      SYNTAX R2CnfgEntry
      MAX-ACCESS not-accessible
      STATUS current
	DESCRIPTION  "An entry in table."
	INDEX {r2CnfgIdx, r2CnfgProfileIdx}
      ::= { r2CnfgTable 1}

R2CnfgEntry ::=
      SEQUENCE {
      r2CnfgIdx            Integer32,
      r2CnfgProfileIdx     Integer32,
      r2Mode               INTEGER,
      r2Country            Integer32,
	  r2Delay              INTEGER,
	  r2MeteringInd        INTEGER,
	  r2BreakMakeRatio     INTEGER,
      r2ReleaseGuardT2     Integer32,
      r2Regret             Integer32,
      r2SeizeDetect        Integer32,
	  r2SeizeAckDelay      Integer32,
	  r2ClearBackDetect    Integer32,
	  r2ClearFwdDetect     Integer32,
	  r2FaultDetect        Integer32,
	  r2FaultRemoveDetect  Integer32,
	  r2MeterPulseDuration Integer32,
	  r2SeizeAckWait       Integer32,
	  r2SeizeAckDetect     Integer32,
	  r2AnswerDetect       Integer32,
	  r2BlockRemoveDetect  Integer32,
	  r2MeterPulseDetect   Integer32,
	  r2ForcedDisconnect   Integer32,
	  r2DisconnectAck      Integer32,
	  r2ReleaseGuardT1     Integer32,
	  r2CnfgRowStatus      RowStatus
      }

r2CnfgIdx OBJECT-TYPE
      SYNTAX  Integer32 (1..255)
      MAX-ACCESS  read-only
      STATUS  current
      DESCRIPTION
      "This attribute indicates the Idx of the Cnfg being accessed.
       255 = TmpCnfg.
       1   = Current Cnfg. 
       Write is allowed only to TmpCnfg."
      ::= {r2CnfgEntry 1}

r2CnfgProfileIdx OBJECT-TYPE
      SYNTAX  Integer32
      MAX-ACCESS  read-only
      STATUS  current
      DESCRIPTION
      "Profile Index.
       Valid values: 1..5
       Only instances of profiles that are defined having agnSigProfType=r2Cas will
       exist in this table."
      ::= {r2CnfgEntry 2}

r2Mode OBJECT-TYPE
      SYNTAX  INTEGER
      { 
          auto  (2),
          manual(3)
      }
      MAX-ACCESS  read-create
      STATUS  current
      DESCRIPTION
      "R2 Mode.
       auto   - in this mode, default value of timers will be used by R2,
                according to the selected r2Country.
       manual - in this mode, user can change the value of R2 timers within the valid
                limits, specific to each country."
      ::= {r2CnfgEntry 3}

r2Country OBJECT-TYPE
     SYNTAX  Integer32 
     MAX-ACCESS   read-create
     STATUS   current
     DESCRIPTION
     "R2 Country. R2 Timers can have different range of values and
      defaults for each country. When r2Mode=auto, the default value is
	  used by R2 according to this selected country.
       1=ITU-T (standard values)
       2=Korea
       3=India
       4=Brasil (continuous)
       5=Brasil (pulsed)
       6..10 - reserved for future countries."
     ::= {r2CnfgEntry 4}

r2Delay OBJECT-TYPE
      SYNTAX  INTEGER 
      { 
       notApplicable (1),
       terrestrial   (2),
       satellite     (3)
      }
      MAX-ACCESS   read-create
      STATUS   current
      DESCRIPTION
      "This object enables user to configure the link as satellite or terrestrial.
       The seize acknowledge detect timing is much shorter (msec) for
       terrestrial link than for satellite link (1-2 sec)."
      ::= {r2CnfgEntry 5}

r2MeteringInd OBJECT-TYPE
      SYNTAX  INTEGER 
      { 
      notApplicable (1),
      cBit          (2), 
      bBit          (3)
      }
      MAX-ACCESS   read-create
      STATUS   current
      DESCRIPTION
      "Which Bit will be used for Metering Indication."
      ::= {r2CnfgEntry 6}

r2BreakMakeRatio OBJECT-TYPE
      SYNTAX    INTEGER
      { 
      notApplicable(1),
      break56Make44(2),
      break64Make36(3),
	  break80Make20(4)
      }
      MAX-ACCESS  read-create
      STATUS  current
      DESCRIPTION
      "This object describes the Break-Make Ratio of Pulse Duration, in [msec].
       RW only when r2Mode=manual."
      ::= {r2CnfgEntry 7}

r2ReleaseGuardT2 OBJECT-TYPE
      SYNTAX     Integer32 
      MAX-ACCESS read-create
      STATUS current
      DESCRIPTION
      "Release Guard timing T2.
       Release guard timing before going to idle, in [msec].
       RW only when r2Mode=manual."
      ::= {r2CnfgEntry 8}

r2Regret OBJECT-TYPE
      SYNTAX  Integer32  
      MAX-ACCESS  read-create
      STATUS  current
      DESCRIPTION
      "Regret duration, in [sec].
       RW only when r2Mode=manual."
      ::= {r2CnfgEntry 9}

r2SeizeDetect OBJECT-TYPE
      SYNTAX  Integer32  
      MAX-ACCESS  read-create
      STATUS  current
      DESCRIPTION
      "Seize Detect. Timer of the R2 incoming side.
       Minimum duration to detect a valid seizure, in [msec].
       RW only when r2Mode=manual."
      ::= {r2CnfgEntry 10}

r2SeizeAckDelay OBJECT-TYPE
      SYNTAX  Integer32  
      MAX-ACCESS  read-create
      STATUS  current
      DESCRIPTION
      "Timer of the R2 incoming side.
      Delay before sending a valid seize ack signal, in [msec].
      Applicable only when r2Mode=manual. only when r2Mode=manual."
      ::= {r2CnfgEntry 11}

r2ClearBackDetect OBJECT-TYPE
      SYNTAX  Integer32  
      MAX-ACCESS  read-create
      STATUS  current
      DESCRIPTION
      "Timer of the R2 incoming side.
      Minimum duration to recognize a valid clear-back, in [msec].
      RW only when r2Mode=manual."
      ::= {r2CnfgEntry 12}

r2ClearFwdDetect OBJECT-TYPE
      SYNTAX  Integer32  
      MAX-ACCESS  read-create
      STATUS  current
      DESCRIPTION
      "Timer of the R2 incoming side.
      Minimum duration to recognize a valid clear-forward, in [msec].
      RW only when r2Mode=manual."
      ::= {r2CnfgEntry 13}

r2FaultDetect OBJECT-TYPE
      SYNTAX  Integer32  
      MAX-ACCESS  read-create
      STATUS  current
      DESCRIPTION
      "Timer of the R2 incoming side.
      Minimum duration to recognize a block signal, in [msec].
      RW only when r2Mode=manual."
      ::= {r2CnfgEntry 14}

r2FaultRemoveDetect OBJECT-TYPE
      SYNTAX  Integer32  
      MAX-ACCESS  read-create
      STATUS  current
      DESCRIPTION
      "Timer of the R2 incoming side.
      Minimum duration to recognize a valid block removal signal, in [msec].
      RW only when r2Mode=manual."
      ::= {r2CnfgEntry 15}

r2MeterPulseDuration OBJECT-TYPE
      SYNTAX  Integer32  
      MAX-ACCESS  read-create
      STATUS  current
      DESCRIPTION
      "Timer of the R2 incoming side.
      Duration of metering pulse to be sent, in [msec].
      RW only when r2Mode=manual."
      ::= {r2CnfgEntry 16}

r2SeizeAckWait OBJECT-TYPE
      SYNTAX  Integer32  
      MAX-ACCESS  read-create
      STATUS  current
      DESCRIPTION
      "Timer of the R2 outgoing side.
      Minimum duration to receive seizure acknowledge signal, in [msec].
      RW only when r2Mode=manual."
      ::= {r2CnfgEntry 17}

r2SeizeAckDetect OBJECT-TYPE
      SYNTAX  Integer32  
      MAX-ACCESS  read-create
      STATUS  current
      DESCRIPTION
      "Timer of the R2 outgoing side.
      Minimum duration to recognize a valid seizure acknowledge signal, in [msec].
      RW only when r2Mode=manual."
      ::= {r2CnfgEntry 18}

r2AnswerDetect OBJECT-TYPE
      SYNTAX  Integer32  
      MAX-ACCESS  read-create
      STATUS  current
      DESCRIPTION
      "Timer of the R2 outgoing side.
      Minimum duration to recognize a valid answer signal, in [msec].
      RW only when r2Mode=manual."
      ::= {r2CnfgEntry 19}

r2BlockRemoveDetect OBJECT-TYPE
      SYNTAX  Integer32  
      MAX-ACCESS  read-create
      STATUS  current
      DESCRIPTION
      "Timer of the R2 outgoing side.
      Minimum duration to recognize a valid block removal signal, in [msec].
      RW only when r2Mode=manual."
      ::= {r2CnfgEntry 20}

r2MeterPulseDetect OBJECT-TYPE
      SYNTAX  Integer32  
      MAX-ACCESS  read-create
      STATUS  current
      DESCRIPTION
      "Timer of the R2 outgoing side.
      Minimum duration of incoming meter pulse, in [msec].
      RW only when r2Mode=manual."
      ::= {r2CnfgEntry 21}

r2ForcedDisconnect OBJECT-TYPE
      SYNTAX  Integer32  
      MAX-ACCESS  read-create
      STATUS  current
      DESCRIPTION
      "Timer of the R2 outgoing side.
      Minimum duration to recognize disconnect signal, in [msec].
      RW only when r2Mode=manual."
      ::= {r2CnfgEntry 22}

r2DisconnectAck OBJECT-TYPE
      SYNTAX  Integer32  
      MAX-ACCESS  read-create
      STATUS  current
      DESCRIPTION
      "Timer of the R2 outgoing side.
      Minimum duration to recognize disconnect acknowledge signal, in [msec].
      RW only when r2Mode=manual."
      ::= {r2CnfgEntry 23}

r2ReleaseGuardT1 OBJECT-TYPE
      SYNTAX  Integer32  
      MAX-ACCESS  read-create
      STATUS  current
      DESCRIPTION
      "Timer of the R2 outgoing side.
      Minimum duration to release guard, in [msec].
      During this time, no new call can be initiated.
      RW only when r2Mode=manual."
      ::= {r2CnfgEntry 24}

r2CnfgRowStatus OBJECT-TYPE
      SYNTAX  RowStatus  
      --active(1),
      --destroy(6)
      MAX-ACCESS  read-create
      STATUS  current
      DESCRIPTION
      "This object enables the user to add/delete entries to/from the table."
      ::= {r2CnfgEntry 25}


--The configuration parameters of the r2TsTable are defined per configuration, 
--per Profile, per TS (RW Table).

r2TsTable  OBJECT-TYPE
     SYNTAX SEQUENCE OF R2TsEntry
     MAX-ACCESS not-accessible
     STATUS  current
     DESCRIPTION
      "The write operation into the Table Objects is valid only
       to the TmpCnfg entry."
     ::= { r2ProfileCnfg 2}

r2TsEntry OBJECT-TYPE
    SYNTAX R2TsEntry
    MAX-ACCESS not-accessible
    STATUS current
	DESCRIPTION  "An entry in table."
	INDEX {r2TsCnfgIdx, r2TsProfileIdx, r2TsIdx}
      ::= { r2TsTable 1}

R2TsEntry ::=
      SEQUENCE {
      r2TsCnfgIdx          Integer32,
      r2TsProfileIdx       Integer32,
      r2TsIdx              Integer32,
      r2TsCallEnable       INTEGER,
	  r2TsMetering         INTEGER,
	  r2TsRowStatus        RowStatus,
	  r2TsReversePolarity  INTEGER
      }

r2TsCnfgIdx OBJECT-TYPE
      SYNTAX  Integer32 (1..255)
      MAX-ACCESS  read-only
      STATUS  current
      DESCRIPTION
      "This attribute indicates the Idx of the Cnfg being accessed.
       255 = TmpCnfg.
       1   = Current Cnfg. 
       Write is allowed only to TmpCnfg."
      ::= {r2TsEntry 1}

r2TsProfileIdx OBJECT-TYPE
      SYNTAX  Integer32
      MAX-ACCESS  read-only
      STATUS  current
      DESCRIPTION
      "Profile Index.
       Valid values: 1..5
       Only instances of profiles that are defined having agnSigProfType=r2Cas will
       exist in this table."
      ::= {r2TsEntry 2}

r2TsIdx OBJECT-TYPE
      SYNTAX  Integer32
      MAX-ACCESS  read-only
      STATUS  current
      DESCRIPTION
      "TS Index.
       Valid values: 1..31"
      ::= {r2TsEntry 3}

r2TsCallEnable OBJECT-TYPE
     SYNTAX  INTEGER
     {
       incoming      (2),
       outgoing      (3),
       both          (4)
     }
     MAX-ACCESS   read-create
     STATUS   current
     DESCRIPTION
     "This object indicates the Enabled Call direction for the specific TS."
     ::= {r2TsEntry 4}

r2TsMetering OBJECT-TYPE
     SYNTAX  INTEGER
     {
       no   (2),
       yes  (3)
     }
     MAX-ACCESS   read-create
     STATUS   current
     DESCRIPTION
     "This object indicates if the specific TS should support Metering."
     ::= {r2TsEntry 5}

r2TsRowStatus OBJECT-TYPE
      SYNTAX  RowStatus  
      --active(1),
      --destroy(6)
      MAX-ACCESS  read-create
      STATUS  current
      DESCRIPTION
      "This object enables the user to add/delete entries to/from the table."
      ::= {r2TsEntry 6}

r2TsReversePolarity OBJECT-TYPE
      SYNTAX  INTEGER
      {
       no   (2),
       yes  (3)
      }
      MAX-ACCESS   read-create
      STATUS   current
      DESCRIPTION
      "This object indicates if the specific TS should support Reverse Polarity."
      ::= {r2TsEntry 7}


--R2 Status table (RO) - TS Level, per Link
--
--The table is applicable only for E1 Links having an R2 Profile.

r2StatusTable  OBJECT-TYPE
     SYNTAX SEQUENCE OF R2StatusEntry
     MAX-ACCESS not-accessible
     STATUS  current
     DESCRIPTION
      "The write operation into the Table Objects is valid only
       to the TmpCnfg entry."
     ::= { r2IfStatus 1}

r2StatusEntry OBJECT-TYPE
      SYNTAX R2StatusEntry
      MAX-ACCESS not-accessible
      STATUS current
	DESCRIPTION  "An entry in table."
	INDEX {r2StatusSlotIdx, r2StatusPortIdx, r2StatusTsIdx}
      ::= { r2StatusTable 1}

R2StatusEntry ::=
      SEQUENCE {
      r2StatusSlotIdx       INTEGER,
      r2StatusPortIdx       Integer32,
      r2StatusTsIdx         Integer32,
      r2StatusSigDirection  INTEGER,
	  r2StatusTsState       INTEGER,
	  r2StatusProtocolState INTEGER
      }

r2StatusSlotIdx OBJECT-TYPE
      SYNTAX  INTEGER
      {
      io1   (5),
      io2   (6),
      io3   (7),
      io4   (8),
      io5   (9),
      io6  (10),
      io7  (11),
      io8  (12),
      io9  (13),
      io10 (14),
      io11 (15),
      io12 (16),
      notApplicable(255)
            }
      MAX-ACCESS  read-only
      STATUS  current
      DESCRIPTION
      "Slot Index"
      ::= {r2StatusEntry 1}

r2StatusPortIdx OBJECT-TYPE
      SYNTAX  Integer32
      MAX-ACCESS  read-only
      STATUS  current
      DESCRIPTION
      "This object indicates a unique  port number of the ML having 
       R2 interface.
       Valid values: exPrt1 (1)..exPrt4 (4)"
      ::= {r2StatusEntry 2}

r2StatusTsIdx OBJECT-TYPE
      SYNTAX  Integer32 (1..31)
      MAX-ACCESS   read-only
      STATUS   current
      DESCRIPTION
      "Time Slot index."
      ::= {r2StatusEntry 3}

r2StatusSigDirection OBJECT-TYPE
      SYNTAX  INTEGER 
      { 
      notApplicable (1),
      incoming      (2),
      outgoing      (3)
      }
      MAX-ACCESS   read-only
      STATUS   current
      DESCRIPTION
      "R2 Time Slot Signaling Direction."
      ::= {r2StatusEntry 4}

r2StatusTsState OBJECT-TYPE
      SYNTAX  INTEGER 
      { 
      notUsed       (1),
      normal        (2),
      remoteBlocked (3),
	  localBlocked  (4),
	  localLoop     (5),
	  remoteLoop    (6)
      }
      MAX-ACCESS   read-only
      STATUS   current
      DESCRIPTION
      "R2 TS State"
      ::= {r2StatusEntry 5}

r2StatusProtocolState OBJECT-TYPE
      SYNTAX  INTEGER 
      { 
      idle                (1),
      seized              (2),
      seizureAcknowledged (3),
	  answered            (4),
	  clearForward        (5),
	  clearBack           (6),
	  blocked             (7),
	  forcedDisc          (8),
	  doubleSeizure       (9),
	  fault              (10),
	  discAcknowledged   (11),
	  fault1             (12),
	  fault6             (13),
	  fault3             (14) 
      }
      MAX-ACCESS   read-only
      STATUS   current
      DESCRIPTION
      "R2 Protocol State."
      ::= {r2StatusEntry 6}

-- 
-- file :D:\Synergy\WorkArea\545\mib_rad\txt\layer2.txt
-- 
-- 
-- file: v:\doc\rdv\mib\ver495\atm\layer2.txt
-- 
--RTR-MIB  
--
--Last update: 25-Sep-2002
--By: Shay Harari 


-- ************************************************
-- Link Layer (layer 2)  MIB
-- ************************************************


atmLayer2  OBJECT IDENTIFIER  ::=  {radAtm 7}

 atmLayer2XVclTable OBJECT-TYPE
	SYNTAX SEQUENCE OF AtmLayer2XVclEntry
	MAX-ACCESS not-accessible
	STATUS current
	DESCRIPTION
    "This table is an extension of VCL table, which is created  
    for each LAN VCC."
	::= { atmLayer2 1 }

 atmLayer2XVclEntry OBJECT-TYPE
	SYNTAX AtmLayer2XVclEntry
	MAX-ACCESS not-accessible
	STATUS current
	DESCRIPTION
    "Conceptual row in atmVclTable.
    This table augments the RFC2515 VCL table."
 AUGMENTS { atmVclEntry }
	::= { atmLayer2XVclTable 1 }

 AtmLayer2XVclEntry ::= SEQUENCE {
	atmLayer2XVclConnMode       INTEGER,
    atmLayer2XVclGroupIdx       Integer32 
 }

 atmLayer2XVclConnMode OBJECT-TYPE
	SYNTAX INTEGER { 
	              main   (1), 
	              sub    (2) 
				   }
	MAX-ACCESS read-create
	STATUS current
	DESCRIPTION
    "Each valid LAN VCC is either Main or Sub. 
	This parameter is configured only once on creation of a LAN VCC.
	It can not be changed after creation. In order to change the Mode, 
	user should delete the connection and create a new one.
		  
    main - A LAN VCC, which holds its own bridge port. 
           Bridge forwarding and Bridge learning is performed only on Main 
	       VCCs.
	       For working on a transparent bridge, that doesn't perform
	       layer 2 priority mapping, a Main VCC should be opened, which 
		   is the default connection Mode. 
		   When working with layer 2 priority, a group of LAN VCCs should
		   be configured, where each group will be associated with only 
		   one Main VCC.
		   A specific Main can not be used by more than one group. 
	sub  - A LAN VCC is not part of the bridging mechanism. 
		   A Sub VCC automatically inherit some general definitions from
		   Main VCC of its group: ATM Slot/Port and LAN Slot/Port.
		   Max number of Sub VCCs allowed per group is:  
		   [Number of Priorities - 1]."
	::= { atmLayer2XVclEntry 1 }

 atmLayer2XVclGroupIdx OBJECT-TYPE
	SYNTAX Integer32
	MAX-ACCESS read-only
	STATUS current
	DESCRIPTION
	"The group identifier.
	A VCC Group identifier = 0 if the VCC was not associated with a 
	group yet.
	This value is updated according to the group identifier set by 
	atmLayer2GroupTable."
	::= { atmLayer2XVclEntry 2 }

 atmLayer2GroupTable OBJECT-TYPE
	SYNTAX SEQUENCE OF AtmLayer2GroupEntry
	MAX-ACCESS not-accessible
	STATUS current
	DESCRIPTION
	"This table contains groups and their members.
	A group is a bundle of VCCs, which acts as different queues.
	Main and Sub VCCs should have the same ATM slot and port,
	and the same LAN slot and port.
    Each group contains: 1 to <number of priorities> VCCs."
	::= { atmLayer2 2 }

 atmLayer2GroupEntry OBJECT-TYPE
	SYNTAX AtmLayer2GroupEntry
	MAX-ACCESS not-accessible
	STATUS current
	DESCRIPTION
	"Conceptual row in atmLayer2GroupTable.
	The indexes: ifIndex, atmVclVpi and atmVclVci indicate 
	the Network ATM End-Point.
	Upon a group creation, one Main VCC must be added first.
	After the group was created, Sub VCCs may be added to the group."
 INDEX { atmLayer2GroupIdx, ifIndex, atmVclVpi, atmVclVci }
	::= { atmLayer2GroupTable 1 }

 AtmLayer2GroupEntry ::= SEQUENCE {
    atmLayer2GroupIdx          Integer32, 
    atmLayer2GroupRowStatus    RowStatus, 
    atmLayer2GroupConnMode     INTEGER, 
    atmLayer2GroupConnPriority OCTET STRING,
    atmLayer2GroupName         SnmpAdminString 
 }

 atmLayer2GroupIdx OBJECT-TYPE
	SYNTAX Integer32
	MAX-ACCESS read-only
	STATUS current
	DESCRIPTION
	"The group identifier. 
	0 is not a valid index."
	::= { atmLayer2GroupEntry 1 }

 atmLayer2GroupRowStatus OBJECT-TYPE
	SYNTAX RowStatus
	MAX-ACCESS read-create
	STATUS current
	DESCRIPTION
	"Creation/Deletion of rows in the table, and indication of the 
	entry's status."
	::= {atmLayer2GroupEntry 2 }
 
 atmLayer2GroupConnMode OBJECT-TYPE
	SYNTAX INTEGER { 
	              main (1), 
	              sub  (2) 
				   }
	MAX-ACCESS read-only
	STATUS current
	DESCRIPTION
	"Each valid LAN VCC is either Main or Sub as configured in 
	atmLayer2XVclTable."
	::= { atmLayer2GroupEntry 3 }

 atmLayer2GroupConnPriority OBJECT-TYPE
    SYNTAX OCTET STRING (SIZE (1))
	MAX-ACCESS read-only
	STATUS current
	DESCRIPTION
	"This parameter is configured by atmLayer2PriorityRx from 
	atmLayer2PriorityTable.
	Each bit in the Octet represents a specific priority as follows:
		  
		                  
             MSB 7  6  5  4  3  2  1  0 LSB	  -> Priorities
                 |____________________|
                 1  0  0  1  0  0  0  1		  ->	  Value
		  
	In this example, a certain VCC has several priorities: 0, 4 and 7."
	::= { atmLayer2GroupEntry 4 }

 atmLayer2GroupName OBJECT-TYPE
	SYNTAX SnmpAdminString (SIZE (1..32))
	MAX-ACCESS read-create
	STATUS current
	DESCRIPTION
	"Group name. Configured by the user.
	The name is unique per system.
	For atmLayer2GroupIdx=0, the name will be null."
	::= { atmLayer2GroupEntry 5 }


 atmLayer2PriorityTable OBJECT-TYPE
	SYNTAX SEQUENCE OF AtmLayer2PriorityEntry
	MAX-ACCESS not-accessible
	STATUS current
	DESCRIPTION
	"This table maps all priorities inside a group.
	Several priorities might be mapped to the same VCC. 
	Upon priority change, the agent will update the VCCs of the 
	changed priority in this table, and will update	-
	atmLayer2GroupConnPriority parameter of both former and new owners 
	of the changed priority.
	Changing a VCC value is actually a change of three parameters
	simultaneously: atmLayer2PriorityIfIndex, atmLayer2PriorityVclVpi
	and atmLayer2PriorityVclVci. Otherwise, the set will be rejected,
	since there might be that such VCC doesn't exist in the specific
	group."
	::= { atmLayer2 3 }

 atmLayer2PriorityEntry OBJECT-TYPE
	SYNTAX AtmLayer2PriorityEntry
	MAX-ACCESS not-accessible
	STATUS current
	DESCRIPTION
	"Conceptual row in atmLayer2PriorityTable.
	Each entry is a Network ATM End-Point per priority.
	Upon a group creation, all priorities are mapped to the Main VCC. 
	Number of entries per group is according to the number of 
	priorities enabled. (For example, for Max priorities = 8,  
	the agent will create 8 entries)."
    INDEX { atmLayer2PriorityGroupIdx, atmLayer2PriorityRx }
	::= { atmLayer2PriorityTable 1 }

 AtmLayer2PriorityEntry ::= SEQUENCE {
    atmLayer2PriorityGroupIdx        Integer32, 
    atmLayer2PriorityRx              Integer32, 
	atmLayer2PriorityIfIndex	     InterfaceIndex,
    atmLayer2PriorityVclVpi          Integer32,
    atmLayer2PriorityVclVci          Integer32        
 }

 atmLayer2PriorityGroupIdx OBJECT-TYPE
	SYNTAX Integer32
	MAX-ACCESS read-only
	STATUS current
	DESCRIPTION
	"The group identifier." 
	::= { atmLayer2PriorityEntry 1 }

 atmLayer2PriorityRx OBJECT-TYPE
	SYNTAX Integer32 (1..8)
	MAX-ACCESS read-only
	STATUS current
	DESCRIPTION
	"The priority values.
	The used values are 0-7, but since this value is part of the index
	of the table, and in order to avoid '0' as an index, the index syntax 
	is 1..8, but the real value is atmLayer2PriorityRx-1: 
		  0 - for Low priority. 
		  7 - for High priority."
	::= { atmLayer2PriorityEntry 2 }

 atmLayer2PriorityIfIndex OBJECT-TYPE
	SYNTAX InterfaceIndex
	MAX-ACCESS read-create
	STATUS current
	DESCRIPTION
	"ATM ifIndex of the network End-Point."
	::= { atmLayer2PriorityEntry 3 }
 
 atmLayer2PriorityVclVpi OBJECT-TYPE
	SYNTAX Integer32
	MAX-ACCESS read-create
	STATUS current
	DESCRIPTION
	"Vpi of the network End-Point."
	::= { atmLayer2PriorityEntry 4 }

 atmLayer2PriorityVclVci OBJECT-TYPE
	SYNTAX Integer32
	MAX-ACCESS read-create
	STATUS current
	DESCRIPTION
	"Vci of the network End-Point."
	::= { atmLayer2PriorityEntry 5 }

atmLayer2GroupIndexNext  OBJECT-TYPE
          SYNTAX         Integer32 (0..2147483647)
          MAX-ACCESS     read-only
          STATUS         current
          DESCRIPTION
           "This object contains an appropriate value to
            be used for atmLayer2GroupIdx when creating
            entries in the atmLayer2GroupTable. The value
            0 indicates that no unassigned entries are
            available. To obtain the atmLayer2GroupIdx
            value for a new entry, the manager gets 
            the current value of this object. The next index
            will be of the first unassigned entry. It will be 
            provided by checking the assigned entries."
          ::= { atmLayer2 4 }

--VLAN
 atmLayer2CfgTable OBJECT-TYPE
	SYNTAX SEQUENCE OF AtmLayer2CfgEntry
	MAX-ACCESS not-accessible
	STATUS current
	DESCRIPTION
	"Bridge configuration Table. This table supports multi-bridge 
	and bridge features within an ATM device."
	::= { atmLayer2 5 }

 atmLayer2CfgEntry OBJECT-TYPE
	SYNTAX AtmLayer2CfgEntry
	MAX-ACCESS not-accessible
	STATUS current
	DESCRIPTION
	"Conceptual row in atmLayer2CfgTable.
	Each entry in this table contains the bridging attributes for
	both Ethernet and ATM sides.
	The interface index is the Ethernet port interface.

	For Ace52: this object represents the Bridge ifIndex."
 INDEX { ifIndex }
	::= { atmLayer2CfgTable 1 }

 AtmLayer2CfgEntry ::= SEQUENCE {
    atmLayer2CfgBridgingMode            INTEGER, 
    atmLayer2CfgVlanMode                INTEGER, 
    atmLayer2CfgAtmAcceptableFrameType  INTEGER,
    atmLayer2CfgAtmIngressFiltering     TruthValue,
    atmLayer2CfgAtmTxFrameType          INTEGER,
    atmLayer2CfgEthAcceptableFrameType  INTEGER,
    atmLayer2CfgBridgeAction            INTEGER,
    atmLayer2CfgLearningMode            INTEGER,
	atmLayer2CfgAgingTime               Integer32	
 }

 atmLayer2CfgBridgingMode OBJECT-TYPE
               SYNTAX  INTEGER {
                       accessOnly(1),
                       accessAndSwitching (2)
               }
 	           MAX-ACCESS  read-write
               STATUS  current
               DESCRIPTION
               "Bridging mode can be one of the following: 
	            ATM <> Ethernet - Bridging is between the Ethernet 
	            port and the ATM port (there is no bridging between VCs).
	            ATM <> Ethernet + ATM - Bridging is done both between 
	            the Ethernet port and the ATM port and also between VCs."
	::= { atmLayer2CfgEntry 1 }

 atmLayer2CfgVlanMode OBJECT-TYPE
               SYNTAX  INTEGER {
                       disable   (2),
                       enable    (3)
               }
 	           MAX-ACCESS  read-write
               STATUS  current
               DESCRIPTION
               "VLAN Mode. Upon Mode changing, all LAN VCCs will be deleted
               by the agent from all tables that include LAN VCCs."
	::= { atmLayer2CfgEntry 2 }
 
 atmLayer2CfgAtmAcceptableFrameType OBJECT-TYPE
	SYNTAX INTEGER { 
	              notApplicable       (1),
	              admitAll            (2), 
	              admitOnlyVlanTagged (3), 
	              admitOnlyUnTagged   (4) 
				   }
 	           MAX-ACCESS  read-write
               STATUS  current
               DESCRIPTION
               "The Frame Type that will be acceptable by the VCCs that 
               are associated with this Ethernet port.
               Frames which don't match the selected type will be discarded.
                
               admitAll -            all frames will be accepted.
               admitOnlyVlanTagged - only Tagged frames will be accepted.
               admitOnlyUnTagged   - only unTagged frames will be accepted."
	::= { atmLayer2CfgEntry 3 }

 atmLayer2CfgAtmIngressFiltering OBJECT-TYPE
              SYNTAX      TruthValue
              MAX-ACCESS  read-write
              STATUS      current
              DESCRIPTION
              "For the VCCs that are associated with this Ethernet port, 
              when this is true(1) the device will discard incoming
              frames for VLANs which do not include this Port in its
              Member set.  When false(2), the port will accept all
              incoming frames."
	::= { atmLayer2CfgEntry 4 }

 atmLayer2CfgAtmTxFrameType OBJECT-TYPE
	SYNTAX INTEGER { 
	              notApplicable(1),
	              unTagged (2), 
	              tagged   (3) 
				   }
 	           MAX-ACCESS  read-write
               STATUS  current
               DESCRIPTION
               "The Frame Type that will be transmitted by the VCCs that 
               are associated with this Ethernet port. 
               
               unTagged -      The transmitted frames will be unTagged.
               tagged -        The transmitted frames will be Tagged."
	::= { atmLayer2CfgEntry 5 }

 atmLayer2CfgEthAcceptableFrameType OBJECT-TYPE
	SYNTAX INTEGER { 
	              notApplicable       (1),
	              admitAll            (2), 
	              admitOnlyVlanTagged (3), 
	              admitOnlyUnTagged   (4) 
				   }
 	           MAX-ACCESS  read-write
               STATUS  current
               DESCRIPTION
               "The Frame Type that this Ethernet port will accept.
			   (for ACE-52: the Frame Type that this Bridge will accept)
			   This parameter is notApplicable for atmLayer2VlanMode=disable.
               Frames which don't match the selected type will be discarded.
                
               admitAll -            all frames will be accepted.
               admitOnlyVlanTagged - only Tagged frames will be accepted.
               admitOnlyUnTagged -   only unTagged frames will be accepted."
	::= { atmLayer2CfgEntry 6 }

 atmLayer2CfgBridgeAction OBJECT-TYPE
    SYNTAX  INTEGER {
       deleteLanTable   (7),
	   noOp             (255)
     }
    MAX-ACCESS  read-write
    STATUS  current
    DESCRIPTION
	"This object enables to perform the	specified action on the 
	selected port."
	::= { atmLayer2CfgEntry 7 }

 atmLayer2CfgLearningMode OBJECT-TYPE
    SYNTAX  INTEGER {
       svl   (1),
       ivl   (2)
     }
    MAX-ACCESS  read-write
    STATUS  current
    DESCRIPTION
	"This object specifies the mode of the learning process of a bridge.
	svl - Shared VLAN process. If an individual MAC Address is learned 
	      in one VLAN, this information is used in forwarding decisions
	      taken for that address for all other VLANs.
	ivl - Independent VLAN process. If an individual MAC Address is learned 
	      in one VLAN, this information is not used in forwarding decisions
	      taken for that address for all other VLANs."
	::= { atmLayer2CfgEntry 8 }

atmLayer2CfgAgingTime OBJECT-TYPE
    SYNTAX Integer32 
    MAX-ACCESS  read-write
    STATUS      current
    DESCRIPTION
    "The timeout period in seconds for aging out
     dynamically learned forwarding information."
    ::= { atmLayer2CfgEntry 9 }
-- 
-- file :D:\Synergy\WorkArea\545\mib_rad\txt\fratm.txt
-- 
-- 
-- file: v:\doc\rdv\mib\ver470\atm\frAtm.txt
-- 
--FR-ATM-IWF-X-MIB  
--
--Last update: 28-Feb-2001
--By: Ilana Schvetz 

 
--atmSuPortFr     OBJECT IDENTIFIER ::= { atmSuPort 4 }
radAtmFr  OBJECT IDENTIFIER  ::=  {radAtm 8}
 
 frAtmIwfXConnectionTable OBJECT-TYPE
	SYNTAX SEQUENCE OF FrAtmIwfXConnectionEntry
	MAX-ACCESS not-accessible
	STATUS current
	DESCRIPTION
    "This table is an extension of frAtmIwfXConnectionTable from
    RFC2955."
	::= { radAtmFr 1 }

 frAtmIwfXConnectionEntry OBJECT-TYPE
	SYNTAX FrAtmIwfXConnectionEntry
	MAX-ACCESS not-accessible
	STATUS current
	DESCRIPTION
    "Conceptual row in frAtmIwfXConnectionTable.
    This table augments the RFC2955."
 AUGMENTS { frAtmIwfConnectionEntry }
	::= { frAtmIwfXConnectionTable 1 }

 FrAtmIwfXConnectionEntry ::= SEQUENCE {
                 frAtmIwfXConnMode         INTEGER,
                 frAtmIwfXConnSscsDlci     Integer32
 }

         frAtmIwfXConnMode OBJECT-TYPE
             SYNTAX      INTEGER { service(1), network(2) }
             MAX-ACCESS  read-create
             STATUS      current
             DESCRIPTION
                     "FR IWF Mode. 
                     service - Service InterWorking (FRF.8),
                     network - Network InterWorking (FRF.5)."
	         ::= { frAtmIwfXConnectionEntry 1 }

         frAtmIwfXConnSscsDlci OBJECT-TYPE
             SYNTAX      Integer32
             MAX-ACCESS  read-create
             STATUS      current
             DESCRIPTION
                     "This parameter is relevant for 
                     frAtmIwfXConnMode=network (FRF.5) only.
                     This parameter allow configuration of the 
                     FR SSCS DLCI that is transferred to the 
                     remote FR unit."
	         ::= { frAtmIwfXConnectionEntry 2 }

-- 
-- file :D:\Synergy\WorkArea\545\mib_rad\txt\radaal5.txt
-- 
-- 
-- file :v:\doc\rdv\mib\ver495\atm\radaal5.txt
-- 
--Last update: 19-Nov-2002 by Ilana Schvetz


--     ATM-X-MIB DEFINITIONS ::= BEGIN
--
--atmGen  OBJECT IDENTIFIER  ::=  {radAtm 2}

--atmPerfHistory  OBJECT IDENTIFIER  ::=  {atmGen 1}

--atmIfPerformance  OBJECT IDENTIFIER  ::=  {atmPerfHistory 1}

     -- AAL5 Virtual Channel Connection Performance Statistics

     -- Table

     -- This table contains the AAL5 extension
     -- performance statistics of a VCC at the
     -- interface associated with an AAL5 entity in an ATM
     -- host or ATM switch.

     aal5VccXTable        OBJECT-TYPE
          SYNTAX         SEQUENCE OF Aal5VccXEntry
          MAX-ACCESS     not-accessible
          STATUS         current
          DESCRIPTION
           "This table is an extension to AAL5 VCC Table."
          ::= { atmIfPerformance 4 }

     aal5VccXEntry        OBJECT-TYPE
          SYNTAX         Aal5VccXEntry
          MAX-ACCESS     not-accessible
          STATUS         current
          DESCRIPTION
           "This list contains the additional AAL5 VCC
            performance parameters and is indexed
            by ifIndex values of AAL5 interfaces
            and the associated VPI/VCI values."
          AUGMENTS { aal5VccEntry }
          ::= { aal5VccXTable 1 }

     Aal5VccXEntry    ::= SEQUENCE  {
          aal5VccInFrames     Counter32,
          aal5VccOutFrames    Counter32,
		  aal5VccUnknownProtocolFrames	 Counter32
               }

     aal5VccInFrames  OBJECT-TYPE
          SYNTAX         Counter32
          MAX-ACCESS     read-only
          STATUS         current
          DESCRIPTION
           "The number of frames received via this interface."
          ::= { aal5VccXEntry 1 }

     aal5VccOutFrames OBJECT-TYPE
          SYNTAX         Counter32
          MAX-ACCESS     read-only
          STATUS         current
          DESCRIPTION
           "The total number of frames transmitted out of the
           interface."
          ::= { aal5VccXEntry 2 }

    aal5VccUnknownProtocolFrames OBJECT-TYPE
          SYNTAX         Counter32
          MAX-ACCESS     read-only
          STATUS         current
          DESCRIPTION
           "The number of frames that were discarded due to unsupported
            protocol encapsulation on this VCC."
          ::= { aal5VccXEntry 3 }


     aal5VccCurrentTable        OBJECT-TYPE
          SYNTAX         SEQUENCE OF Aal5VccCurrentEntry
          MAX-ACCESS     not-accessible
          STATUS         current
          DESCRIPTION
           "The AAL5 Current table."
          ::= { atmIfPerformance 5 }

     aal5VccCurrentEntry        OBJECT-TYPE
          SYNTAX         Aal5VccCurrentEntry
          MAX-ACCESS     not-accessible
          STATUS         current
          DESCRIPTION
           "An entry in the AAL5 Current table."
          INDEX { ifIndex, aal5VccVpi, aal5VccVci }
           ::= { aal5VccCurrentTable 1 }

     Aal5VccCurrentEntry    
     ::= SEQUENCE  {
          aal5VccCurrentInFrames     
             Gauge32,
          aal5VccCurrentOutFrames    
             Gauge32,
		  aal5VccCurrentUnknownProtocolFrames	 
		     Gauge32,
		  aal5VccCurrentCrcErrors	 
		     Gauge32,
		  aal5VccCurrentLengthError	 
		     Gauge32,
		  aal5VccCurrentInputCongestionDropped
			 Gauge32,
		  aal5VccCurrentOutputCongestionDropped
			 Gauge32
               }

aal5VccCurrentInFrames OBJECT-TYPE
      SYNTAX      Gauge32
      MAX-ACCESS  read-only
      STATUS      current
      DESCRIPTION
	  "The counter associated with the number of received frames, 
	  encountered by the AAL5 interface in the current 15 minute 
	  interval."
    ::= { aal5VccCurrentEntry 1 }

aal5VccCurrentOutFrames OBJECT-TYPE
      SYNTAX  Gauge32  
      MAX-ACCESS  read-only
      STATUS  current
      DESCRIPTION
	  "The counter associated with the number of transmitted frames, 
	  encountered by the AAL5 interface in the current 15 minute 
	  interval."
      ::= { aal5VccCurrentEntry 2 }

aal5VccCurrentUnknownProtocolFrames OBJECT-TYPE
      SYNTAX  Gauge32  
      MAX-ACCESS  read-only
      STATUS  current
      DESCRIPTION
	  "The counter associated with the number of frames that were 
	  discarded due to unsupported protocol encapsulation, 
	  encountered by the AAL5 interface in the current 15 minute 
	  interval."
      ::= { aal5VccCurrentEntry 3 }

aal5VccCurrentCrcErrors OBJECT-TYPE
      SYNTAX  Gauge32  
      MAX-ACCESS  read-only
      STATUS  current
      DESCRIPTION
	  "The counter associated with the number of AAL5 CPCS PDUs 
	  received with	CRC-32 errors, encountered by the AAL5 
	  interface in the current 15 minute interval."
      ::= { aal5VccCurrentEntry 4 }

aal5VccCurrentLengthError OBJECT-TYPE
      SYNTAX  Gauge32  
      MAX-ACCESS  read-only
      STATUS  current
      DESCRIPTION
	  "The counter associated with the number of received frames 
	  with length error, encountered by the AAL5 interface in the 
	  current 15 minute interval."
      ::= { aal5VccCurrentEntry 5 }

aal5VccCurrentInputCongestionDropped OBJECT-TYPE
      SYNTAX  Gauge32  
      MAX-ACCESS  read-only
      STATUS  current
      DESCRIPTION
	  "The counter associated with the number of 
	   dropped frames due to congestion, encountered by 
	   the AAL5 interface on the Receive direction 
	   in the current 15 minute interval."
      ::= { aal5VccCurrentEntry 6 }

aal5VccCurrentOutputCongestionDropped OBJECT-TYPE
      SYNTAX  Gauge32  
      MAX-ACCESS  read-only
      STATUS  current
      DESCRIPTION
	  "The counter associated with the number of 
	   dropped frames due to congestion, encountered by 
	   the AAL5 interface on the Transmit direction 
	   in the current 15 minute interval."
      ::= { aal5VccCurrentEntry 7 }


-- Interval Table 
 
     aal5VccIntervalTable        OBJECT-TYPE
          SYNTAX         SEQUENCE OF Aal5VccIntervalEntry
          MAX-ACCESS     not-accessible
          STATUS         current
          DESCRIPTION
           "The AAL5 Interval table."
          ::= { atmIfPerformance 6 }

     aal5VccIntervalEntry        OBJECT-TYPE
          SYNTAX         Aal5VccIntervalEntry
          MAX-ACCESS     not-accessible
          STATUS         current
          DESCRIPTION
           "An entry in the AAL5 Interval table."
          INDEX { ifIndex, aal5VccVpi, aal5VccVci, aal5VccIntervalNumber }
           ::= { aal5VccIntervalTable 1 }

     Aal5VccIntervalEntry    
     ::= SEQUENCE  {
          aal5VccIntervalNumber     
             Integer32,
          aal5VccIntervalInFrames     
             Gauge32,
          aal5VccIntervalOutFrames    
             Gauge32,
		  aal5VccIntervalUnknownProtocolFrames	 
		     Gauge32,
		  aal5VccIntervalCrcErrors	 
		     Gauge32,
		  aal5VccIntervalLengthError	 
		     Gauge32,
		  aal5VccIntervalInputCongestionDropped
			 Gauge32,
		  aal5VccIntervalOutputCongestionDropped
			 Gauge32
               }

aal5VccIntervalNumber OBJECT-TYPE
    SYNTAX  Integer32 (1..96)
    MAX-ACCESS  read-only
    STATUS  current
    DESCRIPTION
        "A number between 1 and 96, where 1 is the most
         recently completed 15 minute interval and 96 is
         the least recently completed 15 minutes interval
         (assuming that all 96 intervals exist)."
    ::= { aal5VccIntervalEntry 1 }


aal5VccIntervalInFrames OBJECT-TYPE
      SYNTAX      Gauge32
      MAX-ACCESS  read-only
      STATUS      current
      DESCRIPTION
	  "The counter associated with the number of received frames, 
	  encountered by the AAL5 interface in one of the previous 
	  96, individual 15 minute, intervals."
    ::= { aal5VccIntervalEntry 2 }

aal5VccIntervalOutFrames OBJECT-TYPE
      SYNTAX  Gauge32  
      MAX-ACCESS  read-only
      STATUS  current
      DESCRIPTION
	  "The counter associated with the number of transmitted frames, 
	  encountered by the AAL5 interface in in one of the previous 
	  96, individual 15 minute, intervals."
      ::= { aal5VccIntervalEntry 3 }

aal5VccIntervalUnknownProtocolFrames OBJECT-TYPE
      SYNTAX  Gauge32  
      MAX-ACCESS  read-only
      STATUS  current
      DESCRIPTION
	  "The counter associated with the number of frames that were 
	  discarded due to unsupported protocol encapsulation, 
	  encountered by the AAL5 interface in one of the previous 
	  96, individual 15 minute, intervals."
      ::= { aal5VccIntervalEntry 4 }

aal5VccIntervalCrcErrors OBJECT-TYPE
      SYNTAX  Gauge32  
      MAX-ACCESS  read-only
      STATUS  current
      DESCRIPTION
	  "The counter associated with the number of AAL5 CPCS PDUs 
	  received with	CRC-32 errors, encountered by the AAL5 
	  interface in one of the previous 96, individual 15 minute, 
	  intervals."
      ::= { aal5VccIntervalEntry 5 }

aal5VccIntervalLengthError OBJECT-TYPE
      SYNTAX  Gauge32  
      MAX-ACCESS  read-only
      STATUS  current
      DESCRIPTION
	  "The counter associated with the number of received frames 
	  with length error, encountered by the AAL5 interface in one 
	  of the previous 96, individual 15 minute, intervals."
      ::= { aal5VccIntervalEntry 6 }

aal5VccIntervalInputCongestionDropped OBJECT-TYPE
      SYNTAX  Gauge32  
      MAX-ACCESS  read-only
      STATUS  current
      DESCRIPTION
	  "The counter associated with the number of dropped frames 
	  due to a congestion, encountered by the AAL5 interface on 
	  the Receive direction in one of the previous 96, individual 
	  15 minute, intervals"
      ::= { aal5VccIntervalEntry 7 }

aal5VccIntervalOutputCongestionDropped OBJECT-TYPE
      SYNTAX  Gauge32  
      MAX-ACCESS  read-only
      STATUS  current
      DESCRIPTION
	  "The counter associated with the number of dropped frames 
	  due to a congestion, encountered by the AAL5 interface on 
	  the Transmit direction in one of the previous 96, individual 
	  15 minute, intervals"
      ::= { aal5VccIntervalEntry 8 }


-- END

-- 
-- file :D:\Synergy\WorkArea\545\mib_rad\txt\atmCes.txt
-- 
-- 
-- File: v:\doc\rdv\mib\ver485\atm\atmCes.txt
-- Date:      17/01/02
-- By:        Ilana Schvetz

-- Last Update: 17-Jan-02 By Ilana Schvetz
-- 
-- AAL1 statistics. An addition to ATMF-CES (ces.mib) 
--
 
atmCes OBJECT IDENTIFIER  ::=  {radAtm 9}
 
atmCesPerformance      OBJECT IDENTIFIER ::= {atmCes 1 }

atmCesAal1CurrentTable OBJECT-TYPE
      SYNTAX  SEQUENCE OF AtmCesAal1CurrentEntry
      MAX-ACCESS   not-accessible
      STATUS  current
      DESCRIPTION
         "The AAL1 Current table."
      ::= { atmCesPerformance 1 }

atmCesAal1CurrentEntry OBJECT-TYPE
      SYNTAX  AtmCesAal1CurrentEntry
      MAX-ACCESS  not-accessible
      STATUS  current
      DESCRIPTION
         "An entry in the AAL1 Current table."
      INDEX   { atmCesAal1CurrentIfIndex }
      ::= { atmCesAal1CurrentTable 1 }

AtmCesAal1CurrentEntry ::=
      SEQUENCE {
      atmCesAal1CurrentIfIndex
           Integer32,
      atmCesAal1CurrentSeqErrors
      	   Gauge32,
      atmCesAal1CurrentHdrErrors
           Gauge32,
      atmCesAal1CurrentPointerReframes
           Gauge32,
      atmCesAal1CurrentBufUnderflows
           Gauge32,
      atmCesAal1CurrentBufOverflows
           Gauge32
      }

atmCesAal1CurrentIfIndex OBJECT-TYPE
      SYNTAX      Integer32
      MAX-ACCESS  read-only
      STATUS      current
      DESCRIPTION
        "The index of the AAL1 interface. 
        It may be ifIndex."
    ::= { atmCesAal1CurrentEntry 1 }

atmCesAal1CurrentSeqErrors OBJECT-TYPE
      SYNTAX  Gauge32  
      MAX-ACCESS  read-only
      STATUS  current
      DESCRIPTION
	  "The counter associated with the number of Discarded 
        cells due to wrong sequence number, encountered 
        by an AAL1 interface in the current 15 minute interval."
      ::= { atmCesAal1CurrentEntry 2 }

atmCesAal1CurrentHdrErrors OBJECT-TYPE
      SYNTAX  Gauge32  
      MAX-ACCESS  read-only
      STATUS  current
      DESCRIPTION
	  "The counter associated with the number of Discarded 
        cells due to bad AAL1 header error (including correctable 
        and uncorrectable CRC, and bad parity), encountered 
        by an AAL1 interface in the current 15 minute interval."
      ::= { atmCesAal1CurrentEntry 3 }

atmCesAal1CurrentPointerReframes OBJECT-TYPE
      SYNTAX  Gauge32  
      MAX-ACCESS  read-only
      STATUS  current
      DESCRIPTION
	  "The counter associated with the number of events in 
	  which a SDT pointer isn't where it is expected to be, 
	  and must be reacquired, encountered by an AAL1 interface 
	  in the current 15 minute interval."
      ::= { atmCesAal1CurrentEntry 4 }

atmCesAal1CurrentBufUnderflows OBJECT-TYPE
      SYNTAX  Gauge32  
      MAX-ACCESS  read-only
      STATUS  current
      DESCRIPTION
	  "The counter associated with the number of buffer 
	  underflow events, encountered by an AAL1 interface 
	  in the current 15 minute interval."
      ::= { atmCesAal1CurrentEntry 5 }

atmCesAal1CurrentBufOverflows OBJECT-TYPE
      SYNTAX  Gauge32  
      MAX-ACCESS  read-only
      STATUS  current
      DESCRIPTION
	  "The counter associated with the number of buffer 
	  overflow events, encountered by an AAL1 interface 
	  in the current 15 minute interval."
      ::= { atmCesAal1CurrentEntry 6 }


--Interval Table


atmCesAal1IntervalTable OBJECT-TYPE
      SYNTAX  SEQUENCE OF AtmCesAal1IntervalEntry
      MAX-ACCESS   not-accessible
      STATUS  current
      DESCRIPTION
         "The AAL1 Interval table."
      ::= { atmCesPerformance 2 }

atmCesAal1IntervalEntry OBJECT-TYPE
      SYNTAX  AtmCesAal1IntervalEntry
      MAX-ACCESS  not-accessible
      STATUS  current
      DESCRIPTION
         "An entry in the AAL1 Interval table."
              INDEX   { atmCesAal1IntervalIfIndex, atmCesAal1IntervalNumber }
              ::= { atmCesAal1IntervalTable 1 }

AtmCesAal1IntervalEntry ::=
      SEQUENCE {
      atmCesAal1IntervalIfIndex
           Integer32,
      atmCesAal1IntervalNumber
           Integer32,
      atmCesAal1IntervalSeqErrors
      	   Gauge32,
      atmCesAal1IntervalHdrErrors
           Gauge32,
      atmCesAal1IntervalPointerReframes
           Gauge32,
      atmCesAal1IntervalBufUnderflows
           Gauge32,
      atmCesAal1IntervalBufOverflows
           Gauge32
      }


atmCesAal1IntervalIfIndex OBJECT-TYPE
    SYNTAX      Integer32
    MAX-ACCESS  read-only
    STATUS      current
    DESCRIPTION
        "The index of the AAL1 interface. 
        It may be ifIndex."
    ::= { atmCesAal1IntervalEntry 1 }

atmCesAal1IntervalNumber OBJECT-TYPE
    SYNTAX  Integer32 (1..96)
    MAX-ACCESS  read-only
    STATUS  current
    DESCRIPTION
        "A number between 1 and 96, where 1 is the most
         recently completed 15 minute interval and 96 is
         the least recently completed 15 minutes interval
         (assuming that all 96 intervals exist)."
    ::= { atmCesAal1IntervalEntry 2 }

atmCesAal1IntervalSeqErrors OBJECT-TYPE
      SYNTAX  Gauge32  
      MAX-ACCESS  read-only
      STATUS  current
      DESCRIPTION
	  "The counter associated with the number of Discarded 
        cells due to wrong sequence number, encountered 
        by an AAL1 interface in one of the previous 96, 
        individual 15 minute, intervals."
      ::= { atmCesAal1IntervalEntry 3 }

atmCesAal1IntervalHdrErrors OBJECT-TYPE
      SYNTAX  Gauge32  
      MAX-ACCESS  read-only
      STATUS  current
      DESCRIPTION
	  "The counter associated with the number of Discarded 
        cells due to bad AAL1 header error (including correctable 
        and uncorrectable CRC, plus bad parity), encountered 
        by an AAL1 interface in one of the previous 96, 
        individual 15 minute, intervals."
      ::= { atmCesAal1IntervalEntry 4 }

atmCesAal1IntervalPointerReframes OBJECT-TYPE
      SYNTAX  Gauge32  
      MAX-ACCESS  read-only
      STATUS  current
      DESCRIPTION
	  "The counter associated with the number of events in 
	  which a SDT pointer isn't where it is expected to be, 
	  and must be reacquired, encountered by an AAL1 interface 
	  in one of the previous 96, individual 15 minute, 
	  intervals."
      ::= { atmCesAal1IntervalEntry 5 }

atmCesAal1IntervalBufUnderflows OBJECT-TYPE
      SYNTAX  Gauge32  
      MAX-ACCESS  read-only
      STATUS  current
      DESCRIPTION
	  "The counter associated with the number of buffer 
	  underflow events, encountered by an AAL1 interface 
	  in one of the previous 96, individual 15 minute, 
	  intervals."
      ::= { atmCesAal1IntervalEntry 6 }

atmCesAal1IntervalBufOverflows OBJECT-TYPE
      SYNTAX  Gauge32  
      MAX-ACCESS  read-only
      STATUS  current
      DESCRIPTION
	  "The counter associated with the number of buffer 
	  overflow events, encountered by an AAL1 interface 
	  in one of the previous 96, individual 15 minute, 
	  intervals."
      ::= { atmCesAal1IntervalEntry 7 }


-- Extension for CES Configuration Table

atmCesConfiguration      OBJECT IDENTIFIER ::= {atmCes 2 }


 atmCesXConfTable OBJECT-TYPE
	SYNTAX SEQUENCE OF AtmCesXConfEntry
	MAX-ACCESS not-accessible
	STATUS current
	DESCRIPTION
    "This table is an extension of atmfCESConfTable table."
	::= { atmCesConfiguration 1 }

 atmCesXConfEntry OBJECT-TYPE
	SYNTAX AtmCesXConfEntry
	MAX-ACCESS not-accessible
	STATUS current
	DESCRIPTION
    "Conceptual row in atmfCESConfTable.
     A new row is created in this table upon each new CES VCC creation."
 AUGMENTS { atmfCESConfEntry }
	::= { atmCesXConfTable 1 }

 AtmCesXConfEntry ::= SEQUENCE {
	atmCesXConfCBRMode       INTEGER
 }

 atmCesXConfCBRMode     OBJECT-TYPE
    SYNTAX        INTEGER {
                      normal (2),
                      spaced (3)
                      }
    MAX-ACCESS    read-create
    STATUS        current
    DESCRIPTION
        "This parameter defines if to use Spaced or Normal CBR.  

         Normal - TD will be allocated from the policing range (described 
                  in ACE2002 NMS SRS). The PCR is expanded with a constant 
                  value of 30 cell/sec.
         Spaced - TD will be allocated from the spacing range (described 
                  in ACE2002 NMS SRS). The PCR and CDVT will be expanded 
                  as described for Normal, and the CES traffic including
                  the OAM will be spaced out at the TD's PCR.
                  This mode is used to prevent CDVT violation due to OAM 
                  cell insertion with the CES traffic."
    ::= { atmCesXConfEntry 1 }
-- 
-- file :D:\Synergy\WorkArea\545\mib_rad\txt\radadsl.txt
-- 
--Version:   1.0
--Date:     27.03.2001              
--By:       Yig'al Hachmon
--File:     ADSL.txt
--
--Last Update: Yig'al Hachmon 21-May-2008
--ADSL configuration

--wanGen   OBJECT IDENTIFIER ::= {radWan 1}
--diverseIfWanGen OBJECT IDENTIFIER ::= {wanGen 6} (see mpmx.txt)
adslIf OBJECT IDENTIFIER ::= {diverseIfWanGen 10} 


adslConfTable OBJECT-TYPE
    SYNTAX SEQUENCE OF AdslConfEntry
    MAX-ACCESS not-accessible
    STATUS current
    DESCRIPTION
     "A list of ADSL Configuration entries "
    ::= { adslIf 1 }

adslConfEntry OBJECT-TYPE
    SYNTAX  AdslConfEntry
    MAX-ACCESS  not-accessible
    STATUS  current
    DESCRIPTION
     "An entry in adslConfTable"
    INDEX   { adslConfCnfgIdx,ifIndex }
    ::= { adslConfTable 1 }

AdslConfEntry ::=
   SEQUENCE {
    adslConfCnfgIdx				    Integer32,
    adslConfFramingType	            INTEGER,
    adslConfPilotToneRequest		INTEGER,
    adslConfTrellisCoding 			INTEGER,
    adslConfTransmissionMode 		INTEGER,
    adslConfStandardCompliance 	    INTEGER,
    adslConfMaxBitPerBin 			Integer32,
    adslConfTxStartFreqBin 	        Integer32,
    adslConfTxEndFreqBin   	        Integer32,
    adslConfRxStartFreqBin 	        Integer32,
    adslConfRxEndFreqBin   	        Integer32,
    adslConfTxPowerAttenuation      Integer32,
    adslConfPSDMask                 INTEGER,
	adslConfCommand					INTEGER
             }

adslConfCnfgIdx      OBJECT-TYPE
     SYNTAX  Integer32 (1..255)
     MAX-ACCESS  read-only
     STATUS  current
     DESCRIPTION
      "This object indicates the Idx of the Config being accessed.
       Idx of 255 relates to the Temporary (Scratch) Config.
       For products that support several configurations, 
       Set can be performed only to the Temporary Config (=255). "
     ::= { adslConfEntry 1}



adslConfFramingType	 OBJECT-TYPE
    SYNTAX INTEGER {
    notApplicable    (1),
    type2            (2), -- 64Kbits/S overhead
    type3            (3), -- 32Kbits/S overhead
	type0            (4), 
	type1            (5),
	type3et          (6)
	                }
    MAX-ACCESS read-write
    STATUS current
    DESCRIPTION
     "ADSL Frame type "
    ::= { adslConfEntry 2 }


adslConfPilotToneRequest	OBJECT-TYPE
    SYNTAX INTEGER {
    notApplicable    (1),
    disable          (2),  -- PTR is disabled 
    enable           (3)   -- PTR is enabled
	                }
    MAX-ACCESS read-write
    STATUS current
    DESCRIPTION
     "This parameter controls Pilot Tone Request (PTR)."
    ::= { adslConfEntry 3}


adslConfTrellisCoding  OBJECT-TYPE
    SYNTAX INTEGER {
    notApplicable    (1),
    disable          (2),  --  Trellis Coding disabled
    enable           (3) --  Trellis Coding enabled
	                }
    MAX-ACCESS read-write
    STATUS current
    DESCRIPTION
     "This parameter enables/disables Trellis error detection code. 
      using error detection code may introduce delays."
    ::= { adslConfEntry 4 }

adslConfTransmissionMode  OBJECT-TYPE
    SYNTAX INTEGER {
    notApplicable    (1),
    echoCancellation (2),  -- EC 
    frequencyDivision(3)   -- FDM
                    }
    MAX-ACCESS read-write
    STATUS current
    DESCRIPTION
     "This parameter controls transmision mode: 
      Echo Cancellation is required when both ATU-C an ATU-R use
      the same frequency.
      Frequency Division (different frequency ranges for ATU-C 
      and ATU-R) may limit data rate."
    ::= { adslConfEntry 5}


adslConfStandardCompliance	OBJECT-TYPE
    SYNTAX INTEGER {
    notApplicable    (1),
    t1Hypen413       (2), -- T1-413 
    gDotDmt          (3), -- G.DMT (Discrete Multi Tones)
    multiMode        (4), -- Multimode 
    alcatel1Dot4     (5), -- Alcatel 1.4
    alcatel          (6), -- Alcatel
    adi              (7),  -- ADI
	adsl2            (8),
	adsl2Plus		 (9),
 	adsl2Auto		 (10),
	adsl2PlusAuto	 (11)
                    }
    MAX-ACCESS read-write
    STATUS current
    DESCRIPTION
     "This parameter indicates standard compliance
      G.Lite enables extended ADSL range, ease of installation,
      but requires lower rate."
    ::= { adslConfEntry 6}

adslConfMaxBitPerBin 	OBJECT-TYPE
    SYNTAX Integer32
    MAX-ACCESS read-write
    STATUS current
    DESCRIPTION
     "This parameter indicates maximum number of bits per ADSL Bin.
      Each Bin has bandwidth of 4khz.
      Range of values for this parameter is 0..15 "
	::= { adslConfEntry 7}

adslConfTxStartFreqBin	  OBJECT-TYPE
    SYNTAX Integer32
    MAX-ACCESS read-write
    STATUS current
    DESCRIPTION
     "This parameter controls Transmit Start Bin number.
      For ADSL Annex A - range of values  is  6 to 31.
      For ADSL Annex B - range of values  is 33 to 63.
      Frequency (in khz unit) is calculated by multiplying this 
      parameter value by bin bandwidth (4Khz) "
    ::= { adslConfEntry 8}

adslConfTxEndFreqBin	  OBJECT-TYPE
    SYNTAX Integer32
    MAX-ACCESS read-write
    STATUS current
    DESCRIPTION
     "This parameter controls Transmit End Bin number.
      For ADSL Annex A - range of values  is  6 to 31.
      For ADSL Annex B - range of values  is 33 to 63.
	  requency (in khz unit) is calculated by multiplying this 
      value by bin bandwidth (4Khz) "
    ::= { adslConfEntry 9}

adslConfRxStartFreqBin		OBJECT-TYPE
    SYNTAX Integer32
    MAX-ACCESS read-write
    STATUS current
    DESCRIPTION
     "This parameter controls Receive Start Bin number.
      Range of values for this parameter depends on ADSL Annex supported,
      and transmisson mode (adslTransmissionMode) selected:
	  ADSL Annex A and Echo Cancellation (EC)   :  6 to 255
	  ADSL Annex A and Frequency Division (FDM) : 32 to 255 	  
	  ADSL Annex B and Echo Cancellation (EC) 	: 33 to 255
      ADSL Annex B and Frequency Division (FDM) : 64 to 255
      Frequency (in khz unit) is calculated by multiplying this 
      value by bin bandwidth (4Khz) "
    ::= { adslConfEntry 10}

adslConfRxEndFreqBin	  OBJECT-TYPE
    SYNTAX Integer32
    MAX-ACCESS read-write
    STATUS current
    DESCRIPTION
     "This parameter controls Receive End Bin number.
      Range of values for this parameter depends on ADSL Annex supported,
      and transmisson mode (adslTransmissionMode) selected:
	  ADSL Annex A and Echo Cancellation (EC)   :  6 to 255
	  ADSL Annex A and Frequency Division (FDM) : 32 to 255 	  
	  ADSL Annex B and Echo Cancellation (EC) 	: 33 to 255
      ADSL Annex B and Frequency Division (FDM) : 64 to 255
      Frequency (in khz unit) is calculated by multiplying this 
      value by bin bandwidth (4Khz) "
    ::= { adslConfEntry 11}


adslConfTxPowerAttenuation	  OBJECT-TYPE
    SYNTAX Integer32
    MAX-ACCESS read-write
    STATUS current
    DESCRIPTION
     "This parameter controls Transmit Gain in dB units
      Range is 0 to 12dB. Resolution is 1 dB"
    ::= { adslConfEntry 12}

adslConfPSDMask   OBJECT-TYPE
    SYNTAX INTEGER {
     notApplicable  (1),
     standard       (2), 
     nonOverlapFlat (3),
     nonOverlapM1   (4),
     nonOverlapM2   (5)
                    }
    MAX-ACCESS read-write
    STATUS current
    DESCRIPTION
     "This parameter controls Power Spectral Density Mask.
      This object is applicable only for ADSL2.
      (adslConfStandardCompliance is one of the following:  
       adsl2, adsl2Plus, adsl2Auto, adsl2PlusAuto"
    ::= { adslConfEntry 13}

adslConfCommand   OBJECT-TYPE
	SYNTAX INTEGER {
		off			(1),
		restart		(2)
	}
	MAX-ACCESS read-write
	STATUS current
	DESCRIPTION
	"This parameter enables the user to perform commands on ADSL.
	 off(1)		- default state.
				  After any operation ends, value should be automatically
				  set to off(1).
	 restart(2)	- restarts line synchronization process.
	 "
    ::= { adslConfEntry 14 }

 
adslStatusTable OBJECT-TYPE
    SYNTAX SEQUENCE OF AdslStatusEntry
    MAX-ACCESS not-accessible
    STATUS current
    DESCRIPTION
     "A list of Adsl Status entries "
    ::= { adslIf 2 }

adslStatusEntry OBJECT-TYPE
   SYNTAX  AdslStatusEntry
   MAX-ACCESS  not-accessible
   STATUS  current
   DESCRIPTION
       "An entry in adslStatusTable"
   INDEX   { ifIndex }
   ::= { adslStatusTable 1 }

AdslStatusEntry ::=
   SEQUENCE {
			 adslStatusBitRxRate           Gauge32,
			 adslStatusSelectedStandard	   INTEGER,
             adslStatusOperationalState    INTEGER,
             adslStatusBitErrorRate        Unsigned32,
             adslStatusSNRCompensationMode INTEGER,
             adslStatusSNRCompensation	   Unsigned32,
             adslStatusSNRCorrection	   Unsigned32
			 }


adslStatusBitRxRate	   OBJECT-TYPE
    SYNTAX Gauge32
    UNITS "bps"
    MAX-ACCESS read-only
    STATUS current
    DESCRIPTION
     "This parameter indicates actual Receive (Downstream)
     rate on this channel."
    ::= { adslStatusEntry 1}

adslStatusSelectedStandard	  OBJECT-TYPE
    SYNTAX INTEGER
	{
	t1Hypen413AnnexA   (2),
	gDotDmtAnnexA      (3),
	multiModeAnnexA    (4),
	alcatel1Dot4AnnexA (5),
	alcatelAnnexA      (6),
	adiAnnexA          (7),
	t1Hypen413AnnexB   (8),
	gDotDmtAnnexB      (9),
	multiModeAnnexB    (10),
	alcatel1Dot4AnnexB (11),
	alcatelAnnexB      (12),
	adiAnnexB          (13),
	adsl2AnnexA        (14),
    adsl2PlusAnnexA    (15),
    adsl2AnnexB        (16),
    adsl2PlusAnnexB    (17),
	reachAadslAnnexL   (18)
	}
    MAX-ACCESS read-only
    STATUS current
    DESCRIPTION
     "This parameter indicates actual Standard 
      (transsmission mode) chosen after syncronization."
    ::= { adslStatusEntry 2}

adslStatusOperationalState	  OBJECT-TYPE
    SYNTAX INTEGER
	{
    idle      (1),
    discovery (2),
    handshake (3),
    training  (4),
    data	  (5),
	fullInit  (6)
	}
    MAX-ACCESS read-only
    STATUS current
    DESCRIPTION
     "This parameter indicates syncronization status."
    ::= { adslStatusEntry 3}

adslStatusBitErrorRate	   OBJECT-TYPE
    SYNTAX Unsigned32
    MAX-ACCESS read-only
    STATUS current
    DESCRIPTION
    "This parameter indicates the ratio between the number 
     of erroneous bits to the total bits number. 
     The value is normalized to 10e-8. 
     e.g. BER = 10 means BER = 10*10e-8 = 10e-7"
    ::= { adslStatusEntry 4}

adslStatusSNRCompensationMode	  OBJECT-TYPE
    SYNTAX INTEGER
	{
    notApplicable (1),
    notActive     (2),
    active        (3)
	}
    MAX-ACCESS read-only
    STATUS current
    DESCRIPTION
     "This parameter indicates whether special SNR compensation mode
      has been activated or not."
    ::= { adslStatusEntry 5}

adslStatusSNRCompensation	   OBJECT-TYPE
    SYNTAX Unsigned32
    UNITS "dB"
    MAX-ACCESS read-only
    STATUS current
    DESCRIPTION
     "This parameter indicates the target-SNR Firmware currently used."
    ::= { adslStatusEntry 6}

adslStatusSNRCorrection	   OBJECT-TYPE
    SYNTAX Unsigned32
    MAX-ACCESS read-only
    STATUS current
    DESCRIPTION
     "This parameter indicates whether the ADSL chip is operating
      according to standard ADSL coding gain (auto) or 
      some other automatic SW configuration (respective to line attenuation).
      Units of this parameter are tenths of dB.
      Special value of 1000 (=100.0 dB) indicates that 'Auto' coding gain is used."
    ::= { adslStatusEntry 7}
-- 
-- file :D:\Synergy\WorkArea\545\mib_rad\txt\radsdsl.txt
-- 
--Version:   1.0
--Date:     27.03.2001              
--By:       Yig'al Hachmon
--File:     SDSL.txt
--
--Last Update: Yig'al Hachmon 12-Apr-2001
--SDSL configuration

--wanGen    OBJECT IDENTIFIER ::= {radWan 1}
--diverseIfWanGen OBJECT IDENTIFIER ::= {wanGen 6} (see mpmx.txt)
sdslIf OBJECT IDENTIFIER ::= {diverseIfWanGen 11} 

sdslConfTable OBJECT-TYPE
    SYNTAX SEQUENCE OF SdslConfEntry
    MAX-ACCESS not-accessible
    STATUS current
    DESCRIPTION
       "A list of SDSL Configuration entries "
    ::= { sdslIf 1 }

sdslConfEntry OBJECT-TYPE
    SYNTAX  SdslConfEntry
    MAX-ACCESS  not-accessible
    STATUS  current
    DESCRIPTION
        "An entry in sdslConfTable        "
    INDEX   {sdslConfCnfgIdx,ifIndex }
    ::= { sdslConfTable 1 }

SdslConfEntry ::=
   SEQUENCE {
sdslConfCnfgIdx                Integer32,
sdslConfRateAquisition		   INTEGER,
sdslConfBaudRate			   INTEGER,
sdslConfMode				   INTEGER

            }

sdslConfCnfgIdx      OBJECT-TYPE
     SYNTAX  Integer32 (1..255)
     MAX-ACCESS  read-only
     STATUS  current
     DESCRIPTION
     "This object indicates the Idx of the Config being accessed.
      Idx of 255 relates to the Temporary (Scratch) Config.
      For products that support several configurations, Set can be performed
      only to the Temporary Config (=255). "
     ::= { sdslConfEntry 1}


sdslConfRateAquisition	OBJECT-TYPE
    SYNTAX INTEGER {
    notApplicable   (1),  
    autoNegotiate   (2),
    fixed           (3) 
	               }
    MAX-ACCESS read-write
    STATUS current
    DESCRIPTION
        "SDSL Rate Aquisition mode
         Default value = fixed." 
    ::= { sdslConfEntry 2 }


sdslConfBaudRate	   OBJECT-TYPE
    SYNTAX INTEGER {
    notApplicable  (1),
    r144kbps       (2), 
    r748kbps       (3),
    r1168kbps      (4),
	r1550kbps      (5),
	r2320kbps      (6)
	               }
    MAX-ACCESS read-write
    STATUS current
    DESCRIPTION
        "SDSL baud rate. Not applicable if rate aquisition is AutoNegotiation.
         Default value = r144kbps"
    ::= { sdslConfEntry 3 }

sdslConfMode	   OBJECT-TYPE
    SYNTAX INTEGER {
    coe   (1), -- HTU-C
    cpe   (2)  -- HTU-R
	               }
    MAX-ACCESS read-write
    STATUS current
    DESCRIPTION
        "SDSL  mode - COE (HTU-C) or CPE (HTU-R) 
         Default value = COE" 
    ::= { sdslConfEntry 4 }
-- 
-- file :D:\Synergy\WorkArea\545\mib_rad\txt\radshdsl.txt
-- 
--Version:   1.0
--Date:     9 Sep 02              
--By:       Yig'al Hachmon
--File:     radshdsl.txt
--
--Last Update: 19-Aug-2008 by Yig'al Hachmon
--SHDSL configuration

--wanGen    OBJECT IDENTIFIER ::= {radWan 1}
--diverseIfWanGen OBJECT IDENTIFIER ::= {wanGen 6} (see mpmx.txt)
shdslIf OBJECT IDENTIFIER ::= {diverseIfWanGen 12} 
radHdsl2ShdslEvents  OBJECT IDENTIFIER ::= {shdslIf 0}

-- Segment Endpoint Current Status/Performance Group


shdslEndpointCurrTable OBJECT-TYPE
      SYNTAX      SEQUENCE OF ShdslEndpointCurrEntry
      MAX-ACCESS  not-accessible
      STATUS      current
      DESCRIPTION
        "This table is an extension of hdsl2ShdslEndpointCurrTable of rfc3276
         It contains current status and performance information
         for segment endpoints in HDSL2/SHDSL Lines.  As with other 
         tables in this MIB indexed by ifIndex, entries in this table 
         MUST be maintained in a persistent manner."
      ::= { shdslIf 1 }

shdslEndpointCurrEntry OBJECT-TYPE
      SYNTAX      ShdslEndpointCurrEntry
      MAX-ACCESS  not-accessible
      STATUS      current
      DESCRIPTION
        "An entry in the shdslEndpointCurrTable.  Each entry 
        contains status and performance information relating to a 
        single segment endpoint.  It is indexed by the ifIndex of the
        HDSL2/SHDSL line, the UnitId of the associated unit, the side
        of the unit, and the wire-pair of the associated modem."
      AUGMENTS {hdsl2ShdslEndpointCurrEntry}
      ::= { shdslEndpointCurrTable 1 }

   ShdslEndpointCurrEntry ::=
      SEQUENCE
      {	
	   hdsl2ShdslEndpointCurrRcvGain			  Integer32, 
       hdsl2ShdslEndpointCurrTransPower			  Integer32,	
       hdsl2ShdslEndpointCurrPowerBO			  Integer32,	
       hdsl2ShdslEndpointCurrLineStatus			  INTEGER,   
       hdsl2ShdslEndpointCurrOpState   			  BITS,	   
       hdsl2ShdslEndpointAccumulatedTimeElapsed	  TimeTicks,
	   hdsl2ShdslEndpointCurrPsd			  	  INTEGER,
	   hdsl2ShdslEndpointValidIntervals			  Unsigned32,
	   hdsl2ShdslEndpointValidDaysIntervals		  Unsigned32
	   }
	                                

 hdsl2ShdslEndpointCurrRcvGain OBJECT-TYPE
    SYNTAX      Integer32
    UNITS       "dB"
    MAX-ACCESS  read-only
    STATUS      current
    DESCRIPTION
        "The current receive gain in hundredth of dB."
     ::= { shdslEndpointCurrEntry 1 }


hdsl2ShdslEndpointCurrTransPower  OBJECT-TYPE
    SYNTAX      Integer32
    MAX-ACCESS  read-only
    STATUS      current
    DESCRIPTION
        "The current transmit power in tenth of dBm."
    ::= { shdslEndpointCurrEntry 2 }

hdsl2ShdslEndpointCurrPowerBO   OBJECT-TYPE	-- added by RAD
    SYNTAX      Integer32
    UNITS       "dB"
    MAX-ACCESS  read-only
    STATUS      current
    DESCRIPTION
        "The current transceiver actual power backoff from 0dB to 31dB."
     ::= { shdslEndpointCurrEntry 3 }


hdsl2ShdslEndpointCurrLineStatus OBJECT-TYPE	-- added by RAD
    SYNTAX      INTEGER
	           {
	            noSync (2),
                sync  (3)
				}
    MAX-ACCESS  read-only
    STATUS      current
    DESCRIPTION
        "The current line synchronization status."
     ::= { shdslEndpointCurrEntry 4 }
 

hdsl2ShdslEndpointCurrOpState OBJECT-TYPE	-- added by RAD
    SYNTAX      BITS
	            {
                 idleMode(0),
                 dataMode(1),
                 bootUpload(2),
                 bootUploadDone(3), 
                 startupHandshakeInProgress(4),
                 startupTrainingInProgress(5),  
                 framerSyncInProgress(6),
                 localAnalogLoopbackInProgress(7),
                 remoteCoreLoopbackInProgress(8), 
                 localDigitalLoopbackInProgress(9),
                 spectrumTestInProgress(10)
				 }
    MAX-ACCESS  read-only
    STATUS      current
    DESCRIPTION
        "The current operational state."  
    ::= { shdslEndpointCurrEntry 5 }


hdsl2ShdslEndpointAccumulatedTimeElapsed   OBJECT-TYPE -- added by RAD
    SYNTAX       TimeTicks
    MAX-ACCESS   read-only
    STATUS       current
    DESCRIPTION
        "The time (in hundredths of a second) since the 
         accumulated counters were last re-initialized:   
         Accumulated counters are hdsl2ShdslEndpointES,           
         hdsl2ShdslEndpointSES, hdsl2ShdslEndpointCRCanomalies 
		 hdsl2ShdslEndpointLOSWS, and hdsl2ShdslEndpointUAS."  
    ::= { shdslEndpointCurrEntry 6 }

hdsl2ShdslEndpointCurrPsd OBJECT-TYPE
   SYNTAX      INTEGER
               {
               asymmetric(2),
			   symmetric(3)
               }
   MAX-ACCESS  read-only
   STATUS      current
   DESCRIPTION
     "This object indicates use of symmetric/asymmetric PSD (Power
      Spectral Density) Mask for the associated SHDSL Line."  
      ::= { shdslEndpointCurrEntry 7 }

hdsl2ShdslEndpointValidIntervals   OBJECT-TYPE
    SYNTAX       Unsigned32
    MAX-ACCESS   read-only
    STATUS       current
    DESCRIPTION
        "The number of previous 15 minutes intervals
         for which valid data was collected."  
	::= { shdslEndpointCurrEntry 8 }

hdsl2ShdslEndpointValidDaysIntervals   OBJECT-TYPE
    SYNTAX       Unsigned32
    MAX-ACCESS   read-only
    STATUS       current
    DESCRIPTION
        "The number of previous Days intervals
         for which valid data was collected."  
	::= { shdslEndpointCurrEntry 9 }
 

shdslEndpointMaintTable OBJECT-TYPE
      SYNTAX      SEQUENCE OF ShdslEndpointMaintEntry
      MAX-ACCESS  not-accessible
      STATUS      current
      DESCRIPTION
        "This table supports maintenance operations (eg. loopbacks)
         to be performed on HDSL2/SHDSL segment endpoints.  This table
         contains live data from equipment.  As such, it is NOT 
         persistent."
      ::= { shdslIf 2 }

shdslEndpointMaintEntry OBJECT-TYPE
      SYNTAX      ShdslEndpointMaintEntry
      MAX-ACCESS  not-accessible
      STATUS      current
      DESCRIPTION
        "An entry in the hdsl2ShdslEndpointMaintTable.  Each entry
         corresponds to a single segment endpoint, and is indexed by the
         ifIndex of the HDSL2/SHDSL line, the UnitId of the associated
         unit and the side of the unit."
      INDEX { ifIndex, hdsl2ShdslInvIndex, hdsl2ShdslEndpointSide }
      ::= { shdslEndpointMaintTable 1 }

ShdslEndpointMaintEntry ::=
      SEQUENCE
      {
      shdslMaintPowerBackOff        INTEGER
      }

shdslMaintPowerBackOff OBJECT-TYPE
      SYNTAX      INTEGER
                  {
                  default(1),
                  enhanced(2),
			      disabled (3) 
                  }
      MAX-ACCESS  read-write
      STATUS      current
      DESCRIPTION
        "This object configures the receiver at the associated
         segment endpoint to operate in default or enhanced power
         backoff mode.
         powerbackoff may also be disabled"

      ::= { shdslEndpointMaintEntry 1 }


  -- Span Configuration Profile Group


shdslSpanConfProfileTable OBJECT-TYPE
      SYNTAX      SEQUENCE OF ShdslSpanConfProfileEntry
      MAX-ACCESS  not-accessible
      STATUS      current
      DESCRIPTION
        "This table supports definitions of span configuration
         profiles for SHDSL lines.  HDSL2 does not support these 
         configuration options.  This table MUST be maintained
         in a persistent manner."
      ::= { shdslIf 3 }

shdslSpanConfProfileEntry OBJECT-TYPE
      SYNTAX      ShdslSpanConfProfileEntry
      MAX-ACCESS  not-accessible
      STATUS      current
      DESCRIPTION
        "Each entry corresponds to a single span configuration
         profile.  Each profile contains a set of span configuration
         parameters.  The configuration parameters in a profile are
         applied to those lines referencing that profile (see the 
         hdsl2ShdslSpanConfProfile object).  Profiles may be 
         created/deleted using the row creation/deletion mechanism 
         via hdsl2ShdslSpanConfProfileRowStatus.  If an active
         entry is referenced in hdsl2ShdslSpanConfProfile, the 
         entry MUST remain active until all references are removed."
      AUGMENTS {hdsl2ShdslSpanConfProfileEntry}
      ::= { shdslSpanConfProfileTable 1 }

ShdslSpanConfProfileEntry ::=
      SEQUENCE
      {
	  hdsl2ShdslSpanConfEocCompatible			INTEGER, 
	  hdsl2ShdslSpanConfAsymmetricPSDRate		INTEGER,
	  hdsl2ShdslSpanConfWireInterfaceUsed		INTEGER,
	  hdsl2ShdslSpanConfHandshake				INTEGER
      }


hdsl2ShdslSpanConfEocCompatible	OBJECT-TYPE  -- Added by RAD
    SYNTAX      INTEGER
                {
                proprietary (2),
                standard    (3)
                }
    MAX-ACCESS  read-only
    STATUS      current
    DESCRIPTION
        "This object indicate if device  supports only 
          standard EOC messages or also proprietary messages."
    ::= { shdslSpanConfProfileEntry 1 }


hdsl2ShdslSpanConfAsymmetricPSDRate  OBJECT-TYPE
    SYNTAX      INTEGER
                {
                notApplicable   (1),
                asymmetricR1    (2),
				asymmetricR2    (3)    
                }
    MAX-ACCESS  read-write
    STATUS      current
    DESCRIPTION
        "This object indicates line rate when 
         rfc3276.hdsl2ShdslSpanConfPSD value is asymmetric(2).
		 Seleceted rate depends on transmission mode - 
		 specified in Annex A or B of G.991.2.
         For Annex A; 
           R1 selects the 776 or 784 kbit/s 
 		   R2 selects the 1544 or 1552 kbit/s  
		 For Annex B ;
           R1 selects the 2312 kbit/s 
           R2 selects the 2056 kbit/s "
    ::= { shdslSpanConfProfileEntry 2 }


hdsl2ShdslSpanConfWireInterfaceUsed	OBJECT-TYPE
    SYNTAX      INTEGER
                {
                notApplicable (1),
                twoWires      (2),
				fourWires     (3),
				autoDetection (4)    
                }
    MAX-ACCESS  read-write
    STATUS      current
    DESCRIPTION
	"This object enable user to configure SHDSL port with 4 wires
     to use 2 or  4 wires, or to auto detect far end number of wires"
    ::= { shdslSpanConfProfileEntry 3 }

hdsl2ShdslSpanConfHandshake	OBJECT-TYPE
    SYNTAX      INTEGER
                {
				automatic		(1),
				g994dot1rev2001	(2)		-- G994.1 02/2001
                }
    MAX-ACCESS  read-write
    STATUS      current
    DESCRIPTION
	"This object indicates the Handshake Procedure."
    ::= { shdslSpanConfProfileEntry 4 }


hdsl2ShdslIfConf OBJECT IDENTIFIER ::= { shdslIf 4 }

--Interface configuration with Configuration index

hdsl2ShdslIfConfTable OBJECT-TYPE
    SYNTAX      SEQUENCE OF Hdsl2ShdslIfConfEntry
    MAX-ACCESS  not-accessible
    STATUS      current
    DESCRIPTION
    "This table enables configuration of HDSL2/SHDSL interfaces
     per configuration index.
     Write operation for products supporting Active+Temp configurations,
     is possible only on the Temp configuration(255)."
    ::= { hdsl2ShdslIfConf 1 }

hdsl2ShdslIfConfEntry OBJECT-TYPE
    SYNTAX      Hdsl2ShdslIfConfEntry
    MAX-ACCESS  not-accessible
    STATUS      current
    DESCRIPTION
        "An entry in the hdsl2ShdslIfConfTable. "
    INDEX { hdsl2ShdslIfConfIdx, ifIndex, hdsl2ShdslSideIdx}
    ::= { hdsl2ShdslIfConfTable 1 }

Hdsl2ShdslIfConfEntry ::=
    SEQUENCE
    {
    hdsl2ShdslIfConfIdx             Integer32,
    hdsl2ShdslSideIdx               INTEGER,
    hdsl2ShdslMaxBw                 INTEGER,
	hdsl2ShdslPwrBackoff            INTEGER,
	hdsl2ShdslTxMode                INTEGER,
	hdsl2ShdslAttenuationThreshold  Integer32,
	hdsl2ShdslSnrMarginThreshold    Integer32,
	hdsl2ShdslTs0OverDsl            INTEGER,
	hdsl2ShdslMode                  INTEGER,
	hdsl2ShdslTsCompactionMode      INTEGER,
	hdsl2ShdslEocEnable             INTEGER,
	hdsl2ShdslFar1stIfNumOfTSs      Unsigned32,
	hdsl2ShdslFarEndDevice          INTEGER,
	hdsl2ShdslPwrBackoffDb          Integer32,     
	hdsl2ShdslFarEndMuxTsa          OCTET STRING
    }

hdsl2ShdslIfConfIdx OBJECT-TYPE
    SYNTAX  Integer32 (1..255)
    MAX-ACCESS  read-only
    STATUS  current
    DESCRIPTION
    "This object indicates the Idx of the Config being accessed.
     Idx of 255 relates to the Temporary (Scratch) Config.
     Write operation for products supporting Active+Temp configurations, 
     is allowed to Temporary configuration only. "
    ::= {hdsl2ShdslIfConfEntry 1}

hdsl2ShdslSideIdx OBJECT-TYPE
      SYNTAX  INTEGER {
	    nearEnd(2),
        farEnd (3)
        }
      MAX-ACCESS  read-only
      STATUS      current
      DESCRIPTION
      "This object indicates the Side of the managed object: Near-End
       or Far-End."
      ::= {hdsl2ShdslIfConfEntry 2}

hdsl2ShdslMaxBw     OBJECT-TYPE
      SYNTAX  INTEGER {
      notApplicable (1),
      r192          (2), 
      r256          (3), 
      r320          (4),
	  r384          (5),
	  r448          (6),
      r512          (7), 
      r576          (8),
	  r640          (9),
	  r704          (10),
      r768          (11), 
      r832          (12),
	  r896          (13),
	  r960          (14),
      r1024         (15), 
      r1088         (16),
	  r1152         (17),
	  r1216         (18),
	  r1280         (19),
	  r1344         (20),
	  r1408         (21),
	  r1472         (22),
	  r1536         (23),
	  r1600         (24),
	  r1664         (25),
	  r1728         (26),
	  r1792         (27),
	  r1856         (28),
	  r1920         (29),
	  r1984         (30),
	  r2048         (31)
        }
      MAX-ACCESS  read-write
      STATUS  current
      DESCRIPTION
      "Maximum BW (Bandwidth) of the Shdsl Line, in Kbps units.
       Respective Max No. of TSs =  Max. Rate/64
       This object can be Set only for a Central (xtuC) unit."
      ::= {hdsl2ShdslIfConfEntry 3}

hdsl2ShdslPwrBackoff OBJECT-TYPE
      SYNTAX  INTEGER {
	    notApplicable(1),
        enhanced(2),  -- enabled
 		disabled (3)  -- added by RAD
        }
      MAX-ACCESS  read-write
      STATUS      current
      DESCRIPTION
      "This object configures the receiver at the associated
       segment endpoint to enable/disable power	backoff mode.
       This object is similar to hdsl2ShdslMaintPowerBackOff, but per
       configuration. Therefore, the order of the enum values is the same. "
      ::= {hdsl2ShdslIfConfEntry 4}

hdsl2ShdslTxMode OBJECT-TYPE
    SYNTAX  INTEGER
      {
      notApplicable(1),
      annexA       (2),
      annexB       (3),
	  annexG       (4),
	  annexF       (5)
      }
    MAX-ACCESS  read-write
    STATUS      current
    DESCRIPTION
    "This object configures the Transmission Mode for the SHDSL Line.
     Normally, This object can be Set only for a Central (xtuC) unit."
    ::= { hdsl2ShdslIfConfEntry 5}

hdsl2ShdslAttenuationThreshold OBJECT-TYPE
    SYNTAX      Integer32
    UNITS       "dB"
    MAX-ACCESS  read-write
    STATUS      current
    DESCRIPTION
    "This object configures the Attentuation alarm threshold.
     0=Off
     Valid values: 0..127 ."
    ::= { hdsl2ShdslIfConfEntry 6}

hdsl2ShdslSnrMarginThreshold OBJECT-TYPE
    SYNTAX      Integer32
    UNITS       "dB"
    MAX-ACCESS  read-write
    STATUS      current
    DESCRIPTION
    "This object configures the SNR margin alarm threshold.
     0=Off
     Valid values: 0..15 ."
    ::= { hdsl2ShdslIfConfEntry 7}

hdsl2ShdslTs0OverDsl OBJECT-TYPE
    SYNTAX  INTEGER
      {
      notApplicable(1),
      looped       (2),
      transparent  (3)
      }
    MAX-ACCESS  read-write
    STATUS      current
    DESCRIPTION
    "This object configures the way TS0 will be treated over the SHDSL Line.
	 looped - looped inside
	 transparent - sent transparently over the DSL Line.
     This object can be Set only for a Central (xtuC) unit."
    ::= { hdsl2ShdslIfConfEntry 8}

hdsl2ShdslMode OBJECT-TYPE
    SYNTAX  INTEGER
      {
      notApplicable(1),
      stuC         (2),
      stuR         (3)
      }
    MAX-ACCESS  read-write
    STATUS      current
    DESCRIPTION
    "This object is relevant only for the Near-End device.
     stuC - Central 
     stuR - Remote ."
    ::= { hdsl2ShdslIfConfEntry 9}

hdsl2ShdslTsCompactionMode OBJECT-TYPE
    SYNTAX  INTEGER
      {
      noCompaction (1),
      noMapping    (2),
      withMapping  (3),
	  lowTsMapping (4),
	  spareMapping (5)
      }
    MAX-ACCESS  read-write
    STATUS      current
    DESCRIPTION
    "This object configures how TSs will be compacted over the SHDSL Line.
	 In both mapping cases (2),(3), only the TSs connected on the E1 line will be 
	 transferred over the SHDSL Line
	 noCompaction - the whole E1 BW is reserved on the SHDSL Line, 
	             even if only part  of the TSs are actually connected.
	 noMapping - there is no mapping between the E1 TSs and the SHDSL frame TSs.
	             Therefore, E1 connected TSs are ordered in ascending order (e.g
				 E1 TSs 2, 16, 20 will occupy places 1, 2, 3 in SHDSL Line).
				 In this case, if user wants to add connection for 
				 a TS that is lower	than the existing ones on SHDSL, 
				 the TSs that are higher will have to  move. 
				 That causes breaks in service for the moved TSs. 
				 (e.g if E1 TS8 is added in the above case, 
				 TSs 16 and 20 will move, so that by the
				 end of this process, the E1 TSs 2, 8, 16, 20 will
				  be ordered in  SHDSL frame as 1, 2, 3, 4).
	 withMapping - there is a mapping between the E1 TSs and the SHDSL frame TSs.
	             Therefore, if some TSs were connected and then user wants to add
	             additional E1 TSs, there is no need to move the existing TSs of the 
	             SHDSL frame. The additional TSs will be added AFTER the existing ones, 
	             or in gaps created by E1 TSs removed by user. The main thing is that
				 the existing TSs will NOT be moved and so, their service will not be 
				 damaged by the addition or removal of E1 TS connections.
	 lowTsMapping - the first 2 TSs are used for Signaling (TS16) and Dedicated TS
	             if relevant. The payload starts afterwards, unmapped (according to 
	             E1 connected TSs order). This will ensure that Signaling and 
	             Dedicated TS will continue to function also when new TSs are 
	             connected.	User will still get service breaks when TSs are moved.
	 spareMapping - applicable only for MP-2100/2104 cards. It should be selected only 
	             when working vs. a MP-2100.2104. It resembles the noMapping option,
	             but it contains Spare TSs for unconnected TSs. These Spare TSs 
	             will prevent service breaks upon added connections, because these
	             will be selected from the Spare existing TSs."
    ::= { hdsl2ShdslIfConfEntry 10}

hdsl2ShdslEocEnable OBJECT-TYPE
    SYNTAX  INTEGER
      {
      notApplicable(1),
      no           (2),
      yes          (3)
      }
    MAX-ACCESS  read-write
    STATUS      current
    DESCRIPTION
    "This object configures whether EOC protocol is supported by the Far-End
     device working with this port."
    ::= { hdsl2ShdslIfConfEntry 11}

hdsl2ShdslFar1stIfNumOfTSs OBJECT-TYPE
    SYNTAX      Unsigned32
    MAX-ACCESS  read-write
    STATUS      current
    DESCRIPTION
    "This object configures the number of TSs of the SHDSL line
     that belong to the 1st Interface of the Far-End device, where
     1st means that these TSs are first on the SHDSL line.

	 It is applicable only for Near-End instance and only when Far-End
	 is an ASMi-52 SA unit having Agent and Mux configuration.
	 SHDSL TSs are arranged so that all TSs of a Far interface are together
	 at the beginning and afterwards all TSs of the other Far interface.
	 The assumption is that only 2 user interfaces exist in the Far End unit.  
	 Examples:
	 - When ASMi-52 has E1+ETH or E1+V.35 user interfaces, this object
	   represents the number of TSs assigned to the E1 interface.
	   They will be first on the SHDSL TSs.
	   Rest of the SHDSL TSs are for the other interface.
	 - When ASMi-52 has ETH+V.35 user interfaces, this object
	   represents the number of TSs assigned to the ETH interface.
	   They will be first on the SHDSL TSs.
	   Rest of the SHDSL TSs are for the V.35 interface.
	 Valid values: 0..32, 255.     
     255=NA "
    ::= { hdsl2ShdslIfConfEntry 12}

hdsl2ShdslFarEndDevice OBJECT-TYPE
    SYNTAX  INTEGER
      {
      other            (2),
	  mpComponent      (3),
	  asmi52SingleIf   (4),   
      asmi52E1AndData  (5),
	  asmi52E1AndEth   (6),
	  asmi52EthAndData (7),
	  fcdip            (8),
	  dxc              (9) 
      }
    MAX-ACCESS  read-write
    STATUS      current
    DESCRIPTION
    "This object indicates the Far-End device.
     It is used for 2 purposes:
    - in order to know if EOC is used (EOC is used only when the device
       is any of the ASMi52 options: (4)..(7))
     - in order to know how to work vs Far-End device, because Megaplex
       uses different SHDSL component than other devices. mpComponent(3)
	   means that Far-End device uses same component as Megaplex. All the
	   rest use a different component.
     other(2) - none of the other options.
     mpComponent(3) - for Megaplex or other future device having the same 
                   component as MP.
     asmi52SingleIf (4) - ASMi-52 with a Single user interface.                   
     asmi52E1AndData(5), asmi52E1AndEth(6), asmi52EthAndData (7),are 
     when Far-End unit is ASMi-52 V>=2.5 and the device has more than one 
     user interface. User should select the combination known to exist in 
     the Far-End unit.
	 Data - indicates an interface of V.35, X.21, RS-530, etc...
	 fcdip - includes both FCD-IP and FCD-IP/M
	 dxc   - includes DXC-30, DXC-30E, DXC-10A, DXC-8R and New. "
    ::= { hdsl2ShdslIfConfEntry 13}

hdsl2ShdslPwrBackoffDb OBJECT-TYPE
    SYNTAX      Integer32
    UNITS       "dB"
    MAX-ACCESS  read-write
    STATUS      current
    DESCRIPTION
    "This object configures the Power Backoff (in dB) of the 
     receiver, at the associated segment endpoint.
     0=Off
     Valid values: 0..31 ."
    ::= { hdsl2ShdslIfConfEntry 14}

hdsl2ShdslFarEndMuxTsa OBJECT-TYPE
    SYNTAX  OCTET STRING
    MAX-ACCESS  read-write
    STATUS  current
    DESCRIPTION
    "This object represents Assignment of E1 TSs to Far-End MUX Interfaces.
	 It is relevant only when hdsl2ShdslSideIdx=nearEnd(2), when for the 
	 Near-End device, hdsl2ShdslMode=stuC(2)AND hdsl2ShdslFarEndDevice=(5),(6)or(7).
     Each Octet is divided in 2 nibbles. Each nibble represents a Near-End E1 TS 
     and indicates to which interface of the Far-End device this TS will be 
     assigned.
     The nibble values are as follows:
     0000  - no interface
     0001  - E1 interface
     0010  - ETH interface
     0011  - Data interface (V.35, X.21, RS-530, etc..)
     Rest  - not used
     Octet 1: TS1, TS2  (TS1 = Most nibble)
     Octet 2: TS3, TS4  (TS3 = Most nibble)
     Octet 3: TS5, TS6  (TS5 = Most nibble)
     ...
     Octet 12: TS23, TS24  (TS23 = Most nibble)
     ...
     Octet 16: TS31, TS32  (TS31 = Most nibble ; TS32 will be always empty )	 
     Only TSs that are connected for E1 port of Near-End can be assigned to
     a Far-End Interface."
    ::= { hdsl2ShdslIfConfEntry 15}    


-- SHSDL Notifications

--SHDSL EOC LOOPBACK TOWARDS NETWORK
radHdsl2ShdslLoopBackTrap NOTIFICATION-TYPE
   OBJECTS   { alarmSeverity,alarmState,ifAlias  }
   STATUS    current
   DESCRIPTION
   "This notification indicates that a remote loopback 
    has been activated on the Embedded Operations Channel (EOC) of the SHDSL
    link."
   ::= { radHdsl2ShdslEvents 1 }-- 
-- file :D:\Synergy\WorkArea\545\mib_rad\txt\services.txt
-- 
-- File:		Services.txt

 services OBJECT IDENTIFIER ::= { radGen 3} 

--Weighted Fair Queueing (WFQ) Table

wfq OBJECT IDENTIFIER ::= { services 1}

wfqTable OBJECT-TYPE
    SYNTAX  SEQUENCE OF WfqEntry
    MAX-ACCESS  not-accessible
    STATUS  current
    DESCRIPTION
    "This table allows user to define several
     WFQ tables per output port.
     
     WFQ supports flows with different bandwidth requirements 
     by giving each queue a weight that assigns it 
     a different percentage of output port bandwidth.

     When Weighted Fair Queuing is used, 
     it is possible to precisely attribute bandwidth 
     partitioning among the queues. 
     When there is congestion, each class (queue) 
     is not allowed to use more bandwidth than the amount 
     allocated to it."
    ::= { wfq 1 }

wfqEntry OBJECT-TYPE
    SYNTAX  WfqEntry
    MAX-ACCESS  not-accessible
    STATUS  current
    DESCRIPTION
    "An entry in the Weighted Fair Queueing table."
    INDEX {wfqCnfgIdx, wfqPrtIdx,wfqTblIdx, wfqQueueIdx }
    ::= { wfqTable 1 }

WfqEntry ::=
    SEQUENCE {
              wfqCnfgIdx     Integer32,
              wfqPrtIdx      Integer32,
              wfqTblIdx      Integer32,
              wfqQueueIdx    Integer32,
              wfqRowStatus   RowStatus,
              wfqWeightValue Integer32,
              wfqSchedulingMode	  	INTEGER,
              wfqMinRateAbsolute  	Unsigned32,
			  wfqMaxPacketSize		Unsigned32
              }

wfqCnfgIdx OBJECT-TYPE
    SYNTAX  Integer32 (1..255)
    MAX-ACCESS  not-accessible
    STATUS  current
    DESCRIPTION
    "This object indicates the Idx of the Agent Cnfg the following 
     objects refer.
     255=Temporary Cnfg (when relevant, 
     Set is done only to this configuration).
     For Agents that support only one configuration, 
     this object will be  constant=1. "
    ::= { wfqEntry 1 }

wfqPrtIdx OBJECT-TYPE
    SYNTAX  Integer32 
    MAX-ACCESS  not-accessible
    STATUS  current
    DESCRIPTION
    "This object indicates a unique port or interface number,
     for which Weighted Fair Queueing table is applicable .
	 For numbering, see product's spec.
     For some products, the numbering can equal ifIndex.
     Value of 255 (not applicable) refer to system level queue"    
    ::= { wfqEntry 2 }

wfqTblIdx OBJECT-TYPE
    SYNTAX  Integer32 
    MAX-ACCESS  not-accessible
    STATUS  current
    DESCRIPTION
    "This object indicates which  Weighted Fair Queueing (WFQ)
     Table is being used. There can be several tables.
     For FCD-155 User will select which one will be used 
     for a virtual concatenation group.Valid values are 1,2"    
    ::= { wfqEntry 3 }

wfqQueueIdx OBJECT-TYPE
    SYNTAX  Integer32
    MAX-ACCESS  not-accessible
    STATUS  current
    DESCRIPTION
    "This object indicates a queue index.
     For FCD-155, valid queues are 1..3.
     The 4th queue is not in MIB. 
     Its weight will be RO, Calculated according to 
     the sum of the 3 first queues."
    ::= { wfqEntry 4 }

wfqRowStatus OBJECT-TYPE
    SYNTAX  RowStatus
    MAX-ACCESS  read-create
    STATUS  current
    DESCRIPTION
    "This object enables Creation/Deletion of 
    rows in the WFQ table.
    For FCD-155, rows are not created nor destroyed by user."
    ::= { wfqEntry 5 }

wfqWeightValue OBJECT-TYPE
    SYNTAX  Integer32  (0..100)
	UNITS      "%"
    MAX-ACCESS  read-create
    STATUS  current
    DESCRIPTION
    "This object indicates a relative weight value.
     User should make sure that the sum of 
     values for all queues will not exceed 100%
     (sum should  be BELOW 100% in order 
     to leave some BW percentage for last queue)  
     Note that when this attribute is being used, the wfqMinRateAbsolute attribute is NA."
    ::= { wfqEntry 6 }

wfqSchedulingMode OBJECT-TYPE
      SYNTAX  INTEGER {
		 disable (2), -- Priority Queue
		 enable  (3)  -- WFQ
					}
	MAX-ACCESS  read-create
    STATUS  current
    DESCRIPTION
    "This object controls which scheduling mode is used:
     Weighted Fair Queuing (WFQ) scheme or priority Queue (Strict Priority)."
    ::= { wfqEntry 7 }

wfqMinRateAbsolute OBJECT-TYPE
    SYNTAX  Unsigned32  
	UNITS      "Kbps"
    MAX-ACCESS  read-create
    STATUS  current
    DESCRIPTION
    "The minimum absolute rate, in kbps, 
    that should be allocated to this queue. 
    If the value is	zero, then there is effectively 
    no minimum rate guarantee. 
    If the value is non-zero, then the servicing of
    this queue in at least this rate is assured.

    Note that when this attribute is being used, the wfqWeightValue attribute is NA."
    ::= { wfqEntry 8 }

wfqMaxPacketSize OBJECT-TYPE
    SYNTAX      Unsigned32
    MAX-ACCESS  read-create
    STATUS      current
    DESCRIPTION
    "The size of the largest packet which can be received
    on this queue, specified in octets.
    Packets larger than this size will be discarded."  
    ::= { wfqEntry 9}

-- Differential Services Code Point Mapping


Dscp ::= TEXTUAL-CONVENTION
    DISPLAY-HINT "d"
    STATUS   current
    DESCRIPTION
     "A Differentiated Services Code-Point that may be used for
       marking a traffic stream."
    REFERENCE
        "RFC 2474, RFC 2780"
    SYNTAX   Integer32 (0..63)


dscpMapping      OBJECT IDENTIFIER ::= {services 2}

dscpMappingTable OBJECT-TYPE
    SYNTAX      SEQUENCE OF DscpMappingEntry
    MAX-ACCESS  not-accessible
    STATUS      current
    DESCRIPTION
    "Mapping of DSCP value to a regenerated priority level."
    ::= { dscpMapping 1 }

dscpMappingEntry  OBJECT-TYPE
    SYNTAX      DscpMappingEntry
    MAX-ACCESS  not-accessible
    STATUS      current
    DESCRIPTION
    "An entry in dscpMappingTable."
    INDEX   { dscpMappingCnfgIdx,dscpMappingDscpIdx }
    ::= { dscpMappingTable 1 }

DscpMappingEntry ::=
    SEQUENCE {
        dscpMappingCnfgIdx       Integer32,
        dscpMappingDscpIdx            Dscp,
        dscpMappingRegenPriority      Integer32
    }

dscpMappingCnfgIdx OBJECT-TYPE
    SYNTAX  Integer32 (1..2147483647)
    MAX-ACCESS  not-accessible
    STATUS  current
    DESCRIPTION
    "This object indicates the Idx of the Agent Cnfg the following 
     objects refer to.
     255=Temporary Cnfg (when relevant, Set is done only 
     to this configuration).
     For Agents that support only one configuration, 
     this object will be  constant=1. 
     This object can be used to carry additional indexing 
     (e.g port index) when needed."
    ::= { dscpMappingEntry 1 }

dscpMappingDscpIdx OBJECT-TYPE
    SYNTAX      Dscp
    MAX-ACCESS  not-accessible
    STATUS      current
    DESCRIPTION
    " DSCP value of the incoming IP packet"
    ::= { dscpMappingEntry 2 }

dscpMappingRegenPriority OBJECT-TYPE
    SYNTAX      Integer32 
    MAX-ACCESS  read-write
    STATUS      current
    DESCRIPTION
    "The Regenerated Priority level the
     incoming DSCP value is mapped to.
     For FCD-155, valid values are 0,1,2,3"
    ::= { dscpMappingEntry 3 }


-- IfTeQos - Traffic Engineering Quality of Service Interface

ifTeQos		 OBJECT IDENTIFIER ::= { services 3 }

ifTeQosTable OBJECT-TYPE
    SYNTAX      SEQUENCE OF IfTeQosEntry
    MAX-ACCESS  not-accessible
    STATUS      current
    DESCRIPTION
    "The TE QOS Interface Table."
    ::= {  ifTeQos 1 }

ifTeQosEntry  OBJECT-TYPE
    SYNTAX      IfTeQosEntry
    MAX-ACCESS  not-accessible
    STATUS      current
    DESCRIPTION
    "An entry in the TE QOS Interface table."
    INDEX   { ifTeQosIdx1, ifTeQosIdx2, ifTeQosIdx3 }
    ::= { ifTeQosTable 1 }

IfTeQosEntry ::=
	SEQUENCE { 
        ifTeQosIdx1			Integer32,
		ifTeQosIdx2			Integer32,
		ifTeQosIdx3			Integer32,
		ifTeQosParam		OCTET STRING,
		ifTeQosParam2		OCTET STRING,
		ifTeQosStatus       INTEGER
    	}

ifTeQosIdx1 OBJECT-TYPE
    SYNTAX  Integer32
    MAX-ACCESS  not-accessible
    STATUS  current
    DESCRIPTION
    "This object indicates the 1st Index of the table."
    ::= { ifTeQosEntry 1 }

ifTeQosIdx2 OBJECT-TYPE
    SYNTAX  Integer32
    MAX-ACCESS  not-accessible
    STATUS  current
    DESCRIPTION
    "This object indicates the 2nd Index of the table."
    ::= { ifTeQosEntry 2 }

ifTeQosIdx3 OBJECT-TYPE
    SYNTAX  Integer32
    MAX-ACCESS  not-accessible
    STATUS  current
    DESCRIPTION
    "This object indicates the 3rd Index of the table."
    ::= { ifTeQosEntry 3 }

ifTeQosParam OBJECT-TYPE
    SYNTAX  OCTET STRING
    MAX-ACCESS  read-write
    STATUS  current
    DESCRIPTION
    "This object is used for QOS attributes 
     of the entry's entities."
    ::= { ifTeQosEntry 4 }

ifTeQosParam2 OBJECT-TYPE
    SYNTAX  OCTET STRING
    MAX-ACCESS  read-write
    STATUS  current
    DESCRIPTION
    "This object is used for 2nd group QOS attributes 
     of the entry's entities."
    ::= { ifTeQosEntry 5 }

ifTeQosStatus OBJECT-TYPE
    SYNTAX  INTEGER
	       {  active (1),
		      createAndGo (4),
		      destroy (6) }     
	MAX-ACCESS  read-write
    STATUS  current
    DESCRIPTION
    "This object is used to create, activate and 
     destroy entries of this table."
    ::= { ifTeQosEntry 6 }


portQos		 OBJECT IDENTIFIER ::= { services 4 }

prtPriorityTable OBJECT-TYPE
	SYNTAX  SEQUENCE OF PrtPriorityEntry
	MAX-ACCESS  not-accessible
	STATUS current
	DESCRIPTION  
	"A table - Parameters per port per Priority ."
	::= {portQos 1}

prtPriorityEntry OBJECT-TYPE
    SYNTAX PrtPriorityEntry
    MAX-ACCESS not-accessible
    STATUS current
	DESCRIPTION  "An entry in table."
	INDEX {prtPriorityIdx1, prtPriorityPrtIdx, prtPriorityIdx}
    ::= { prtPriorityTable 1}

PrtPriorityEntry ::=
    SEQUENCE {
    prtPriorityIdx1   Integer32,
    prtPriorityPrtIdx	 Integer32,
    prtPriorityIdx       Integer32,
    prtPriorityIngressRateLimit   Integer32
	}

prtPriorityIdx1 OBJECT-TYPE
    SYNTAX Integer32 (1..255)
    MAX-ACCESS not-accessible
    STATUS current
    DESCRIPTION
    "This attribute indicates the Idx of the Cnfg(1..255) being 
     accessed ; Idx of 255 relates to the TmpCnfg. or any other Index."
    ::= { prtPriorityEntry 1}

prtPriorityPrtIdx OBJECT-TYPE
    SYNTAX  Integer32  (0..2147483647)
    MAX-ACCESS  not-accessible
    STATUS  current
    DESCRIPTION
    "This object indicates a unique Port Index.
     Refer to device specification for port Index."
    ::= { prtPriorityEntry 2}

prtPriorityIdx OBJECT-TYPE
    SYNTAX  Integer32  (0..7)
    MAX-ACCESS  not-accessible
    STATUS  current
    DESCRIPTION
    "This object indicates the Traffic Priority Index."
    ::= { prtPriorityEntry 3}

prtPriorityIngressRateLimit OBJECT-TYPE
    SYNTAX  Integer32
    MAX-ACCESS  read-write
    STATUS  current
    DESCRIPTION
    "The maximum rate permitted at Ingress of 
     this port with this Traffic Priority, in Kbps."      
    ::= { prtPriorityEntry 4}


prtQosTable OBJECT-TYPE
	SYNTAX		SEQUENCE OF PrtQosEntry
	MAX-ACCESS	not-accessible
	STATUS		current
	DESCRIPTION  
	"Port QoS (Quality of Service) table."
	::= { portQos 2 }

prtQosEntry OBJECT-TYPE
    SYNTAX		PrtQosEntry
    MAX-ACCESS	not-accessible
    STATUS		current
	DESCRIPTION  "An entry in table."
	INDEX { prtQosIdx, prtQosPrtIdx, prtQosDirection }
    ::= { prtQosTable 1 }

PrtQosEntry ::=
    SEQUENCE {
		prtQosIdx					Unsigned32,
		prtQosPrtIdx				Unsigned32,
		prtQosDirection				INTEGER,
		prtQosRateLimitPacketType	INTEGER,
		prtQosRateLimitCIR			Unsigned32,
		prtQosRateLimitCBS			Unsigned32,
		prtQosRateLimitEIR			Unsigned32,
		prtQosRateLimitEBS			Unsigned32
	}

prtQosIdx OBJECT-TYPE
    SYNTAX		Unsigned32
    MAX-ACCESS	not-accessible
    STATUS		current
    DESCRIPTION
    "The first index of the table.
     This attribute might indicate the Idx of the Cnfg (1..255) being 
     accessed ; Idx of 255 relates to the TmpCnfg or any other Index."
    ::= { prtQosEntry 1 }

prtQosPrtIdx OBJECT-TYPE
    SYNTAX		Unsigned32
    MAX-ACCESS	not-accessible
    STATUS		current
    DESCRIPTION
    "This object indicates a unique Port Index.
     Refer to device specification for port Index."
    ::= { prtQosEntry 2 }

prtQosDirection OBJECT-TYPE
    SYNTAX		INTEGER {
		all			(1),
		ingress		(2),
		egress		(3)
	}
    MAX-ACCESS	not-accessible
    STATUS		current
    DESCRIPTION
    "This object indicates the port's QoS Direction."
    ::= { prtQosEntry 3 }

prtQosRateLimitPacketType OBJECT-TYPE
    SYNTAX		INTEGER {
		all								(1),
		bcastAndMcastAndFloodedUcast	(2), -- BroadCast + Multicast + Flooded Unicast
		bcastAndMcast					(3), -- BroadCast + Multicast
		bcast							(4)  -- BroadCast
	}
    MAX-ACCESS	read-write
    STATUS		current
    DESCRIPTION
    "This object indicates the Type of Packets on which Rate Limitation is applied."
    ::= { prtQosEntry 4 }

prtQosRateLimitCIR OBJECT-TYPE
    SYNTAX		Unsigned32
    MAX-ACCESS	read-write
    STATUS		current
    DESCRIPTION
    "This object indicates the port's CIR (Committed Information Rate) in Kbps.
     Value=0 represents best effort."      
    ::= { prtQosEntry 5 }

prtQosRateLimitCBS OBJECT-TYPE
    SYNTAX		Unsigned32
    MAX-ACCESS	read-write
    STATUS		current
    DESCRIPTION
    "This object indicates the port's CBS (Committed Burst Size) in KB.
     Value=0 represents best effort."            
    ::= { prtQosEntry 6 }

prtQosRateLimitEIR OBJECT-TYPE
    SYNTAX		Unsigned32
    MAX-ACCESS	read-write
    STATUS		current
    DESCRIPTION
    "This object indicates the port's EIR (Excess Information Rate) in Kbps."            
    ::= { prtQosEntry 7 }

prtQosRateLimitEBS OBJECT-TYPE
    SYNTAX		Unsigned32
    MAX-ACCESS	read-write
    STATUS		current
    DESCRIPTION
    "This object indicates the port's EBS (Excess  Burst Size) in KB."            
    ::= { prtQosEntry 8 }

prtTrafficClass		 OBJECT IDENTIFIER ::= { services 5 }

portTrafficClassTable OBJECT-TYPE
    SYNTAX      SEQUENCE OF PortTrafficClassEntry
    MAX-ACCESS  not-accessible
    STATUS      current
    DESCRIPTION
    "Mapping of port to Traffic Class level."
    ::= { prtTrafficClass 1 }

portTrafficClassEntry  OBJECT-TYPE
    SYNTAX      PortTrafficClassEntry
    MAX-ACCESS  not-accessible
    STATUS      current
    DESCRIPTION
    "An entry in portTrafficClassTable."
    INDEX   { portTrafficClassIdx1, portTrafficClassPortIdx }
    ::= { portTrafficClassTable 1 }

PortTrafficClassEntry ::=
    SEQUENCE {
        portTrafficClassIdx1       		Integer32,
        portTrafficClassPortIdx         Integer32,
        portTrafficClass    			Integer32
    }

portTrafficClassIdx1 OBJECT-TYPE
    SYNTAX  Integer32 (1..255)
    MAX-ACCESS  not-accessible
    STATUS  current
    DESCRIPTION
    "This attribute indicates the 1st index of the table.
    This may be the Idx of the Cnfg(1..255) being accessed; 
    Idx of 255 relates to the TmpCnfg, or any other Index."
    ::= { portTrafficClassEntry 1 }

portTrafficClassPortIdx OBJECT-TYPE
    SYNTAX      Integer32  (0..2147483647)
    MAX-ACCESS  not-accessible
    STATUS      current
    DESCRIPTION
    "This object indicates a unique Port Index.
     Refer to device specification for port Index."
    ::= { portTrafficClassEntry 2 }

portTrafficClass OBJECT-TYPE
    SYNTAX      Integer32  (0..7)
    MAX-ACCESS  read-write
    STATUS      current
    DESCRIPTION
    "This object indicates the Traffic Class level of this port."
    ::= { portTrafficClassEntry 3 }

--------------------------
--  Services Definitions
--------------------------
serviceTable OBJECT-TYPE
    SYNTAX     SEQUENCE OF ServiceEntry
    MAX-ACCESS not-accessible
    STATUS     current
    DESCRIPTION
      "Table of services."
   ::= { services 6 }

serviceEntry OBJECT-TYPE
    SYNTAX     ServiceEntry
    MAX-ACCESS not-accessible
    STATUS     current
    DESCRIPTION
      "An entry in the Service Table."
    INDEX { ifIndex, flowIndex, serviceIndex  }
    ::= { serviceTable 1 }

ServiceEntry ::= SEQUENCE {
    flowIndex				  Unsigned32,
    serviceIndex              Unsigned32,
    serviceRowStatus          RowStatus,
	serviceName				  SnmpAdminString,
    serviceBwProfileId	      Unsigned32
}

flowIndex	  OBJECT-TYPE
    SYNTAX     Unsigned32
    MAX-ACCESS not-accessible
    STATUS     current
    DESCRIPTION
      "Defines the Flow ID the service is associated to."
    ::= { serviceEntry 1 }

serviceIndex  OBJECT-TYPE
    SYNTAX     Unsigned32 (0..7)
    MAX-ACCESS not-accessible
    STATUS     current
    DESCRIPTION
      "Defines the Service ID - according to the CoS."
    ::= { serviceEntry 2 }

serviceRowStatus    OBJECT-TYPE
    SYNTAX        RowStatus
    MAX-ACCESS  read-create
    STATUS      current
    DESCRIPTION
      "This attribute is used to create a new row or to delete an existing row
       in the table."
    ::= {  serviceEntry 3 }

serviceName	     OBJECT-TYPE
    SYNTAX      SnmpAdminString
    MAX-ACCESS  read-create
    STATUS      current
    DESCRIPTION
      "This attribute defines the service name."
    ::= {  serviceEntry 4 }

serviceBwProfileId   OBJECT-TYPE
    SYNTAX       Unsigned32
    MAX-ACCESS  read-create
    STATUS      current
    DESCRIPTION
      "This variable holds the index of the Ingress BW profile assigned 
      to that service."
    ::= {  serviceEntry 5 }

--EVC CoS Table 

evcCosTable OBJECT-TYPE
 	SYNTAX  SEQUENCE OF EvcCosEntry
 	MAX-ACCESS  not-accessible
 	STATUS current
 	DESCRIPTION  
 	"This table defines  mapping of Ethernet Virtual Connection 
 	 (EVC) ID to Class of Service (CoS) ID "
 	::= {services 7}
 
evcCosEntry OBJECT-TYPE
     SYNTAX EvcCosEntry
     MAX-ACCESS not-accessible
     STATUS current
     DESCRIPTION  "An entry in table."
     INDEX {evcCosCnfgIdx,evcCosEvcIdx}
     ::= { evcCosTable 1}
 
EvcCosEntry ::=
     SEQUENCE {	
     evcCosCnfgIdx              Unsigned32,
     evcCosEvcIdx 	            Unsigned32,
     evcCosRowStatus            RowStatus,
--     evcCosServiceProfileIdx  Unsigned32,
	 evcCosEvcName				SnmpAdminString,
	 evcCosSpVlanId				Unsigned32
  	}
 
evcCosCnfgIdx OBJECT-TYPE
     SYNTAX Unsigned32 (1..255)
     MAX-ACCESS not-accessible
     STATUS current
     DESCRIPTION
     "This attribute indicates the Idx of the Cnfg(1..255) being 
      accessed ; Idx of 255 relates to the TmpCnfg."
     ::= {evcCosEntry 1}

evcCosEvcIdx OBJECT-TYPE
     SYNTAX Unsigned32 (1..4095)
     MAX-ACCESS not-accessible
     STATUS current
     DESCRIPTION
     "This attribute indicates EVC Id."
     ::= {evcCosEntry 2}

evcCosRowStatus	 OBJECT-TYPE
      SYNTAX     RowStatus 
      MAX-ACCESS read-create
      STATUS     current
      DESCRIPTION
      "This attribute allows to create/delete a row in this table."
      ::= {evcCosEntry 3}

--    ::= {evcCosEntry 4} (reserved)

evcCosEvcName   OBJECT-TYPE
     SYNTAX  	SnmpAdminString 
     MAX-ACCESS read-create
     STATUS current
     DESCRIPTION
     "A string that identifies the EVC. It should be unique 
     in the Maintenance Domain (i.e., in the managed network)
     Used as MEG ID field in OAM messages."
     ::= {evcCosEntry 5}

evcCosSpVlanId   OBJECT-TYPE
     SYNTAX     Unsigned32 
     MAX-ACCESS read-create
     STATUS current
     DESCRIPTION
     "This object indicates the SP (Service Provider) VLAN used when sending 
     an OAM message for the specified EVC."
     ::= {evcCosEntry 6}


-----------------------------------
--  Service Statistics Definitions
-----------------------------------

serviceStatTable OBJECT-TYPE
    SYNTAX     SEQUENCE OF ServiceStatEntry
    MAX-ACCESS not-accessible
    STATUS     current
    DESCRIPTION
      "Service statistics table."
   ::= { services 8 }

serviceStatEntry OBJECT-TYPE
    SYNTAX     ServiceStatEntry
    MAX-ACCESS not-accessible
    STATUS     current
    DESCRIPTION
      "An entry in the Service Statistics Table. "
    INDEX { ifIndex, flowIndex, serviceIndex, serviceStatDirection  }
    ::= { serviceStatTable 1 }

ServiceStatEntry ::= SEQUENCE {
	serviceStatDirection                INTEGER, 
	srvForwardGreenPackets	            Gauge32,
	srvForwardGreenPacktesOverflow	    Gauge32,
	srvForwardYellowPackets             Gauge32,
	srvForwardYellowPacketsOverflow     Gauge32,
	srvDiscardGreenPacket               Gauge32,
	srvDiscardGreenPacketOverflow       Gauge32,
	srvDiscardYellowRedPackets          Gauge32,
	srvDiscardYellowRedPacketsOverflow  Gauge32,
	srvForwardGreenBytes	            Gauge32,
	srvForwardGreenBytesOverflow        Gauge32,
	srvForwardYellowBytes               Gauge32,
	srvForwardYellowBytesOverflow       Gauge32,
	srvDiscardGreenBytes	            Gauge32,
	srvDiscardGreenBytesOverflow        Gauge32,
	srvDiscardYellowRedBytes            Gauge32,
	srvDiscardYellowRedBytesOverflow    Gauge32,
	srvResetStatsCmd                    INTEGER,
	srvDiscardYellowPackets             Gauge32,
	srvDiscardYellowPacketsOverflow     Gauge32,
	srvDiscardYellowBytes               Gauge32,
	srvDiscardYellowBytesOverflow       Gauge32,
	srvDiscardRedPackets                Gauge32,
	srvDiscardRedPacketsOverflow        Gauge32,
	srvDiscardRedBytes                  Gauge32,
	srvDiscardRedBytesOverflow          Gauge32
}

serviceStatDirection  OBJECT-TYPE
    SYNTAX     INTEGER 
    {
         upstream   (1),
         downstream (2)
    }
    MAX-ACCESS not-accessible
    STATUS     current
    DESCRIPTION
      "The direction in wich the measurement is taken."
    ::= {  serviceStatEntry 1 }


srvForwardGreenPackets	   OBJECT-TYPE
    SYNTAX    Gauge32
    MAX-ACCESS read-only
    STATUS     current
    DESCRIPTION
      "This attribute displays the counted number of forwarded packets 
      that where marked Green."
    ::= {  serviceStatEntry 2 }

srvForwardGreenPacktesOverflow OBJECT-TYPE
    SYNTAX    Gauge32
    MAX-ACCESS read-only
    STATUS     current
    DESCRIPTION
      "This attribute displays the number of times that the 
         forwardGreenPackets counter has overflowed."
    ::= {  serviceStatEntry 3 }

srvForwardYellowPackets  OBJECT-TYPE
    SYNTAX    Gauge32
    MAX-ACCESS read-only
    STATUS     current
    DESCRIPTION
      "This attribute displays the counted number of forwarded packets 
      that where marked Yellow."
    ::= {  serviceStatEntry 4 }

srvForwardYellowPacketsOverflow OBJECT-TYPE
    SYNTAX    Gauge32
    MAX-ACCESS read-only
    STATUS     current
    DESCRIPTION
      "This attribute displays the number of times that the 
         forwardYellowPackets counter has overflowed."
    ::= {  serviceStatEntry 5 }

srvDiscardGreenPacket OBJECT-TYPE
    SYNTAX    Gauge32
    MAX-ACCESS read-only
    STATUS     current
    DESCRIPTION
      "This attribute displays the counted number of discarded packets 
      that where marked Green."
    ::= {  serviceStatEntry 6 }

srvDiscardGreenPacketOverflow  OBJECT-TYPE
    SYNTAX    Gauge32
    MAX-ACCESS read-only
    STATUS     current
    DESCRIPTION
      "This attribute displays the number of times that the 
         discardGreenPacket counter has overflowed."
    ::= {  serviceStatEntry 7 }

srvDiscardYellowRedPackets OBJECT-TYPE
    SYNTAX    Gauge32
    MAX-ACCESS read-only
    STATUS     current
    DESCRIPTION
      "This attribute displays the counted number of discarded packets 
      that where marked Yellow or Red."
    ::= {  serviceStatEntry 8 }

srvDiscardYellowRedPacketsOverflow OBJECT-TYPE
    SYNTAX    Gauge32
    MAX-ACCESS read-only
    STATUS     current
    DESCRIPTION
      "This attribute displays the number of times that the 
         discardYellowRedPackets counter has overflowed."
    ::= {  serviceStatEntry 9 }

srvForwardGreenBytes	    OBJECT-TYPE
    SYNTAX    Gauge32
    MAX-ACCESS read-only
    STATUS     current
    DESCRIPTION
      "This attribute displays the counted number of forwarded bytes 
      that where marked Green."
    ::= {  serviceStatEntry 10 }

srvForwardGreenBytesOverflow    OBJECT-TYPE
    SYNTAX    Gauge32
    MAX-ACCESS read-only
    STATUS     current
    DESCRIPTION
      "This attribute displays the number of times that the 
         forwardGreenBytes counter has overflowed."
    ::= {  serviceStatEntry 11 }

srvForwardYellowBytes   OBJECT-TYPE
    SYNTAX    Gauge32
    MAX-ACCESS read-only
    STATUS     current
    DESCRIPTION
      "This attribute displays the counted number of forwarded bytes 
      that where marked Yellow."
    ::= {  serviceStatEntry 12 }

srvForwardYellowBytesOverflow OBJECT-TYPE
    SYNTAX    Gauge32
    MAX-ACCESS read-only
    STATUS     current
    DESCRIPTION
      "This attribute displays the number of times that the 
         forwardYellowBytes counter has overflowed."
    ::= {  serviceStatEntry 13 }

srvDiscardGreenBytes  OBJECT-TYPE
    SYNTAX    Gauge32
    MAX-ACCESS read-only
    STATUS     current
    DESCRIPTION
      "This attribute displays the counted number of discarded bytes 
      that where marked Green."
    ::= {  serviceStatEntry 14 }

srvDiscardGreenBytesOverflow  OBJECT-TYPE
    SYNTAX    Gauge32
    MAX-ACCESS read-only
    STATUS     current
    DESCRIPTION
      "This attribute displays the number of times that the 
         discardGreenBytes counter has overflowed."
    ::= {  serviceStatEntry 15}

srvDiscardYellowRedBytes OBJECT-TYPE
    SYNTAX    Gauge32
    MAX-ACCESS read-only
    STATUS     current
    DESCRIPTION
      "This attribute displays the counted number of discarded bytes 
      that where marked Yellow or Red."
    ::= {  serviceStatEntry 16 }

srvDiscardYellowRedBytesOverflow OBJECT-TYPE
    SYNTAX    Gauge32
    MAX-ACCESS read-only
    STATUS     current
    DESCRIPTION
      "This attribute displays the number of times that the 
         discardYellowRedBytes counter has overflowed."
    ::= {  serviceStatEntry 17 }


srvResetStatsCmd   OBJECT-TYPE
    SYNTAX       INTEGER
	{
       off(2),
	   on (3)
	}
    MAX-ACCESS  read-create
    STATUS  current
    DESCRIPTION
    "Reset statistic counters of the service."
   ::= { serviceStatEntry 18 }

srvDiscardYellowPackets  OBJECT-TYPE          
    SYNTAX    Gauge32
    MAX-ACCESS read-only
    STATUS     current
    DESCRIPTION
      "This attribute displays the counted number of discarded packets 
      that where marked Yellow."
    ::= {  serviceStatEntry 19 }


srvDiscardYellowPacketsOverflow  OBJECT-TYPE       
    SYNTAX    Gauge32
    MAX-ACCESS read-only
    STATUS     current
    DESCRIPTION
      "This attribute displays the number of times that the 
       discardYellowPackets counter has overflowed."
    ::= {  serviceStatEntry 20 }


srvDiscardYellowBytes               OBJECT-TYPE
   SYNTAX    Gauge32
   MAX-ACCESS read-only
   STATUS     current
   DESCRIPTION
      "This attribute displays the counted number of discarded bytes 
      that where marked Yellow."
    ::= {  serviceStatEntry 21 }

srvDiscardYellowBytesOverflow       OBJECT-TYPE
   SYNTAX    Gauge32
   MAX-ACCESS read-only
   STATUS     current
   DESCRIPTION
      "This attribute displays the number of times that the 
       discardYellowBytes counter has overflowed."
    ::= {  serviceStatEntry 22 }

srvDiscardRedPackets                OBJECT-TYPE
   SYNTAX    Gauge32
   MAX-ACCESS read-only
   STATUS     current
   DESCRIPTION
      "This attribute displays the counted number of discarded packets 
      that where marked Red." 
    ::= {  serviceStatEntry 23 }

srvDiscardRedPacketsOverflow        OBJECT-TYPE
   SYNTAX    Gauge32
   MAX-ACCESS read-only
   STATUS     current
   DESCRIPTION
       "This attribute displays the number of times that the 
        discardRedPackets counter has overflowed."
    ::= {  serviceStatEntry 24 }

srvDiscardRedBytes                  OBJECT-TYPE
   SYNTAX    Gauge32
   MAX-ACCESS read-only
   STATUS     current
   DESCRIPTION
      "This attribute displays the counted number of discarded bytes 
      that where marked Red."
    ::= {  serviceStatEntry 25 }

srvDiscardRedBytesOverflow          OBJECT-TYPE
   SYNTAX    Gauge32
   MAX-ACCESS read-only
   STATUS     current
   DESCRIPTION
      "This attribute displays the number of times that the 
       discardRedBytes counter has overflowed."
    ::= {  serviceStatEntry 26 }


 -- QoS Flow Mapping Definition
mappingProfileObjects OBJECT IDENTIFIER ::= {  services 9 }

 -- QoS Flow Mapping Profile table
flowMappingProfileTable OBJECT-TYPE
    SYNTAX SEQUENCE OF FlowMappingProfileEntry
    MAX-ACCESS not-accessible
    STATUS current
    DESCRIPTION
        "This table holds flow mapping profiles."
    ::= { mappingProfileObjects 1 } 

flowMappingProfileEntry OBJECT-TYPE
    SYNTAX  FlowMappingProfileEntry
    MAX-ACCESS not-accessible
    STATUS current
    DESCRIPTION
        "Each entry in this table describes one Flow mapping profile with
         one of its Flow Mapping supported, according to the Priority order.
         The information includes a reference to a Flow Mapping index.
        "
    INDEX { flowMappingProfileIndex, flowMappingProfilePriority }
    ::= { flowMappingProfileTable 1 }

FlowMappingProfileEntry ::= SEQUENCE {
    flowMappingProfileIndex        Unsigned32,
    flowMappingProfilePriority     INTEGER,
    flowMappingProfileRowStatus    RowStatus,
	flowMappingProfileNumOfMaps    Unsigned32,
    flowMappingProfileMapIndex     Unsigned32,
	flowMappingProfileName		   SnmpAdminString

}

flowMappingProfileIndex OBJECT-TYPE
    SYNTAX  Unsigned32
    MAX-ACCESS not-accessible
    STATUS current
    DESCRIPTION
        "A running index for the Flow Mapping Profile table."
    ::= { flowMappingProfileEntry 1 }

flowMappingProfilePriority OBJECT-TYPE
    SYNTAX  INTEGER
    MAX-ACCESS not-accessible
    STATUS current
    DESCRIPTION
        "The priority of the Mapping selected by flowMappingProfileMapIndex
         within the Flow Mapping Profile."
    ::= { flowMappingProfileEntry 2 }

flowMappingProfileRowStatus OBJECT-TYPE
    SYNTAX RowStatus
    MAX-ACCESS  read-create
    STATUS  current
    DESCRIPTION
       "This attribute is used to create a new row or to delete an existing row
       in the table."
    ::= { flowMappingProfileEntry 3 }

flowMappingProfileNumOfMaps OBJECT-TYPE
    SYNTAX  Unsigned32
    MAX-ACCESS read-create
    STATUS current
    DESCRIPTION
        "This attribute determines the number of the mappings
        associated to the Flow Mapping Profile."
    ::= { flowMappingProfileEntry 4 }

flowMappingProfileMapIndex OBJECT-TYPE
    SYNTAX  Unsigned32
    MAX-ACCESS read-create
    STATUS current
    DESCRIPTION
        "This attribute holds a reference to the mapping index.
        It specifies the mapping selected for the Mapping Profile
        for the selected Priority.
        When flowMappingProfileNumOfMaps=0, this attribute is not relevant."
    ::= { flowMappingProfileEntry 5 }

flowMappingProfileName    OBJECT-TYPE
    SYNTAX      SnmpAdminString
    MAX-ACCESS read-create
    STATUS     current
    DESCRIPTION
      "This attribute defines the name assigned to flowMappingIndex profile."
    ::= { flowMappingProfileEntry 6 }

-- QoS: Flow Mapping table

qosFlowMappingTable OBJECT-TYPE
    SYNTAX SEQUENCE OF QosFlowMappingEntry
    MAX-ACCESS not-accessible
    STATUS current
    DESCRIPTION
        "A table of Flow Mapping."
    ::= { mappingProfileObjects 2 }

qosFlowMappingEntry OBJECT-TYPE
    SYNTAX QosFlowMappingEntry
    MAX-ACCESS not-accessible
    STATUS current
    DESCRIPTION
        "Each entry in this table describes one Flow Mapping.
         The information includes combination (AND function) of all the 
         classifications, as defined in the qosFlowMappingCriteria field.
         Classifiers are: TOS, DSCP, VLAN ID, MAC and IP source and destination addresses, 
         IP protocol, IP Precedence, TCP and UDP source and destination ports."
    INDEX { qosFlowMappingIdx1, qosFlowMappingIdx2, qosFlowMappingIdx3 }
    ::= { qosFlowMappingTable 1 }

QosFlowMappingEntry ::= SEQUENCE {
    qosFlowMappingIdx1                Unsigned32,
	qosFlowMappingIdx2				  Unsigned32,
	qosFlowMappingIdx3				  Unsigned32,
    qosFlowMappingRowStatus           RowStatus,
    qosFlowMappingCriteria            BITS,
	qosFlowMappingIeee802dot1p		  Unsigned32,
	qosFlowMappingTos				  Unsigned32,
    qosFlowMappingFromDscp            Unsigned32,
    qosFlowMappingToDscp              Unsigned32,
    qosFlowMappingFromVlanId          Unsigned32,
    qosFlowMappingToVlanId            Unsigned32,
    qosFlowMappingFromSrcMacAddr      MacAddress,
    qosFlowMappingToSrcMacAddr        MacAddress,
    qosFlowMappingFromDestMacAddr     MacAddress,
    qosFlowMappingToDestMacAddr       MacAddress,
    qosFlowMappingFromSrcIpAddr       IpAddress,
    qosFlowMappingToSrcIpAddr         IpAddress,
    qosFlowMappingFromDestIpAddr      IpAddress,
    qosFlowMappingToDestIpAddr        IpAddress,
    qosFlowMappingFromTcpSrcPort      Unsigned32,
    qosFlowMappingToTcpSrcPort        Unsigned32,
    qosFlowMappingFromTcpDestPort     Unsigned32,
    qosFlowMappingToTcpDestPort       Unsigned32,
    qosFlowMappingFromUdpSrcPort      Unsigned32,
    qosFlowMappingToUdpSrcPort        Unsigned32,
    qosFlowMappingFromUdpDestPort     Unsigned32,
    qosFlowMappingToUdpDestPort       Unsigned32,
	qosFlowMappingFromIpPrecedence    Unsigned32,
    qosFlowMappingToIpPrecedence      Unsigned32,
	qosFlowMappingInnerIeee802dot1p   Unsigned32,
	qosFlowMappingFromInnerVlanId     Unsigned32,
	qosFlowMappingToInnerVlanId       Unsigned32,
	qosFlowMappingEtherType			  Unsigned32
		}

qosFlowMappingIdx1 OBJECT-TYPE
    SYNTAX Unsigned32
    MAX-ACCESS not-accessible
    STATUS current
    DESCRIPTION
        "
        - In case the table is accessed via flowMappingProfileTable
        this is a running index for the QoS Flow Mapping table.
		- In case the table is not accessed via flowMappingProfileTable,
        this will be the ifIndex of the XNI (bridge port) to which the 
        QoS mapping applies.
        "
    ::= { qosFlowMappingEntry 1 }

qosFlowMappingIdx2 OBJECT-TYPE
    SYNTAX Unsigned32
    MAX-ACCESS not-accessible
    STATUS current
    DESCRIPTION
        "An index for the QoS Flow Mapping table.
        - In case the table is accessed via flowMappingProfileTable
        the index will be fixed = 1.
        - In case the table is not accessed via flowMappingProfileTable,
        this will be the index of the Flow (EVC) to which the QoS mapping applies.
        "
    ::= { qosFlowMappingEntry 2 }

qosFlowMappingIdx3 OBJECT-TYPE
    SYNTAX Unsigned32
    MAX-ACCESS not-accessible
    STATUS current
    DESCRIPTION
        "An index for the QoS Flow Mapping table.
        - In case the table is accessed via flowMappingProfileTable
        the index will be fixed = 1.
        - In case the table is not accessed via flowMappingProfileTable,
        this will be the Priority to which the QoS mapping applies.
        "
    ::= { qosFlowMappingEntry 3 }

qosFlowMappingRowStatus OBJECT-TYPE
    SYNTAX RowStatus
    MAX-ACCESS  read-create
    STATUS  current
    DESCRIPTION
       "This attribute is used to create a new row or to delete an existing row
       in the table."
    ::= { qosFlowMappingEntry 4 }

qosFlowMappingCriteria OBJECT-TYPE
    SYNTAX BITS {
		 ieee802dot1p (0),
         tos          (1),
         dscp         (2),
         vlanId       (3),
         macSrcAddr   (4),
         macDestAddr  (5),
         ipSrcAddr    (6),
         ipDestAddr   (7),
         tcpSrcPort   (8),
         tcpDestPort  (9),
         udpSrcPort   (10),
         udpDestPort  (11),
		 ipPrecedence (12),
		 innerIeee802dot1p (13),
         innerVlanId (14),
         untagged     (15),
         nonIP        (16),
         etherType    (17)  
    }
    MAX-ACCESS read-create
    STATUS current
    DESCRIPTION
        "This attribute determines upon which criterion the flow
        will be mapped."
    ::= { qosFlowMappingEntry 5 }

qosFlowMappingIeee802dot1p OBJECT-TYPE
    SYNTAX Unsigned32
    MAX-ACCESS read-create
    STATUS current
    DESCRIPTION
        "This attribute determines which TOS values are applicable for that flow.
		Each bit (0..7) represents a different 802.1 P-bit value. 
		Setting '1' to the bit means that the corresponding 802.1 P-bit value is applicable.
         It is relevant only in case the ieee802dot1p bit(0) in qosFlowMappingCriteria equals 1."
    ::= { qosFlowMappingEntry 6 }

qosFlowMappingTos   OBJECT-TYPE
    SYNTAX     Unsigned32
    MAX-ACCESS read-create
    STATUS current
    DESCRIPTION
        "This attribute determines which TOS values are applicable for that flow.
		Each bit (0..7) represents a different TOS value. 
		Setting '1' to the bit means that the corresponding TOS value is applicable.
        It is relevant only in case the tos bit (1) in qosFlowMappingCriteria equals 1."
    ::= { qosFlowMappingEntry 7 }

qosFlowMappingFromDscp      OBJECT-TYPE
    SYNTAX     Unsigned32
    MAX-ACCESS read-create
    STATUS current
    DESCRIPTION
        "This attribute determines the first DSCP value to compare with in a range.
         It is relevant only in case the dscp bit (2) in qosFlowMappingCriteria equals 1."
    ::= { qosFlowMappingEntry 8 }

qosFlowMappingToDscp OBJECT-TYPE
    SYNTAX     Unsigned32
    MAX-ACCESS read-create
    STATUS current
    DESCRIPTION
        "This attribute determines the first DSCP value to compare with in a range.
         It is relevant only in case the dscp bit (2) in qosFlowMappingCriteria equals 1."
    ::= { qosFlowMappingEntry 9 }

qosFlowMappingFromVlanId    OBJECT-TYPE
    SYNTAX    Unsigned32
    MAX-ACCESS read-create
    STATUS current
    DESCRIPTION
        "This attribute determines the first VLAN ID value to compare with in a range.
         It is relevant only in case the vlanId bit (3) in qosFlowMappingCriteria equals 1."
    ::= { qosFlowMappingEntry 10 }

qosFlowMappingToVlanId    OBJECT-TYPE
    SYNTAX    Unsigned32
    MAX-ACCESS read-create
    STATUS current
    DESCRIPTION
        "This attribute determines the last VLAN ID value to compare with in a range.
         It is relevant only in case the vlanId bit (3) in qosFlowMappingCriteria equals 1."
    ::= { qosFlowMappingEntry 11 }

qosFlowMappingFromSrcMacAddr OBJECT-TYPE
    SYNTAX MacAddress
    MAX-ACCESS read-create
    STATUS current
    DESCRIPTION
        "This attribute determines the first source MAC address to compare with in a range.
         It is relevant only in case the macSrcAddr bit (4) in qosFlowMappingCriteria equals 1."
    ::= { qosFlowMappingEntry 12 }

qosFlowMappingToSrcMacAddr    OBJECT-TYPE
    SYNTAX    MacAddress
    MAX-ACCESS read-create
    STATUS current
    DESCRIPTION
        "This attribute determines the last source MAC address to compare with in a range.
         It is relevant only in case the macSrcAddr bit (4) in qosFlowMappingCriteria equals 1."
    ::= { qosFlowMappingEntry 13 }

qosFlowMappingFromDestMacAddr OBJECT-TYPE
    SYNTAX MacAddress
    MAX-ACCESS read-create
    STATUS current
    DESCRIPTION
        "This attribute determines the first destination MAC address to compare with in a range.
         It is relevant only in case the macDestAddr (5) bit in qosFlowMappingCriteria equals 1."
    ::= { qosFlowMappingEntry 14 }

qosFlowMappingToDestMacAddr OBJECT-TYPE
    SYNTAX MacAddress
    MAX-ACCESS read-create
    STATUS current
    DESCRIPTION
        "This attribute determines the last destination MAC address to compare with in a range.
         It is relevant only in case the macDestAddr (5) bit in qosFlowMappingCriteria equals 1."
    ::= { qosFlowMappingEntry 15 }

qosFlowMappingFromSrcIpAddr      OBJECT-TYPE
    SYNTAX      IpAddress
    MAX-ACCESS  read-create
    STATUS current
    DESCRIPTION
        "This attribute determines the first source IP address to compare with in a range.
         It is relevant only in case the ipSrcAddr (6) bit in qosFlowMappingCriteria equals 1."
    ::= { qosFlowMappingEntry 16 }

qosFlowMappingToSrcIpAddr  OBJECT-TYPE
    SYNTAX      IpAddress
    MAX-ACCESS  read-create
    STATUS current
    DESCRIPTION
        "This attribute determines the last source IP address to compare with in a range.
         It is relevant only in case the ipSrcAddr (6) bit in qosFlowMappingCriteria equals 1."
    ::= { qosFlowMappingEntry 17 }

qosFlowMappingFromDestIpAddr   OBJECT-TYPE
    SYNTAX       IpAddress
    MAX-ACCESS   read-create
    STATUS current
    DESCRIPTION
        "This attribute determines the first destination IP address to compare with in a range.
         It is relevant only in case the ipDestAddr (7) bit in qosFlowMappingCriteria equals 1."
    ::= { qosFlowMappingEntry 18 }

qosFlowMappingToDestIpAddr    OBJECT-TYPE
    SYNTAX       IpAddress
    MAX-ACCESS   read-create
    STATUS current
    DESCRIPTION
        "This attribute determines the last destination IP address to compare with in a range.
         It is relevant only in case the ipDestAddr (7) bit in qosFlowMappingCriteria equals 1."
    ::= { qosFlowMappingEntry 19 }

qosFlowMappingFromTcpSrcPort   OBJECT-TYPE
    SYNTAX     Unsigned32
    MAX-ACCESS read-create
    STATUS current
    DESCRIPTION
        "This attribute determines the first TCP source port to compare with in a range.
         It is relevant only in case the tcpSrcPort bit (8) in qosFlowMappingCriteria equals 1."
    ::= { qosFlowMappingEntry 20 }

qosFlowMappingToTcpSrcPort OBJECT-TYPE
    SYNTAX Unsigned32
    MAX-ACCESS read-create
    STATUS current
    DESCRIPTION
        "This attribute determines the last TCP source port to compare with in a range.
         It is relevant only in case the tcpSrcPort bit (8) in qosFlowMappingCriteria equals 1."
    ::= { qosFlowMappingEntry 21 }

qosFlowMappingFromTcpDestPort OBJECT-TYPE
    SYNTAX Unsigned32
    MAX-ACCESS read-create
    STATUS current
    DESCRIPTION
        "This attribute determines the first TCP destination port to compare with in a range.
         It is relevant only in case the tcpDestPort bit (9) in qosFlowMappingCriteria equals 1."
    ::= { qosFlowMappingEntry 22 }

qosFlowMappingToTcpDestPort    OBJECT-TYPE
    SYNTAX    Unsigned32
    MAX-ACCESS read-create
    STATUS current
    DESCRIPTION
        "This attribute determines the last TCP destination port to compare with in a range.
         It is relevant only in case the tcpDestPort bit (9) in qosFlowMappingCriteria equals 1."
    ::= { qosFlowMappingEntry 23 }

qosFlowMappingFromUdpSrcPort OBJECT-TYPE
    SYNTAX Unsigned32
    MAX-ACCESS read-create
    STATUS current
    DESCRIPTION
        "This attribute determines the first UDP source port to compare with in a range.
         It is relevant only in case the udpSrcPort bit (10) in qosFlowMappingCriteria equals 1."
   ::= { qosFlowMappingEntry 24 }

qosFlowMappingToUdpSrcPort OBJECT-TYPE
    SYNTAX Unsigned32
    MAX-ACCESS read-create
    STATUS current
    DESCRIPTION
        "This attribute determines the last UDP source port to compare with in a range.
         It is relevant only in case the udpSrcPort bit (10) in qosFlowMappingCriteria equals 1."
    ::= { qosFlowMappingEntry 25 }

qosFlowMappingFromUdpDestPort OBJECT-TYPE
    SYNTAX Unsigned32
    MAX-ACCESS read-create
    STATUS current
    DESCRIPTION
        "This attribute determines the first UDP destination port to compare with in a range.
         It is relevant only in case the udpDestPort bit (11) in qosFlowMappingCriteria equals 1."
    ::= { qosFlowMappingEntry 26 }

qosFlowMappingToUdpDestPort OBJECT-TYPE
    SYNTAX Unsigned32
    MAX-ACCESS read-create
    STATUS current
    DESCRIPTION
        "This attribute determines the last UDP destination port to compare with in a range.
         It is relevant only in case the udpDestPort bit (11) in qosFlowMappingCriteria equals 1."
    ::= { qosFlowMappingEntry 27 }

qosFlowMappingFromIpPrecedence OBJECT-TYPE
    SYNTAX     Unsigned32
    MAX-ACCESS read-create
    STATUS current
    DESCRIPTION
        "This attribute determines the first IpPrecedence value to compare with in a range.
         It is relevant only in case the IpPrecedence bit (12) in qosFlowMappingCriteria equals 1."
    ::= { qosFlowMappingEntry 28 }

qosFlowMappingToIpPrecedence OBJECT-TYPE
    SYNTAX     Unsigned32
    MAX-ACCESS read-create
    STATUS current
    DESCRIPTION
        "This attribute determines the last IpPrecedence value to compare with in a range.
         It is relevant only in case the IpPrecedence bit (12) in qosFlowMappingCriteria equals 1."
    ::= { qosFlowMappingEntry 29 }
 
qosFlowMappingInnerIeee802dot1p OBJECT-TYPE
    SYNTAX Unsigned32
    MAX-ACCESS read-create
    STATUS current
    DESCRIPTION
        "This attribute determines which TOS values are applicable for that flow.
		 Each bit (0..7) represents a different inner 802.1 P-bit value. 
		 Setting '1' to the bit means that the corresponding inner 802.1 P-bit value is applicable.
         It is relevant only in case the innerIeee802dot1p bit (13) in qosFlowMappingCriteria equals 1."
     ::= { qosFlowMappingEntry 30 }

qosFlowMappingFromInnerVlanId    OBJECT-TYPE
    SYNTAX    Unsigned32
    MAX-ACCESS read-create
    STATUS current
    DESCRIPTION
        "This attribute determines the first inner VLAN ID value to compare with in a range.
         It is relevant only in case the innerVlanId bit(14) in qosFlowMappingCriteria equals 1."
    ::= { qosFlowMappingEntry 31 }

qosFlowMappingToInnerVlanId    OBJECT-TYPE
    SYNTAX    Unsigned32
    MAX-ACCESS read-create
    STATUS current
    DESCRIPTION
        "This attribute determines the last inner VLAN ID value to compare with in a range.
         It is relevant only in case the innerVlanId bit(14) in qosFlowMappingCriteria equals 1."
    ::= { qosFlowMappingEntry 32 }

qosFlowMappingEtherType    OBJECT-TYPE
    SYNTAX    Unsigned32
    MAX-ACCESS read-create
    STATUS current
    DESCRIPTION
     "Determines the Tag Protocol Identifier (in Hex).
      For example: 
      0x8100 (C-TAG)
      0x88A8 (S-TAG)
      It is relevant only in case the etherType bit (17) in qosFlowMappingCriteria equals 1."
         ::= { qosFlowMappingEntry 33 }

  
-- CoS Profile Definition
cosProfileTable OBJECT-TYPE
    SYNTAX     SEQUENCE OF CosProfileEntry
    MAX-ACCESS not-accessible
    STATUS     current
    DESCRIPTION
      "Class of Service Profile table. 
      Each profile holds a priority method, and a mappring function 
      that maps the priority values (range according to the method) 
      into CoS values."
   ::= { services 10 }

cosProfileEntry OBJECT-TYPE
    SYNTAX     CosProfileEntry
    MAX-ACCESS not-accessible
    STATUS     current
    DESCRIPTION
      "A conceptual row where each row contains one CoS attributes."
    INDEX { cosProfileIndex }
    ::= { cosProfileTable 1 }

CosProfileEntry ::= SEQUENCE {
    cosProfileIndex          Unsigned32,
	cosProfileRowStatus      RowStatus,
    cosProfileCosMethod	     INTEGER,
    cosProfileName           SnmpAdminString,
	cosProfileCosMapping     OCTET STRING
}

cosProfileIndex   OBJECT-TYPE
    SYNTAX     Unsigned32 
    MAX-ACCESS not-accessible
    STATUS     current
    DESCRIPTION
      "Defines the CoS Profile ID."
    ::= { cosProfileEntry 1 }

cosProfileRowStatus   OBJECT-TYPE
    SYNTAX      RowStatus
    MAX-ACCESS  read-create
    STATUS      current
    DESCRIPTION
      "This attribute is used to create a new row or to delete an existing row
       in the table."
    ::= {  cosProfileEntry 2 }

cosProfileCosMethod	  OBJECT-TYPE
    SYNTAX      INTEGER
	{
	    ieee802dot1p 	(2),
	    tos          	(3),
        dscp     		(4),
		ipPrecedence    (5)
    }
    MAX-ACCESS  read-create
    STATUS     current
    DESCRIPTION
      "Defines the priority method upon CoS mapping is done."
    ::= { cosProfileEntry 3 }

cosProfileName    OBJECT-TYPE
    SYNTAX      SnmpAdminString
    MAX-ACCESS read-create
    STATUS     current
    DESCRIPTION
      "This attribute defines the name assigned to CoS profile."
    ::= { cosProfileEntry 4 }

cosProfileCosMapping  OBJECT-TYPE
    SYNTAX      OCTET STRING (SIZE(0..63))
    MAX-ACCESS read-create
    STATUS     current
    DESCRIPTION
      "This attribute defines the value of the CoS that is assigned
      for each priority. The number of the valid octets depends upon
	  the priority method selected:
      Octet 0 corresponds to priority = 0
      Octet 1 corresponds to priority = 1
      ...
      Octet 63 corresponds to priority = 63.
      "
    ::= { cosProfileEntry 5 }




-- Queue Profile Attributes
queueProfileObjects OBJECT IDENTIFIER ::= {  services 11 }

qProfileTable OBJECT-TYPE
    SYNTAX     SEQUENCE OF QProfileEntry
    MAX-ACCESS not-accessible
    STATUS     current
    DESCRIPTION
      "This table defines the profiles for a cluster of queues.
      "
   ::= { queueProfileObjects 1 }


qProfileEntry OBJECT-TYPE
    SYNTAX     QProfileEntry
    MAX-ACCESS not-accessible
    STATUS     current
    DESCRIPTION
      "A conceptual row where each row contains one Queue Cluster attribute. "
    INDEX { qProfileIndex  }
    ::= { qProfileTable 1 }

QProfileEntry ::= SEQUENCE {
    qProfileIndex                Unsigned32,
    qProfileRowStatus            RowStatus,
	qProfileName                 SnmpAdminString,
	qProfileNumberOfInternalQ	 Unsigned32,
	qProfileInternalQProfile     OCTET STRING
}

qProfileIndex  OBJECT-TYPE
    SYNTAX     Unsigned32
    MAX-ACCESS not-accessible
    STATUS     current
    DESCRIPTION
      "Defines the Queue Cluster Profile ID."
    ::= { qProfileEntry 1 }

qProfileRowStatus  OBJECT-TYPE
    SYNTAX      RowStatus
    MAX-ACCESS read-create
    STATUS     current
    DESCRIPTION
      "This attribute is used to create a new row or to delete an existing row
       in the table."
    ::= { qProfileEntry 2 }

qProfileName    OBJECT-TYPE
    SYNTAX       SnmpAdminString
    MAX-ACCESS read-create
    STATUS     current
    DESCRIPTION
      "This attribute holds the name of the Queue cluster profile."
    ::= { qProfileEntry 3 }

qProfileNumberOfInternalQ	OBJECT-TYPE
    SYNTAX      Unsigned32
    MAX-ACCESS read-create
    STATUS     current
    DESCRIPTION
      "This attribute holds the number of the internal queue profiles
      that are pointed by qInternalQProfile."
    ::= { qProfileEntry 4 }


qProfileInternalQProfile  OBJECT-TYPE
    SYNTAX      OCTET STRING
    MAX-ACCESS read-create
    STATUS     current
    DESCRIPTION
      "This attribute holds the indexes to the queue profiles
      in the qInternalProfileTable.
      Each couple of octets holds an index to the qInternalProfileTable."
    ::= { qProfileEntry 5 }


qInternalProfileTable OBJECT-TYPE
    SYNTAX     SEQUENCE OF QInternalProfileEntry
    MAX-ACCESS not-accessible
    STATUS     current
    DESCRIPTION
      "This table holds queue profiles."
   ::= { queueProfileObjects 2 }


qInternalProfileEntry OBJECT-TYPE
    SYNTAX     QInternalProfileEntry
    MAX-ACCESS not-accessible
    STATUS     current
    DESCRIPTION
      "A conceptual row where each row contains one Queue attribute. "
    INDEX { qInternalProfileIndex  }
    ::= { qInternalProfileTable 1 }


QInternalProfileEntry ::= SEQUENCE {
    qInternalProfileIndex                Unsigned32,
	qInternalProfileRowStatus            RowStatus,
    qInternalProfileScheduling	         INTEGER,
    qInternalProfileWFQWeight            Unsigned32,
	qInternalProfileQueueLength          Unsigned32,
	qInternalProfileWredStartDropThresh	 Unsigned32,
	qInternalProfileWredDropAllThresh	 Unsigned32,
	qInternalProfileWredDropProbability  Unsigned32,
	qInternalProfileRateLimit            Unsigned32,
	qInternalProfileShaperProfile        Unsigned32


 }

qInternalProfileIndex  OBJECT-TYPE
    SYNTAX     Unsigned32
    MAX-ACCESS not-accessible
    STATUS     current
    DESCRIPTION
      "Defines the Queue Profile ID."
    ::= { qInternalProfileEntry 1 }

qInternalProfileRowStatus  OBJECT-TYPE
    SYNTAX      RowStatus
    MAX-ACCESS read-create
    STATUS     current
    DESCRIPTION
      "This attribute is used to create a new row or to delete an existing row
       in the table."
    ::= { qInternalProfileEntry 2 }


qInternalProfileScheduling	  OBJECT-TYPE
    SYNTAX       INTEGER
	{
	   wfq         (1),
	   strict      (2),
	   bestEffort  (3)
	}
    MAX-ACCESS read-create
    STATUS     current
    DESCRIPTION
      "This attribute determines the queue scheduling method."
    ::= { qInternalProfileEntry 3 }

qInternalProfileWFQWeight    OBJECT-TYPE
    SYNTAX        Unsigned32
    MAX-ACCESS read-create
    STATUS     current
    DESCRIPTION
      "This attribute determines the weight that each WFQ (Weighted Fair Queue)
      participant gets.
      It is applicable only when scheduling is configured to WFQ."
    ::= { qInternalProfileEntry 4 }

qInternalProfileQueueLength   OBJECT-TYPE
    SYNTAX        Unsigned32
    MAX-ACCESS read-create
    STATUS     current
    DESCRIPTION
      "This attribute determines the length of the queue."
    ::= { qInternalProfileEntry 5 }

qInternalProfileWredStartDropThresh OBJECT-TYPE
    SYNTAX     	 Unsigned32
    MAX-ACCESS read-create
    STATUS     current
    DESCRIPTION
      "This attribute determines the length that the queue (Start Value)
      must reach before the packets colored yellow will start being dropped
      by the WRED (Weighted Random Early Detection/Discard) mechanism.
      WRED is one the most commonly used method for congestion avoidance."
    ::= { qInternalProfileEntry 6 }

qInternalProfileWredDropAllThresh  OBJECT-TYPE
    SYNTAX     	 Unsigned32
    MAX-ACCESS read-create
    STATUS     current
    DESCRIPTION
      "This attribute determines the length that the queue (Stop Value)
      must reach before the WRED (Weighted Random Early Detection)
      shaper mechanism stops dropping randomly, 
      and just drops all further packets marked as yellow."
    ::= { qInternalProfileEntry 7 }

qInternalProfileWredDropProbability  OBJECT-TYPE
    SYNTAX      Unsigned32
    MAX-ACCESS read-create
    STATUS     current
    DESCRIPTION
      "This attribute determines the percentage of packets that are being dropped
      at the point when the length of the queue reaches the Stop value. 
      So, effectively, this defines how quickly the rate of dropping packet must
      increase as the queue length grows from the Start Value to the Stop Value."
    ::= { qInternalProfileEntry 8 }

qInternalProfileRateLimit   OBJECT-TYPE
    SYNTAX		Unsigned32
    MAX-ACCESS	read-create
    STATUS		current
    DESCRIPTION
    "This attribute determines the Rate Limit of the queue in Kbps.
     Value=0 represents best effort."      
    ::= { qInternalProfileEntry 9 }

qInternalProfileShaperProfile   OBJECT-TYPE
    SYNTAX		Unsigned32
    MAX-ACCESS	read-create
    STATUS		current
    DESCRIPTION
    "This attribute defines the Shaper Profile (bwProfileIndex from bwProfileTable)
     assigned to this qInternalProfile. Valid range of bwProfileIndex for Shaper
     Profiles is 0x8000001-0x8000041.
     If set to '0', no  profile is assigned to this qInternalProfile."      
    ::= { qInternalProfileEntry 10 }


queueGroupTable OBJECT-TYPE
    SYNTAX     SEQUENCE OF QueueGroupEntry
    MAX-ACCESS not-accessible
    STATUS     current
    DESCRIPTION
      "This table defines the queue groups/blocks,their level and connections between them."
   ::= { queueProfileObjects 3 }

queueGroupEntry OBJECT-TYPE
    SYNTAX     QueueGroupEntry
    MAX-ACCESS not-accessible
    STATUS     current
    DESCRIPTION
      "A conceptual row where each row contains one Queue group. "
    INDEX {queueGroupName, queueGroupQBlockLevel,queueGroupQBlockIdx}
    ::= { queueGroupTable 1 }

QueueGroupEntry ::= SEQUENCE {
    queueGroupName                 SnmpAdminString,
	queueGroupQBlockLevel          Unsigned32,
    queueGroupQBlockIdx		       Unsigned32,  
    queueGroupRowStatus            RowStatus,  
   	queueGroupQBlockProfile        Unsigned32,
	queueGroupQBlockShaperProfile  Unsigned32,
	queueGroupPointToQBlock	       SnmpAdminString, 
	queueGroupPointToInternalQueue Unsigned32 ,
	queueGroupQBlockName	       SnmpAdminString
	   }

queueGroupName  OBJECT-TYPE
    SYNTAX     SnmpAdminString (SIZE (1..32))
    MAX-ACCESS not-accessible
    STATUS     current
    DESCRIPTION
      "Defines the Queue Group unique name."
    ::= { queueGroupEntry 1 }

queueGroupQBlockLevel	OBJECT-TYPE
    SYNTAX     Unsigned32
    MAX-ACCESS not-accessible
    STATUS     current
    DESCRIPTION
      "This attribute holds the Level of the Queue Block .First level is 1.
       NA=2^32-1."
    ::= { queueGroupEntry 2 } 

queueGroupQBlockIdx    OBJECT-TYPE
    SYNTAX     Unsigned32
    MAX-ACCESS not-accessible
    STATUS     current
    DESCRIPTION
      "This attribute holds the ID of the Queue Block.
       NA=2^32-1."
       ::= { queueGroupEntry 3 }

queueGroupRowStatus  OBJECT-TYPE
    SYNTAX      RowStatus
    MAX-ACCESS read-create
    STATUS     current
    DESCRIPTION
      "This attribute is used to create a new row or to delete an existing row
       in the table."
    ::= { queueGroupEntry 4 }	

queueGroupQBlockProfile  OBJECT-TYPE
    SYNTAX      Unsigned32
    MAX-ACCESS read-create
    STATUS     current
    DESCRIPTION
      "This attribute defines the Queue profile assigned to this Queue Block.
       This object points to qProfileIndex in qProfileTable. "
    ::= { queueGroupEntry 5 }

queueGroupQBlockShaperProfile  OBJECT-TYPE
    SYNTAX     Unsigned32
    MAX-ACCESS read-create
    STATUS     current
    DESCRIPTION
      "This attribute defines the Shaper profile assigned to this Queue Block."
    ::= { queueGroupEntry 6 }

queueGroupPointToQBlock  OBJECT-TYPE
    SYNTAX      SnmpAdminString(SIZE (1..32))
    MAX-ACCESS read-create
    STATUS     current
    DESCRIPTION
      "This attribute defines the Queue Block name of the next Queue Block level 
       that is pointed by this Queue Block."
    ::= { queueGroupEntry 7 }							  

queueGroupPointToInternalQueue  OBJECT-TYPE
    SYNTAX      Unsigned32
    MAX-ACCESS read-create
    STATUS     current
    DESCRIPTION
      "This attribute defines the internal queue whithin queueGroupPointToQBlock
       that is pointed by this Queue Block."
    ::= { queueGroupEntry 8 }

queueGroupQBlockName    OBJECT-TYPE
    SYNTAX     SnmpAdminString(SIZE (1..32))
    MAX-ACCESS read-create
    STATUS     current
    DESCRIPTION
      "This attribute holds the name of the Queue Block."
    ::= { queueGroupEntry 9 }

-- Marking Profile Attributes
markingProfileTable OBJECT-TYPE
    SYNTAX     SEQUENCE OF MarkingProfileEntry
    MAX-ACCESS not-accessible
    STATUS     current
    DESCRIPTION
      "Marking profile table. Each profile holds a marking function 
      which converts CoS values to Service Provider priority values."
   ::= { services 12 }


markingProfileEntry OBJECT-TYPE
    SYNTAX     MarkingProfileEntry
    MAX-ACCESS not-accessible
    STATUS     current
    DESCRIPTION
      "A conceptual row where each row contains one Marking attribute. "
    INDEX { markingProfileIndex }
    ::= { markingProfileTable 1 }

MarkingProfileEntry ::= SEQUENCE {
    markingProfileIndex        Unsigned32,
	markingProfileRowStatus    RowStatus,
	markingProfileName         SnmpAdminString,
	markingSpVlanPBit  		   OCTET STRING,
	markingProfileMethod	   INTEGER
}

markingProfileIndex   OBJECT-TYPE
    SYNTAX          Unsigned32 
    MAX-ACCESS not-accessible
    STATUS     current
    DESCRIPTION
      "Defines the Marking Profile ID."
    ::= { markingProfileEntry 1 }


markingProfileRowStatus    OBJECT-TYPE
    SYNTAX        RowStatus
    MAX-ACCESS  read-create
    STATUS      current
    DESCRIPTION
      "This attribute is used to create a new row or to delete an existing row
       in the table."
    ::= {  markingProfileEntry 2 }


markingProfileName OBJECT-TYPE
    SYNTAX           SnmpAdminString
    MAX-ACCESS read-create
    STATUS     current
    DESCRIPTION
      "This attribute defines the unique name assigned to the Marking profile."
    ::= { markingProfileEntry 3 }


markingSpVlanPBit	 OBJECT-TYPE
    SYNTAX     	   OCTET STRING (SIZE (0..63))
    MAX-ACCESS read-create
    STATUS     current
    DESCRIPTION
     "For ETX-202A :
      This attribute defines the value of the SP VLAN P-Bit that is assigned
      for each CoS: 
      Octet 0 corresponds to CoS = 0
      Octet 1 corresponds to CoS = 1
      ...
      Octet 7 corresponds to CoS = 7.

      For LA-210 from V1.5 :
	  This attribute defines the value of the SP VLAN P-Bit that is assigned
      for each frame according to the value of markingProfileMethod parameter :
	  Octet 0 corresponds to value 0 of 802.1 P-bit/DSCP/TOS.
      Octet 1 corresponds to value 1 of 802.1 P-bit/DSCP/TOS.
      ...
      Octet 7 corresponds to value 7 of 802.1 P-bit/DSCP/TOS.
	  Octets 8-63 correspond to DSCP values 8-63.
      "
    ::= { markingProfileEntry 4 }

markingProfileMethod OBJECT-TYPE
    SYNTAX      INTEGER
	{
	    ieee802dot1p 	(2),
	    tos          	(3),
        dscp     		(4),
		ipPrecedence    (5)
    }
    MAX-ACCESS  read-create
    STATUS     current
    DESCRIPTION
      "This attribute defines the method upon which marking is done."
    ::= { markingProfileEntry 5 }

-- 
-- file :D:\Synergy\WorkArea\545\mib_rad\txt\atmRoute.txt
-- 
--Version:   4.95
--
--First Version Date:   12-Aug-2002              
--By:        Shay Harari
--File:      atmRouter.txt
--
--Last update: 20-Oct-2002
--By: Ilana Schvetz 


radAtmRouter  OBJECT IDENTIFIER  ::= { radAtm 10 }


-- Extension of the ATM Logical IP Subnet Interface Mapping Table
-- ( ipoaLisIfMappingTable from RFC 2320 )

atmIpoaLisIfMappingXTable OBJECT-TYPE
	SYNTAX SEQUENCE OF AtmIpoaLisIfMappingXEntry
	MAX-ACCESS not-accessible
	STATUS current
	DESCRIPTION
    "This table is an extension of a table 
     from RFC 2320: ipoaLisIfMappingTable - 
     The ATM Logical IP Subnet Interface Mapping Table."
	::= { radAtmRouter 1 }

atmIpoaLisIfMappingXEntry OBJECT-TYPE
	SYNTAX AtmIpoaLisIfMappingXEntry
	MAX-ACCESS not-accessible
	STATUS current
	DESCRIPTION
    "Conceptual row in ipoaLisIfMappingTable."
	AUGMENTS { ipoaLisIfMappingEntry }
	::= { atmIpoaLisIfMappingXTable 1 }

AtmIpoaLisIfMappingXEntry ::= SEQUENCE {
	atmIpoaLisIfMappingType
		INTEGER,
	atmIpoaLisIfMappingIPAddress
		IpAddress	 
 }

atmIpoaLisIfMappingType OBJECT-TYPE
	SYNTAX  INTEGER {
       notApplicable(1),
	   static(2),
	   inAtmArp(3)
     }
    MAX-ACCESS  read-create
    STATUS  current
    DESCRIPTION
	"This object indicates the Mapping Type."
	::= { atmIpoaLisIfMappingXEntry 1 }

atmIpoaLisIfMappingIPAddress OBJECT-TYPE
    SYNTAX  IpAddress
	MAX-ACCESS  read-create
    STATUS  current
    DESCRIPTION
	"This parameter is applicable for 
	atmIpoaLisIfMappingTypeIP=static(2). 
	This parameter is the IP Address assigned 
	by the user when applicable."
	::= { atmIpoaLisIfMappingXEntry 2 }


radAtmRtrInAtmArpInterval OBJECT-TYPE   
	SYNTAX  Integer32 
	MAX-ACCESS  read-write    
	STATUS  current
	DESCRIPTION
	"The time interval (in seconds) between sending of
	 two InATMARP requests."
	::= { radAtmRouter 2 }

radAtmRtrInAtmArpAgingTime OBJECT-TYPE   
	SYNTAX  Integer32 
	MAX-ACCESS  read-write    
	STATUS  current
	DESCRIPTION
	"The time (in seconds) that passes until an 
	 entry is deleted, unless this entry
	 was previously updated by a new inATMARP 
	 request or response.
	 
	 This variable value should be greater than 
	 the value of radAtmRtrInAtmArpInterval,
	 so that the entry won't be deleted before
	 an InATMARP request was sent."
	::= { radAtmRouter 3 }
-- 
-- file :D:\Synergy\WorkArea\545\mib_rad\txt\voiceIf.txt
-- 
--Version: 
--Date: 25/02/2003
--By: Yig'al Hachmon
--V:\doc\rdv\mib\ver495\voiceIf.txt


--Last changed by Liora Gafni, 17 Aug 2004

--diverseIfWanGen	OBJECT IDENTIFIER ::= {wanGen 6 }

voiceIf		 OBJECT IDENTIFIER ::= {diverseIfWanGen 13}

-- Voice Interface Ringing Cadence Configuration table  

voiceIfCadenceCnfgTable OBJECT-TYPE
       SYNTAX  SEQUENCE OF VoiceIfCadenceCnfgEntry
       MAX-ACCESS  not-accessible
       STATUS  current
       DESCRIPTION
       "Voice port ringing cadence configuration table.
        Each ringing cycle, indexed by voiceIfCadenceIdx,
        consists of a number of ring ON-Period/ring OFF-Period 
        pairs. Pairs are indexed sequentially, according to 
        voiceIfCadencePeriodIdx: 1,2,...number of pairs"
      ::= { voiceIf 1 }
  
voiceIfCadenceCnfgEntry OBJECT-TYPE
       SYNTAX VoiceIfCadenceCnfgEntry
       MAX-ACCESS not-accessible
       STATUS current
       DESCRIPTION
          "Ringing cadence configuration per voice port."
       INDEX  {voiceIfCadenceCnfgIdx, 
               voiceIfCadencePortIdx,	
       		   voiceIfCadenceIdx,
       		   voiceIfCadencePeriodIdx}
       ::= {voiceIfCadenceCnfgTable 1}

VoiceIfCadenceCnfgEntry ::=
         SEQUENCE {
         voiceIfCadenceCnfgIdx	          Integer32,
         voiceIfCadencePortIdx	          Integer32,
         voiceIfCadenceIdx	              Integer32,
         voiceIfCadencePeriodIdx		  Integer32,
         voiceIfCadenceRowStatus		  RowStatus,
         voiceIfCadenceRingOnPeriod       Integer32,
         voiceIfCadenceRingOffPeriod      Integer32
        	}
  
voiceIfCadenceCnfgIdx OBJECT-TYPE
    SYNTAX  Integer32
    MAX-ACCESS  not-accessible
    STATUS  current
    DESCRIPTION
    "This object indicates the Idx of the 
     Agent Cnfg the following objects refer to.
     255=Temporary Cnfg (when relevant, 
	 Set is done only to this configuration).
     For Agents that support only one configuration, 
     this object will be  constant=1. "
    ::= {voiceIfCadenceCnfgEntry 1}

voiceIfCadencePortIdx	 OBJECT-TYPE
    SYNTAX  Integer32 
    MAX-ACCESS  not-accessible
    STATUS  current
    DESCRIPTION
    "Voice Port Index. May equal to the value of ifIndex."
    ::= {voiceIfCadenceCnfgEntry 2}

voiceIfCadenceIdx	       OBJECT-TYPE  
    SYNTAX  Integer32 
    MAX-ACCESS  not-accessible
    STATUS  current
    DESCRIPTION
    "Cadence (ringing type) index."
    ::= {voiceIfCadenceCnfgEntry 3}

voiceIfCadencePeriodIdx	       OBJECT-TYPE  
    SYNTAX  Integer32 
    MAX-ACCESS  not-accessible
    STATUS  current
    DESCRIPTION
    "Periods index (pair number) in a ringing cycle Cadence.
    This index must be sequential, start from 1. Its maximum 
    value is the number of pairs of certain ringing type.
    
    For Vmux-110, one or two period pairs may be defined."
    ::= { voiceIfCadenceCnfgEntry 4}

voiceIfCadenceRowStatus OBJECT-TYPE
    SYNTAX RowStatus
    MAX-ACCESS read-create
    STATUS current
    DESCRIPTION
    "This attribute allows to create/delete
     ringing cadence entry in this table.
     For Vmux-110, only a single cadance can be defined.
     Delete action of a period entry can be performed only 
     if it is the last existing period of the cadance."
    ::= {voiceIfCadenceCnfgEntry 5 }

voiceIfCadenceRingOnPeriod	 OBJECT-TYPE	
    SYNTAX  Integer32 
    MAX-ACCESS  read-create
    STATUS  current
    DESCRIPTION
	"Duration (in tenth of seconds) of Ringing (ON) 
	 period."
    ::= { voiceIfCadenceCnfgEntry 6}

voiceIfCadenceRingOffPeriod  OBJECT-TYPE	
    SYNTAX  Integer32 
    MAX-ACCESS  read-create
    STATUS  current
    DESCRIPTION
	"Duration (in tenth of seconds) of Silence (OFF) 
     period."
    ::= { voiceIfCadenceCnfgEntry 7}


-- Voice Interface Configuration & Status table  

voiceIfCnfgTable OBJECT-TYPE
       SYNTAX  SEQUENCE OF VoiceIfCnfgEntry
       MAX-ACCESS  not-accessible
       STATUS  current
       DESCRIPTION
           "Voice port configuration table."
       ::= { voiceIf 2 }
  
voiceIfCnfgEntry OBJECT-TYPE
       SYNTAX VoiceIfCnfgEntry
       MAX-ACCESS not-accessible
       STATUS current
       DESCRIPTION
          "Configuration per voice port."
       INDEX   {voiceIfCnfgIdx,voiceIfPortIdx}
       ::= { voiceIfCnfgTable 1 }

VoiceIfCnfgEntry ::=
         SEQUENCE {
         voiceIfCnfgIdx         Integer32,
         voiceIfPortIdx         Integer32,
		 voiceIfRingingTimeout  Integer32,
		 voiceIfFlashTimeout    Integer32,
		 voiceIfRxGain		    Integer32,
		 voiceIfTxGain		    Integer32,
		 voiceIfSignalingABCD   OCTET STRING,
		 voiceIfState           INTEGER,
		 voiceIfCallState		INTEGER
		 }
  
voiceIfCnfgIdx  OBJECT-TYPE
    SYNTAX  Integer32
    MAX-ACCESS  not-accessible
    STATUS  current
    DESCRIPTION
    "This object indicates the Idx of the 
     Agent Cnfg the following objects refer to.
     255=Temporary Cnfg (when relevant, 
	 Set is done only to this configuration).
     For Agents that support only one configuration, 
     this object will be  constant=1. "
    ::= { voiceIfCnfgEntry 1}

voiceIfPortIdx  OBJECT-TYPE
    SYNTAX  Integer32 
    MAX-ACCESS  not-accessible
    STATUS  current
    DESCRIPTION
    "Index of voice port ."
    ::= {voiceIfCnfgEntry 2}

voiceIfRingingTimeout  OBJECT-TYPE  
    SYNTAX  Integer32 
    MAX-ACCESS  read-write
    STATUS  current
    DESCRIPTION
    "Ringing timeout in seconds."
    ::= {voiceIfCnfgEntry 3}
 
voiceIfFlashTimeout OBJECT-TYPE  
    SYNTAX  Integer32 
    MAX-ACCESS  read-write
    STATUS  current
    DESCRIPTION
    "A time period in milliseconds. Flash (Register Recall)
     is detected if On-Hook time is shorter than this timeout."
    ::= {voiceIfCnfgEntry 4}

voiceIfRxGain OBJECT-TYPE  
    SYNTAX  Integer32 
    MAX-ACCESS  read-write
    STATUS  current
    DESCRIPTION
    "Receive gain in dB."
    ::= {voiceIfCnfgEntry 5}

voiceIfTxGain OBJECT-TYPE  
    SYNTAX  Integer32 
    MAX-ACCESS  read-write
    STATUS  current
    DESCRIPTION
    "Transmission gain in dB."
    ::= {voiceIfCnfgEntry 6}


voiceIfSignalingABCD OBJECT-TYPE  
    SYNTAX  OCTET STRING 
    MAX-ACCESS  read-write
    STATUS  current
    DESCRIPTION
    "Octet String. 
     Nibble No. 1 represents ON  Hook (same for Rx and Tx).
     Nibble No. 2 represents OFF Hook (same for Rx and Tx).
     Nibble No. 3 represents Reverse Polarity.
     Nibble No. 4 represents Ring pattern 1.
	 Nibble No. 5 represents Ring pattern 2.
	 Nibble No. 6 is not used.
	 The bits will be as following:
       Bit 1 = Bit A - ON  Hook	 (LSB)
	   Bit 2 = Bit B - ON  Hook
	   Bit 3 = Bit C - ON  Hook
	   Bit 4 = Bit D - ON  Hook
	   Bit 5 = Bit A - OFF Hook
	   Bit 6 = Bit B - OFF Hook
	   Bit 7 = Bit C - OFF Hook
	   Bit 8 = Bit D - OFF Hook	 
	   Bit  9 = Bit A - Reverse Polarity
       Bit 10 = Bit B - Reverse Polarity
       Bit 11 = Bit C - Reverse Polarity
       Bit 12 = Bit D - Reverse Polarity  
       Bit 13 = Bit A - Ring 1
       Bit 14 = Bit B - Ring 1
       Bit 15 = Bit C - Ring 1
       Bit 16 = Bit D - Ring 1   
 	   Bit 17 = Bit A - Ring 2
       Bit 18 = Bit B - Ring 2
       Bit 19 = Bit C - Ring 2
       Bit 20 = Bit D - Ring 2   
       Bits 21...24 = 0 (not used).  (Bit 24 is MSB).

	   For Vmux-110:
	   Ring 1 and Ring 2 are used. The default is 3 octets.
	   (MSB) 0000  1011  1011  1001  1011  1010 (LSB)"  
    ::= {voiceIfCnfgEntry 7}

voiceIfState          OBJECT-TYPE   
      SYNTAX  INTEGER {
		 notApplicable (1),
		 onHook        (2),	--ON Hook State = idle
		 offHook       (3) -- OFF HOOK state
		}
      MAX-ACCESS  read-only
      STATUS  current
      DESCRIPTION
      "Attribute indicating voice port state."   
     ::= { voiceIfCnfgEntry 8}

voiceIfCallState    OBJECT-TYPE   
      SYNTAX  INTEGER {
		 noCall        (1),
		 oos           (2),	-- out of service
		 dialing       (3), 
         waitForAlert  (4),
         waitForConnect(5),
         ringing       (6),
         active        (7),
         waitForReject (8),
         waitForInfo   (9)
		}
      MAX-ACCESS  read-only
      STATUS  current
      DESCRIPTION
      "Attribute indicating the status of the call on this port.
       In Vmux devices this attribute is used for FXS ports."   
     ::= { voiceIfCnfgEntry 9}

  

-- 
-- file :D:\Synergy\WorkArea\545\mib_rad\txt\radGsm.txt
-- 
-- RAD-GSM-MIB DEFINITIONS ::= BEGIN

--Title:     RAD's GSM INTERFACE MIB
--Version:   5.30
--Date:      25.01.2006
--By:        Shay Harari
--File:      radGsm.txt
--
--Last update: 23-Dec-2007 by Shay Harari


gsmInterface  OBJECT IDENTIFIER  ::=  {diverseIfWanGen 14}

prtGsmConfig  OBJECT IDENTIFIER  ::=  {gsmInterface 1}


-- GSM Interface Configuration Table

prtGsmConfigTable OBJECT-TYPE
	SYNTAX  SEQUENCE OF PrtGsmConfigEntry
	MAX-ACCESS  not-accessible
	STATUS  current
	DESCRIPTION
	"GSM Interface Configuration Table."
	::= { prtGsmConfig 1}
   
prtGsmConfigEntry   OBJECT-TYPE
	SYNTAX  PrtGsmConfigEntry
	MAX-ACCESS  not-accessible
	STATUS  current
	DESCRIPTION
	"An entry in the GSM Interface Configuration Table."
	INDEX { prtGsmConfigIdx1, prtGsmConfigIdx2 }
	::= { prtGsmConfigTable 1}

PrtGsmConfigEntry ::=
	SEQUENCE {
		prtGsmConfigIdx1						Unsigned32,
		prtGsmConfigIdx2						Unsigned32,
		prtGsmConfigIfType						INTEGER,
		prtGsmConfigUplinkTxDirection			INTEGER,
		prtGsmConfigSubChRate					INTEGER,
		prtGsmConfigClockTracking				INTEGER,
		prtGsmConfigTrauIdleFrame				INTEGER,
		prtGsmConfigDownlinkTrauSilenceFrame	INTEGER,
		prtGsmConfigGprsFrame					INTEGER,
		prtGsmConfigUnkTrauFrameSuppression		INTEGER,
		prtGsmConfigUnkTrauFrameOptimization	INTEGER,
		prtGsmConfigSilenceSuppressionRatio		Unsigned32,
		prtGsmConfigStatus						INTEGER,
		prtGsmConfigUpstreamOptimization		BITS,
		prtGsmConfigDownstreamOptimization		BITS,
		prtGsmConfigByteReversal				INTEGER,
		prtGsmConfigTxJitter					Unsigned32,
		prtGsmConfigSpdThreshold				Unsigned32
		}
 
prtGsmConfigIdx1 OBJECT-TYPE
	SYNTAX  Unsigned32
	MAX-ACCESS  not-accessible
	STATUS  current
	DESCRIPTION
	"The first index of the table.
	 
	 This object might represent the Configuration Index (1..100) being accessed,
	 where Index=255 relates to the TmpCnfg.
	 For devices with multiple configurations, Set is permitted to TmpCnfg(255) only.
	 
	 Not-Applicable = 1."
	::= { prtGsmConfigEntry 1}

prtGsmConfigIdx2 OBJECT-TYPE
	SYNTAX  Unsigned32
	MAX-ACCESS  not-accessible
	STATUS  current
	DESCRIPTION
	"The second index of the table.
	 
	 This object might represent the port index
	 and for some devices might be the ifIndex.
	 	 
	 For System level or when NA, value = 1."
	::= { prtGsmConfigEntry 2}

prtGsmConfigIfType OBJECT-TYPE
	SYNTAX  INTEGER
	{
		abis	(1),
		ater	(2)
	}
	MAX-ACCESS  read-write
	STATUS  current
	DESCRIPTION
	"The GSM Interface Type."
	::= { prtGsmConfigEntry 3 }

prtGsmConfigUplinkTxDirection OBJECT-TYPE
	SYNTAX  INTEGER
	{
		upStream	(1),
		downStream	(2)
	}
	MAX-ACCESS  read-write
	STATUS  current
	DESCRIPTION
	"The Tx Direction toward the network."
	::= { prtGsmConfigEntry 4 }

prtGsmConfigSubChRate OBJECT-TYPE
	SYNTAX  INTEGER
	{
		dynamic		(1),
		r8Kbps		(2),
		r16Kbps		(3)
	}
	MAX-ACCESS  read-write
	STATUS  current
	DESCRIPTION
	"The Sub Channel Rate."
	::= { prtGsmConfigEntry 5 }

prtGsmConfigClockTracking OBJECT-TYPE
	SYNTAX  INTEGER
	{
		notApplicable	(1),
		disable			(2),
		enable			(3)
	}
	MAX-ACCESS  read-write
	STATUS  current
	DESCRIPTION
	"The Clock Tracking.
	 This object is relevant only when Egress Uplink is LAN and
	 the device (e.g. Vmux) on the BSC side is Rx Clock and
	 the device (e.g. Vmux) on the BTS side is Internal Clock.
	 
	 On this configuration the Vmux-400 on the BTS side
	 will adjust its internal oscillator frequency according to
	 the information it gets from the Vmux-400 on the BSC side."
	::= { prtGsmConfigEntry 6 }

prtGsmConfigTrauIdleFrame OBJECT-TYPE
	SYNTAX  INTEGER
	{
		idlePcm			(1),
		idleSpeech		(2),
		asymIdleSpeech	(3)  -- Asymmetric Idle Speech
	}
	MAX-ACCESS  read-write
	STATUS  current
	DESCRIPTION
	"The TRAU frame to be used between calls."
	::= { prtGsmConfigEntry 7 }

prtGsmConfigDownlinkTrauSilenceFrame OBJECT-TYPE
	SYNTAX  INTEGER
	{
		sidFrame		(1),	-- Silence Insertion Description Frame
		idleSpeech		(2),
		lastReceive		(3)
	}
	MAX-ACCESS  read-write
	STATUS  current
	DESCRIPTION
	"The TRAU frame to be used in the downlink direction
	 for silence/missing data."
	::= { prtGsmConfigEntry 8 }

prtGsmConfigGprsFrame OBJECT-TYPE
	SYNTAX  INTEGER
	{
		other			(1),
		trau			(2)
	}
	MAX-ACCESS  read-write
	STATUS  current
	DESCRIPTION
	"The GPRS Frame Type."
	::= { prtGsmConfigEntry 9 }

prtGsmConfigUnkTrauFrameSuppression OBJECT-TYPE
	SYNTAX  INTEGER
	{
		disable			(2),
		enable			(3)
	}
	MAX-ACCESS  read-write
	STATUS  current
	DESCRIPTION
	"This object enables/disables suppression of unknown TRAU frames."
	::= { prtGsmConfigEntry 10 }

prtGsmConfigUnkTrauFrameOptimization OBJECT-TYPE
	SYNTAX  INTEGER
	{
		disable			(2),
		enable			(3)
	}
	MAX-ACCESS  read-write
	STATUS  current
	DESCRIPTION
	"This object enables/disables optimization of unknown TRAU frames."
	::= { prtGsmConfigEntry 11 }

prtGsmConfigSilenceSuppressionRatio OBJECT-TYPE
	SYNTAX		Unsigned32
	MAX-ACCESS	read-write
	STATUS		current
	DESCRIPTION
	"The Silence Suppression Ratio, measured in percentages (1%).
	 0 = No Suppression.

	 In case comfort noise is rapidly changed,
	 it may cause the silence to be heard like a dead line
	 instead of hearing the comfort noise.	 

	 This parameter enables improvement of comfort noise generation,
	 at the expense of less optimization.
	 
	 In case an invalid value is set,
	 the Agent should accept such a request by setting it to the nearest LOWER valid value.
	 
	 For example:
	 - Valid values are 0, 50, 90 and 98
	 - Attribute is set to 89
	 - Agent should set the attribute to 50
	 ."
	::= { prtGsmConfigEntry 12 }

prtGsmConfigStatus OBJECT-TYPE
	SYNTAX  INTEGER
	{
		active			(1),
		notInService	(2),
		notReady		(3),
		createAndGo		(4),
		createAndWait	(5),
		destroy			(6),
		notApplicable	(255)
	}
	MAX-ACCESS  read-write
	STATUS  current
	DESCRIPTION
	"This object enables the user to create/delete entries in this table.
	 Its usage for values (1)..(6) should be identical to RowStatus SYNTAX.
	 
	 notApplicable(255) - should be used when the table is static
	                      (i.e. whenever create/delete entries is not allowed)."
	::= { prtGsmConfigEntry 13 }

prtGsmConfigUpstreamOptimization OBJECT-TYPE
	SYNTAX  BITS
	{
		optimization	(0),
		compression		(1)		
	}
	MAX-ACCESS  read-write
	STATUS		current
	DESCRIPTION
	"This object represents the Optimization Mode
	 at the Upstream direction (BTS -> BSC)."
	::= { prtGsmConfigEntry 14 }

prtGsmConfigDownstreamOptimization OBJECT-TYPE
	SYNTAX  BITS
	{
		optimization	(0),
		compression		(1)		
	}
	MAX-ACCESS  read-write
	STATUS		current
	DESCRIPTION
	"This object represents the Optimization Mode
	 at the Downstream direction (BSC -> BTS)."
	::= { prtGsmConfigEntry 15 }

prtGsmConfigByteReversal OBJECT-TYPE
	SYNTAX  INTEGER
	{
		notApplicable	(1),
		no				(2),
		yes				(3)		
	}
	MAX-ACCESS  read-write
	STATUS  current
	DESCRIPTION
	"This object defines whether BTS/BSC reverses the bytes or not."
	::= { prtGsmConfigEntry 16 }

prtGsmConfigTxJitter OBJECT-TYPE
	SYNTAX		Unsigned32
	MAX-ACCESS	read-write
	STATUS		current
	DESCRIPTION
	"The Transmit Jitter size (in msec), towards the BTS/BSC"
	::= { prtGsmConfigEntry 17 }

prtGsmConfigSpdThreshold OBJECT-TYPE
	SYNTAX		Unsigned32
	MAX-ACCESS	read-write
	STATUS		current
	DESCRIPTION
	"The SPD (Smart Packet Drop) Threshold.

	 SPD mechanism decides which frames to drop
	 according to the voice energy of the frame.
	 
	 A frame should be dropped in case its voice energy
	 is lower than the SPD Threshold."
	::= { prtGsmConfigEntry 18 }


-- GSM Interface Traffic Table

prtGsmTrafficTable OBJECT-TYPE
	SYNTAX  SEQUENCE OF PrtGsmTrafficEntry
	MAX-ACCESS  not-accessible
	STATUS  current
	DESCRIPTION
	"GSM Interface Traffic Table."
	::= { prtGsmConfig 2 }
   
prtGsmTrafficEntry   OBJECT-TYPE
	SYNTAX  PrtGsmTrafficEntry
	MAX-ACCESS  not-accessible
	STATUS  current
	DESCRIPTION
	"An entry in the GSM Interface Traffic Table."
	INDEX { prtGsmTrafficIdx1, prtGsmTrafficIdx2, prtGsmTrafficType }
	::= { prtGsmTrafficTable 1}

PrtGsmTrafficEntry ::=
	SEQUENCE {
		prtGsmTrafficIdx1						Unsigned32,
		prtGsmTrafficIdx2						Unsigned32,
		prtGsmTrafficType						INTEGER,
		prtGsmTrafficVpi						Unsigned32,
		prtGsmTrafficVci						Unsigned32,
		prtGsmTrafficMultiplexFrameSize			Unsigned32,
		prtGsmTrafficTxInterval					Unsigned32
		}
 
prtGsmTrafficIdx1 OBJECT-TYPE
	SYNTAX  Unsigned32
	MAX-ACCESS  not-accessible
	STATUS  current
	DESCRIPTION
	"The first index of the table.
	 
	 This object might represent the Configuration Index (1..100) being accessed,
	 where Index=255 relates to the TmpCnfg.
	 For devices with multiple configurations, Set is permitted to TmpCnfg(255) only.
	 
	 Not-Applicable = 1."
	::= { prtGsmTrafficEntry 1}

prtGsmTrafficIdx2 OBJECT-TYPE
	SYNTAX  	Unsigned32
	MAX-ACCESS  not-accessible
	STATUS  	current
	DESCRIPTION
	"The second index of the table.
	 
	 This object might represent the port index
	 and for some devices might be the ifIndex.
	 	 
	 For System level or when NA, value = 1."
	::= { prtGsmTrafficEntry 2}

prtGsmTrafficType OBJECT-TYPE
	SYNTAX  INTEGER
	{
		signaling	(1),
		voice		(2),
		data		(3)
	}
	MAX-ACCESS  not-accessible
	STATUS		current
	DESCRIPTION
	"The GSM Interface Traffic Type."
	::= { prtGsmTrafficEntry 3 }

prtGsmTrafficVpi OBJECT-TYPE
	SYNTAX		Unsigned32
	MAX-ACCESS	read-write
	STATUS		current
	DESCRIPTION
	"The VPI (of VPI/VCI pair) that should be used in connection
	 with this traffic type."
	::= { prtGsmTrafficEntry 4 }

prtGsmTrafficVci OBJECT-TYPE
	SYNTAX		Unsigned32
	MAX-ACCESS	read-write
	STATUS		current
	DESCRIPTION
	"The VCI (of VPI/VCI pair) that should be used in connection
	 with this traffic type."
	::= { prtGsmTrafficEntry 5 }

prtGsmTrafficMultiplexFrameSize OBJECT-TYPE
	SYNTAX		Unsigned32
	MAX-ACCESS	read-write
	STATUS		current
	DESCRIPTION
	"The Multiplexed Frame Size (in bytes) of this traffic type."
	::= { prtGsmTrafficEntry 6 }

prtGsmTrafficTxInterval OBJECT-TYPE
	SYNTAX		Unsigned32
	MAX-ACCESS	read-write
	STATUS		current
	DESCRIPTION
	"The Tx Interval (in msec) of this traffic type."
	::= { prtGsmTrafficEntry 7 }


-- END
-- 
-- file :D:\Synergy\WorkArea\545\mib_rad\txt\Pw.txt
-- 
-- RAD Pseudo Wire Text file

-- Version:   5.35
-- First Version Date:   16-May-2006              
-- By:        Yig'al Hachmon
-- File:      pw.txt


-- Last update:  29-May-2008 by Yig'al Hachmon
				  

radPwNotifications		OBJECT IDENTIFIER ::= { radPw 0 }
radPwCfgObjects			OBJECT IDENTIFIER ::= { radPw 1 }
radPwPerfMonitoring		OBJECT IDENTIFIER ::= { radPw 2 }

radPwGenCfgObjects		OBJECT IDENTIFIER ::= { radPwCfgObjects 1 }
radPwPsnCfgObjects		OBJECT IDENTIFIER ::= { radPwCfgObjects 2 }
radPwServiceCfgObjects	OBJECT IDENTIFIER ::= { radPwCfgObjects 3 }

-- *** PW General Parameters ***


pwGenTable  OBJECT-TYPE
     SYNTAX        SEQUENCE OF PwGenEntry
     MAX-ACCESS    not-accessible
     STATUS        current
     DESCRIPTION
         "This table contains general configuration for 
         PW connection."
     ::= { radPwGenCfgObjects 1 }

pwGenEntry OBJECT-TYPE
     SYNTAX        PwGenEntry
     MAX-ACCESS    not-accessible
     STATUS        current
     DESCRIPTION
         "This table is indexed by pwIdx, the value of which is equal
          to the same index that was created for the associated entry 
          in the PW Table (in the PW-STD-MIB)- the pwIndex.	
          An entry is created in this table by the agent for every
          entry in the pwTable."
     INDEX  { pwIdx }
        ::= { pwGenTable 1 }

PwGenEntry ::= SEQUENCE {
		pwIdx						Unsigned32,
		pwGenPeerIdx				Unsigned32,
        pwGenAttachmentCircuit		InterfaceIndexOrZero,
		pwGenOutgoingInterface		InterfaceIndexOrZero,
		pwGenOamMode				INTEGER,
		pwGenOamType				INTEGER,
 		pwGenSequenceNumberField	INTEGER,
		pwGenNextHopType			INTEGER,
		pwGenNextHop				Unsigned32,
  		pwGenIpNextHop				IpAddress,
  		pwGenMacNextHop				MacAddress,
		pwGenEnableVlanTag          INTEGER,
		pwGenVlanId                 Unsigned32,
		pwGenVlanPriority           Unsigned32,
		pwGenIpTos                  Unsigned32,
		pwGenSourceUdpPort			Unsigned32,
		pwGenSubType				INTEGER,
		pwGenSourceIpAddress        IpAddress,
		pwGenSourceIpMask 			IpAddress
		}

pwIdx  OBJECT-TYPE
     SYNTAX        Unsigned32 
     MAX-ACCESS    not-accessible
     STATUS        current
     DESCRIPTION
     "Index of this table.
      The value for this object is equal to the value
      of pwIndex from the pwTable of PW-STD-MIB" 
    ::= { pwGenEntry 1}

pwGenPeerIdx OBJECT-TYPE
     SYNTAX       Unsigned32
     MAX-ACCESS   read-write
     STATUS       current
     DESCRIPTION
	 "This object indicates the Index of the Peer
	  (as it is defined in the Peer Table), which terminated this PW."
    ::= { pwGenEntry 2 } 

pwGenAttachmentCircuit OBJECT-TYPE
     SYNTAX        InterfaceIndexOrZero
     MAX-ACCESS    read-write
     STATUS        current
     DESCRIPTION
         "This is a unique index within the ifTable. It represents
          the attached circuit interface (e.g ATM VC, HDLC) attached to 
          this PW connection (from  service initiator side).

          A value of zero indicates an interface index that has yet
          to be determined.
          Once set, if the attached circuit  is (for some reason) later
          removed, the agent should DELETE the associated PW rows.
          If the agent does not delete the rows,
          the agent MUST set this object to zero.
          
          This object is applicable only for device which
          translates  Attachment Circuit to other logical interface. "
    ::= { pwGenEntry 3 } 

pwGenOutgoingInterface OBJECT-TYPE
     SYNTAX        InterfaceIndexOrZero
     MAX-ACCESS    read-write
     STATUS        current
     DESCRIPTION
         "This is a unique index within the ifTable. It represents
          the outgoing interface (towards the PSN ) attached to 
          this PW connection.

		  This object is applicable only for MPLS peer, for device 
		  without router, when Next Hop is not defined.
			
          A value of zero indicates an interface index that has yet
          to be determined, or it is not applicable.
          
          Once set, if the outgoing interface is (for some reason) later
          removed, the agent should DELETE the associated PW rows.
          If the agent does not delete the rows,
          the agent MUST set this object to zero.
          
          This object is applicable only for devices that allow 
          manual configuration of outgoing interface."
    ::= { pwGenEntry 4 }

pwGenOamMode  OBJECT-TYPE
      SYNTAX        INTEGER
 	                {
 	                 notApplicable (1), 
 	                 disabled      (2),
 	                 enabled       (3)
 	                }
      MAX-ACCESS    read-write
      STATUS        current
      DESCRIPTION
 	 "This objects defines whether OAM will be enabled on this PW.
 	  notApplicable(1) value will be used when
 	  PW type does not support OAM."
     ::= { pwGenEntry 5 } 

 pwGenOamType    OBJECT-TYPE
      SYNTAX        INTEGER
 	                {
 	                 notApplicable (1), 
 	                 propietary    (2),
 	                 bfd           (3)
 	                }
      MAX-ACCESS    read-write
      STATUS        current
      DESCRIPTION
 	 "This objects defines the failure detection mechanism used 
 	  on this PW.
 	  BFD - Bidirectional Forwarding Detection
   	  notApplicable(1) value will be used when
 	  pwGenOamMode is notApplicable."
     ::= { pwGenEntry 6 }
 
pwGenSequenceNumberField    OBJECT-TYPE
      SYNTAX        INTEGER
 	                {
 	                 notApplicable (1), 
 	                 disabled      (2), 
 	                 enabled       (3) 
 	                }
      MAX-ACCESS    read-write
      STATUS        current
      DESCRIPTION
       "This object defines whether processing of Sequence Number field 
       (ATM cell encapsulation) will be done by device, on this PW."
     ::= { pwGenEntry 7 }

pwGenNextHopType OBJECT-TYPE
      SYNTAX        INTEGER
	  {
	  notApplicable  (1),
	  atmVc          (2),
	  bridgePort     (3),
	  ipV4           (4)	  
	  }
      MAX-ACCESS    read-write
      STATUS        current
      DESCRIPTION
      "Indicates address type of the Next Hop.
	  Not applicable for device with router."
      ::= { pwGenEntry 8 }
 
pwGenNextHop  OBJECT-TYPE
     SYNTAX        Unsigned32 
     MAX-ACCESS    read-write
     STATUS        current
     DESCRIPTION
     "Not applicable (=0) when pwMplsEgressTunnelNextHopType=notApplicable.
      When applicable, represents ATM VC, Bridge Port, 
      according to pwMplsEgressTunnelNextHopType."
    ::= { pwGenEntry 9}

pwGenIpNextHop OBJECT-TYPE
      SYNTAX        IpAddress
      MAX-ACCESS    read-write
      STATUS        current
      DESCRIPTION
 	  "This object defines local Next Hop IP Address for this PW.
 	  0.0.0.0  - means  - not applicable. 
 	  This object is applicable only when pwGenNextHopType=ipV4"
     ::= { pwGenEntry 10 }

pwGenMacNextHop OBJECT-TYPE
      SYNTAX        MacAddress
      MAX-ACCESS    read-write
      STATUS        current
      DESCRIPTION
 	  "This object defines local Next Hop MAC Address for this PW.
 	  0:0:0:0:0:0  - means  - not applicable.
 	  This object is applicable only when pwGenNextHopType=bridgePort"
     ::= { pwGenEntry 11 } 
     
pwGenEnableVlanTag OBJECT-TYPE
     SYNTAX        INTEGER
	                {
	                 notApplicable (1), 
	                 disabled      (2),
	                 enabled       (3)
	                }
     MAX-ACCESS    read-write
     STATUS        current
     DESCRIPTION
	 "This object enables or diables a VLAN tag on 
	  every transmitted paket via this PW connection"
    ::= { pwGenEntry 12 } 
 
pwGenVlanId      OBJECT-TYPE
     SYNTAX      Unsigned32  (1..4095) 
     MAX-ACCESS  read-write
     STATUS      current
     DESCRIPTION
	 "This object indicates the VLAN ID tag attached 
	  to every transmitted packet via this PW connection.
	  This entry is applicable only if pwGenEnableVlanTag=enabled (3)."
    ::= { pwGenEntry 13 } 

pwGenVlanPriority OBJECT-TYPE
     SYNTAX       Unsigned32 (0..7) 
     MAX-ACCESS   read-write
     STATUS       current
     DESCRIPTION
	 "This object indicates the VLAN priority assigned 
	  to every transmitted packet via this PW connection.
 	  This entry is applicable only if pwGenEnableVlanTag=enabled (3)"
    ::= { pwGenEntry 14 }

pwGenIpTos OBJECT-TYPE
     SYNTAX       Unsigned32  
     MAX-ACCESS   read-write
     STATUS       current
     DESCRIPTION
	 "This object indicates TOS field value
	  for pw having pwPsnType= ip (3)"
    ::= { pwGenEntry 15 }

pwGenSourceUdpPort OBJECT-TYPE
     SYNTAX       Unsigned32  
     MAX-ACCESS   read-write
     STATUS       current
     DESCRIPTION
	 "This object indicates source UDP port (1...65535) value
	  for pw having pwPsnType= ip (3)"
    ::= { pwGenEntry 16 }

pwGenSubType  OBJECT-TYPE
     SYNTAX        INTEGER
		{
			notApplicable		(1), 
			clockRecovery		(2),
			clockDistribution	(3),
			data				(4)
		}
     MAX-ACCESS    read-write
     STATUS        current
     DESCRIPTION
	 "This object indicates the PW Sub Type
	  (i.e. Sub Type of 'pwType' from 'pwTable').
	  
	  For ACE-3000 devices:
	  It is applicable only when pwType = basicCesPsn(21)."
    ::= { pwGenEntry 17 }

pwGenSourceIpAddress  OBJECT-TYPE
     SYNTAX       IpAddress  
     MAX-ACCESS   read-write
     STATUS       current
     DESCRIPTION
	 "Source IP Address per PW"
    ::= { pwGenEntry 18 }

pwGenSourceIpMask  OBJECT-TYPE
     SYNTAX       IpAddress  
     MAX-ACCESS   read-write
     STATUS       current
     DESCRIPTION
	 "Source IP Mask per PW"
    ::= { pwGenEntry 19 }


     
pwGenTimeout     OBJECT-TYPE
   SYNTAX        Unsigned32
   MAX-ACCESS    read-write
   STATUS        current
   DESCRIPTION
       "This object defines the Timeout period, measured in usec.
        This object is relevant only for ATM service."
   ::= { radPwGenCfgObjects 2 }

pwGenMisorderWindowSize  OBJECT-TYPE
   SYNTAX        Unsigned32
   MAX-ACCESS    read-write
   STATUS        current
   DESCRIPTION
       "This object defines the Window Size (in packets),
		in which the device will attempt to reorder packets.

		Packets having sequence number with gap greater than the Window Size -
		will not take part in the process.	 
        
        This object is relevant only for ATM service."
   ::= { radPwGenCfgObjects 3 }

pwGenFixMisorderSupport  OBJECT-TYPE
   SYNTAX        INTEGER
   {
   notApplicable (1), 
   disabled      (2),
   enabled       (3)
   }
   MAX-ACCESS    read-write
   STATUS        current
   DESCRIPTION
       "This object defines whether the process of reorder,
        within the Window Size (pwGenMisorderWindowSize), should be activated or not.

        This object is relevant only for ATM service."
   ::= { radPwGenCfgObjects 4 }

 pwGenLabelTable  OBJECT-TYPE
    SYNTAX        SEQUENCE OF PwGenLabelEntry
    MAX-ACCESS    not-accessible
    STATUS        current
    DESCRIPTION
        "This table defines supported range of PW labels."
    ::= { radPwGenCfgObjects 5 }
 
 pwGenLabelEntry OBJECT-TYPE
      SYNTAX        PwGenLabelEntry
      MAX-ACCESS    not-accessible
      STATUS        current
      DESCRIPTION
          "Entry in this table defines range of PW labels in the direction and type 
           indicated by pwGenLabelType and pwGenLabelDirection."
      INDEX  { pwGenLabelType,
               pwGenLabelDirection}
         ::= { pwGenLabelTable 1 }
 
 PwGenLabelEntry ::= SEQUENCE {
 		pwGenLabelType        INTEGER,
 		pwGenLabelDirection   INTEGER,
 		pwGenLabelMinValue    Unsigned32,
 		pwGenLabelMaxValue	  Unsigned32
 		         }
 	
 pwGenLabelType  OBJECT-TYPE
      SYNTAX        INTEGER
      {
 	  static (2),
 	  dynamic(3)
      } 
      MAX-ACCESS    not-accessible
      STATUS        current
      DESCRIPTION
 	     "This object defines type of label."
     ::= { pwGenLabelEntry 1 } 
 
 pwGenLabelDirection  OBJECT-TYPE
      SYNTAX        INTEGER
      {
 	  ingress (2),
 	  egress  (3)
      } 
      MAX-ACCESS    not-accessible
      STATUS        current
      DESCRIPTION
 	   "This object defines PW direction."
     ::= { pwGenLabelEntry 2 }
 
 pwGenLabelMinValue OBJECT-TYPE
      SYNTAX        Unsigned32 
      MAX-ACCESS    read-write
      STATUS        current
      DESCRIPTION
    	"This object defines minimum value of PW labels, 
    	  in the direction and type indicated by 
    	  pwGenLabelType and pwGenLabelDirection."
     ::= { pwGenLabelEntry 3 } 
  
 pwGenLabelMaxValue  OBJECT-TYPE
      SYNTAX        Unsigned32 
      MAX-ACCESS    read-write
      STATUS        current
      DESCRIPTION
 	  "This object define maximum value of PW labels,
 	   in the direction and type indicated by 
 	   pwGenLabelType and pwGenLabelDirection."
     ::= { pwGenLabelEntry 4 } 


-- Peer Table

peerTable OBJECT-TYPE
	SYNTAX		SEQUENCE OF PeerEntry
	MAX-ACCESS	not-accessible
	STATUS		current
	DESCRIPTION
		"The Peer Table"
	::= { radPwGenCfgObjects 6 }

peerEntry OBJECT-TYPE
	SYNTAX		PeerEntry
	MAX-ACCESS	not-accessible
	STATUS		current
	DESCRIPTION
		"An entry in this table."
	INDEX { peerIndex }
	::= { peerTable 1 }

PeerEntry ::= SEQUENCE {
	peerIndex				Unsigned32,
	peerRowStatus			RowStatus,         
	peerAddressType			InetAddressType,         
	peerAddress				InetAddress,         
	peerName				SnmpAdminString,
	peerNoOfUsages			Unsigned32,
	peerTargeted			INTEGER,
	peerNextHopAddressType  InetAddressType,           
    peerNextHopAddress		InetAddress
	}

peerIndex OBJECT-TYPE
	SYNTAX		Unsigned32
	MAX-ACCESS	not-accessible
	STATUS		current
	DESCRIPTION
		"This object represents the Peer Index."
	::= { peerEntry 1 }

peerRowStatus OBJECT-TYPE
	SYNTAX		RowStatus
	MAX-ACCESS	read-create
	STATUS		current
	DESCRIPTION
		"This object is used for creating, modifying and deleting
		 a row of this table."
	::= { peerEntry 2 }

peerAddressType OBJECT-TYPE
	SYNTAX		InetAddressType
	MAX-ACCESS	read-create
	STATUS		current
	DESCRIPTION
		"This object represents the Address Type of the Peer node.
		 It should be set to 'unknown' if PE/PW maintenance protocol
		 is not used and the address is unknown." 
	::= { peerEntry 3 }

peerAddress OBJECT-TYPE
	SYNTAX		InetAddress
	MAX-ACCESS	read-create
	STATUS		current
	DESCRIPTION
		"This object represents the Peer node Address.
		 of the PW/PE maintenance protocol entity.
		 This object SHOULD contain a value of all zeroes if not applicable  
         (peerAddrType is 'unknown')."
	::= { peerEntry 4 }

peerName OBJECT-TYPE
	SYNTAX		SnmpAdminString
	MAX-ACCESS	read-create
	STATUS		current
	DESCRIPTION
		"This object represents the Peer Name."
	::= { peerEntry 5 }

peerNoOfUsages OBJECT-TYPE
	SYNTAX		Unsigned32
	MAX-ACCESS	read-only
	STATUS		current
	DESCRIPTION
		"This object indicates the number of times this Peer is used
		 (by PWs, Egress LSP Tunnels etc)."
	::= { peerEntry 6 } 

peerTargeted OBJECT-TYPE
	SYNTAX		INTEGER
		{
			notApplicable	(1),
			no				(2),
			yes				(3)
		}
	MAX-ACCESS	read-create
	STATUS		current
	DESCRIPTION
		"This object indicates whether the Peer is configured
		 as a Targeted Peer or not."
	::= { peerEntry 7 }

peerNextHopAddressType OBJECT-TYPE
	SYNTAX		InetAddressType
	MAX-ACCESS	read-create
	STATUS		current
	DESCRIPTION
		"This object represents the Address Type of the Peer Next Hop node.
		 It should be set to 'unknown' if the address is unknown." 
	::= { peerEntry 8 }

peerNextHopAddress OBJECT-TYPE
	SYNTAX		InetAddress
	MAX-ACCESS	read-create
	STATUS		current
	DESCRIPTION
		"This object represents the Peer Next Hop node Address.
		 This object SHOULD contain a value of all zeroes if not applicable  
         (peerAddrType is 'unknown')."
	::= { peerEntry 9 }




-- *** PW PSN Parameters

-- *** MPLS PSN type parameters ***

radPwPsnCfgMpls   OBJECT IDENTIFIER ::= { radPwPsnCfgObjects 1}

-- MPLS Type PSN Configuration Table

pwMplsCfgTable  OBJECT-TYPE
     SYNTAX        SEQUENCE OF PwMplsCfgEntry
     MAX-ACCESS    not-accessible
     STATUS        current
     DESCRIPTION
         "This table contains MPLS PSN related configuration for 
          PW connection."
     ::= { radPwPsnCfgMpls 1 }

pwMplsCfgEntry OBJECT-TYPE
     SYNTAX        PwMplsCfgEntry
     MAX-ACCESS    not-accessible
     STATUS        current
     DESCRIPTION
         "This table is indexed by pwIdx, the value of which is equal
          to the same index that was created for the associated entry 
          in the PW Table (in the PW-STD-MIB)- the pwIndex.
          An entry is created in this table by the agent for every
          entry in the pwGenTable with a pwGenPsnType=MPLS."
     INDEX  { pwIdx }
        ::= { pwMplsCfgTable 1 }

PwMplsCfgEntry ::= SEQUENCE {
		pwMplsCfgIngressTunnel Unsigned32,
		pwMplsCfgEgressTunnel  Unsigned32
        }
	
pwMplsCfgIngressTunnel  OBJECT-TYPE
     SYNTAX        Unsigned32 
     MAX-ACCESS    read-create
     STATUS        current
     DESCRIPTION
	 "This object points to an entry of pwMplsIngressTunnelTable.
	 Its value is equal to pwMplsIngressTunnelIndex"
    ::= { pwMplsCfgEntry  1} 

pwMplsCfgEgressTunnel    OBJECT-TYPE
     SYNTAX        Unsigned32 
     MAX-ACCESS    read-create
     STATUS        current
     DESCRIPTION
	 "This object points to an entry of pwMplsEgressTunnelTable.
	  Its value is equal to pwMplsEgressTunnelIndex."
    ::= { pwMplsCfgEntry 2 } 

-- *** ETH PSN Type tables were removed
-- since there's no ETH PSN.
-- VLAN parameters were replaced by
-- pwGenEnableVlanTag, pwGenVlanId,pwGenVlanPriority 

-- *** IP PSN Type tables were removed.


-- *** Service Parameters ***

-- *** TDM over IP / CESoPSN Service
radPwServiceCfgTDMoIp   OBJECT IDENTIFIER ::= { radPwServiceCfgObjects 1}

pwTDMoIpTable  OBJECT-TYPE
     SYNTAX        SEQUENCE OF PwTDMoIpEntry
     MAX-ACCESS    not-accessible
     STATUS        current
     DESCRIPTION
         "This table contains TDMoIP Service  related configuration for 
          PW connection."
     ::= { radPwServiceCfgTDMoIp 1 }

pwTDMoIpEntry OBJECT-TYPE
     SYNTAX        PwTDMoIpEntry
     MAX-ACCESS    not-accessible
     STATUS        current
     DESCRIPTION
         "This table is indexed by pwIdx, the value of which is equal
          to the same index that was created for the associated entry 
          in the PW Table (in the PW-STD-MIB)- the pwIndex.

          An entry is created in this table by the agent for every
          entry in the pwTable with a pwType equal to one of the
          following:          
          e1Satop(17), t1Satop(18), e3Satop(19), t3Satop(20),
          basicCesPsn(21), basicTdmIp(22),  tdmCasCesPsn(23),
          tdmCasTdmIp(24)."
     INDEX  { pwIdx }
        ::= { pwTDMoIpTable 1 }

PwTDMoIpEntry ::= SEQUENCE {
        pwTDMoIpCfgIndex    	  Unsigned32
        }

pwTDMoIpCfgIndex     OBJECT-TYPE
     SYNTAX        Unsigned32 
     MAX-ACCESS    read-write
     STATUS        current
     DESCRIPTION
	 "Index to TDMoIP table below. Multiple TDMoIP PWs  
      MAY share a single pwTDMoIpCfgEntry"
    ::= { pwTDMoIpEntry 1}

-- *** TDM over IP / CESoPSN Service configuration table


pwTDMoIpIndexNext  OBJECT-TYPE
      SYNTAX        IndexIntegerNextFree 
      MAX-ACCESS    read-only
      STATUS        current
      DESCRIPTION
          "This object contains an unused value for
           pwTDMoIpCfgTableIndex, or a zero to indicate
           that none exist. Negative values are not allowed,
           as they do not correspond to valid values of
           pwTDMoIpCfgTableIndex."
      ::= { radPwServiceCfgTDMoIp 2 }

pwTDMoIpCfgTable OBJECT-TYPE
     SYNTAX        SEQUENCE OF PwTDMoIpCfgEntry
     MAX-ACCESS    not-accessible
     STATUS        current
     DESCRIPTION
         "This table contains TDM over IP service configuration 
         for PW connection."
     ::= { radPwServiceCfgTDMoIp 3 }

pwTDMoIpCfgEntry OBJECT-TYPE
     SYNTAX        PwTDMoIpCfgEntry
     MAX-ACCESS    not-accessible
     STATUS        current
     DESCRIPTION
         "This table is indexed by pwIdx, the value of which is equal
          to the same index that was created for the associated entry 
          in the PW Table (in the PW-STD-MIB)- the pwIndex.
          
          An entry is created in this table by the agent for every
          entry in the pwTable with a pwType equal to one of the
          following:   
          e1Satop(17), t1Satop(18), e3Satop(19), t3Satop(20),
          basicCesPsn(21), basicTdmIp(22),  tdmCasCesPsn(23),
          tdmCasTdmIp(24)."
     INDEX  { pwTDMoIpCfgTableIndex }
        ::= { pwTDMoIpCfgTable 1 }

PwTDMoIpCfgEntry ::= SEQUENCE {
        pwTDMoIpCfgTableIndex   	  Unsigned32,
        pwTDMoIpCfgRowStatus          RowStatus,
        pwTDMoIpCfgPayloadFormat      INTEGER,
		pwTDMoIpCfgFarEndType		  INTEGER,
		pwTDMoIpCfgDelaySensitivity   INTEGER,
    	pwTDMoIpCfgFramesInPacket     Unsigned32
        }

pwTDMoIpCfgTableIndex  OBJECT-TYPE
     SYNTAX        Unsigned32 
     MAX-ACCESS    not-accessible
     STATUS        current
     DESCRIPTION
	 "Index to an entry in this table"
    ::= { pwTDMoIpCfgEntry 1}

pwTDMoIpCfgRowStatus    OBJECT-TYPE
     SYNTAX               RowStatus
     MAX-ACCESS           read-create
     STATUS               current
     DESCRIPTION
         "Object used for creating, modifying, and deleting
          a row of this table."
     ::= { pwTDMoIpCfgEntry 2 }

pwTDMoIpCfgPayloadFormat OBJECT-TYPE
     SYNTAX        INTEGER
	               {
	                notApplicable (1),
	                v1  (2),
	                v2	(3)
	               }
     MAX-ACCESS    read-create
     STATUS        current
     DESCRIPTION
     "determine TDM over IP proprietary 
      payload format."
    ::= { pwTDMoIpCfgEntry 3 } 

pwTDMoIpCfgFarEndType OBJECT-TYPE
     SYNTAX        INTEGER
	                {
	                 notApplicable (1), 
	                 dsx1E1        (2),	--E1
	                 dsx1ESF       (3), --T1 (ESF)
					 dsx1SF        (4),	--T1 (SF)
					 unframed      (5) -- Serial
	                }

     MAX-ACCESS    read-create
     STATUS        current
     DESCRIPTION
     "Determines TDM over IP Far End type."
    ::= { pwTDMoIpCfgEntry 4 }

pwTDMoIpCfgDelaySensitivity OBJECT-TYPE
     SYNTAX        INTEGER
	                {
	                 notApplicable (1), 
	                 disable       (2),--Accurate Clock
	                 enable        (3) --Constant Delay
	                }
     MAX-ACCESS    read-create
     STATUS        current
     DESCRIPTION
     "Determines whether to optimize the clock 
      for accurateness or for constant delay:
         o Disable (Accurate clock is more important than constant delay)
         o Enable (Constant delay is more important than accurate clock).
         This parameter is applicable only if PSN Type
         is TDMoIP , CESoIP, SATOP "
    ::= { pwTDMoIpCfgEntry 5 } 

pwTDMoIpCfgFramesInPacket OBJECT-TYPE   
     SYNTAX        Unsigned32 
     MAX-ACCESS    read-create
     STATUS        current
     DESCRIPTION
     "UDP payload length - determines the ethernet packet size "
    ::= { pwTDMoIpCfgEntry 6 }


-- *** ATM Service
radPwServiceCfgAtm   OBJECT IDENTIFIER ::= { radPwServiceCfgObjects 2}

pwAtmCfgXTable OBJECT-TYPE				 
     SYNTAX        SEQUENCE OF PwAtmCfgXEntry
     MAX-ACCESS    not-accessible
     STATUS        current
     DESCRIPTION
         "This table is an extension of pwAtmCfgTable
          of PW-ATM-R-MIB. Each row that is added/removed there
          will be added/removed in this table."
     ::= { radPwServiceCfgAtm 1 }

pwAtmCfgXEntry OBJECT-TYPE
     SYNTAX        PwAtmCfgXEntry
     MAX-ACCESS    not-accessible
     STATUS        current
     DESCRIPTION
         "This table is indexed by pwIdx, the value of which is equal
          to the same index that was created for the associated entry 
          in the PW Table (in the PW-STD-MIB)- the pwIndex. 
          An entry may be  created by Agent in this table for 
          pseudo wires having ATM pwType"
     INDEX  { pwIdx }	   
        ::= { pwAtmCfgXTable 1 }

PwAtmCfgXEntry ::= SEQUENCE {
	pwAtmCfgAal5Mode			INTEGER,
	pwAtmCfgAal5SduTermType		INTEGER,
	pwAtmCfgTimeout				Unsigned32
	}

pwAtmCfgAal5Mode OBJECT-TYPE
	SYNTAX        INTEGER
	{
		notApplicable (1), 
		disabled      (2),
		enabled       (3)
	}
	MAX-ACCESS    read-write
	STATUS        current
	DESCRIPTION
	"This objects defines whether AAL5 Mode is enabled for this PW."
	::= { pwAtmCfgXEntry 1 } 

pwAtmCfgAal5SduTermType OBJECT-TYPE
	SYNTAX        INTEGER
	{
		notApplicable	(1), 
		atm				(2),
		router			(3)
	}
	MAX-ACCESS    read-write
	STATUS        current
	DESCRIPTION
	"This objects defines the AAL5-SDU Termination Type.
	 It means - where should the AAL5-SDU PW frame, received from PSN, be forwarded:  
	 
	 atm(2)		- forwarded into ATM VCC.
	 router(3)	- forwarded into router. 
	 ."
	::= { pwAtmCfgXEntry 2 } 

pwAtmCfgTimeout OBJECT-TYPE
	SYNTAX        Unsigned32
	MAX-ACCESS    read-write
	STATUS        current
	DESCRIPTION
       "This object defines the Timeout period, measured in usec.
	    Timeout mechanism is used in order to send out a packet
	    before the maximum concatenated cells limit has been reached."
	::= { pwAtmCfgXEntry 3 } 


-- ***Frame Relay Service PW Table

radPwServiceCfgFr   OBJECT IDENTIFIER ::= { radPwServiceCfgObjects 3}


pwFrCfgTable OBJECT-TYPE
     SYNTAX        SEQUENCE OF PwFrCfgEntry
     MAX-ACCESS    not-accessible
     STATUS        current
     DESCRIPTION
         "This table contains a set of parameters for
          Frame Relay PW in the pwFrTable."
     ::= { radPwServiceCfgFr 1 }

pwFrCfgEntry OBJECT-TYPE
     SYNTAX        PwFrCfgEntry
     MAX-ACCESS    not-accessible
     STATUS        current
     DESCRIPTION
         "These parameters define the characteristics of a
          Frame Relay PW.
          This table is indexed by pwIdx, the value of which is equal
          to the same index that was created for the associated entry 
          in the PW Table (in the PW-STD-MIB)- the pwIndex. 
          An entry may be created by Agent in this table for 
          pseudo wires having Frame Relay pwType"
          INDEX  { pwIdx }
        ::= { pwFrCfgTable 1 }

PwFrCfgEntry ::= SEQUENCE {
        pwFrCfgDlciFieldLength Unsigned32,
		pwFrCfgBitMarking      BITS,
		pwFrCfgDlci 		   Unsigned32
        }

pwFrCfgDlciFieldLength	OBJECT-TYPE
     SYNTAX        Unsigned32 (10|17|24)
     MAX-ACCESS    read-write
     STATUS        current
     DESCRIPTION
	 "DLCI Field length in bytes. Possible values ae
	 10, 17 or 24"
    ::= { pwFrCfgEntry 1 }

pwFrCfgBitMarking OBJECT-TYPE
     SYNTAX        BITS
	  {
       pwFrDeIncomingMarking    (0),
       pwFrFecnIncomingMarking  (1),
       pwFrBecnIncomingMarking	(2),
       pwFrDeOutgoingMarking  	(3),
       pwFrFecnOutgoingMarking	(4),
       pwFrBecnOutgoingMarking	(5)
	 }
     MAX-ACCESS    read-write
     STATUS        current
     DESCRIPTION
	 "This object defines which Frame Relay bits are copied
	 into the outgoing interface or from the incoming interface.
	 When labeled bit is 1, FR bit is copied.
     For incoming FR bits - DE, FECN and BECN:
        DE   - pwFrDeIncomingMarking  
        FECN - pwFrFecnIncomingMarking
	    BECN - pwFrBecnIncomingMarking
	For outgoing FR bits - DE, FECN and BECN:
	    DE   - pwFrDeOutgoingMarking  
	    FECN - pwFrFecnOutgoingMarking
	    BECN - pwFrBecnOutgoingMarking "
    ::= { pwFrCfgEntry 2 }

pwFrCfgDlci        OBJECT-TYPE
     SYNTAX        Unsigned32 
     MAX-ACCESS    read-write
     STATUS        current
     DESCRIPTION
	 "DLCI value of Frame Relay VC associated with this PW."
    ::= { pwFrCfgEntry 3 }


-- PW Performance 

pwPerfCurrentXTable  OBJECT-TYPE 
	SYNTAX		SEQUENCE OF PwPerfCurrentXEntry 
	MAX-ACCESS	not-accessible 
	STATUS		current 
	DESCRIPTION 
         "This table is an extension of pwPerfCurrentTable (PW-STD-R-MIB)."
   ::= { radPwPerfMonitoring 1 } 

pwPerfCurrentXEntry OBJECT-TYPE 
	SYNTAX        PwPerfCurrentXEntry 
	MAX-ACCESS    not-accessible 
	STATUS        current 
	DESCRIPTION 
		"An entry in a table." 
	INDEX  { pwIdx } 
	::= { pwPerfCurrentXTable 1 } 

PwPerfCurrentXEntry ::= SEQUENCE { 
	pwPerfCurrentInCongestDropPackets			PerfCurrentCount, 
	pwPerfCurrentOutCongestDropPackets			PerfCurrentCount 
	} 

pwPerfCurrentInCongestDropPackets OBJECT-TYPE 
	SYNTAX		PerfCurrentCount  
	MAX-ACCESS	read-only 
	STATUS		current 
	DESCRIPTION 
		"The counter for number of received packets that are dropped
		 due to congestion by the PW (from the PSN)
		 in the current 15-minute interval." 
	::= { pwPerfCurrentXEntry 1 } 

pwPerfCurrentOutCongestDropPackets OBJECT-TYPE 
	SYNTAX		PerfCurrentCount  
	MAX-ACCESS	read-only 
	STATUS		current 
	DESCRIPTION 
		"The counter for number of transmitted packets that are dropped
		 due to congestion by the PW (to the PSN)
		 in the current 15-minute interval." 
	::= { pwPerfCurrentXEntry 2 } 


pwPerfIntervalXTable  OBJECT-TYPE 
   SYNTAX		SEQUENCE OF PwPerfIntervalXEntry 
	MAX-ACCESS	not-accessible 
	STATUS		current 
	DESCRIPTION 
         "This table is an extension of pwPerfIntervalTable (PW-STD-R-MIB)."
	::= { radPwPerfMonitoring 2 } 

pwPerfIntervalXEntry OBJECT-TYPE 
	SYNTAX		PwPerfIntervalXEntry 
	MAX-ACCESS	not-accessible 
	STATUS		current 
	DESCRIPTION 
		"An entry in a table." 
	INDEX  { pwIdx, pwPerfIntervalXNumber } 
	::= { pwPerfIntervalXTable 1 } 

PwPerfIntervalXEntry ::= SEQUENCE { 
	pwPerfIntervalXNumber				Integer32, 
	pwPerfIntervalInCongestDropPackets		PerfIntervalCount, 
	pwPerfIntervalOutCongestDropPackets		PerfIntervalCount 
	} 

pwPerfIntervalXNumber OBJECT-TYPE 
	SYNTAX		Integer32 (1..96) 
	MAX-ACCESS	not-accessible 
	STATUS		current 
	DESCRIPTION 
		"A number N, between 1 and 96, which identifies the 
		 interval for which the set of statistics is available. 
		 The interval identified by 1 is the most recently 
		 completed 15 minute interval, and the interval identified 
		 by N is the interval immediately preceding the one 
		 identified by N-1. 
		 The minimum range of N is 1 through 4. The default range 
		 is 1 to 32. The maximum range of N is 1 through 96." 
   ::= { pwPerfIntervalXEntry 1 } 

pwPerfIntervalInCongestDropPackets OBJECT-TYPE 
	SYNTAX		PerfIntervalCount 
	MAX-ACCESS	read-only 
	STATUS		current 
	DESCRIPTION 
		"The counter for number of received packets that are dropped
		 due to congestion by the PW (to the PSN) during the interval." 
	::= { pwPerfIntervalXEntry 2 } 

pwPerfIntervalOutCongestDropPackets OBJECT-TYPE 
	SYNTAX		PerfIntervalCount 
	MAX-ACCESS	read-only 
	STATUS		current 
	DESCRIPTION 
		"The counter for number of transmitted packets that are dropped
		 due to congestion by the PW (to the PSN) during the interval." 
	::= { pwPerfIntervalXEntry 3 } 


-- ATM PW Performance 

pwAtmPerfCurrentXTable  OBJECT-TYPE 
	SYNTAX		SEQUENCE OF PwAtmPerfCurrentXEntry 
	MAX-ACCESS	not-accessible 
	STATUS		current 
	DESCRIPTION 
         "This table is an extension of pwArmPerfCurrentTable (PW-ATM-R-MIB)."
   ::= { radPwPerfMonitoring 3 } 

pwAtmPerfCurrentXEntry OBJECT-TYPE 
	SYNTAX        PwAtmPerfCurrentXEntry 
	MAX-ACCESS    not-accessible 
	STATUS        current 
	DESCRIPTION 
		"An entry in a table." 
	INDEX  { pwIdx } 
	::= { pwAtmPerfCurrentXTable 1 } 

PwAtmPerfCurrentXEntry ::= SEQUENCE
	{ 
		pwAtmPerfCurrentInDiscardTotalCells			PerfCurrentCount,
		pwAtmPerfCurrentInDiscardClp0Cells			PerfCurrentCount,
		pwAtmPerfCurrentTaggedCells					PerfCurrentCount
	} 

pwAtmPerfCurrentInDiscardTotalCells OBJECT-TYPE 
	SYNTAX		PerfCurrentCount  
	MAX-ACCESS	read-only 
	STATUS		current 
	DESCRIPTION 
		"The number of total received cells (CLP0 and CLP1)
		 that were discarded by the traffic policer,
		 in the current 15-minute interval." 
	::= { pwAtmPerfCurrentXEntry 1 } 

pwAtmPerfCurrentInDiscardClp0Cells OBJECT-TYPE 
	SYNTAX		PerfCurrentCount  
	MAX-ACCESS	read-only 
	STATUS		current 
	DESCRIPTION 
		"The number of received CLP0 cells
		 that were discarded by the traffic policer,
		 in the current 15-minute interval." 
	::= { pwAtmPerfCurrentXEntry 2 } 

pwAtmPerfCurrentTaggedCells OBJECT-TYPE 
	SYNTAX		PerfCurrentCount  
	MAX-ACCESS	read-only 
	STATUS		current 
	DESCRIPTION 
		"The number of cells that were tagged
		 by the traffic policer from CLP=0 to CLP=1,
		 in the current 15-minute interval." 
	::= { pwAtmPerfCurrentXEntry 3 } 


pwAtmPerfIntervalXTable  OBJECT-TYPE 
   SYNTAX		SEQUENCE OF PwAtmPerfIntervalXEntry 
	MAX-ACCESS	not-accessible 
	STATUS		current 
	DESCRIPTION 
         "This table is an extension of pwAtmPerfIntervalTable (PW-ATM-R-MIB)."
	::= { radPwPerfMonitoring 4 } 

pwAtmPerfIntervalXEntry OBJECT-TYPE 
	SYNTAX		PwAtmPerfIntervalXEntry 
	MAX-ACCESS	not-accessible 
	STATUS		current 
	DESCRIPTION 
		"An entry in a table." 
	INDEX  { pwIdx, pwAtmPerfIntervalXNumber } 
	::= { pwAtmPerfIntervalXTable 1 } 

PwAtmPerfIntervalXEntry ::= SEQUENCE
	{ 
		pwAtmPerfIntervalXNumber					Integer32, 
		pwAtmPerfIntervalInDiscardTotalCells		PerfIntervalCount,
		pwAtmPerfIntervalInDiscardClp0Cells			PerfIntervalCount,
		pwAtmPerfIntervalTaggedCells				PerfIntervalCount
	} 

pwAtmPerfIntervalXNumber OBJECT-TYPE 
	SYNTAX		Integer32 (1..96) 
	MAX-ACCESS	not-accessible 
	STATUS		current 
	DESCRIPTION 
		"A number N, between 1 and 96, which identifies the 
		 interval for which the set of statistics is available. 
		 The interval identified by 1 is the most recently 
		 completed 15 minute interval, and the interval identified 
		 by N is the interval immediately preceding the one 
		 identified by N-1. 
		 The minimum range of N is 1 through 4. The default range 
		 is 1 to 32. The maximum range of N is 1 through 96." 
   ::= { pwAtmPerfIntervalXEntry 1 } 

pwAtmPerfIntervalInDiscardTotalCells OBJECT-TYPE 
	SYNTAX		PerfIntervalCount 
	MAX-ACCESS	read-only 
	STATUS		current 
	DESCRIPTION 
		"The number of total received cells (CLP0 and CLP1)
		 that were discarded by the traffic policer,
		 during the interval."
	::= { pwAtmPerfIntervalXEntry 2 }

pwAtmPerfIntervalInDiscardClp0Cells OBJECT-TYPE 
	SYNTAX		PerfIntervalCount  
	MAX-ACCESS	read-only 
	STATUS		current 
	DESCRIPTION 
		"The number of received CLP0 cells
		 that were discarded by the traffic policer,
		 during the interval." 
	::= { pwAtmPerfIntervalXEntry 3 } 

pwAtmPerfIntervalTaggedCells OBJECT-TYPE 
	SYNTAX		PerfIntervalCount  
	MAX-ACCESS	read-only 
	STATUS		current 
	DESCRIPTION 
		"The number of cells that were tagged
		 by the traffic policer from CLP=0 to CLP=1,
		 during the interval." 
	::= { pwAtmPerfIntervalXEntry 4 } 


-- 
-- file :D:\Synergy\WorkArea\545\mib_rad\txt\mpls.txt
-- 
-- RAD  Multi-Protocol Label Switching (MPLS) Text file

-- Version:   5.40
-- First Version Date:   22-Aug-2006              
-- By:        Yig'al Hachmon
-- File:      mpls.txt

-- Last update: 14-Jan-2008 by Shay Harari

radMplsNotifications OBJECT IDENTIFIER ::= { radMpls 0 }
radMplsCfgObjects    OBJECT IDENTIFIER ::= { radMpls 1 }

mplsMinStaticIngressLabel  OBJECT-TYPE
   SYNTAX        MplsLabel
   MAX-ACCESS    read-write
   STATUS        current
   DESCRIPTION
       "This is the minimum value of a static MPLS ingress label 
       that is supported by the device."
   ::= { radMplsCfgObjects 1 }

mplsMaxStaticIngressLabel OBJECT-TYPE
   SYNTAX        MplsLabel
   MAX-ACCESS    read-write
   STATUS        current
   DESCRIPTION
       "This is the maximum value of static 
       MPLS ingress label that is supported by the device"
   ::= { radMplsCfgObjects 2 }

mplsMinIngressDynamicLabel  OBJECT-TYPE
   SYNTAX        MplsLabel
   MAX-ACCESS    read-write
   STATUS        current
   DESCRIPTION
       "This is the minimum value of a dynamic MPLS ingress label 
       that is supported by the device."
   ::= { radMplsCfgObjects 3 }

mplsMaxIngressDynamicLabel OBJECT-TYPE
   SYNTAX        MplsLabel
   MAX-ACCESS    read-write
   STATUS        current
   DESCRIPTION
       "This is the maximum value of a dynamic 
       MPLS ingress label that is supported by the device"
   ::= { radMplsCfgObjects 4 }

mplsIngressTunnelIndexNext  OBJECT-TYPE
      SYNTAX        IndexIntegerNextFree 
      MAX-ACCESS    read-only
      STATUS        current
      DESCRIPTION
          "This object contains an unused value for
           mplsIngressTunnelIndex, or a zero to indicate
           that none exist. Negative values are not allowed,
           as they do not correspond to valid values of
           mplsTunnelIndex.

           Note that this object offers an unused value
           for an mplsTunnelIndex value at the ingress
           side of a tunnel. "
      ::= { radMplsCfgObjects 5 }


mplsIngressTunnelTable OBJECT-TYPE
      SYNTAX        SEQUENCE OF MplsIngressTunnelEntry
      MAX-ACCESS    not-accessible
      STATUS        current
      DESCRIPTION
           "The mpls Ingress Tunnel Table"
      ::= {  radMplsCfgObjects 6 }

mplsIngressTunnelEntry OBJECT-TYPE
      SYNTAX        MplsIngressTunnelEntry
      MAX-ACCESS    not-accessible
      STATUS        current
      DESCRIPTION
           "An entry in this table represents an MPLS tunnel.
             An entry can be created by a network administrator
             or by an SNMP agent as instructed by an MPLS
             signaling protocol.  "
      INDEX {  mplsIngressTunnelIndex  }
      ::= { mplsIngressTunnelTable 1 }

MplsIngressTunnelEntry ::= SEQUENCE {
           mplsIngressTunnelIndex             MplsTunnelIndex,
           mplsIngressTunnelName              SnmpAdminString,         
           mplsIngressTunnelOwner             MplsOwner,
           mplsIngressTunnelAttachedInterface InterfaceIndexOrZero,
		   mplsIngressTunnelNumberOfLabels    Unsigned32,
		   mplsIngressTunnelAdminStatus	      INTEGER,
		   mplsIngressTunnelOuterLabel	      Unsigned32,
		   mplsIngressTunnelInnerLabel	      Unsigned32,
		   mplsIngressTunnelRowStatus		  RowStatus,
		   mplsIngressTunnelPWCounter		  Gauge32,
		   mplsIngressTunnelOperStatus	      INTEGER
									}

mplsIngressTunnelIndex OBJECT-TYPE
      SYNTAX        MplsTunnelIndex
      MAX-ACCESS    not-accessible
      STATUS        current
      DESCRIPTION
           "Ingress Tunnel index."
      ::= { mplsIngressTunnelEntry 1 }


mplsIngressTunnelName OBJECT-TYPE
      SYNTAX        SnmpAdminString
      MAX-ACCESS    read-create
      STATUS        current
      DESCRIPTION
           "The  name assigned to the ingress tunnel."
      DEFVAL {""}
      ::= { mplsIngressTunnelEntry 2 }

mplsIngressTunnelOwner OBJECT-TYPE
      SYNTAX        MplsOwner
      MAX-ACCESS    read-create
      STATUS        current
      DESCRIPTION
            "Denotes the entity (or protocol) that created and is responsible
             for managing this tunnel."
      ::= { mplsIngressTunnelEntry 3 }

mplsIngressTunnelAttachedInterface OBJECT-TYPE
      SYNTAX        InterfaceIndexOrZero
      MAX-ACCESS    read-create
      STATUS        current
      DESCRIPTION
           "The incoming interface leads 
            to a predefined ifindex based on connection type."
      ::= { mplsIngressTunnelEntry 4 }

mplsIngressTunnelNumberOfLabels   OBJECT-TYPE
     SYNTAX        Unsigned32 
     MAX-ACCESS    read-create
     STATUS        current
     DESCRIPTION
     "The number of tunnel labels that should be received 
      on this ingress tunnel. 
      This number does not include the pW label"
    ::= { mplsIngressTunnelEntry 5 } 

mplsIngressTunnelAdminStatus OBJECT-TYPE
      SYNTAX     INTEGER {
                      up(1), -- ready to pass packets
                      down(2),
                      testing(3) -- in some test mode
                }
      MAX-ACCESS    read-create
      STATUS        current
      DESCRIPTION
           "Indicates the desired operational status of this
             tunnel."
      ::= { mplsIngressTunnelEntry 6 }

mplsIngressTunnelOuterLabel     OBJECT-TYPE
     SYNTAX        Unsigned32 
     MAX-ACCESS    read-create
     STATUS        current
     DESCRIPTION
     "The Label that is 'closer' to the network  encapsulation."
    ::= { mplsIngressTunnelEntry 7 } 

mplsIngressTunnelInnerLabel	    OBJECT-TYPE
     SYNTAX        Unsigned32 
     MAX-ACCESS    read-create
     STATUS        current
     DESCRIPTION
     "The Label that is 'closer' to the user payload."
    ::= { mplsIngressTunnelEntry 8 } 

mplsIngressTunnelRowStatus	OBJECT-TYPE
     SYNTAX						RowStatus
     MAX-ACCESS    read-create
     STATUS        current
     DESCRIPTION
     "Object used for creating, modifying, and deleting
      a row of this table"
     ::= { mplsIngressTunnelEntry 9 }

mplsIngressTunnelPWCounter OBJECT-TYPE
	SYNTAX Gauge32 
	MAX-ACCESS read-only
 	STATUS current
	DESCRIPTION
	"The number of Pseudo Wires that use the ingress tunnel."
	::= { mplsIngressTunnelEntry 10 }

mplsIngressTunnelOperStatus OBJECT-TYPE
      SYNTAX     INTEGER {
			up		(1),
 			down	(2)
			}
      MAX-ACCESS    read-only
      STATUS        current
      DESCRIPTION
           "Indicates the operational status of this ingress tunnel."
      ::= { mplsIngressTunnelEntry 11 }
 

mplsEgressTunnelIndexNext  OBJECT-TYPE
      SYNTAX        IndexIntegerNextFree
      MAX-ACCESS    read-only
      STATUS        current
      DESCRIPTION
          "This object contains an unused value for
           mplsEgressTunnelIndex, or a zero to indicate
           that none exist. Negative values are not allowed,
           as they do not correspond to valid values of
           mplsTunnelIndex.

           Note that this object offers an unused value
           for an mplsTunnelIndex value at the egress
           side of a tunnel. "
      ::= { radMplsCfgObjects 7 }

mplsEgressTunnelTable OBJECT-TYPE
      SYNTAX        SEQUENCE OF MplsEgressTunnelEntry
      MAX-ACCESS    not-accessible
      STATUS        current
      DESCRIPTION
           "The mpls Egress Tunnel Table"
      ::= {  radMplsCfgObjects 8 }

mplsEgressTunnelEntry OBJECT-TYPE
      SYNTAX        MplsEgressTunnelEntry
      MAX-ACCESS    not-accessible
      STATUS        current
      DESCRIPTION
           "An entry in this table represents an MPLS tunnel.
             An entry can be created by a network administrator
             or by an SNMP agent as instructed by an MPLS
             signalling protocol."
      INDEX {  mplsEgressTunnelIndex  }
      ::= { mplsEgressTunnelTable 1 }

MplsEgressTunnelEntry ::= SEQUENCE {
         mplsEgressTunnelIndex				MplsTunnelIndex,
         mplsEgressTunnelName				SnmpAdminString,         
         mplsEgressTunnelOwner				MplsOwner,
         mplsEgressTunnelAttachedInterface	InterfaceIndexOrZero,
		 mplsEgressTunnelNextHopType		INTEGER,
		 mplsEgressTunnelNextHop			Unsigned32,
		 mplsEgressTunnelIpNextHop			IpAddress,
		 mplsEgressTunnelNumberOfLabels		Unsigned32,
		 mplsEgressTunnelAdminStatus		INTEGER,
		 mplsEgressTunnelOuterLabel			Unsigned32,
		 mplsEgressTunnelInnerLabel			Unsigned32,
		 mplsEgressTunnelRowStatus			RowStatus,
         mplsEgressTunnelPWCounter		    Gauge32,
		 mplsEgressTunnelPeerIdx			Unsigned32,
		 mplsEgressTunnelExpBitsMode		INTEGER,
		 mplsEgressTunnelExpBits			Unsigned32,
		 mplsEgressTunnelOperStatus			INTEGER
		}

mplsEgressTunnelIndex OBJECT-TYPE
      SYNTAX        MplsTunnelIndex
      MAX-ACCESS    not-accessible
      STATUS        current
      DESCRIPTION
           "Egress Tunnel index ."
      ::= { mplsEgressTunnelEntry 1 }


mplsEgressTunnelName OBJECT-TYPE
      SYNTAX        SnmpAdminString
      MAX-ACCESS    read-create
      STATUS        current
      DESCRIPTION
           "The  name assigned to the egress tunnel."
      DEFVAL {""}
      ::= { mplsEgressTunnelEntry 2 }

mplsEgressTunnelOwner OBJECT-TYPE
      SYNTAX        MplsOwner
      MAX-ACCESS    read-create
      STATUS        current
      DESCRIPTION
            "Denotes the entity (or protocol) that created and is responsible
             for managing this tunnel."
      ::= { mplsEgressTunnelEntry 3 }

mplsEgressTunnelAttachedInterface OBJECT-TYPE
      SYNTAX        InterfaceIndexOrZero
      MAX-ACCESS    read-create
      STATUS        current
      DESCRIPTION
           "The outgoing interface leads 
            to a predefined ifindex based on connection type."
      ::= { mplsEgressTunnelEntry 4 }

mplsEgressTunnelNextHopType OBJECT-TYPE
      SYNTAX        INTEGER
	  {
	  notApplicable  (1),
	  atmVc (2),
	  bridgePort (3),
	  ipV4       (4)	  
	  }
      MAX-ACCESS    read-create
      STATUS        current
      DESCRIPTION
      "Indicates address type of the Next Hop.
	   Not applicable for device with router."
      ::= { mplsEgressTunnelEntry 5 }

mplsEgressTunnelNextHop			OBJECT-TYPE
     SYNTAX        Unsigned32 
     MAX-ACCESS    read-create
     STATUS        current
     DESCRIPTION
     "Not applicable (=0) when mplsEgressTunnelNextHopType=notApplicable.
      When applicable, represents ATM VC, Bridge Port, 
      according to mplsEgressTunnelNextHopType."
    ::= { mplsEgressTunnelEntry 6}

mplsEgressTunnelIpNextHop		OBJECT-TYPE
     SYNTAX        IpAddress 
     MAX-ACCESS    read-create
     STATUS        current
     DESCRIPTION
     "Applicable only when mplsEgressTunnelNextHopType =ipV4."
    ::= { mplsEgressTunnelEntry 7} 

mplsEgressTunnelNumberOfLabels   OBJECT-TYPE
     SYNTAX        Unsigned32 
     MAX-ACCESS    read-create
     STATUS        current
     DESCRIPTION
     "Number of Tunnel Labels that should be transmitted 
      on this egress LSP (Labeled-Switched Path).
      This number of labels does not include the PW number.
      Valid values 0 - no label, 1, 2" 
    ::= { mplsEgressTunnelEntry 8 } 

mplsEgressTunnelAdminStatus OBJECT-TYPE
      SYNTAX     INTEGER {
                      up(1), -- ready to pass packets
                      down(2),
                      testing(3) -- in some test mode
                }
      MAX-ACCESS    read-create
      STATUS        current
      DESCRIPTION
           "Indicates the desired operational status of this
            egress tunnel."
      ::= { mplsEgressTunnelEntry 9 }

mplsEgressTunnelOuterLabel     OBJECT-TYPE
     SYNTAX        Unsigned32 
     MAX-ACCESS    read-create
     STATUS        current
     DESCRIPTION
     "The Label that is 'closer' to the network  encapsulation."
    ::= { mplsEgressTunnelEntry 10 } 

mplsEgressTunnelInnerLabel	    OBJECT-TYPE
     SYNTAX        Unsigned32 
     MAX-ACCESS    read-create
     STATUS        current
     DESCRIPTION
     "The Label that is 'closer' to the user payload."
    ::= { mplsEgressTunnelEntry 11 } 

mplsEgressTunnelRowStatus	OBJECT-TYPE
     SYNTAX						RowStatus
     MAX-ACCESS    read-create
     STATUS        current
     DESCRIPTION
     "Object used for creating, modifying, and deleting
      a row of this table"
     ::= { mplsEgressTunnelEntry 12 }

mplsEgressTunnelPWCounter OBJECT-TYPE
	SYNTAX 		Gauge32 
	MAX-ACCESS  read-only
 	STATUS current
	DESCRIPTION
	"The number of Pseudo Wires that use the egress tunnel."
	::= { mplsEgressTunnelEntry 13 }

mplsEgressTunnelPeerIdx OBJECT-TYPE
	SYNTAX 		Unsigned32 
	MAX-ACCESS  read-create
 	STATUS current
	DESCRIPTION
	"Represents the Index of the Peer (as it is defined in the Peer Table),
	 for which this egress tunnel should be established."
	::= { mplsEgressTunnelEntry 14 }

mplsEgressTunnelExpBitsMode OBJECT-TYPE
      SYNTAX     INTEGER {
			notApplicable	(1),
			copyFromPw		(2),
			static			(3)
                }
      MAX-ACCESS    read-create
      STATUS        current
      DESCRIPTION
	  "Indicates the EXP Bits Mode of this egress tunnel:
	   
	   copyFromPw(2)- EXP Bits of this tunnel are copied from the EXP bits
					  of the PW, as configured for the PW.

	   static(3) 	- EXP Bits value is set to a fixed value,
					  specifies in mplsEgressTunnelExpBits.
	   ."
      ::= { mplsEgressTunnelEntry 15 }

mplsEgressTunnelExpBits     OBJECT-TYPE
     SYNTAX        Unsigned32 
     MAX-ACCESS    read-create
     STATUS        current
     DESCRIPTION
     "Indicates the EXP Bits of this egress tunnel.
      Relevant only when EXP Bits Mode is 'static(3)'."
    ::= { mplsEgressTunnelEntry 16 } 

mplsEgressTunnelOperStatus OBJECT-TYPE
      SYNTAX     INTEGER {
			up		(1),
 			down	(2)
			}
      MAX-ACCESS    read-only
      STATUS        current
      DESCRIPTION
           "Indicates the operational status of this egress tunnel."
    ::= { mplsEgressTunnelEntry 17 }


mplsPhpMode  OBJECT-TYPE
	SYNTAX		INTEGER
	{
		disable		(2),
		enable		(3)
	}
	MAX-ACCESS	read-write
	STATUS		current
	DESCRIPTION
		"This variable represents the PHP (Penultimate Hop Popping) Mode
		 of the device."
	::= { radMplsCfgObjects 9 }


radMplsLdp				OBJECT IDENTIFIER ::= { radMpls 2 }
radMplsLdpCfgObjects	OBJECT IDENTIFIER ::= { radMplsLdp 1 }

--
-- The MPLS LDP Entity Table
-- Table is based on 'mplsLdpEntityTable' from MPLS-LDP-STD-MIB (RFC 3815)
--

radMplsLdpEntityTable OBJECT-TYPE
	SYNTAX      SEQUENCE OF MplsLdpEntityEntry
	MAX-ACCESS  not-accessible
	STATUS      current
	DESCRIPTION
		"This table contains information about the
		 MPLS Label Distribution Protocol Entities which
		 exist on this Label Switching Router (LSR)
		 or Label Edge Router (LER)."
	::= { radMplsLdpCfgObjects 1 }

radMplsLdpEntityEntry OBJECT-TYPE
SYNTAX		MplsLdpEntityEntry
MAX-ACCESS	not-accessible
STATUS	current
DESCRIPTION
	"An entry in this table represents an LDP entity.
	 An entry can be created by a network administrator
	 or by an SNMP agent as instructed by LDP."
	INDEX { radMplsLdpEntityLdpId, radMplsLdpEntityIndex }
	::= { radMplsLdpEntityTable 1 }

MplsLdpEntityEntry ::= SEQUENCE {
	radMplsLdpEntityLdpId					MplsLdpIdentifier,	-- Leaf 1
	radMplsLdpEntityIndex					IndexInteger,		-- Leaf 2
																-- Leaf 3 reserved
	radMplsLdpEntityAdminStatus				INTEGER,			-- Leaf 4
																-- Leaf 5 reserved
																-- Leaf 6 reserved
																-- Leaf 7 reserved
																-- Leaf 8 reserved
	radMplsLdpEntityKeepAliveHoldTimer		Unsigned32,			-- Leaf 9
	radMplsLdpEntityHelloHoldTimer			Unsigned32,			-- Leaf 10
																-- Leaf 11 reserved
																-- Leaf 12 reserved
																-- Leaf 13 reserved
																-- Leaf 14 reserved
																-- Leaf 15 reserved
																-- Leaf 16 reserved
																-- Leaf 17 reserved
																-- Leaf 18 reserved
																-- Leaf 19 reserved
																-- Leaf 20 reserved
																-- Leaf 21 reserved
																-- Leaf 22 reserved
	radMplsLdpEntityRowStatus				RowStatus			-- Leaf 23
	}

radMplsLdpEntityLdpId OBJECT-TYPE
	SYNTAX		MplsLdpIdentifier
	MAX-ACCESS  not-accessible
	STATUS      current
	DESCRIPTION
		"The LDP identifier.
		 When irrelevant, value = (2^48)-1 (all ones in all 6 octets)."
	::= { radMplsLdpEntityEntry 1 }

radMplsLdpEntityIndex OBJECT-TYPE
	SYNTAX      IndexInteger
	MAX-ACCESS  not-accessible
	STATUS      current
	DESCRIPTION
		"This index is used as a secondary index to uniquely
	 	 identify this row.

	 	 A secondary index (this object) is meaningful to some
	 	 but not all, LDP implementations.  For example
	 	 an LDP implementation which uses PPP would
	 	 use this index to differentiate PPP sub-links.

	 	 Another way to use this index is to give this the
	 	 value of ifIndex.  However, this is dependant
	 	 on the implementation.

		 When irrelevant, value = value = (2^32)-1 (all ones in all bits)."
	::= { radMplsLdpEntityEntry 2 }

	 -- { radMplsLdpEntityEntry 3 } reserved

radMplsLdpEntityAdminStatus OBJECT-TYPE
	SYNTAX	INTEGER
	{
		enable	(1),
		disable	(2)
	}
	MAX-ACCESS  read-create
	STATUS      current
	DESCRIPTION
	 	"The administrative status of this LDP Entity.
	 	 If this object is changed from 'enable' to 'disable'
	 	 and this entity has already attempted to establish
	 	 contact with a Peer, then all contact with that
	 	 Peer is lost and all information from that Peer
	 	 needs to be removed from the MIB. (This implies
	 	 that the network management subsystem should clean
	 	 up any related entry in the mplsLdpPeerTable.  This
	 	 further implies that a 'tear-down' for that session
	 	 is issued and the session and all information related
	 	 to that session cease to exist).

	 	 At this point the operator is able to change values
	 	 which are related to this entity.

	 	 When the admin status is set back to 'enable', then
	 	 this Entity will attempt to establish a new session
	 	 with the Peer."
	::= { radMplsLdpEntityEntry 4 }

	 -- { radMplsLdpEntityEntry 5 } reserved
	 -- { radMplsLdpEntityEntry 6 } reserved
	 -- { radMplsLdpEntityEntry 7 } reserved
	 -- { radMplsLdpEntityEntry 8 } reserved

radMplsLdpEntityKeepAliveHoldTimer OBJECT-TYPE
	SYNTAX      Unsigned32 (1..65535)
	UNITS       "seconds"
	MAX-ACCESS  read-create
	STATUS      current
	DESCRIPTION
		"The 16-bit integer value which is the proposed keep
	 	 alive hold timer for this LDP Entity."
	::= { radMplsLdpEntityEntry 9 }

radMplsLdpEntityHelloHoldTimer OBJECT-TYPE
	SYNTAX      Unsigned32 (0..65535)
	UNITS       "seconds"
	MAX-ACCESS  read-create
	STATUS      current
	DESCRIPTION
		"The 16-bit integer value which is the proposed Hello
		 hold timer for this LDP Entity. The Hello Hold time
		 in seconds.

		 An LSR maintains a record of Hellos received
		 from potential peers.  This object represents
		 the Hold Time in the Common Hello Parameters TLV of
		 the Hello Message.

		 A value of 0 is a default value and should be
		 interpretted in conjunction with the
		 radMplsLdpEntityTargetPeer object.

		 If the value of this object is 0: if the value of the
		 radMplsLdpEntityTargetPeer object is false(2), then this
		 specifies that the Hold Time's actual default value is
		 15 seconds (i.e., the default Hold time for Link Hellos
		 is 15 seconds).  Otherwise if the value of the
		 radMplsLdpEntityTargetPeer object is true(1), then this
		 specifies that the Hold Time's actual default value is
		 45 seconds (i.e., the default Hold time for Targeted
		 Hellos is 45 seconds).

		 A value of 65535 means infinite (i.e., wait forever).

		 All other values represent the amount of time in
		 seconds to wait for a Hello Message.  Setting the
		 hold time to a value smaller than 15 is not
		 recommended, although not forbidden according
		 to RFC3036."
	::= { radMplsLdpEntityEntry 10 }

	 -- { radMplsLdpEntityEntry 11 } reserved
	 -- { radMplsLdpEntityEntry 12 } reserved
	 -- { radMplsLdpEntityEntry 13 } reserved
	 -- { radMplsLdpEntityEntry 14 } reserved
	 -- { radMplsLdpEntityEntry 15 } reserved
	 -- { radMplsLdpEntityEntry 16 } reserved
	 -- { radMplsLdpEntityEntry 17 } reserved
	 -- { radMplsLdpEntityEntry 18 } reserved
	 -- { radMplsLdpEntityEntry 19 } reserved
	 -- { radMplsLdpEntityEntry 20 } reserved
	 -- { radMplsLdpEntityEntry 21 } reserved
	 -- { radMplsLdpEntityEntry 22 } reserved

radMplsLdpEntityRowStatus OBJECT-TYPE
	SYNTAX      RowStatus
	MAX-ACCESS  read-create
	STATUS      current
	DESCRIPTION
		"The status of this conceptual row.  All writable
     	 objects in this row may be modified at any
     	 time, however, as described in detail in
     	 the section entitled, 'Changing Values After
     	 Session Establishment', and again described
     	 in the DESCRIPTION clause of the
     	 radMplsLdpEntityAdminStatus object, if a session
     	 has been initiated with a Peer, changing objects
     	 in this table will wreak havoc with the session
     	 and interrupt traffic.  To repeat again:
     	 the recommended procedure is to
     	 set the radMplsLdpEntityAdminStatus to down, thereby
     	 explicitly causing a session to be torn down. Then,
     	 change objects in this entry, then set
     	 the radMplsLdpEntityAdminStatus to enable,
     	 which enables a new session to be initiated."
	::= { radMplsLdpEntityEntry 23 }


-- Based on 'mplsLdpLsrId' (RO) from MPLS-LDP-STD-MIB (RFC 3815)
radMplsLdpLsrId OBJECT-TYPE
	SYNTAX      MplsLsrIdentifier
	MAX-ACCESS  read-write
	STATUS      current
	DESCRIPTION
		"The Label Switching Router's Identifier."
	::= { radMplsLdpCfgObjects 2 }

-- 
-- file :D:\Synergy\WorkArea\545\mib_rad\txt\radDs0.txt
-- 
-- Title:    RAD-DS0   MIB
--
-- Copyright 1998 RAD Data Communications, Ltd.
-- All Rights Reserved.  
--
--                RAD-DS0 MIB   
--
--Title:     RAD's DS0 Bundle MIB
--Date:      13.09.06
--By:        Liora Gafni
--File:      radds0.txt

-- Last updated by Orly Bachar 2-May-2007

ds0BundleIf   OBJECT IDENTIFIER  ::=  {diverseIfWanGen 15} -- see mpmx.txt for all interfaces


--   Extension to the standard dsx0 bundle table
  
ds0BundleTable  OBJECT-TYPE
       SYNTAX      SEQUENCE OF Ds0BundleEntry
       MAX-ACCESS  not-accessible
       STATUS      current
       DESCRIPTION
       "This table contains additional objects for the standard dsx0BundleTable."
       ::= { ds0BundleIf 1 }

ds0BundleEntry OBJECT-TYPE
       SYNTAX  Ds0BundleEntry 
       MAX-ACCESS  not-accessible
       STATUS      current
       DESCRIPTION
       "An entry augmenting the standard dsx0BundleEntry."
		AUGMENTS { dsx0BundleEntry }
        ::= { ds0BundleTable 1 }

Ds0BundleEntry     ::=
      SEQUENCE
      {
        ds0BundleTsBitFilter	    INTEGER,
        ds0BundleUserDefTsBitFilter Integer32,
		ds0BundleTdmPortNum			Unsigned32,
		ds0BundleTimeslotMask       Unsigned32
       }

ds0BundleTsBitFilter OBJECT-TYPE
        SYNTAX INTEGER
		{
		  notApplicable (1),
		  f64Kbps       (2),
		  f56Kbps       (3),
		  userDefined   (4)
		}
        MAX-ACCESS  read-create
        STATUS  current
        DESCRIPTION
        "Filter for controlling the bandwidth of the bundle.
         The TS Bit Filter contains 8 bits (Hex): 00..FF.
         When a bit is 0: it means that no data will be Tx/Rx on this bit.
         For example: FF means 64K. In this case all 8 bits will be Tx/Rx.
         f64Kbps - Bit Filter will be FF
         f56Kbps - Bit Filter will be FE
         userDefined - Filter will defined by the user via ds0BundleUserDefTsBitFilter.
         
         For Vmux - this object is used to define the ML Card Channelized Bundle BW."
        ::= { ds0BundleEntry 1 }

ds0BundleUserDefTsBitFilter OBJECT-TYPE
        SYNTAX Integer32
        MAX-ACCESS  read-create
        STATUS  current
        DESCRIPTION
        "User Defined Filter for controlling the bandwidth of the bundle.
		 This MIB object is relevant only when ds0BundleTsBitFilter = userDefined (4)
		 This object is useful for users who want to define a special Filter
		 that cannot be defined via ds0BundleTsBitFilter.
		 The TS Bit Filter contains 8 bits (Hex): 00..FF.
         When a bit is 0: it means that no data will be Tx/Rx on this bit."
        ::= { ds0BundleEntry 2 }

ds0BundleTdmPortNum OBJECT-TYPE
    SYNTAX  Unsigned32 
    MAX-ACCESS  read-create
    STATUS  current
    DESCRIPTION
    "This parameter indicates the TDM port number that the bundle 
    is associated to."
    ::= { ds0BundleEntry 3 }

ds0BundleTimeslotMask OBJECT-TYPE
    SYNTAX  Unsigned32 
    MAX-ACCESS  read-create
    STATUS  current
    DESCRIPTION
    "This parameter indicates the timeslots allocated for the bundle:
     Each bit represents a timeslot. Setting a bit to '1' denotes that
     the corresponding timeslot is allocated for that bundle.
     Bit 0 is not in use, since timeslot 0 is never assigned."
    ::= { ds0BundleEntry 4 }

-- 
-- file :D:\Synergy\WorkArea\545\mib_rad\txt\radPdh.txt
-- 
-- RAD-PDH-MIB DEFINITIONS ::= BEGIN
--
--Title:     RAD's PDH INTERFACE MIB
--Version:   1.0
--Date:      15-Nov-06
--By:        Liora Gafni
--File:      radpdh.txt
--
--Last update: 19-Nov-2006 by Liora Gafni


pdhInterface  OBJECT IDENTIFIER  ::=  {diverseIfWanGen 16}

pdhIfConfig     OBJECT IDENTIFIER  ::=  { pdhInterface 1 }      -- Node for configuration
pdhIfStatus     OBJECT IDENTIFIER  ::=  { pdhInterface 2 }      -- Node for status
pdhIfStatis     OBJECT IDENTIFIER  ::=  { pdhInterface 3 }      -- Node for statistics


-- C  O  N  F  I  G  U  R  A  T  I  O  N

-- PDH (Plesiochronous Digital Hierarchy) logical port/interface configuration 

pdhLogPrtConfigTable OBJECT-TYPE
       SYNTAX  SEQUENCE OF PdhLogPrtConfigEntry
       MAX-ACCESS  not-accessible
       STATUS  current
       DESCRIPTION
       "Configuration for PDH (Plesiochronous Digital Hierarchy) Logical 
        ports/interfaces.
        For example: GFP (Generic Framing Procedure) logical interface
        or VCG (Virtual Concatenation Group) logical interface."
       ::= { pdhIfConfig 1 }
  
pdhLogPrtConfigEntry OBJECT-TYPE
       SYNTAX PdhLogPrtConfigEntry
       MAX-ACCESS not-accessible
       STATUS current
       DESCRIPTION
       "Entry in Configuration Table for PDH Logical Ports."
       INDEX   {pdhLogPrtCnfgIdx,pdhLogPrtIndex}
       ::= { pdhLogPrtConfigTable 1 }

PdhLogPrtConfigEntry ::=
         SEQUENCE
         {
		 pdhLogPrtCnfgIdx        Integer32,
		 pdhLogPrtIndex          Unsigned32,         		 		 		 
		 pdhLogPrtMaxDiffDelay   Unsigned32
		 }

-- Note: for the parameter Payload FCS, see radgen.txt: gfpPayloadFcs  (gfpCnfgTable)
 
pdhLogPrtCnfgIdx OBJECT-TYPE
     SYNTAX  Integer32 (1..255)
     MAX-ACCESS  not-accessible
     STATUS  current
     DESCRIPTION
     "This object indicates the Index of the Configuration being accessed.
      Index of 255 relates to the Temporary/Edit (Scratch) Configuration.
      For products that support several configurations, Set can be performed
      only to the Temporary Config (=255).
      For products that don't support Temporary/Edit (Scratch) configuration, 
      this index will be 1."
     ::= { pdhLogPrtConfigEntry 1}

pdhLogPrtIndex OBJECT-TYPE
      SYNTAX  Unsigned32
      MAX-ACCESS  not-accessible
      STATUS  current
      DESCRIPTION
      "This object indicates the number or ifIndex of the selected logical port."
      ::= { pdhLogPrtConfigEntry 2 }

pdhLogPrtMaxDiffDelay  OBJECT-TYPE
     SYNTAX  Unsigned32
     MAX-ACCESS  read-write
     STATUS  current
     DESCRIPTION
     "Maximum Differential Delay.
      Largest allowed difference in msec. between delays in two links (E1/T1)
      that are members of the selected VCG.
      
      This object is relevant for VCG (Virtual Concatenation Group) only."
      ::= { pdhLogPrtConfigEntry 3 }


-- S T A T U S

-- PDH (Plesiochronous Digital Hierarchy) Logical Port Status 

pdhLogPrtStatusTable OBJECT-TYPE
       SYNTAX  SEQUENCE OF PdhLogPrtStatusEntry
       MAX-ACCESS  not-accessible
       STATUS  current
       DESCRIPTION
       "Status of PDH logical port"
       ::= { pdhIfStatus 1 }
  
pdhLogPrtStatusEntry OBJECT-TYPE
       SYNTAX PdhLogPrtStatusEntry
       MAX-ACCESS not-accessible
       STATUS current
       DESCRIPTION
       "Entry in the PDH Logical Port Status Table"
       INDEX   { pdhLogPrtStatusIndex }
       ::= { pdhLogPrtStatusTable 1 }

PdhLogPrtStatusEntry ::=
         SEQUENCE
         {
		 pdhLogPrtStatusIndex     Unsigned32,
		 pdhLogPrtFrameDelineation  INTEGER,
		 pdhLogPrtDiffDelay         Unsigned32
		 }

pdhLogPrtStatusIndex OBJECT-TYPE
      SYNTAX  Unsigned32
      MAX-ACCESS  not-accessible
      STATUS  current
      DESCRIPTION
      "This object indicates the number or ifIndex of the selected logical port."
      ::= { pdhLogPrtStatusEntry 1 }

pdhLogPrtFrameDelineation OBJECT-TYPE
     SYNTAX  INTEGER
      {
       notApplicable    (1),
       notDelineated    (2),
	   delineated  		(3)
      }
      MAX-ACCESS  read-only
      STATUS  current
      DESCRIPTION
      "This object is relevant for GFP (Generic Framing Procedure) only.
       It indicates the GFP Frame delineation status.
       Frame delineation means that the device has found the start of a frame -
       the protocol is synchronized"
      ::= { pdhLogPrtStatusEntry 2 }

pdhLogPrtDiffDelay  OBJECT-TYPE
     SYNTAX  Unsigned32
      MAX-ACCESS  read-only
      STATUS  current
      DESCRIPTION
      "Differential Delay.
       This object indicates the largest detected difference in msec. between 
       delays in two links (E1/T1) that are members of the selected VCG."
      ::= { pdhLogPrtStatusEntry 3 }


-- VCG LCAS (Link Capacity Adjustment Scheme) Members Status table  

vcgLcasMembersStatusTable OBJECT-TYPE
       SYNTAX  SEQUENCE OF VcgLcasMembersStatusEntry
       MAX-ACCESS  not-accessible
       STATUS  current
       DESCRIPTION
       "Status for LCAS (Link Capacity Adjustment Scheme) members (links) of VCG 
        logical port."
       ::= { pdhIfStatus 2 }
  
vcgLcasMembersStatusEntry OBJECT-TYPE
       SYNTAX VcgLcasMembersStatusEntry
       MAX-ACCESS not-accessible
       STATUS current
       DESCRIPTION
       "Entry in LCAS (Link Capacity Adjustment Scheme) links status table for
        VCG (Virtual Concatenation Group) logical port."
       INDEX   { vcgLcasMembersVcgIndex, vcgLcasMembersLinkIndex }
       ::= { vcgLcasMembersStatusTable 1 }

VcgLcasMembersStatusEntry ::=
         SEQUENCE
         {
		 vcgLcasMembersVcgIndex     Unsigned32,
		 vcgLcasMembersLinkIndex    Unsigned32,
		 vcgLcasMembersSourceStatus   INTEGER,
		 vcgLcasMembersSinkStatus     INTEGER
		 }

vcgLcasMembersVcgIndex OBJECT-TYPE
      SYNTAX  Unsigned32
      MAX-ACCESS  not-accessible
      STATUS  current
      DESCRIPTION
      "This object indicates the number or ifIndex of the selected VCG
       (Virtual Concatenation Group) logical port."
      ::= { vcgLcasMembersStatusEntry 1 }

 vcgLcasMembersLinkIndex OBJECT-TYPE
      SYNTAX  Unsigned32
      MAX-ACCESS  not-accessible
      STATUS  current
      DESCRIPTION
      "This object indicates the number or ifIndex of the PDH link
       that is a member of the VCG."
      ::= { vcgLcasMembersStatusEntry 2 }

vcgLcasMembersSourceStatus  OBJECT-TYPE
      SYNTAX INTEGER
      {
       notApplicable (1),
       fail          (2),
       ok            (3)
	  }
      MAX-ACCESS read-only
      STATUS current
      DESCRIPTION
      "This object summarizes the LCAS status of the source (Tx) side of the link."
       ::= { vcgLcasMembersStatusEntry 3 }

vcgLcasMembersSinkStatus  OBJECT-TYPE
      SYNTAX INTEGER
      {
       notApplicable (1),
       fail          (2),
       ok            (3)
      }
      MAX-ACCESS read-only
      STATUS current
      DESCRIPTION
      "This object summarizes the LCAS status of the sink (Rx) side of the link."                    											 
       ::= { vcgLcasMembersStatusEntry 4 }


-- S T A T I S T I C S

-- PDH (Plesiochronous Digital Hierarchy) Logical Port Statistics 

pdhLogPrtStatisTable OBJECT-TYPE
       SYNTAX  SEQUENCE OF PdhLogPrtStatisEntry
       MAX-ACCESS  not-accessible
       STATUS  current
       DESCRIPTION
       "Statistics for PDH (Plesiochronous Digital Hierarchy) Logical Port,
        currently used for GFP (Generic Framing Procedure) interface."
       ::= { pdhIfStatis 1 }
  
pdhLogPrtStatisEntry OBJECT-TYPE
       SYNTAX PdhLogPrtStatisEntry
       MAX-ACCESS not-accessible
       STATUS current
       DESCRIPTION
       "Entry in Statistics Table for PDH (Plesiochronous Digital Hierarchy) Logical Port."
       INDEX   { pdhLogPrtStatisIndex }
       ::= { pdhLogPrtStatisTable 1 }

PdhLogPrtStatisEntry ::=
         SEQUENCE
         {
		 pdhLogPrtStatisIndex         Unsigned32,
		 pdhLogPrtStatisRxCorrFrames  Counter32,
		 pdhLogPrtStatisRxCorrOctets  Counter32,
		 pdhLogPrtStatisRxCHecErrors  Counter32,
		 pdhLogPrtStatisRxTHecErrors  Counter32,
		 pdhLogPrtStatisRxFcsErrors   Counter32
		 }

pdhLogPrtStatisIndex OBJECT-TYPE
      SYNTAX  Unsigned32
      MAX-ACCESS  not-accessible
      STATUS  current
      DESCRIPTION
      "This object indicates the number or ifIndex of the selected Interface."
      ::= { pdhLogPrtStatisEntry 1 }

pdhLogPrtStatisRxCorrFrames OBJECT-TYPE
      SYNTAX  Counter32
      MAX-ACCESS  read-only
      STATUS  current
      DESCRIPTION
      "This object indicates the total number of Correct Frames received."
      ::= { pdhLogPrtStatisEntry 2 }          

pdhLogPrtStatisRxCorrOctets OBJECT-TYPE
      SYNTAX  Counter32
      MAX-ACCESS  read-only
      STATUS  current
      DESCRIPTION
      "This object indicates the total number of Correct Octets received."
      ::= { pdhLogPrtStatisEntry 3 } 

pdhLogPrtStatisRxCHecErrors OBJECT-TYPE
      SYNTAX  Counter32
      MAX-ACCESS  read-only
      STATUS  current
      DESCRIPTION
      "This object indicates the total number of Frames received with errors in 
       the Core header (i.e. cHEC field. cHEC means Core Header Error Correction)."
      ::= { pdhLogPrtStatisEntry 4 } 

pdhLogPrtStatisRxTHecErrors OBJECT-TYPE
      SYNTAX  Counter32
      MAX-ACCESS  read-only
      STATUS  current
      DESCRIPTION
      "This object indicates the total number of Frames received with errors in 
       the Type header (i.e. tHEC field. tHEC means Type Header Error Correction)."
      ::= { pdhLogPrtStatisEntry 5 } 

pdhLogPrtStatisRxFcsErrors OBJECT-TYPE
      SYNTAX  Counter32
      MAX-ACCESS  read-only
      STATUS  current
      DESCRIPTION
      "This object indicates the total number of Frames received with Frame 
       Check Sequence errors."
      ::= { pdhLogPrtStatisEntry 6 } 

-- 
-- file :D:\Synergy\WorkArea\545\mib_rad\txt\radEms.txt
-- 
--Title:     RAD EMS MIB
--Version:   540
--Date:      16-August-07
--By:        Smadar Tauber
--File:      radEms.txt
--
--Last update: 30-March-2008 by Smadar Tauber

--This branch of MIB deals with objects implemented by EMS towards an OSS (other
--vendor's NMS)

radEMS 	 OBJECT IDENTIFIER ::= { rad 15 }  -- RAD EMS

radEmsEvents OBJECT-IDENTITY
     STATUS  current
     DESCRIPTION
     "The events sent by RAD EMS to other vendor's NMS."
     ::= { radEMS 0 }

emsTrapData     OBJECT IDENTIFIER  ::=  { radEMS 1 }    

emsTrapSeverity  OBJECT-TYPE
   SYNTAX   SnmpAdminString
   MAX-ACCESS  accessible-for-notify
   STATUS  current
   DESCRIPTION
    "EMS will send this object as an attached parameter, of traps sent 
     to another vendor's NMS.
     It will include the Severity configured by user for the respective
     trap via Admin Console of the Fault Management.
     The implementation was done so that the string includes characters of 
     digits, while each digit represents a severity, as follows:
     '0' - undefined   
     '1' - normal       
     '2' - indeterminate
     '3' - warning      
     '4' - minor		 
     '5' - major		 
     '6' - critical	  "
     ::= { emsTrapData 1 }

emsEventSeverity  OBJECT-TYPE
   SYNTAX   INTEGER
	 {
      undefined(0),
      normal(1),
	  indeterminate(2),
	  warning(3),
	  minor(4),
	  major(5),
	  critical(6)
   }
   MAX-ACCESS  accessible-for-notify
   STATUS  current
   DESCRIPTION
   "EMS Event Severity by enumerated integer."
     ::= { emsTrapData 2 }

emsTrapOriginatorAddress  OBJECT-TYPE
   SYNTAX   SnmpAdminString
   MAX-ACCESS  accessible-for-notify
   STATUS  current
   DESCRIPTION
    "The Address of the trap originator (when trap is forwarded)."
     ::= { emsTrapData 3 }

emsTrapOriginatorNodeName  OBJECT-TYPE
   SYNTAX   SnmpAdminString
   MAX-ACCESS  accessible-for-notify
   STATUS  current
   DESCRIPTION
    "Node Name given in EMS to the trap originator."
     ::= { emsTrapData 4 }
 
emsEventClassName  OBJECT-TYPE
   SYNTAX   SnmpAdminString
   MAX-ACCESS  accessible-for-notify
   STATUS  current
   DESCRIPTION
    "Event Class Name assigned in EMS."
     ::= { emsTrapData 5 }

emsEventInstance  OBJECT-TYPE
   SYNTAX   SnmpAdminString
   MAX-ACCESS  accessible-for-notify
   STATUS  current
   DESCRIPTION
    "Instance assigned to Event by EMS."
     ::= { emsTrapData 6 }

emsEventDescription  OBJECT-TYPE
   SYNTAX   SnmpAdminString
   MAX-ACCESS  accessible-for-notify
   STATUS  current
   DESCRIPTION
    "Description assigned to this Event in EMS."
     ::= { emsTrapData 7 }

emsEventType  OBJECT-TYPE
   SYNTAX   INTEGER
	 {
       raise(1),  --problem
	   clear(2)	  --resolution
   }
   MAX-ACCESS  accessible-for-notify
   STATUS  current
   DESCRIPTION
    "Event Type assigned by EMS."
     ::= { emsTrapData 8 }

emsEventOperation  OBJECT-TYPE
   SYNTAX   INTEGER
	 {
      noOperation(0),
	  noAck(1),
	  ack(2),
	  delete(3),
	  delete-all(4)
   }
   MAX-ACCESS  accessible-for-notify
   STATUS  current
   DESCRIPTION
    "EMS operation related to this Event."
     ::= { emsTrapData 9 }

emsNodeId  OBJECT-TYPE
   SYNTAX   Counter64
   MAX-ACCESS  accessible-for-notify
   STATUS  current
   DESCRIPTION
    "The EMS ID of the Node. Unique 64-bit identifier."
     ::= { emsTrapData 10 }

emsName  OBJECT-TYPE
   SYNTAX   SnmpAdminString
   MAX-ACCESS  accessible-for-notify
   STATUS  current
   DESCRIPTION
    "EMS station name."
     ::= { emsTrapData 11 }

emsUserName  OBJECT-TYPE
   SYNTAX   SnmpAdminString
   MAX-ACCESS  accessible-for-notify
   STATUS  current
   DESCRIPTION
    "EMS User Name (User who performed emsEventOperation).
     When emsEventOperation=noOperation(0), the string will be 'NA'."
     ::= { emsTrapData 12 }

--NOTIFICATIONS
emsEventLogSizeStatusChange  NOTIFICATION-TYPE
	STATUS	current
	DESCRIPTION
	"This trap is sent in order to provide certain size changes of EMS Event Log. 
	 It is periodically generated and sent when EMS discovers that Event Log 
	 size exceeds Major or Critical thresholds defined by user (relative to 
	 maximum capacity) or when Event Log returns to Normal size." 
	::= { radEmsEvents 1 }

emsEventGenericTrap  NOTIFICATION-TYPE
	OBJECTS { emsTrapOriginatorAddress,  -- Address of the trap originator
              emsTrapOriginatorNodeName, -- EMS Name of the trap originator
		      emsEventClassName,  --  Name of Event Class, assigned in EMS
			  emsEventInstance,   --  Event Instance assigned in EMS
			  emsEventSeverity,   --  Event Severity assigned in EMS
			  emsEventDescription,--  Event Description assigned in EMS
			  emsEventType,       --  Event Type assigned by EMS
			  emsEventOperation,  --  EMS operation related to this Event
			  emsNodeId,          --  EMS ID of the trap originator
			  emsName,            --  EMS station name
			  emsUserName         --  EMS User Name (related to Operation)
            }
	STATUS	current
	DESCRIPTION
	"Generic trap forwarding facility. Used for integration purposes between 
	 RADview EMS and other systems, for example Netcool." 
	::= { radEmsEvents 2 }



END

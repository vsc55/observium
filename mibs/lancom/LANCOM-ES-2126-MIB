LANCOM-ES-2126-MIB DEFINITIONS ::= BEGIN

IMPORTS
    DisplayString FROM SNMPv2-TC
    MODULE-COMPLIANCE,OBJECT-GROUP, NOTIFICATION-GROUP       FROM SNMPv2-CONF
    enterprises,MODULE-IDENTITY,OBJECT-TYPE,NOTIFICATION-TYPE,Counter32,IpAddress        FROM SNMPv2-SMI
    ifIndex    FROM RFC1213-MIB;

-- @ENTERPRISE-SECTION-START
lancomSystems MODULE-IDENTITY
    LAST-UPDATED "200904010000Z"
        ORGANIZATION "LANCOM Systems GmbH"
        CONTACT-INFO
            "Adenauerstrasse 20 / B2, 52146 Wuerselen, Germany
                 Email: info@lancom.de
                 TEL: +49 (0)2405 49936 0
                 FAX: +49 (0)2405 49936 99"
        DESCRIPTION
                "The MIB module is for LANCOM Systems"
        ::= { enterprises 2356 }

switchingSystems               OBJECT IDENTIFIER ::= { lancomSystems 800 }

fastEthernetSwitches            OBJECT IDENTIFIER ::= { switchingSystems 2 }

lancomES2126            OBJECT IDENTIFIER ::= { fastEthernetSwitches 2126 }

-- @ENTERPRISE-SECTION-END
es2126Produces            OBJECT IDENTIFIER ::= { lancomES2126 1 }

es2126System            OBJECT IDENTIFIER ::= { es2126Produces 1 }

es2126CommonSys             OBJECT IDENTIFIER ::= { es2126System 1 }

es2126Reboot OBJECT-TYPE
    SYNTAX      INTEGER(0|1|2)
    MAX-ACCESS      read-write
    STATUS      current
    DESCRIPTION
        "Reboot the system. Get this OID always return zero.
            0 - do nothing
            1 - Reboot without saving start
            2 - Reboot with saving start"
    ::= { es2126CommonSys 1 }

es2126BiosVsersion  OBJECT-TYPE
    SYNTAX      DisplayString
    MAX-ACCESS      read-only
    STATUS      current
    DESCRIPTION
        "Get the BIOS version of the system."
    ::= { es2126CommonSys 2 }

es2126FirmwareVersion   OBJECT-TYPE
    SYNTAX      DisplayString
    MAX-ACCESS      read-only
    STATUS      current
    DESCRIPTION
        "Get the firmware version of the system."
    ::= { es2126CommonSys 3 }

es2126HardwareVersion   OBJECT-TYPE
    SYNTAX      DisplayString
    MAX-ACCESS      read-only
    STATUS      current
    DESCRIPTION
        "Get the hardware version of the system."
    ::= { es2126CommonSys 4 }

es2126MechanicalVersion OBJECT-TYPE
    SYNTAX      DisplayString
    MAX-ACCESS      read-only
    STATUS      current
    DESCRIPTION
        "Get the mechanical version of the system."
    ::= { es2126CommonSys 5 }

es2126SerialNumber  OBJECT-TYPE
    SYNTAX      DisplayString
    MAX-ACCESS      read-only
    STATUS      current
    DESCRIPTION
        "Get the Serial number of the system."
    ::= { es2126CommonSys 6 }

es2126HostMacAddress    OBJECT-TYPE
    SYNTAX      DisplayString
    MAX-ACCESS      read-only
    STATUS      current
    DESCRIPTION
        "Get the MAC address of the system."
    ::= { es2126CommonSys 7 }

es2126DevicePort    OBJECT-TYPE
    SYNTAX      DisplayString
    MAX-ACCESS      read-only
    STATUS      current
    DESCRIPTION
        "Get the quantity of ports that this system owns now."
    ::= { es2126CommonSys 8 }

es2126RamSize  OBJECT-TYPE
    SYNTAX      DisplayString
    MAX-ACCESS      read-only
    STATUS      current
    DESCRIPTION
        "Get the RAM size of the system."
    ::= { es2126CommonSys 9 }

es2126FlashSize  OBJECT-TYPE
    SYNTAX      DisplayString
    MAX-ACCESS      read-only
    STATUS      current
    DESCRIPTION
        "Get the flash size of the system."
    ::= { es2126CommonSys 10 }

es2126SystemDescription  OBJECT-TYPE
    SYNTAX      DisplayString
    MAX-ACCESS      read-only
    STATUS      current
    DESCRIPTION
        "Get the system description."
    ::= { es2126CommonSys 11 }

es2126DeviceName  OBJECT-TYPE
    SYNTAX      DisplayString
    MAX-ACCESS      read-write
    STATUS      current
    DESCRIPTION
        "Get/Set the device Name."
    ::= { es2126CommonSys 12 }

es2126IP            OBJECT IDENTIFIER ::= { es2126System 2 }

es2126DhcpSetting OBJECT-TYPE
    SYNTAX          INTEGER(0|1)
    MAX-ACCESS          read-write
    STATUS          current
    DESCRIPTION
        "Get/Set DHCP status of the system.
            0 - DHCP disable
            1 - DHCP enable"
    ::= { es2126IP 1 }

es2126IPAddress OBJECT-TYPE
    SYNTAX      IpAddress
    MAX-ACCESS      read-write
    STATUS      current
    DESCRIPTION
        "Get/Set the IP address of the system.
         You can't set this OID if DHCP status is enabled."
    ::= { es2126IP 2 }

es2126NetMask OBJECT-TYPE
    SYNTAX      IpAddress
    MAX-ACCESS      read-write
    STATUS      current
    DESCRIPTION
        "Get/Set the subnet mask of the system.
         You can't set this OID if DHCP status is enabled."
    ::= { es2126IP 3 }

es2126DefaultGateway OBJECT-TYPE
    SYNTAX      IpAddress
    MAX-ACCESS      read-write
    STATUS      current
    DESCRIPTION
        "Get/Set the default gateway of the system.
         You can't set this OID if DHCP status is enabled."
    ::= { es2126IP 4 }

es2126DnsSetting OBJECT-TYPE
    SYNTAX      INTEGER(0|1)
    MAX-ACCESS      read-write
    STATUS      current
    DESCRIPTION
        "Get/Set the source of DNS server.
         You can't set this OID if DHCP status is disabled.
            0 - manual, the DNS server is from manual setting
            1 - Auto, the DNS server is assigned by DHCP server."
    ::= { es2126IP 5 }

es2126DnsServer OBJECT-TYPE
    SYNTAX      IpAddress
    MAX-ACCESS      read-write
    STATUS      current
    DESCRIPTION
        "Get/Set the DNS server of the system."
    ::= { es2126IP 6 }

es2126Time              OBJECT IDENTIFIER ::= { es2126System 3 }

es2126SystemCurrentTime OBJECT-TYPE
    SYNTAX      DisplayString
    MAX-ACCESS      read-only
    STATUS      current
    DESCRIPTION
        "Get the current time of the system."
    ::= { es2126Time 1 }

es2126ManualTimeSetting OBJECT-TYPE
    SYNTAX      DisplayString
    MAX-ACCESS      read-write
    STATUS      current
    DESCRIPTION
        "Get/Set the system time of the device.
        The input format is 'Year/Month/Day/Hour/Minute/Second'.
        Ex: 2004/1/1/12/34/25 means 2004/1/1 - 12:24:25.
        Value range:
        Year    : 2000 - 2036,
        Mouth   : 1 - 12,
        Day     : 1 - 31,
        Hour    : 0 - 23,
        Minute  : 0 - 59,
        Sec     : 0 - 59."
    ::= { es2126Time 2 }

es2126NTPServer OBJECT-TYPE
    SYNTAX      DisplayString
    MAX-ACCESS      read-write
    STATUS      current
    DESCRIPTION
        "Get/Set the NTP Time Server. You can use the IP address or domain name."
    ::= { es2126Time 3 }

es2126NTPTimeZone OBJECT-TYPE
    SYNTAX      INTEGER(-12..13)
    MAX-ACCESS      read-write
    STATUS      current
    DESCRIPTION
        "Get/Set the NTP Time Zone.
        Value range is between -12 and 13
        -12 - GMT -12:00,
        -11 - GMT -11:00,
        -10 - GMT -10:00,
         -9 - GMT -09:00,
         -8 - GMT -08:00,
         -7 - GMT -07:00,
         -6 - GMT -06:00,
         -5 - GMT -05:00,
         -4 - GMT -04:00,
         -3 - GMT -03:00,
         -2 - GMT -02:00,
         -1 - GMT -01:00,
          0 - GMT +00:00,
          1 - GMT +01:00,
          2 - GMT +02:00,
          3 - GMT +03:00,
          4 - GMT +04:00,
          5 - GMT +05:00,
          6 - GMT +06:00,
          7 - GMT +07:00,
          8 - GMT +08:00,
          9 - GMT +09:00,
         10 - GMT +10:00,
         11 - GMT +11:00,
         12 - GMT +12:00,
         13 - GMT +13:00. "
    ::= { es2126Time 4 }

es2126NTPTimeSync OBJECT-TYPE
    SYNTAX      INTEGER(0|1)
    MAX-ACCESS      read-write
    STATUS      current
    DESCRIPTION
        "Sync time from NTP Server. Get this OID always return zero.
        Set the Time Server and Time Zone before doing time sync.
        Notice that time server must be correct!
        Value range (1|0):
        1 - Sync.
        0 - do nothing."
    ::= { es2126Time 5 }

es2126DaylightSavingTime OBJECT-TYPE
    SYNTAX      INTEGER(-5..5)
    MAX-ACCESS      read-write
    STATUS      current
    DESCRIPTION
        "Get/Set the daylight saving time.
        Value range is between -5 and 5. Unit: hour. "
    ::= { es2126Time 6 }

es2126DaylightStartTime OBJECT-TYPE
    SYNTAX      DisplayString
    MAX-ACCESS      read-write
    STATUS      current
    DESCRIPTION
        "Get/Set the Start time of Daylight Saving.
        The input format is 'MM/DD/HH',
        and daylight saving start month can't equal end month.
        Example: month/day/hour   10/01/00
        Month: 01~12, day: 01~31, hour: 00~23."
    ::= { es2126Time 7 }

es2126DaylightEndTime OBJECT-TYPE
    SYNTAX      DisplayString
    MAX-ACCESS      read-write
    STATUS      current
    DESCRIPTION
        "Get/Set the End time of Daylight Saving.
        The input format is 'MM/DD/HH',
        and daylight saving start month can't equal end month.
        Example: month/day/hour   04/01/00
        Month: 01~12, day: 01~31, hour: 00~23."
    ::= { es2126Time 8 }


es2126Account               OBJECT IDENTIFIER ::= { es2126System 4 }

es2126AccountNumber OBJECT-TYPE
    SYNTAX      INTEGER(1..5)
    MAX-ACCESS      read-only
    STATUS      current
    DESCRIPTION
        "Get the current account number(s) of the system."
    ::= { es2126Account 1 }

es2126AccountTable  OBJECT-TYPE
    SYNTAX      SEQUENCE OF ES2126AccountEntry
    MAX-ACCESS  not-accessible
    STATUS      current
    DESCRIPTION
        "This is a list of es2126AccountEntry. The numbers of entries are given by
        the value of es2126AccountNumber."
    ::= { es2126Account 2 }

ES2126AccountEntry ::=
SEQUENCE {
    es2126AccountIndex          INTEGER,
    es2126AccountAuthorization  DisplayString,
    es2126AccountName             DisplayString,
    es2126AccountPassword         DisplayString
}

es2126AccountEntry  OBJECT-TYPE
    SYNTAX      ES2126AccountEntry
    MAX-ACCESS      not-accessible
    STATUS      current
    DESCRIPTION
        "This is the Entry(s) for account information."
    INDEX {es2126AccountIndex}
    ::= { es2126AccountTable 1 }

es2126AccountIndex  OBJECT-TYPE
    SYNTAX      INTEGER(1..5)
    MAX-ACCESS      read-only
    STATUS      current
    DESCRIPTION
        "This is the index of the account entry."
    ::= { es2126AccountEntry 1 }

es2126AccountAuthorization  OBJECT-TYPE
    SYNTAX      DisplayString
    MAX-ACCESS      read-only
    STATUS      current
    DESCRIPTION
        "This is the authorization of the account entry."
    ::= { es2126AccountEntry 2 }

es2126AccountName   OBJECT-TYPE
    SYNTAX      DisplayString
    MAX-ACCESS      read-write
    STATUS      current
    DESCRIPTION
        "This is the username of the account entry."
    ::= { es2126AccountEntry 3 }

es2126AccountPassword   OBJECT-TYPE
    SYNTAX      DisplayString
    MAX-ACCESS      read-write
    STATUS      current
    DESCRIPTION
        "This is the password of the account entry. The return value is always '********'."
    ::= { es2126AccountEntry 4 }

es2126AccountAddName OBJECT-TYPE
    SYNTAX      DisplayString
    MAX-ACCESS      read-write
    STATUS      current
    DESCRIPTION
        "This is the account name for adding operation."
    ::= { es2126Account 3 }

es2126AccountAddPassword OBJECT-TYPE
    SYNTAX      DisplayString
    MAX-ACCESS      read-write
    STATUS      current
    DESCRIPTION
        "This is the account password for adding operation. The return value is always '********'."
    ::= { es2126Account 4 }

es2126DoAccountAdd OBJECT-TYPE
    SYNTAX      INTEGER(0|1)
    MAX-ACCESS      read-write
    STATUS      current
    DESCRIPTION
        "Add account name. OID es2126AccountAddName and es2126AccountAddPassword must be
        filled first. Get this OID always return zero.
            1 - Add account.
            0 - do nothing."
    ::= { es2126Account 5 }

es2126AccountDel    OBJECT-TYPE
    SYNTAX      INTEGER(2..5)
    MAX-ACCESS      read-write
    STATUS      current
    DESCRIPTION
        "Delete account. The value is valid es2126AccountIndex(Can't delete administrator)."
    ::= { es2126Account 6 }


es2126Snmp              OBJECT IDENTIFIER ::= { es2126Produces 2 }

es2126GetCommunity OBJECT-TYPE
    SYNTAX      DisplayString
    MAX-ACCESS      read-write
    STATUS      current
    DESCRIPTION
        "Get/Set the get-community of the SNMP."
    ::= { es2126Snmp 1 }

es2126SetCommunity OBJECT-TYPE
    SYNTAX      DisplayString
    MAX-ACCESS      read-write
    STATUS      current
    DESCRIPTION
        "Get/Set the set-community of the SNMP."
    ::= { es2126Snmp 2 }

es2126TrapHostNumber OBJECT-TYPE
    SYNTAX      INTEGER(1..6)
    MAX-ACCESS      read-only
    STATUS      current
    DESCRIPTION
        "Get the number of trap hosts."
    ::= { es2126Snmp 3 }

es2126TrapHostTable OBJECT-TYPE
    SYNTAX      SEQUENCE OF ES2126TrapHostEntry
    MAX-ACCESS  not-accessible
    STATUS      current
    DESCRIPTION
        "This is a list of trap host entry. The numbers of entries are given by the value of es2126TrapHostNumber."
    ::= { es2126Snmp 4 }

ES2126TrapHostEntry ::=
SEQUENCE {
    es2126TrapHostIndex         INTEGER,
    es2126TrapHostIP            IpAddress,
    es2126TrapHostPort            INTEGER,
    es2126TrapHostCommunity       DisplayString
}

es2126TrapHostEntry OBJECT-TYPE
    SYNTAX      ES2126TrapHostEntry
    MAX-ACCESS      not-accessible
    STATUS      current
    DESCRIPTION
        "This is the Entry Information for trap host."
    INDEX {es2126TrapHostIndex}
    ::= { es2126TrapHostTable 1 }

es2126TrapHostIndex OBJECT-TYPE
    SYNTAX      INTEGER(1..6)
    MAX-ACCESS      read-only
    STATUS      current
    DESCRIPTION
        "The index of the trap host entry."
    ::= { es2126TrapHostEntry 1 }

es2126TrapHostIP    OBJECT-TYPE
    SYNTAX      IpAddress
    MAX-ACCESS      read-write
    STATUS      current
    DESCRIPTION
        "This is the IP of the trap host."
    ::= { es2126TrapHostEntry 2 }


es2126TrapHostPort  OBJECT-TYPE
    SYNTAX      INTEGER(1..65535)
    MAX-ACCESS      read-write
    STATUS      current
    DESCRIPTION
        "This is the receiving-port number of the trap host."
    ::= { es2126TrapHostEntry 3 }


es2126TrapHostCommunity OBJECT-TYPE
    SYNTAX      DisplayString
    MAX-ACCESS      read-write
    STATUS      current
    DESCRIPTION
        "The community name for the trap PDU."
    ::= { es2126TrapHostEntry 4 }

es2126RegisterMonitor OBJECT-TYPE
                SYNTAX DisplayString
                MAX-ACCESS read-write
                STATUS current
                DESCRIPTION "Register-Monitor"
                ::= {  es2126Snmp 5 }

es2126DeleteMonitor OBJECT-TYPE
               SYNTAX DisplayString
               MAX-ACCESS read-write
               STATUS current
               DESCRIPTION "Delete-Monitor"
               ::= {  es2126Snmp 6 }

es2126MonitorTable OBJECT-TYPE
                    SYNTAX SEQUENCE OF ES2126MonitorEntry
                    MAX-ACCESS not-accessible
                    STATUS current
                    DESCRIPTION "Monitor-Table"
                    ::= {  es2126Snmp 7 }

ES2126MonitorEntry ::= SEQUENCE {
                    es2126MonitorTableIp IpAddress,
                    es2126MonitorTableMac DisplayString
                   }

es2126MonitorEntry OBJECT-TYPE
                    SYNTAX ES2126MonitorEntry
                    MAX-ACCESS not-accessible
                    STATUS current
                    DESCRIPTION "entry in table"
                    INDEX { es2126MonitorTableIp }
                    ::= {  es2126MonitorTable 1 }

es2126MonitorTableIp OBJECT-TYPE
                  SYNTAX IpAddress
                  MAX-ACCESS read-only
                  STATUS current
                  DESCRIPTION "IP-Address"
                  ::= {  es2126MonitorEntry 1 }

es2126MonitorTableMac OBJECT-TYPE
                  SYNTAX DisplayString
                  MAX-ACCESS read-only
                  STATUS current
                  DESCRIPTION "MAC-Address"
                  ::= {  es2126MonitorEntry 2 }

es2126TrapBootDelayTime OBJECT-TYPE
    SYNTAX      INTEGER(0..120)
    MAX-ACCESS      read-write
    STATUS      current
    DESCRIPTION
        "Get/Set trap boot delay time in second. Default: 0"
    ::= { es2126Snmp 8 }

es2126Alarm             OBJECT IDENTIFIER ::= { es2126Produces 3 }

es2126Event             OBJECT IDENTIFIER ::= { es2126Alarm 1 }

es2126EventNumber OBJECT-TYPE
    SYNTAX      INTEGER(1..2147483647)
    MAX-ACCESS      read-only
    STATUS      current
    DESCRIPTION
        "Get the total number of alarm events."
    ::= { es2126Event 1 }

es2126EventTable    OBJECT-TYPE
    SYNTAX      SEQUENCE OF ES2126EventEntry
    MAX-ACCESS  not-accessible
    STATUS      current
    DESCRIPTION
        "This is a list of alarm event entry. The numbers of entries are given by the value of es2126EventNumber."
    ::= { es2126Event 2 }

ES2126EventEntry ::=
SEQUENCE {
    es2126EventIndex            INTEGER,
    es2126EventName             DisplayString,
    es2126EventSendEmail      INTEGER,
    es2126EventSendTrap       INTEGER
}

es2126EventEntry    OBJECT-TYPE
    SYNTAX      ES2126EventEntry
    MAX-ACCESS      not-accessible
    STATUS      current
    DESCRIPTION
        "This is the entry information for alarm event."
    INDEX {es2126EventIndex}
    ::= { es2126EventTable 1 }

es2126EventIndex    OBJECT-TYPE
    SYNTAX      INTEGER(1..2147483647)
    MAX-ACCESS      read-only
    STATUS      current
    DESCRIPTION
        "This is the index of the alarm event entry."
    ::= { es2126EventEntry 1 }

es2126EventName OBJECT-TYPE
    SYNTAX      DisplayString
    MAX-ACCESS      read-only
    STATUS      current
    DESCRIPTION
        "This is the alarm event name."
    ::= { es2126EventEntry 2 }

es2126EventSendEmail    OBJECT-TYPE
    SYNTAX      INTEGER(0|1)
    MAX-ACCESS      read-write
    STATUS      current
    DESCRIPTION
        "Send email when alarm event is triggered."
    ::= { es2126EventEntry 3 }

es2126EventSendTrap OBJECT-TYPE
    SYNTAX      INTEGER(0|1)
    MAX-ACCESS      read-write
    STATUS      current
    DESCRIPTION
        "Send trap when alarm event is triggered."
    ::= { es2126EventEntry 4 }


es2126Email             OBJECT IDENTIFIER ::= { es2126Alarm 2 }

es2126EmailServer OBJECT-TYPE
    SYNTAX      DisplayString
    MAX-ACCESS      read-write
    STATUS      current
    DESCRIPTION
        "This is the SMTP server for alarm event."
    ::= { es2126Email 1 }

es2126EmailUsername OBJECT-TYPE
    SYNTAX      DisplayString
    MAX-ACCESS      read-write
    STATUS      current
    DESCRIPTION
        "This is the Username of SMTP server."
    ::= { es2126Email 2 }

es2126EmailPassword OBJECT-TYPE
    SYNTAX      DisplayString
    MAX-ACCESS      read-write
    STATUS      current
    DESCRIPTION
        "This is the User Password of SMTP server."
    ::= { es2126Email 3 }

es2126EmailSender OBJECT-TYPE
	SYNTAX      DisplayString
	MAX-ACCESS	    read-write
	STATUS		current
	DESCRIPTION
		"This is the Sender of SMTP server."
	::= { es2126Email 4 }

es2126EmailReturnPath OBJECT-TYPE
	SYNTAX      DisplayString
	MAX-ACCESS	    read-write
	STATUS		current
	DESCRIPTION
		"This is the return path of mail."
	::= { es2126Email 5 }

es2126EmailUserNumber OBJECT-TYPE
    SYNTAX      INTEGER(1..6)
    MAX-ACCESS      read-only
    STATUS      current
    DESCRIPTION
        "The number of the email users that you want to send the alarm notification."
    ::= { es2126Email 6 }

es2126EmailUserTable    OBJECT-TYPE
    SYNTAX      SEQUENCE OF ES2126EmailUserEntry
    MAX-ACCESS  not-accessible
    STATUS      current
    DESCRIPTION
        "This is a list of email user entry. The numbers of entries are given by the value of es2126EmailUserNumber."
    ::= { es2126Email 7 }

ES2126EmailUserEntry ::=
SEQUENCE {
    es2126EmailUserIndex            INTEGER,
    es2126EmailUserAddress          DisplayString
}

es2126EmailUserEntry    OBJECT-TYPE
    SYNTAX      ES2126EmailUserEntry
    MAX-ACCESS      not-accessible
    STATUS      current
    DESCRIPTION
        "This is the Entry information for email user entry."
    INDEX {es2126EmailUserIndex}
    ::= { es2126EmailUserTable 1 }

es2126EmailUserIndex    OBJECT-TYPE
    SYNTAX      INTEGER(1..6)
    MAX-ACCESS      read-only
    STATUS      current
    DESCRIPTION
        "This is the index of the email user entry."
    ::= { es2126EmailUserEntry 1 }

es2126EmailUserAddress  OBJECT-TYPE
    SYNTAX      DisplayString
    MAX-ACCESS      read-write
    STATUS      current
    DESCRIPTION
        "This is the email address of the email user entry."
    ::= { es2126EmailUserEntry 2 }

es2126Tftp              OBJECT IDENTIFIER ::= { es2126Produces 4 }

es2126RemoteTftpServer OBJECT-TYPE
    SYNTAX      IpAddress
    MAX-ACCESS      read-write
    STATUS      current
    DESCRIPTION
        "Get/Set the remote tftp server."
    ::= { es2126Tftp 1 }

es2126InternalTftpServerState OBJECT-TYPE
    SYNTAX      INTEGER(0|1)
    MAX-ACCESS      read-write
    STATUS      current
    DESCRIPTION
        "Get/Set internal tftp server state.
         0 : Disable
         1 : Enable
        "
    ::= { es2126Tftp 2 }

es2126Configuration             OBJECT IDENTIFIER ::= { es2126Produces 5 }

es2126SaveRestore               OBJECT IDENTIFIER ::= { es2126Configuration 1 }

es2126SaveStart OBJECT-TYPE
    SYNTAX      INTEGER(0|1)
    MAX-ACCESS      read-write
    STATUS      current
    DESCRIPTION
        "Save current configuration into flash memory (Save as Start Configuration).
        Get this OID always return zero.
            1 - Save.
            0 - do nothing. "
    ::= { es2126SaveRestore 1 }

es2126SaveUser OBJECT-TYPE
    SYNTAX      INTEGER(0|1)
    MAX-ACCESS      read-write
    STATUS      current
    DESCRIPTION
        "Save current configuration into flash memory (Save as User Configuration).
        Get this OID always return zero.
            1 - Save.
            0 - do nothing. "
    ::= { es2126SaveRestore 2 }

es2126RestoreDefault OBJECT-TYPE
    SYNTAX      INTEGER(0|1|2)
    MAX-ACCESS      read-write
    STATUS      current
    DESCRIPTION
        "Restore factory default configuration.
        Get this OID always return zero.
            2 - Restore default included default ip address.
        1 - Restore default without changing current ip address.
            0 - do nothing. "
    ::= { es2126SaveRestore 3 }

es2126RestoreUser OBJECT-TYPE
    SYNTAX      INTEGER(0|1)
    MAX-ACCESS      read-write
    STATUS      current
    DESCRIPTION
        "Restore user configuration.
        Get this OID always return zero.
            1 - Restore.
            0 - do nothing. "
    ::= { es2126SaveRestore 4 }


es2126ConfigFile            OBJECT IDENTIFIER ::= { es2126Configuration 2 }

es2126ExportConfigName OBJECT-TYPE
    SYNTAX      DisplayString
    MAX-ACCESS      read-write
    STATUS      current
    DESCRIPTION
        "Get/Set the export file path and name."
    ::= { es2126ConfigFile 1 }

es2126DoExportConfig OBJECT-TYPE
    SYNTAX      INTEGER(1|2)
    MAX-ACCESS      read-write
    STATUS      current
    DESCRIPTION
        "Do export-config.
        Get this OID always return zero.
            1   -   Export start section.
            2   -   Export user-conf section."
    ::= { es2126ConfigFile 2 }

es2126ImportConfigName OBJECT-TYPE
    SYNTAX      DisplayString
    MAX-ACCESS      read-write
    STATUS      current
    DESCRIPTION
        "Get/Set the import file path and name."
    ::= { es2126ConfigFile 3 }

es2126DoImportConfig OBJECT-TYPE
    SYNTAX      INTEGER(1|2)
    MAX-ACCESS      read-write
    STATUS      current
    DESCRIPTION
        "Do import-config.
        Get this OID always return zero.
            1   -   Import start section.
            2   -   Import user-conf section."
    ::= { es2126ConfigFile 4 }

es2126Diagnostic            OBJECT IDENTIFIER ::= { es2126Produces 6 }

es2126InternalLoopbackTest OBJECT-TYPE
    SYNTAX      DisplayString
    MAX-ACCESS      read-only
    STATUS      current
    DESCRIPTION
        "Internal loop back test."
    ::= { es2126Diagnostic 1 }

es2126ExternalLoopbackTest OBJECT-TYPE
    SYNTAX      DisplayString
    MAX-ACCESS      read-only
    STATUS      current
    DESCRIPTION
        "External loop back test."
    ::= { es2126Diagnostic 2 }

es2126PingTest OBJECT-TYPE
    SYNTAX      DisplayString
    MAX-ACCESS      read-write
    STATUS      current
    DESCRIPTION
        "Set the host address that you want to ping and the system will return the test result."
    ::= { es2126Diagnostic 3 }

es2126Watchdog               OBJECT IDENTIFIER ::= { es2126Diagnostic 4 }

es2126WatchdogState OBJECT-TYPE
    SYNTAX      INTEGER(0|1)
    MAX-ACCESS      read-write
    STATUS      current
    DESCRIPTION
        "Set the watchdog state.
            1 - Enable.
            0 - Disable."
    ::= { es2126Watchdog 1 }

es2126WatchdogTimeGap OBJECT-TYPE
    SYNTAX      INTEGER(0..100)
    MAX-ACCESS      read-write
    STATUS      current
    DESCRIPTION
        "Set the watchdog time gap, from 1 to 100."
    ::= { es2126Watchdog 2 }

es2126WatchdogHost OBJECT-TYPE
    SYNTAX      DisplayString
    MAX-ACCESS      read-write
    STATUS      current
    DESCRIPTION
        "Set the watchdog host"
    ::= { es2126Watchdog 3 }

es2126WatchdogResetMgtInf OBJECT-TYPE
    SYNTAX      INTEGER(0|1)
    MAX-ACCESS      read-write
    STATUS      current
    DESCRIPTION
        "Set the state of resetting the management cpu interface.
            1 - Enable.
            0 - Disable."
    ::= { es2126Watchdog 4 }

es2126WatchdogResetMgtInfCount OBJECT-TYPE
    SYNTAX      INTEGER(1..20)
    MAX-ACCESS      read-write
    STATUS      current
    DESCRIPTION
        "Set the count of resetting the management cpu interface."
    ::= { es2126Watchdog 5 }

es2126WatchdogResetSystem OBJECT-TYPE
    SYNTAX      INTEGER(0|1)
    MAX-ACCESS      read-write
    STATUS      current
    DESCRIPTION
        "Set the state of rebooting the system.
            1 - Enable.
            0 - Disable."
    ::= { es2126Watchdog 6 }

es2126WatchdogResetSystemCount OBJECT-TYPE
    SYNTAX      INTEGER(1..1000)
    MAX-ACCESS      read-write
    STATUS      current
    DESCRIPTION
        "Set the count of rebooting the system"
    ::= { es2126Watchdog 7 }

es2126Log               OBJECT IDENTIFIER ::= { es2126Produces 7 }

es2126ClearLog OBJECT-TYPE
    SYNTAX      INTEGER(0|1)
    MAX-ACCESS      read-write
    STATUS      current
    DESCRIPTION
        "Clear system log.
        Get this OID always return zero.
            1 - Clear log.
            0 - do nothing. "
    ::= { es2126Log 1 }

es2126UploadLog OBJECT-TYPE
    SYNTAX      INTEGER(0|1)
    MAX-ACCESS      read-write
    STATUS      current
    DESCRIPTION
        "Upload current system log. Set the correct tftp server first.
        The format of log file is 'ModelName_SerialNumbuer_YYMMDD_HHMM'.
        Get this OID always return zero.
            1 - Upload log
            0 - do nothing. "
    ::= { es2126Log 2 }

es2126AutoUploadLogState OBJECT-TYPE
    SYNTAX      INTEGER(0|1)
    MAX-ACCESS      read-write
    STATUS      current
    DESCRIPTION
        "Enable auto-upload log function. Set the correct tftp server first.
        The format of log file is 'ModelName_SerialNumbuer_YYMMDD_HHMM'.
        Get this OID always return zero.
            1 - Enable auto-upload
            0 - do nothing. "
    ::= { es2126Log 3 }

es2126LogNumber OBJECT-TYPE
    SYNTAX      INTEGER(0..120)
    MAX-ACCESS      read-only
    STATUS      current
    DESCRIPTION
        "Get the number of current system log. "
    ::= { es2126Log 4 }

es2126LogTable  OBJECT-TYPE
    SYNTAX      SEQUENCE OF ES2126LogEntry
    MAX-ACCESS  not-accessible
    STATUS      current
    DESCRIPTION
        "This is a list of log entry. The numbers of entries are given by the value of es2126LogNumber."
    ::= { es2126Log 5 }

ES2126LogEntry ::=
SEQUENCE {
    es2126LogIndex          INTEGER,
    es2126LogEvent              DisplayString
}

es2126LogEntry  OBJECT-TYPE
    SYNTAX      ES2126LogEntry
    MAX-ACCESS      not-accessible
    STATUS      current
    DESCRIPTION
        "This is the Entry information for system log."
    INDEX {es2126LogIndex}
    ::= { es2126LogTable 1 }

es2126LogIndex  OBJECT-TYPE
    SYNTAX      INTEGER(1..120)
    MAX-ACCESS      read-only
    STATUS      current
    DESCRIPTION
        "This is the index of the log entry."
    ::= { es2126LogEntry 1 }

es2126LogEvent  OBJECT-TYPE
    SYNTAX      DisplayString
    MAX-ACCESS      read-only
    STATUS      current
    DESCRIPTION
        "This is the detail information of the log entry."
    ::= { es2126LogEntry 2 }

es2126Firmware              OBJECT IDENTIFIER ::= { es2126Produces 8 }

es2126FirmwareFileName OBJECT-TYPE
    SYNTAX      DisplayString
    MAX-ACCESS      read-write
    STATUS      current
    DESCRIPTION
        "Get/Set the path and filename for firmware upgrading."
    ::= { es2126Firmware 1 }

es2126DoFirmwareUpgrade OBJECT-TYPE
    SYNTAX      INTEGER(0|1)
    MAX-ACCESS      read-write
    STATUS      current
    DESCRIPTION
        "Do firmware upgrade. Get this OID always return zero.
            1 - Do firmware upgrade.
            0 - do nothing."
    ::= { es2126Firmware 2 }


es2126Port              OBJECT IDENTIFIER ::= { es2126Produces 9 }

es2126PortStatus            OBJECT IDENTIFIER ::= { es2126Port 1 }

es2126PortStatusNumber OBJECT-TYPE
    SYNTAX      INTEGER(1..2147483647)
    MAX-ACCESS      read-only
    STATUS      current
    DESCRIPTION
        "Get the number of port."
    ::= { es2126PortStatus 1 }

es2126PortStatusTable   OBJECT-TYPE
    SYNTAX      SEQUENCE OF ES2126PortStatusEntry
    MAX-ACCESS  not-accessible
    STATUS      current
    DESCRIPTION
        "This is a list of port status entry. The numbers of entries are given by the value of es2126PortStatusNumber."
    ::= { es2126PortStatus 2 }

ES2126PortStatusEntry ::=
SEQUENCE {
    es2126PortStatusIndex           INTEGER,
    es2126PortStatusMedia          DisplayString,
    es2126PortStatusLink           DisplayString,
    es2126PortStatusPortState      DisplayString,
    es2126PortStatusAutoNego       DisplayString,
    es2126PortStatusSpdDpx         DisplayString,
    es2126PortStatusRxPause        DisplayString,
    es2126PortStatusTxPause        DisplayString,
    es2126PortStatusDescription     DisplayString
}

es2126PortStatusEntry   OBJECT-TYPE
    SYNTAX      ES2126PortStatusEntry
    MAX-ACCESS      not-accessible
    STATUS      current
    DESCRIPTION
        "This is the entry(s) for port status information."
    INDEX {es2126PortStatusIndex}
    ::= { es2126PortStatusTable 1 }

es2126PortStatusIndex   OBJECT-TYPE
    SYNTAX      INTEGER(1..2147483647)
    MAX-ACCESS      read-only
    STATUS      current
    DESCRIPTION
        "This is the index of the port status entry."
    ::= { es2126PortStatusEntry 1 }

es2126PortStatusMedia   OBJECT-TYPE
    SYNTAX      DisplayString
    MAX-ACCESS      read-only
    STATUS      current
    DESCRIPTION
        "The port media type of the port status entry."
    ::= { es2126PortStatusEntry 2 }

es2126PortStatusLink    OBJECT-TYPE
    SYNTAX      DisplayString
    MAX-ACCESS      read-only
    STATUS      current
    DESCRIPTION
        "This is the port link of the port status entry."
    ::= { es2126PortStatusEntry 3 }

es2126PortStatusPortState   OBJECT-TYPE
    SYNTAX      DisplayString
    MAX-ACCESS      read-only
    STATUS      current
    DESCRIPTION
        "This is the port state of the port status entry."
    ::= { es2126PortStatusEntry 4 }

es2126PortStatusAutoNego    OBJECT-TYPE
    SYNTAX      DisplayString
    MAX-ACCESS      read-only
    STATUS      current
    DESCRIPTION
        "This is the auto negotiation of the port status entry."
    ::= { es2126PortStatusEntry 5 }

es2126PortStatusSpdDpx  OBJECT-TYPE
    SYNTAX      DisplayString
    MAX-ACCESS      read-only
    STATUS      current
    DESCRIPTION
        "This is the speed/duplex of the port status entry."
    ::= { es2126PortStatusEntry 6 }

es2126PortStatusRxPause     OBJECT-TYPE
    SYNTAX      DisplayString
    MAX-ACCESS      read-only
    STATUS      current
    DESCRIPTION
        "The Rx Pause of the port status entry."
    ::= { es2126PortStatusEntry 7 }

es2126PortStatusTxPause     OBJECT-TYPE
    SYNTAX      DisplayString
    MAX-ACCESS      read-only
    STATUS      current
    DESCRIPTION
        "The Tx Pause of the port status entry."
    ::= { es2126PortStatusEntry 8 }

es2126PortStatusDescription OBJECT-TYPE
    SYNTAX      DisplayString
    MAX-ACCESS      read-only
    STATUS      current
    DESCRIPTION
        "This is the description of port."
    ::= { es2126PortStatusEntry 9 }

es2126PortConf              OBJECT IDENTIFIER ::= { es2126Port 2 }

es2126PortConfNumber OBJECT-TYPE
    SYNTAX      INTEGER(1..2147483647)
    MAX-ACCESS      read-only
    STATUS      current
    DESCRIPTION
        "Get the number of port configuration."
    ::= { es2126PortConf 1 }

es2126PortConfTable OBJECT-TYPE
    SYNTAX      SEQUENCE OF ES2126PortConfEntry
    MAX-ACCESS  not-accessible
    STATUS      current
    DESCRIPTION
        "This is a list of port configuration entry. The numbers of entries are given by the value of es2126PortConfNumber."
    ::= { es2126PortConf 2 }

ES2126PortConfEntry ::=
SEQUENCE {
    es2126PortConfIndex        INTEGER,
    es2126PortConfPortState        INTEGER,
    es2126PortConfSpdDpx           INTEGER,
    es2126PortConfFlwCtrl          INTEGER,
    es2126PortConfDescription      DisplayString
}

es2126PortConfEntry OBJECT-TYPE
    SYNTAX      ES2126PortConfEntry
    MAX-ACCESS      not-accessible
    STATUS      current
    DESCRIPTION
        "This is the Entry(s) for port configuration information."
    INDEX {es2126PortConfIndex}
    ::= { es2126PortConfTable 1 }

es2126PortConfIndex OBJECT-TYPE
    SYNTAX      INTEGER(1..2147483647)
    MAX-ACCESS      read-only
    STATUS      current
    DESCRIPTION
        "This is the index of the port configuration entry."
    ::= { es2126PortConfEntry 1 }

es2126PortConfPortState OBJECT-TYPE
    SYNTAX      INTEGER(0|1)
    MAX-ACCESS      read-write
    STATUS      current
    DESCRIPTION
        "This is the port state of the port configuration entry.
         0 - disabled.
         1 - enabled. "
    ::= { es2126PortConfEntry 2 }

es2126PortConfSpdDpx    OBJECT-TYPE
    SYNTAX      INTEGER(0..5)
    MAX-ACCESS      read-write
    STATUS      current
    DESCRIPTION
        "This is the speed/duplex of the port configuration entry.
         0 - auto.
         1 - 10M/Half.
         2 - 10M/Full.
         3 - 100M/Half.
         4 - 100M/Full.
         5 - 1G/Full.  "
    ::= { es2126PortConfEntry 3 }

es2126PortConfFlwCtrl   OBJECT-TYPE
    SYNTAX      INTEGER(0|1)
    MAX-ACCESS      read-write
    STATUS      current
    DESCRIPTION
        "This is the flow control of the port configuration entry.
         0 - asymmetric.
         1 - symmetric.  "
    ::= { es2126PortConfEntry 4 }

es2126PortConfDescription   OBJECT-TYPE
    SYNTAX      DisplayString
    MAX-ACCESS      read-write
    STATUS      current
    DESCRIPTION
        "This is the description of port."
    ::= { es2126PortConfEntry 5 }

es2126PortBandwidth             OBJECT IDENTIFIER ::= { es2126Port 3 }

es2126PortBandwidthTable    OBJECT-TYPE
    SYNTAX      SEQUENCE OF ES2126PortBandwidthEntry
    MAX-ACCESS  not-accessible
    STATUS      current
    DESCRIPTION
        "This is a list of port bandwidth entry."
    ::= { es2126PortBandwidth 1 }

ES2126PortBandwidthEntry ::=
SEQUENCE {
    es2126PortBandwidthIndex                  INTEGER,
    es2126PortBandwidthIngressRate        INTEGER,
    es2126PortBandwidthEgressRate         INTEGER
}

es2126PortBandwidthEntry    OBJECT-TYPE
    SYNTAX      ES2126PortBandwidthEntry
    MAX-ACCESS      not-accessible
    STATUS      current
    DESCRIPTION
        "This is the Entry(s) for port bandwidth configuration."
    INDEX {es2126PortBandwidthIndex}
    ::= { es2126PortBandwidthTable 1 }

es2126PortBandwidthIndex    OBJECT-TYPE
    SYNTAX      INTEGER(1..26)
    MAX-ACCESS      read-only
    STATUS      current
    DESCRIPTION
        "This is the index of the port bandwidth entry."
    ::= { es2126PortBandwidthEntry 1 }

es2126PortBandwidthIngressRate  OBJECT-TYPE
    SYNTAX      INTEGER(66..1024000)
    MAX-ACCESS      read-write
    STATUS      current
    DESCRIPTION
        "Get/Set the port bandwidth ingress rate.
         Fast Ethernet port range: 66~102400(Kb)
         Gigabit Ethernet port range: 66~1024000(Kb)"
    ::= { es2126PortBandwidthEntry 2 }

es2126PortBandwidthEgressRate   OBJECT-TYPE
    SYNTAX      INTEGER(66..1024000)
    MAX-ACCESS      read-write
    STATUS      current
    DESCRIPTION
        "Get/Set the port bandwidth egress rate.
         Fast Ethernet port range: 66~102400(Kb)
         Gigabit Ethernet port range: 66~1024000(Kb)"
    ::= { es2126PortBandwidthEntry 3 }

es2126PortBandwidthStormType    OBJECT-TYPE
    SYNTAX      INTEGER(0..4)
    MAX-ACCESS      read-write
    STATUS      current
    DESCRIPTION
        "This is the bandwidth storm type.
        0:Disable
                1:Broadcast Storm Control
                2:Multicast Storm Control
                3:Unknown Unicast Storm Control
                4:Broadcast, Multicast, and Unknown Unicast Storm Control"
    ::= { es2126PortBandwidth 2 }

es2126PortBandwidthStormRate    OBJECT-TYPE
    SYNTAX      INTEGER(1..100)
    MAX-ACCESS      read-write
    STATUS      current
    DESCRIPTION
        "This is the storm rate."
    ::= { es2126PortBandwidth 3 }

es2126PortSFPInfo               OBJECT IDENTIFIER ::= { es2126Port 4 }

es2126PortSFPInfoNumber OBJECT-TYPE
    SYNTAX      INTEGER(1..2147483647)
    MAX-ACCESS      read-only
    STATUS      current
    DESCRIPTION
        "Get the number of sfp info entry."
    ::= { es2126PortSFPInfo 1 }

es2126PortSFPInfoTable  OBJECT-TYPE
    SYNTAX      SEQUENCE OF ES2126PORTSFPInfoEntry
    MAX-ACCESS  not-accessible
    STATUS      current
    DESCRIPTION
        "A list of sfp info entry. The numbers of entries are given by the value of es2126PortSFPInfoNumber."
    ::= { es2126PortSFPInfo 2 }

ES2126PORTSFPInfoEntry ::=
SEQUENCE {
    es2126PortSFPInfoIndex      INTEGER,
    es2126PortSFPConnectorType  DisplayString,
    es2126PortSFPFiberType      DisplayString,
    es2126PortSFPWavelength     DisplayString,
    es2126PortSFPBaudRate       DisplayString,
    es2126PortSFPVendorOUI      DisplayString,
    es2126PortSFPVendorName     DisplayString,
    es2126PortSFPVendorPN       DisplayString,
    es2126PortSFPVendorRev      DisplayString,
    es2126PortSFPVendorSN       DisplayString,
    es2126PortSFPDateCode       DisplayString,
    es2126PortSFPTemperature    DisplayString,
    es2126PortSFPVcc            DisplayString,
    es2126PortSFPTxBias         DisplayString,
    es2126PortSFPTxPWR          DisplayString,
    es2126PortSFPRxPWR          DisplayString
}

es2126PortSFPInfoEntry  OBJECT-TYPE
    SYNTAX      ES2126PORTSFPInfoEntry
    MAX-ACCESS      not-accessible
    STATUS      current
    DESCRIPTION
        "Entry(s) for SFP information."
    INDEX {es2126PortSFPInfoIndex}
    ::= { es2126PortSFPInfoTable 1 }

es2126PortSFPInfoIndex  OBJECT-TYPE
    SYNTAX      INTEGER(1..2147483647)
    MAX-ACCESS      read-only
    STATUS      current
    DESCRIPTION
        "The index of the sfp info entry."
    ::= { es2126PortSFPInfoEntry 1 }

es2126PortSFPConnectorType  OBJECT-TYPE
    SYNTAX      DisplayString
    MAX-ACCESS      read-only
    STATUS      current
    DESCRIPTION
        "Get connector type of the sfp."
    ::= { es2126PortSFPInfoEntry 2 }

es2126PortSFPFiberType  OBJECT-TYPE
    SYNTAX      DisplayString
    MAX-ACCESS      read-only
    STATUS      current
    DESCRIPTION
        "Get fiber type of the sfp."
    ::= { es2126PortSFPInfoEntry 3 }

es2126PortSFPWavelength OBJECT-TYPE
    SYNTAX      DisplayString
    MAX-ACCESS      read-only
    STATUS      current
    DESCRIPTION
        "Get tx central wavelength of the sfp."
    ::= { es2126PortSFPInfoEntry 4 }

es2126PortSFPBaudRate   OBJECT-TYPE
    SYNTAX      DisplayString
    MAX-ACCESS      read-only
    STATUS      current
    DESCRIPTION
        "Get baud rate of the sfp."
    ::= { es2126PortSFPInfoEntry 5 }

es2126PortSFPVendorOUI  OBJECT-TYPE
    SYNTAX      DisplayString
    MAX-ACCESS      read-only
    STATUS      current
    DESCRIPTION
        "Get vendor OUI of the sfp."
    ::= { es2126PortSFPInfoEntry 6 }

es2126PortSFPVendorName OBJECT-TYPE
    SYNTAX      DisplayString
    MAX-ACCESS      read-only
    STATUS      current
    DESCRIPTION
        "Get vendor name of the sfp."
    ::= { es2126PortSFPInfoEntry 7 }

es2126PortSFPVendorPN   OBJECT-TYPE
    SYNTAX      DisplayString
    MAX-ACCESS      read-only
    STATUS      current
    DESCRIPTION
        "Get vendor part number of the sfp."
    ::= { es2126PortSFPInfoEntry 8 }

es2126PortSFPVendorRev  OBJECT-TYPE
    SYNTAX      DisplayString
    MAX-ACCESS      read-only
    STATUS      current
    DESCRIPTION
        "Get vendor revision number of the sfp."
    ::= { es2126PortSFPInfoEntry 9 }

es2126PortSFPVendorSN   OBJECT-TYPE
    SYNTAX      DisplayString
    MAX-ACCESS      read-only
    STATUS      current
    DESCRIPTION
        "Get vendor serial number of the sfp."
    ::= { es2126PortSFPInfoEntry 10 }

es2126PortSFPDateCode   OBJECT-TYPE
    SYNTAX      DisplayString
    MAX-ACCESS      read-only
    STATUS      current
    DESCRIPTION
        "Get data code of the sfp."
    ::= { es2126PortSFPInfoEntry 11 }

es2126PortSFPTemperature    OBJECT-TYPE
    SYNTAX      DisplayString
    MAX-ACCESS      read-only
    STATUS      current
    DESCRIPTION
        "Get current temperature of the sfp."
    ::= { es2126PortSFPInfoEntry 12 }

es2126PortSFPVcc    OBJECT-TYPE
    SYNTAX      DisplayString
    MAX-ACCESS      read-only
    STATUS      current
    DESCRIPTION
        "Get current internal supply voltage of the sfp."
    ::= { es2126PortSFPInfoEntry 13 }

es2126PortSFPTxBias OBJECT-TYPE
    SYNTAX      DisplayString
    MAX-ACCESS      read-only
    STATUS      current
    DESCRIPTION
        "Get current TX Bias of the sfp."
    ::= { es2126PortSFPInfoEntry 14 }

es2126PortSFPTxPWR  OBJECT-TYPE
    SYNTAX      DisplayString
    MAX-ACCESS      read-only
    STATUS      current
    DESCRIPTION
        "Get current TX output power of the sfp."
    ::= { es2126PortSFPInfoEntry 15 }

es2126PortSFPRxPWR  OBJECT-TYPE
    SYNTAX      DisplayString
    MAX-ACCESS      read-only
    STATUS      current
    DESCRIPTION
        "Get current Received Power of the sfp."
    ::= { es2126PortSFPInfoEntry 16 }


es2126LoopDetectedConf              OBJECT IDENTIFIER ::= { es2126Produces 10 }

es2126LoopDetectedNumber OBJECT-TYPE
    SYNTAX      INTEGER(1..2147483647)
    MAX-ACCESS      read-only
    STATUS      current
    DESCRIPTION
        "Get the number of loop detected entry."
    ::= { es2126LoopDetectedConf 1 }

es2126LoopDetectedTable OBJECT-TYPE
    SYNTAX      SEQUENCE OF ES2126LoopDetectedEntry
    MAX-ACCESS  not-accessible
    STATUS      current
    DESCRIPTION
        "This is a list of loop detected entry. The number of entries are given by the value of es2126LoopDetectedNumber."
    ::= { es2126LoopDetectedConf 2 }

ES2126LoopDetectedEntry ::=
SEQUENCE {
    es2126LoopDetectedfIndex           INTEGER,
    es2126LoopDetectedStateEbl         INTEGER,
    es2126LoopDetectedCurrentStatus    INTEGER,
    es2126LoopDetectedResumed          INTEGER
}

es2126LoopDetectedEntry OBJECT-TYPE
    SYNTAX      ES2126LoopDetectedEntry
    MAX-ACCESS      not-accessible
    STATUS      current
    DESCRIPTION
        "Entry(s) for loop detected information."
    INDEX {es2126LoopDetectedfIndex}
    ::= { es2126LoopDetectedTable 1 }

es2126LoopDetectedfIndex    OBJECT-TYPE
    SYNTAX      INTEGER(1..2147483647)
    MAX-ACCESS      read-only
    STATUS      current
    DESCRIPTION
        "This is the index of the loop detected entry."
    ::= { es2126LoopDetectedEntry 1 }

es2126LoopDetectedStateEbl  OBJECT-TYPE
    SYNTAX      INTEGER(0|1)
    MAX-ACCESS      read-write
    STATUS      current
    DESCRIPTION
        "The state of the loop detected entry.
         0 - disabled.
         1 - enabled. "
    ::= { es2126LoopDetectedEntry 2 }

es2126LoopDetectedCurrentStatus OBJECT-TYPE
    SYNTAX      INTEGER(0|1)
    MAX-ACCESS      read-only
    STATUS      current
    DESCRIPTION
        "The current status of the loop detected port.
         0 - Unlocked
         1 - Locked due to the loop condition "
    ::= { es2126LoopDetectedEntry 3 }

es2126LoopDetectedResumed   OBJECT-TYPE
    SYNTAX      INTEGER(0|1)
    MAX-ACCESS      read-write
    STATUS      current
    DESCRIPTION
        "Unlock the port which is locked due to loop condition. Get this OID always return zero.
         1 - Unlock the port,
         0 - do nothing."
    ::= { es2126LoopDetectedEntry 4 }

es2126LoopDetectedAction OBJECT-TYPE
    SYNTAX      INTEGER(0|1)
    MAX-ACCESS      read-write
    STATUS      current
    DESCRIPTION
        "Set the corresponding action while loop is detected.
         1 - Lock the loop port,
         0 - do nothing."
    ::= { es2126LoopDetectedConf 3 }

es2126MacTableInfo              OBJECT IDENTIFIER ::= { es2126Produces 11 }

es2126MacTableMaintenance       OBJECT IDENTIFIER ::= { es2126MacTableInfo 1 }

es2126MacTableAgingTime  OBJECT-TYPE
    SYNTAX      INTEGER(0|10..1000000)
    MAX-ACCESS  read-write
    STATUS      current
    DESCRIPTION
        "Set the Mac Table Aging Time (10~1000000 Secs).
         0 : Disable.
        "
    ::= { es2126MacTableMaintenance 1 }

es2126MacTableFlush  OBJECT-TYPE
    SYNTAX      INTEGER(0|1)
    MAX-ACCESS  read-write
    STATUS      current
    DESCRIPTION
        "1 : Flush Mac Table."
    ::= { es2126MacTableMaintenance 2 }

es2126MacTableLearnPortLimitTable  OBJECT-TYPE
    SYNTAX      SEQUENCE OF ES2126MacTableLearnPortLimitEntry
    MAX-ACCESS  not-accessible
    STATUS      current
    DESCRIPTION
        "This is a list of MAC Learning Limitentry."
    ::= { es2126MacTableMaintenance 3 }

ES2126MacTableLearnPortLimitEntry ::=
SEQUENCE {
    es2126MacTableLearnPortLimitIndex   INTEGER,
    es2126MacTableLearnPortLimit        INTEGER
}

es2126MacTableLearnPortLimitEntry  OBJECT-TYPE
    SYNTAX      ES2126MacTableLearnPortLimitEntry
    MAX-ACCESS  not-accessible
    STATUS      current
    DESCRIPTION
        "Entry(s) for Mac Table Port Learning Limit."
    INDEX {es2126MacTableLearnPortLimitIndex}
    ::= { es2126MacTableLearnPortLimitTable 1 }

es2126MacTableLearnPortLimitIndex  OBJECT-TYPE
    SYNTAX      INTEGER(1..26)
    MAX-ACCESS  not-accessible
    STATUS      current
    DESCRIPTION
        "The index of the Mac Table Learning Limit entry."
    ::= { es2126MacTableLearnPortLimitEntry 1 }

es2126MacTableLearnPortLimit  OBJECT-TYPE
    SYNTAX      INTEGER(0..8191)
    MAX-ACCESS  read-write
    STATUS      current
    DESCRIPTION
        "Port Learning Limit (0~8191)."
    ::= { es2126MacTableLearnPortLimitEntry 2 }

es2126MacTableStaticMac       OBJECT IDENTIFIER ::= { es2126MacTableInfo 3 }

es2126MacTableStaticMacNumber  OBJECT-TYPE
    SYNTAX      INTEGER(0..1024)
    MAX-ACCESS  read-only
    STATUS      current
    DESCRIPTION
        "This is number of static Mac table entry"
    ::= { es2126MacTableStaticMac 1 }

es2126MacTableStaticMacEntryCreate  OBJECT-TYPE
    SYNTAX      INTEGER(0..1024)
    MAX-ACCESS  read-write
    STATUS      current
    DESCRIPTION
        "Creat a static mac entry."
    ::= { es2126MacTableStaticMac 2 }

es2126MacTableStaticMacTable  OBJECT-TYPE
    SYNTAX      SEQUENCE OF ES2126MacTableStaticMacEntry
    MAX-ACCESS  not-accessible
    STATUS      current
    DESCRIPTION
        "This is a list of static MAC table."
    ::= { es2126MacTableStaticMac 3 }

ES2126MacTableStaticMacEntry ::=
SEQUENCE {
    es2126MacTableStaticMacIndex        INTEGER,
    es2126MacTableStaticMacAddress      DisplayString,
    es2126MacTableStaticMacVid            INTEGER,
    es2126MacTableStaticMacQueue        INTEGER,
    es2126MacTableStaticMacFwRule       INTEGER,
    es2126MacTableStaticMacPort         INTEGER,
    es2126MacTableStaticMacEntryAction  INTEGER
}

es2126MacTableStaticMacEntry  OBJECT-TYPE
    SYNTAX      ES2126MacTableStaticMacEntry
    MAX-ACCESS  not-accessible
    STATUS      current
    DESCRIPTION
        "Entry(s) for Static Mac Table."
    INDEX {es2126MacTableStaticMacIndex}
    ::= { es2126MacTableStaticMacTable 1 }

es2126MacTableStaticMacIndex  OBJECT-TYPE
    SYNTAX      INTEGER(1..1024)
    MAX-ACCESS      not-accessible
    STATUS      current
    DESCRIPTION
        "The index of the static Mac Table."
    ::= { es2126MacTableStaticMacEntry 1 }

es2126MacTableStaticMacAddress  OBJECT-TYPE
    SYNTAX      DisplayString
    MAX-ACCESS  read-write
    STATUS      current
    DESCRIPTION
        "The mac address of the static mac table entry."
    ::= { es2126MacTableStaticMacEntry 2 }

es2126MacTableStaticMacVid  OBJECT-TYPE
    SYNTAX      INTEGER(1..4094)
    MAX-ACCESS  read-write
    STATUS      current
    DESCRIPTION
        "The vlan id of the static mac table entry."
    ::= { es2126MacTableStaticMacEntry 3 }

es2126MacTableStaticMacQueue  OBJECT-TYPE
    SYNTAX      INTEGER(0..3)
    MAX-ACCESS  read-write
    STATUS      current
    DESCRIPTION
        "The queue of the static mac table entry."
    ::= { es2126MacTableStaticMacEntry 4 }

es2126MacTableStaticMacFwRule  OBJECT-TYPE
    SYNTAX      INTEGER(0..2)
    MAX-ACCESS  read-write
    STATUS      current
    DESCRIPTION
        "The forwarding rule of the static mac table entry.
         0 : static
         1 : Static with Destination Drop
         2 : Static with Source Drop
        "
    ::= { es2126MacTableStaticMacEntry 5 }

es2126MacTableStaticMacPort  OBJECT-TYPE
    SYNTAX      INTEGER(1..26)
    MAX-ACCESS  read-write
    STATUS      current
    DESCRIPTION
        "The port of the static mac table entry."
    ::= { es2126MacTableStaticMacEntry 6 }

es2126MacTableStaticMacEntryAction  OBJECT-TYPE
    SYNTAX      INTEGER(1..3)
    MAX-ACCESS  read-write
    STATUS      current
    DESCRIPTION
        "The port of the static mac table entry."
    ::= { es2126MacTableStaticMacEntry 7 }

es2126MacTableMacAlias       OBJECT IDENTIFIER ::= { es2126MacTableInfo 4 }

es2126MacTableMacAliasNumber  OBJECT-TYPE
    SYNTAX      INTEGER(0..8192)
    MAX-ACCESS  read-only
    STATUS      current
    DESCRIPTION
        "This is number of static Mac table entry"
    ::= { es2126MacTableMacAlias 1 }

es2126MacTableMacAliasEntryCreate  OBJECT-TYPE
    SYNTAX      INTEGER(0..8192)
    MAX-ACCESS  read-write
    STATUS      current
    DESCRIPTION
        "Creat a static mac alias entry."
    ::= { es2126MacTableMacAlias 2 }

es2126MacTableMacAliasTable  OBJECT-TYPE
    SYNTAX      SEQUENCE OF ES2126MacTableMacAliasEntry
    MAX-ACCESS  not-accessible
    STATUS      current
    DESCRIPTION
        "This is a list of MAC Alias table."
    ::= { es2126MacTableMacAlias 3 }

ES2126MacTableMacAliasEntry ::=
SEQUENCE {
    es2126MacTableMacAliasIndex        INTEGER,
    es2126MacTableMacAliasAddress      DisplayString,
    es2126MacTableMacAliasAlias        DisplayString,
    es2126MacTableMacAliasEntryAction  INTEGER
}

es2126MacTableMacAliasEntry  OBJECT-TYPE
    SYNTAX      ES2126MacTableMacAliasEntry
    MAX-ACCESS  not-accessible
    STATUS      current
    DESCRIPTION
        "Entry(s) for Alias Mac Table."
    INDEX {es2126MacTableMacAliasIndex}
    ::= { es2126MacTableMacAliasTable 1 }

es2126MacTableMacAliasIndex  OBJECT-TYPE
    SYNTAX      INTEGER(1..1024)
    MAX-ACCESS      not-accessible
    STATUS      current
    DESCRIPTION
        "The index of the Alias Mac Table."
    ::= { es2126MacTableMacAliasEntry 1 }

es2126MacTableMacAliasAddress  OBJECT-TYPE
    SYNTAX      DisplayString
    MAX-ACCESS      read-write
    STATUS      current
    DESCRIPTION
        "The Mac address of the Alias Mac Table."
    ::= { es2126MacTableMacAliasEntry 2 }

es2126MacTableMacAliasAlias  OBJECT-TYPE
    SYNTAX      DisplayString
    MAX-ACCESS      read-write
    STATUS      current
    DESCRIPTION
        "The Mac Alias of the Alias Mac Table."
    ::= { es2126MacTableMacAliasEntry 3 }

es2126MacTableMacAliasEntryAction  OBJECT-TYPE
    SYNTAX      INTEGER(1..3)
    MAX-ACCESS  read-write
    STATUS      current
    DESCRIPTION
        "The action of the alias mac table entry."
    ::= { es2126MacTableMacAliasEntry 4 }

es2126GVRPInfo              OBJECT IDENTIFIER ::= { es2126Produces 12 }

es2126GvrpConf              OBJECT IDENTIFIER ::= { es2126GVRPInfo 1 }

es2126GvrpConfState OBJECT-TYPE
    SYNTAX      INTEGER(0|1)
    MAX-ACCESS      read-write
    STATUS      current
    DESCRIPTION
        "The state of GVRP.
         0 - Disable
         1 - Enable
    "
    ::= { es2126GvrpConf 1 }

es2126GvrpConfTable OBJECT-TYPE
    SYNTAX      SEQUENCE OF ES2126GvrpConfEntry
    MAX-ACCESS  not-accessible
    STATUS      current
    DESCRIPTION
        "This is a list of the GVRP conf table."
    ::= { es2126GvrpConf 2 }

ES2126GvrpConfEntry ::=
SEQUENCE {
    es2126GvrpConfIndex             INTEGER,
    es2126GvrpConfJoinTime          INTEGER,
    es2126GvrpConfLeaveTime         INTEGER,
    es2126GvrpConfLeaveAllTime      INTEGER,
    es2126GvrpConfDefaultAppMode    INTEGER,
    es2126GvrpConfDefaultRegMode    INTEGER,
    es2126GvrpConfRestrictedMode    INTEGER
}

es2126GvrpConfEntry OBJECT-TYPE
    SYNTAX      ES2126GvrpConfEntry
    MAX-ACCESS      not-accessible
    STATUS      current
    DESCRIPTION
        "Entry(s) for the GVRP conf table."
    INDEX {es2126GvrpConfIndex}
    ::= { es2126GvrpConfTable 1 }

es2126GvrpConfIndex OBJECT-TYPE
    SYNTAX      INTEGER(1..26)
    MAX-ACCESS      not-accessible
    STATUS      current
    DESCRIPTION
        "The index of the GVRP conf table."
    ::= { es2126GvrpConfEntry 1 }

es2126GvrpConfJoinTime  OBJECT-TYPE
    SYNTAX      INTEGER(20..100)
    MAX-ACCESS      read-write
    STATUS      current
    DESCRIPTION
        "The join time of the GVRP entry.
         range: 20~100
         default 20 centisecond"
    ::= { es2126GvrpConfEntry 2 }

es2126GvrpConfLeaveTime OBJECT-TYPE
    SYNTAX      INTEGER(60..300)
    MAX-ACCESS      read-write
    STATUS      current
    DESCRIPTION
        "The leave time of the GVRP entry.
         range: 60~300
        default:60 centisecond"
    ::= { es2126GvrpConfEntry 3 }

es2126GvrpConfLeaveAllTime  OBJECT-TYPE
    SYNTAX      INTEGER(1000..5000)
    MAX-ACCESS      read-write
    STATUS      current
    DESCRIPTION
        "The leave all time of the GVRP entry.
         range: 1000~5000
         default: 1000 unit time"
    ::= { es2126GvrpConfEntry 4 }

es2126GvrpConfDefaultAppMode    OBJECT-TYPE
    SYNTAX      INTEGER(0|1)
    MAX-ACCESS      read-write
    STATUS      current
    DESCRIPTION
        "The default application mode of the GVRP entry.
         0 - Normal
         1 - Non-Participant
         default: Normal"
    ::= { es2126GvrpConfEntry 5 }

es2126GvrpConfDefaultRegMode    OBJECT-TYPE
    SYNTAX      INTEGER(0|1|2)
    MAX-ACCESS      read-write
    STATUS      current
    DESCRIPTION
        "The default registrar mode of the GVRP entry.
         0 - Normal
         1 - Fixed
         2 - Forbidden
         default: Normal"
    ::= { es2126GvrpConfEntry 6 }

es2126GvrpConfRestrictedMode    OBJECT-TYPE
    SYNTAX      INTEGER(0|1)
    MAX-ACCESS      read-write
    STATUS      current
    DESCRIPTION
        "The restricted mode of the GVRP entry.
         0 - Disable
         1 - Enable
         default: Disable"
    ::= { es2126GvrpConfEntry 7 }

es2126GvrpCounter               OBJECT IDENTIFIER ::= { es2126GVRPInfo 2 }

es2126GvrpCounterTable  OBJECT-TYPE
    SYNTAX      SEQUENCE OF ES2126GvrpCounterEntry
    MAX-ACCESS  not-accessible
    STATUS      current
    DESCRIPTION
        "This is a list of the GVRP counter table."
    ::= { es2126GvrpCounter 1 }

ES2126GvrpCounterEntry ::=
SEQUENCE {
    es2126GvrpCounterIndex              INTEGER,
    es2126GvrpCounterRxTotalGvrpPkts    Counter32,
    es2126GvrpCounterRxInvalidGvrpPkts  Counter32,
    es2126GvrpCounterRxLeaveAllMsg      Counter32,
    es2126GvrpCounterRxJoinEmptyMsg     Counter32,
    es2126GvrpCounterRxJoinInMsg        Counter32,
    es2126GvrpCounterRxLeaveEmptyMsg    Counter32,
    es2126GvrpCounterRxEmptyMsg         Counter32,
    es2126GvrpCounterTxTotalGvrpPkts    Counter32,
    es2126GvrpCounterTxLeaveAllMsg      Counter32,
    es2126GvrpCounterTxJoinEmptyMsg     Counter32,
    es2126GvrpCounterTxJoinInMsg        Counter32,
    es2126GvrpCounterTxLeaveEmptyMsg    Counter32,
    es2126GvrpCounterTxEmptyMsg         Counter32
}

es2126GvrpCounterEntry  OBJECT-TYPE
    SYNTAX      ES2126GvrpCounterEntry
    MAX-ACCESS      not-accessible
    STATUS      current
    DESCRIPTION
        "Entry(s) for the GVRP counter table."
    INDEX {es2126GvrpCounterIndex}
    ::= { es2126GvrpCounterTable 1 }

es2126GvrpCounterIndex  OBJECT-TYPE
    SYNTAX      INTEGER(1..26)
    MAX-ACCESS      not-accessible
    STATUS      current
    DESCRIPTION
        "The port index of the GVRP counter table."
    ::= { es2126GvrpCounterEntry 1 }

es2126GvrpCounterRxTotalGvrpPkts    OBJECT-TYPE
    SYNTAX      Counter32
    MAX-ACCESS      read-only
    STATUS      current
    DESCRIPTION
        "This is Rx Total GVRP packet counters."
    ::= { es2126GvrpCounterEntry 2 }

es2126GvrpCounterRxInvalidGvrpPkts  OBJECT-TYPE
    SYNTAX      Counter32
    MAX-ACCESS      read-only
    STATUS      current
    DESCRIPTION
        "This is Rx Invalid GVRP packet counters."
    ::= { es2126GvrpCounterEntry 3 }

es2126GvrpCounterRxLeaveAllMsg  OBJECT-TYPE
    SYNTAX      Counter32
    MAX-ACCESS      read-only
    STATUS      current
    DESCRIPTION
        "This is Rx LeaveAll message packet counters."
    ::= { es2126GvrpCounterEntry 4 }

es2126GvrpCounterRxJoinEmptyMsg OBJECT-TYPE
    SYNTAX      Counter32
    MAX-ACCESS      read-only
    STATUS      current
    DESCRIPTION
        "This is Rx JoinEmpty message packet counters."
    ::= { es2126GvrpCounterEntry 5 }

es2126GvrpCounterRxJoinInMsg    OBJECT-TYPE
    SYNTAX      Counter32
    MAX-ACCESS      read-only
    STATUS      current
    DESCRIPTION
        "This is Rx JoinIn message packet counters."
    ::= { es2126GvrpCounterEntry 6 }

es2126GvrpCounterRxLeaveEmptyMsg    OBJECT-TYPE
    SYNTAX      Counter32
    MAX-ACCESS      read-only
    STATUS      current
    DESCRIPTION
        "This is Rx LeaveEmpty message packet counters."
    ::= { es2126GvrpCounterEntry 7 }

es2126GvrpCounterRxEmptyMsg OBJECT-TYPE
    SYNTAX      Counter32
    MAX-ACCESS      read-only
    STATUS      current
    DESCRIPTION
        "This is Rx Empty message packet counters."
    ::= { es2126GvrpCounterEntry 8 }

es2126GvrpCounterTxTotalGvrpPkts    OBJECT-TYPE
    SYNTAX      Counter32
    MAX-ACCESS      read-only
    STATUS      current
    DESCRIPTION
        "This is Tx Total GVRP packet counters."
    ::= { es2126GvrpCounterEntry 9 }

es2126GvrpCounterTxLeaveAllMsg  OBJECT-TYPE
    SYNTAX      Counter32
    MAX-ACCESS      read-only
    STATUS      current
    DESCRIPTION
        "This is Tx LeaveAll message packet counters."
    ::= { es2126GvrpCounterEntry 10 }

es2126GvrpCounterTxJoinEmptyMsg OBJECT-TYPE
    SYNTAX      Counter32
    MAX-ACCESS      read-only
    STATUS      current
    DESCRIPTION
        "This is Tx JoinEmpty message packet counters."
    ::= { es2126GvrpCounterEntry 11 }

es2126GvrpCounterTxJoinInMsg    OBJECT-TYPE
    SYNTAX      Counter32
    MAX-ACCESS      read-only
    STATUS      current
    DESCRIPTION
        "This is Tx JoinIn message packet counters."
    ::= { es2126GvrpCounterEntry 12 }

es2126GvrpCounterTxLeaveEmptyMsg    OBJECT-TYPE
    SYNTAX      Counter32
    MAX-ACCESS      read-only
    STATUS      current
    DESCRIPTION
        "This is Tx LeaveEmpty message packet counters."
    ::= { es2126GvrpCounterEntry 13 }

es2126GvrpCounterTxEmptyMsg OBJECT-TYPE
    SYNTAX      Counter32
    MAX-ACCESS      read-only
    STATUS      current
    DESCRIPTION
        "This is Tx Empty message packet counters."
    ::= { es2126GvrpCounterEntry 14 }

es2126GvrpGroup             OBJECT IDENTIFIER ::= { es2126GVRPInfo 3 }

es2126GvrpGroupNumber   OBJECT-TYPE
    SYNTAX      INTEGER(0..4094)
    MAX-ACCESS      read-only
    STATUS      current
    DESCRIPTION
        "This is number of the GVRP group table entry."
    ::= { es2126GvrpGroup 1 }

es2126GvrpGroupTable    OBJECT-TYPE
    SYNTAX      SEQUENCE OF ES2126GvrpGroupEntry
    MAX-ACCESS  not-accessible
    STATUS      current
    DESCRIPTION
        "This is a list of the GVRP group table."
    ::= { es2126GvrpGroup 2 }

ES2126GvrpGroupEntry ::=
SEQUENCE {
    es2126GvrpGroupId            INTEGER,
    es2126GvrpGroupVid           INTEGER,
    es2126GvrpGroupMemberPort    DisplayString
}

es2126GvrpGroupEntry    OBJECT-TYPE
    SYNTAX      ES2126GvrpGroupEntry
    MAX-ACCESS      not-accessible
    STATUS      current
    DESCRIPTION
        "Entry(s) for the GVRP group table."
    INDEX {es2126GvrpGroupId}
    ::= { es2126GvrpGroupTable 1 }

es2126GvrpGroupId   OBJECT-TYPE
    SYNTAX      INTEGER(1..4094)
    MAX-ACCESS      read-only
    STATUS      current
    DESCRIPTION
        "The index of the GVRP group table."
    ::= { es2126GvrpGroupEntry 1 }

es2126GvrpGroupVid  OBJECT-TYPE
    SYNTAX      INTEGER(1..4094)
    MAX-ACCESS      read-only
    STATUS      current
    DESCRIPTION
        "This is vid of GVRP group."
    ::= { es2126GvrpGroupEntry 2 }

es2126GvrpGroupMemberPort   OBJECT-TYPE
    SYNTAX      DisplayString
    MAX-ACCESS      read-only
    STATUS      current
    DESCRIPTION
        "This is the member port of GVRP group."
    ::= { es2126GvrpGroupEntry 3 }

es2126Security              OBJECT IDENTIFIER ::= { es2126Produces 13 }

es2126IsolatedPortGroup OBJECT-TYPE
    SYNTAX      DisplayString
    MAX-ACCESS      read-write
    STATUS      current
    DESCRIPTION
        "This is isolated group.
         0: Disable"
    ::= { es2126Security 1 }

es2126Mirror            OBJECT IDENTIFIER ::= { es2126Security 2 }

es2126MirrorMode OBJECT-TYPE
    SYNTAX      INTEGER(0|1)
    MAX-ACCESS      read-write
    STATUS      current
    DESCRIPTION
        "This is mirror mode.
         0 - Disable
         1 - Enable
    "
    ::= { es2126Mirror 1 }

es2126MonitoringPort OBJECT-TYPE
    SYNTAX      INTEGER(1..26)
    MAX-ACCESS      read-write
    STATUS      current
    DESCRIPTION
        "This is monitoring port."
    ::= { es2126Mirror 2 }

es2126MonitoredIngressPort OBJECT-TYPE
    SYNTAX      DisplayString
    MAX-ACCESS      read-write
    STATUS      current
    DESCRIPTION
        "This is monitored ingress ports."
    ::= { es2126Mirror 3 }

es2126MonitoredEgressPort OBJECT-TYPE
    SYNTAX      DisplayString
    MAX-ACCESS      read-write
    STATUS      current
    DESCRIPTION
        "This is monitored egress ports."
    ::= { es2126Mirror 4 }

es2126VirtualStack        OBJECT IDENTIFIER ::= { es2126Produces 14 }

es2126VirtualStackState   OBJECT-TYPE
    SYNTAX      INTEGER(0|1)
    MAX-ACCESS  read-write
    STATUS      current
    DESCRIPTION
        "Set the Virtual Stack State.
         0 : disable,
         1 : enable
        "
    ::= { es2126VirtualStack 1 }

es2126VirtualStackRole   OBJECT-TYPE
    SYNTAX      INTEGER(0|1)
    MAX-ACCESS  read-write
    STATUS      current
    DESCRIPTION
        "Set the Virtual Stack Role.
         0 : slave,
         1 : master
        "
    ::= { es2126VirtualStack 2 }

es2126VirtualStackGroupID  OBJECT-TYPE
    SYNTAX      DisplayString
    MAX-ACCESS  read-write
    STATUS      current
    DESCRIPTION
        "Set the Virtual Stack Group ID."
    ::= { es2126VirtualStack 3 }

es2126ManagementSecurity            OBJECT IDENTIFIER ::= { es2126Produces 15 }

es2126ManagementSecurityNumber OBJECT-TYPE
    SYNTAX      INTEGER(0..64)
    MAX-ACCESS      read-only
    STATUS      current
    DESCRIPTION
        "This is number of the management security table entry."
    ::= { es2126ManagementSecurity 1 }

es2126ManagementSecurityEntryCreate OBJECT-TYPE
    SYNTAX      INTEGER(0..64)
    MAX-ACCESS      read-write
    STATUS      current
    DESCRIPTION
        "Creat a management security entry."
    ::= { es2126ManagementSecurity 2 }

es2126ManagementSecurityTable   OBJECT-TYPE
    SYNTAX      SEQUENCE OF ES2126ManagementSecurityEntry
    MAX-ACCESS  not-accessible
    STATUS      current
    DESCRIPTION
        "This is a list of the management security table."
    ::= { es2126ManagementSecurity 3 }

ES2126ManagementSecurityEntry ::=
SEQUENCE {
    es2126ManagementSecurityIndex          INTEGER,
    es2126ManagementSecurityName           DisplayString,
    es2126ManagementSecurityVid            INTEGER,
    es2126ManagementSecurityIpRange        DisplayString,
    es2126ManagementSecurityIncomigPort    DisplayString,
    es2126ManagementSecurityAccessType     DisplayString,
    es2126ManagementSecurityAction         INTEGER,
    es2126ManagementSecurityEntryAction    INTEGER
}

es2126ManagementSecurityEntry   OBJECT-TYPE
    SYNTAX      ES2126ManagementSecurityEntry
    MAX-ACCESS      not-accessible
    STATUS      current
    DESCRIPTION
        "Entry(s) for the management security table."
    INDEX {es2126ManagementSecurityIndex}
    ::= { es2126ManagementSecurityTable 1 }

es2126ManagementSecurityIndex   OBJECT-TYPE
    SYNTAX      INTEGER(1..64)
    MAX-ACCESS      not-accessible
    STATUS      current
    DESCRIPTION
        "The index of the management security table."
    ::= { es2126ManagementSecurityEntry 1 }

es2126ManagementSecurityName    OBJECT-TYPE
    SYNTAX      DisplayString
    MAX-ACCESS      read-write
    STATUS      current
    DESCRIPTION
        "The name of the management security entry."
    ::= { es2126ManagementSecurityEntry 2 }

es2126ManagementSecurityVid OBJECT-TYPE
    SYNTAX      INTEGER(0..4094)
    MAX-ACCESS      read-write
    STATUS      current
    DESCRIPTION
        "This is the vid of the management security entry.
         0: any VID."
    ::= { es2126ManagementSecurityEntry 3 }

es2126ManagementSecurityIpRange OBJECT-TYPE
    SYNTAX      DisplayString
    MAX-ACCESS      read-write
    STATUS      current
    DESCRIPTION
        "This is the IP range of the management security entry.
         0: any IP."
    ::= { es2126ManagementSecurityEntry 4 }

es2126ManagementSecurityIncomigPort OBJECT-TYPE
    SYNTAX      DisplayString
    MAX-ACCESS      read-write
    STATUS      current
    DESCRIPTION
        "This is the ports of the management security entry.
         0: any incoming port."
    ::= { es2126ManagementSecurityEntry 5 }

es2126ManagementSecurityAccessType  OBJECT-TYPE
    SYNTAX      DisplayString
    MAX-ACCESS      read-write
    STATUS      current
    DESCRIPTION
        "This is the access type of the management security entry.
         0: http, telnet, and SNMP."
    ::= { es2126ManagementSecurityEntry 6 }

es2126ManagementSecurityAction  OBJECT-TYPE
    SYNTAX      INTEGER(0|1)
    MAX-ACCESS      read-write
    STATUS      current
    DESCRIPTION
        "This is the action of the management security entry.
         0:deny
         1:accept"
    ::= { es2126ManagementSecurityEntry 7 }

es2126ManagementSecurityEntryAction OBJECT-TYPE
    SYNTAX      INTEGER(0..3)
    MAX-ACCESS      read-write
    STATUS      current
    DESCRIPTION
        "The action the management security entry."
    ::= { es2126ManagementSecurityEntry 8 }

es2126QoS               OBJECT IDENTIFIER ::= { es2126Produces 16 }

es2126QoSGlobalConfig               OBJECT IDENTIFIER ::= { es2126QoS 1 }

es2126QoSMode OBJECT-TYPE
    SYNTAX      INTEGER(0|1)
    MAX-ACCESS      read-write
    STATUS      current
    DESCRIPTION
        "The mode of QoS.
         0 - Disable
         1 - Enable
    "
    ::= { es2126QoSGlobalConfig 1 }

es2126QosPriorityControl1p OBJECT-TYPE
    SYNTAX      INTEGER(0|1)
    MAX-ACCESS      read-write
    STATUS      current
    DESCRIPTION
        "This is the priority control for 802.1p.
         0 - Disable
         1 - Enable
    "
    ::= { es2126QoSGlobalConfig 2 }

es2126QosPriorityControlTOS OBJECT-TYPE
    SYNTAX      INTEGER(0|1)
    MAX-ACCESS      read-write
    STATUS      current
    DESCRIPTION
        "This is the priority control for TOS.
         0 - Disable
         1 - Enable
    "
    ::= { es2126QoSGlobalConfig 3 }

es2126QosPriorityControlDSCP OBJECT-TYPE
    SYNTAX      INTEGER(0|1)
    MAX-ACCESS      read-write
    STATUS      current
    DESCRIPTION
        "This is the priority control for DSCP.
         0 - Disable
         1 - Enable
    "
    ::= { es2126QoSGlobalConfig 4 }

es2126QoSSchedulingMethod OBJECT-TYPE
    SYNTAX      INTEGER(0|1)
    MAX-ACCESS      read-write
    STATUS      current
    DESCRIPTION
        "This is the scheduling method.
         0 - WRR
         1 - Strict
    "
    ::= { es2126QoSGlobalConfig 5 }

es2126QoSWeightQ0 OBJECT-TYPE
    SYNTAX      INTEGER(1..55)
    MAX-ACCESS      read-write
    STATUS      current
    DESCRIPTION
        "This is the weigtht of Queue0."
    ::= { es2126QoSGlobalConfig 6 }

es2126QoSWeightQ1 OBJECT-TYPE
    SYNTAX      INTEGER(1..55)
    MAX-ACCESS      read-write
    STATUS      current
    DESCRIPTION
        "This is the weigtht of Queue1."
    ::= { es2126QoSGlobalConfig 7 }

es2126QoSWeightQ2 OBJECT-TYPE
    SYNTAX      INTEGER(1..55)
    MAX-ACCESS      read-write
    STATUS      current
    DESCRIPTION
        "This is the weigtht of Queue2."
    ::= { es2126QoSGlobalConfig 8 }

es2126QoSWeightQ3 OBJECT-TYPE
    SYNTAX      INTEGER(1..55)
    MAX-ACCESS      read-write
    STATUS      current
    DESCRIPTION
        "This is the weigtht of Queue3."
    ::= { es2126QoSGlobalConfig 9 }

es2126QoSVIPPort OBJECT-TYPE
    SYNTAX      DisplayString
    MAX-ACCESS      read-write
    STATUS      current
    DESCRIPTION
        "This is the VIP group for QoS."
    ::= { es2126QoS 2 }

es2126QoS1pPriority             OBJECT IDENTIFIER ::= { es2126QoS 3 }

es2126QoS1pPriorityTable    OBJECT-TYPE
    SYNTAX      SEQUENCE OF ES2126QoS1pPriorityEntry
    MAX-ACCESS  not-accessible
    STATUS      current
    DESCRIPTION
        "This is a list of the 802.1p."
    ::= { es2126QoS1pPriority 1 }

ES2126QoS1pPriorityEntry ::=
SEQUENCE {
    es2126QoS1pPriorityIndex    INTEGER,
    es2126QoS1pPriorityValue    INTEGER,
    es2126QoS1pPriorityQueue    INTEGER
}

es2126QoS1pPriorityEntry    OBJECT-TYPE
    SYNTAX      ES2126QoS1pPriorityEntry
    MAX-ACCESS      not-accessible
    STATUS      current
    DESCRIPTION
        "Entry(s) for the 802.1p priority table."
    INDEX {es2126QoS1pPriorityIndex}
    ::= { es2126QoS1pPriorityTable 1 }

es2126QoS1pPriorityIndex    OBJECT-TYPE
    SYNTAX      INTEGER(1..8)
    MAX-ACCESS      not-accessible
    STATUS      current
    DESCRIPTION
        "The index of the 802.1p priority table."
    ::= { es2126QoS1pPriorityEntry 1 }

es2126QoS1pPriorityValue    OBJECT-TYPE
    SYNTAX      INTEGER(0..7)
    MAX-ACCESS      read-only
    STATUS      current
    DESCRIPTION
        "The value of 802.1p priority entry."
    ::= { es2126QoS1pPriorityEntry 2 }

es2126QoS1pPriorityQueue    OBJECT-TYPE
    SYNTAX      INTEGER(0..3)
    MAX-ACCESS      read-write
    STATUS      current
    DESCRIPTION
        "The queue of 802.1p priority entry."
    ::= { es2126QoS1pPriorityEntry 3 }

es2126QoSDTypeTOSPriority               OBJECT IDENTIFIER ::= { es2126QoS 4 }

es2126QoSDTypeTOSPriorityTable  OBJECT-TYPE
    SYNTAX      SEQUENCE OF ES2126QoSDTypeTOSPriorityEntry
    MAX-ACCESS  not-accessible
    STATUS      current
    DESCRIPTION
        "This is a list of the TOS delay priority mapping entry."
    ::= { es2126QoSDTypeTOSPriority 1 }

ES2126QoSDTypeTOSPriorityEntry ::=
SEQUENCE {
    es2126QoSDTypeTOSPriorityIndex    INTEGER,
    es2126QoSDTypeTOSPriorityValue    INTEGER,
    es2126QoSDTypeTOSPriorityQueue    INTEGER
}

es2126QoSDTypeTOSPriorityEntry  OBJECT-TYPE
    SYNTAX      ES2126QoSDTypeTOSPriorityEntry
    MAX-ACCESS      not-accessible
    STATUS      current
    DESCRIPTION
        "Entry(s) for the ToS delay priority mapping entry."
    INDEX {es2126QoSDTypeTOSPriorityIndex}
    ::= { es2126QoSDTypeTOSPriorityTable 1 }

es2126QoSDTypeTOSPriorityIndex  OBJECT-TYPE
    SYNTAX      INTEGER(1..8)
    MAX-ACCESS      not-accessible
    STATUS      current
    DESCRIPTION
        "The index of the ToS delay priority mapping table."
    ::= { es2126QoSDTypeTOSPriorityEntry 1 }

es2126QoSDTypeTOSPriorityValue  OBJECT-TYPE
    SYNTAX      INTEGER(0..7)
    MAX-ACCESS      read-only
    STATUS      current
    DESCRIPTION
        "The value of ToS delay priority mapping entry."
    ::= { es2126QoSDTypeTOSPriorityEntry 2 }

es2126QoSDTypeTOSPriorityQueue  OBJECT-TYPE
    SYNTAX      INTEGER(0..3)
    MAX-ACCESS      read-write
    STATUS      current
    DESCRIPTION
        "The queue of ToS delay priority mapping entry."
    ::= { es2126QoSDTypeTOSPriorityEntry 3 }

es2126QoSTTypeTOSPriority               OBJECT IDENTIFIER ::= { es2126QoS 5 }

es2126QoSTTypeTOSPriorityTable  OBJECT-TYPE
    SYNTAX      SEQUENCE OF ES2126QoSTTypeTOSPriorityEntry
    MAX-ACCESS  not-accessible
    STATUS      current
    DESCRIPTION
        "This is a list of the ToS throughput priority mapping entry."
    ::= { es2126QoSTTypeTOSPriority 1 }

ES2126QoSTTypeTOSPriorityEntry ::=
SEQUENCE {
    es2126QoSTTypeTOSPriorityIndex    INTEGER,
    es2126QoSTTypeTOSPriorityValue    INTEGER,
    es2126QoSTTypeTOSPriorityQueue    INTEGER
}

es2126QoSTTypeTOSPriorityEntry  OBJECT-TYPE
    SYNTAX      ES2126QoSTTypeTOSPriorityEntry
    MAX-ACCESS      not-accessible
    STATUS      current
    DESCRIPTION
        "Entry(s) for the TOS Throughput mapping entry."
    INDEX {es2126QoSTTypeTOSPriorityIndex}
    ::= { es2126QoSTTypeTOSPriorityTable 1 }

es2126QoSTTypeTOSPriorityIndex  OBJECT-TYPE
    SYNTAX      INTEGER(1..8)
    MAX-ACCESS      not-accessible
    STATUS      current
    DESCRIPTION
        "The index of the TOS throughput priority mapping table."
    ::= { es2126QoSTTypeTOSPriorityEntry 1 }

es2126QoSTTypeTOSPriorityValue  OBJECT-TYPE
    SYNTAX      INTEGER(0..7)
    MAX-ACCESS      read-only
    STATUS      current
    DESCRIPTION
        "The value of TOS throughput priority mapping entry."
    ::= { es2126QoSTTypeTOSPriorityEntry 2 }

es2126QoSTTypeTOSPriorityQueue  OBJECT-TYPE
    SYNTAX      INTEGER(0..3)
    MAX-ACCESS      read-write
    STATUS      current
    DESCRIPTION
        "The queue of TOS throughput priority mapping entry."
    ::= { es2126QoSTTypeTOSPriorityEntry 3 }

es2126QoSRTypeTOSPriority               OBJECT IDENTIFIER ::= { es2126QoS 6 }

es2126QoSRTypeTOSPriorityTable  OBJECT-TYPE
    SYNTAX      SEQUENCE OF ES2126QoSRTypeTOSPriorityEntry
    MAX-ACCESS  not-accessible
    STATUS      current
    DESCRIPTION
        "This is a list of the ToS reliability priority mapping entry."
    ::= { es2126QoSRTypeTOSPriority 1 }

ES2126QoSRTypeTOSPriorityEntry ::=
SEQUENCE {
    es2126QoSRTypeTOSPriorityIndex    INTEGER,
    es2126QoSRTypeTOSPriorityValue    INTEGER,
    es2126QoSRTypeTOSPriorityQueue    INTEGER
}

es2126QoSRTypeTOSPriorityEntry  OBJECT-TYPE
    SYNTAX      ES2126QoSRTypeTOSPriorityEntry
    MAX-ACCESS      not-accessible
    STATUS      current
    DESCRIPTION
        "Entry(s) for the TOS reliability mapping entry."
    INDEX {es2126QoSRTypeTOSPriorityIndex}
    ::= { es2126QoSRTypeTOSPriorityTable 1 }

es2126QoSRTypeTOSPriorityIndex  OBJECT-TYPE
    SYNTAX      INTEGER(1..8)
    MAX-ACCESS      not-accessible
    STATUS      current
    DESCRIPTION
        "The index of the TOS reliability priority mapping table."
    ::= { es2126QoSRTypeTOSPriorityEntry 1 }

es2126QoSRTypeTOSPriorityValue  OBJECT-TYPE
    SYNTAX      INTEGER(0..7)
    MAX-ACCESS      read-only
    STATUS      current
    DESCRIPTION
        "The value of TOS reliability priority mapping entry."
    ::= { es2126QoSRTypeTOSPriorityEntry 2 }

es2126QoSRTypeTOSPriorityQueue  OBJECT-TYPE
    SYNTAX      INTEGER(0..3)
    MAX-ACCESS      read-write
    STATUS      current
    DESCRIPTION
        "The queue of TOS reliability priority mapping entry."
    ::= { es2126QoSRTypeTOSPriorityEntry 3 }

es2126QoSMTypeTOSPriority               OBJECT IDENTIFIER ::= { es2126QoS 7 }

es2126QoSMTypeTOSPriorityTable  OBJECT-TYPE
    SYNTAX      SEQUENCE OF ES2126QoSMTypeTOSPriorityEntry
    MAX-ACCESS  not-accessible
    STATUS      current
    DESCRIPTION
        "This is a list of the ToS monetary cost priority mapping entry."
    ::= { es2126QoSMTypeTOSPriority 1 }

ES2126QoSMTypeTOSPriorityEntry ::=
SEQUENCE {
    es2126QoSMTypeTOSPriorityIndex    INTEGER,
    es2126QoSMTypeTOSPriorityValue    INTEGER,
    es2126QoSMTypeTOSPriorityQueue    INTEGER
}

es2126QoSMTypeTOSPriorityEntry  OBJECT-TYPE
    SYNTAX      ES2126QoSMTypeTOSPriorityEntry
    MAX-ACCESS      not-accessible
    STATUS      current
    DESCRIPTION
        "Entry(s) for the TOS monetary cost mapping entry."
    INDEX {es2126QoSMTypeTOSPriorityIndex}
    ::= { es2126QoSMTypeTOSPriorityTable 1 }

es2126QoSMTypeTOSPriorityIndex  OBJECT-TYPE
    SYNTAX      INTEGER(1..8)
    MAX-ACCESS      not-accessible
    STATUS      current
    DESCRIPTION
        "The index of the TOS monetary cost priority mapping table."
    ::= { es2126QoSMTypeTOSPriorityEntry 1 }

es2126QoSMTypeTOSPriorityValue  OBJECT-TYPE
    SYNTAX      INTEGER(0..7)
    MAX-ACCESS      read-only
    STATUS      current
    DESCRIPTION
        "The value of TOS monetary cost priority mapping entry."
    ::= { es2126QoSMTypeTOSPriorityEntry 2 }

es2126QoSMTypeTOSPriorityQueue  OBJECT-TYPE
    SYNTAX      INTEGER(0..3)
    MAX-ACCESS      read-write
    STATUS      current
    DESCRIPTION
        "The queue of TOS monetary cost priority mapping entry."
    ::= { es2126QoSMTypeTOSPriorityEntry 3 }

es2126QoSDSCPPriority               OBJECT IDENTIFIER ::= { es2126QoS 8 }

es2126QoSDSCPPriorityTable  OBJECT-TYPE
    SYNTAX      SEQUENCE OF ES2126QoSDSCPPriorityEntry
    MAX-ACCESS  not-accessible
    STATUS      current
    DESCRIPTION
        "This is a list of the DSCP priority entry."
    ::= { es2126QoSDSCPPriority 1 }

ES2126QoSDSCPPriorityEntry ::=
SEQUENCE {
    es2126QoSDSCPPriorityIndex    INTEGER,
    es2126QoSDSCPPriorityValue    INTEGER,
    es2126QoSDSCPPriorityQueue    INTEGER
}

es2126QoSDSCPPriorityEntry  OBJECT-TYPE
    SYNTAX      ES2126QoSDSCPPriorityEntry
    MAX-ACCESS      not-accessible
    STATUS      current
    DESCRIPTION
        "Entry(s) for the DSCP priority mapping entry."
    INDEX {es2126QoSDSCPPriorityIndex}
    ::= { es2126QoSDSCPPriorityTable 1 }

es2126QoSDSCPPriorityIndex  OBJECT-TYPE
    SYNTAX      INTEGER(1..64)
    MAX-ACCESS      not-accessible
    STATUS      current
    DESCRIPTION
        "The index of the DSCP priority priority mapping table."
    ::= { es2126QoSDSCPPriorityEntry 1 }

es2126QoSDSCPPriorityValue  OBJECT-TYPE
    SYNTAX      INTEGER(0..63)
    MAX-ACCESS      read-only
    STATUS      current
    DESCRIPTION
        "The value of DSCP priority priority mapping entry."
    ::= { es2126QoSDSCPPriorityEntry 2 }

es2126QoSDSCPPriorityQueue  OBJECT-TYPE
    SYNTAX      INTEGER(0..3)
    MAX-ACCESS      read-write
    STATUS      current
    DESCRIPTION
        "The queue of DSCP priority priority mapping entry."
    ::= { es2126QoSDSCPPriorityEntry 3 }

es2126Vlan      OBJECT IDENTIFIER ::= { es2126Produces 17 }

es2126VlanModeConfig      OBJECT IDENTIFIER ::= { es2126Vlan 1 }

es2126VlanMode  OBJECT-TYPE
    SYNTAX      INTEGER(0..2)
    MAX-ACCESS  read-write
    STATUS      current
    DESCRIPTION
        "0:Tag-based, 1:Port-based, 2:Metro mode"
    ::= { es2126VlanModeConfig 1 }

es2126SymmetricVlan  OBJECT-TYPE
    SYNTAX      INTEGER(0|1)
    MAX-ACCESS  read-write
    STATUS      current
    DESCRIPTION
        "Symmetric VLAN: for tag-based
        0:disable, 1:enable"
    ::= { es2126VlanModeConfig 2 }

es2126VlanSVL  OBJECT-TYPE
    SYNTAX      INTEGER(0|1)
    MAX-ACCESS  read-write
    STATUS      current
    DESCRIPTION
        "SVL: : for tag-based
        0:disable, 1:enable"
    ::= { es2126VlanModeConfig 3 }

es2126DoubleTag  OBJECT-TYPE
    SYNTAX      INTEGER(0|1)
    MAX-ACCESS  read-write
    STATUS      current
    DESCRIPTION
        "Double Tag: for tag-based
        0:disable, 1:enable"
    ::= { es2126VlanModeConfig 4 }

es2126UpLinkPort  OBJECT-TYPE
    SYNTAX      INTEGER(0..2)
    MAX-ACCESS  read-write
    STATUS      current
    DESCRIPTION
        "Up link Port: for Metro mode
        0:Port 25, 1:Port 26, 2:Port 25 & 26"
    ::= { es2126VlanModeConfig 5 }

es2126TagBasedVlanGroup      OBJECT IDENTIFIER ::= { es2126Vlan 2 }

es2126TagBasedVlanNumbers  OBJECT-TYPE
    SYNTAX      INTEGER(1..4094)
    MAX-ACCESS  read-only
    STATUS      current
    DESCRIPTION
        "Total numbers for tag-based vlan."
    ::= { es2126TagBasedVlanGroup 1 }

es2126TagBasedCreateStatus  OBJECT-TYPE
    SYNTAX      INTEGER(0..4094)
    MAX-ACCESS  read-write
    STATUS      current
    DESCRIPTION
        "Creat a temp vlan in tag-based vlan table.
         0 : none,
         1~4094 : creat with this vid.
        "
    ::= { es2126TagBasedVlanGroup 2 }

es2126TagBasedVlanTable  OBJECT-TYPE
    SYNTAX      SEQUENCE OF ES2126TagBasedVlanEntry
    MAX-ACCESS  not-accessible
    STATUS      current
    DESCRIPTION
        " "
    ::= { es2126TagBasedVlanGroup 3 }

ES2126TagBasedVlanEntry ::=
SEQUENCE {
    es2126TagBasedVlanVid               INTEGER,
    es2126TagBasedVlanName                  DisplayString,
    es2126TagBasedVlanMember                DisplayString,
    es2126TagBasedVlanUntag                 DisplayString,
    es2126TagBasedVlanRowStatus             INTEGER
}

es2126TagBasedVlanEntry OBJECT-TYPE
    SYNTAX      ES2126TagBasedVlanEntry
    MAX-ACCESS  not-accessible
    STATUS      current
    DESCRIPTION
        "Entry(s) for tag-based vlan table."
    INDEX {es2126TagBasedVlanVid}
    ::= { es2126TagBasedVlanTable 1 }

es2126TagBasedVlanVid  OBJECT-TYPE
    SYNTAX      INTEGER(1..4094)
    MAX-ACCESS  not-accessible
    STATUS      current
    DESCRIPTION
        "The vid of vlan."
    ::= { es2126TagBasedVlanEntry 1 }

es2126TagBasedVlanName  OBJECT-TYPE
    SYNTAX      DisplayString
    MAX-ACCESS  read-write
    STATUS      current
    DESCRIPTION
        "The name of vlan."
    ::= { es2126TagBasedVlanEntry 2 }

es2126TagBasedVlanMember  OBJECT-TYPE
    SYNTAX      DisplayString
    MAX-ACCESS  read-write
    STATUS      current
    DESCRIPTION
        "The member of vlan."
    ::= { es2126TagBasedVlanEntry 3 }

es2126TagBasedVlanUntag  OBJECT-TYPE
    SYNTAX      DisplayString
    MAX-ACCESS  read-write
    STATUS      current
    DESCRIPTION
        "The untag port of vlan."
    ::= { es2126TagBasedVlanEntry 4 }

es2126TagBasedVlanRowStatus  OBJECT-TYPE
    SYNTAX      INTEGER(1..3)
    MAX-ACCESS  read-write
    STATUS      current
    DESCRIPTION
        "The row status of vlan.
         1 : active,
         2 : not-inService,
         3 : delete
        "
    ::= { es2126TagBasedVlanEntry 5 }

es2126VlanPvid      OBJECT IDENTIFIER ::= { es2126Vlan 3 }

es2126VlanPvidTable  OBJECT-TYPE
    SYNTAX      SEQUENCE OF ES2126VlanPvidEntry
    MAX-ACCESS  not-accessible
    STATUS      current
    DESCRIPTION
        " "
    ::= { es2126VlanPvid 1 }

ES2126VlanPvidEntry ::=
SEQUENCE {
    es2126VlanPvidPort              INTEGER,
    es2126VlanPvidValue             INTEGER,
    es2126VlanPvidDefaultPriority           INTEGER,
    es2126VlanPvidDropUntag             INTEGER
}

es2126VlanPvidEntry OBJECT-TYPE
    SYNTAX      ES2126VlanPvidEntry
    MAX-ACCESS  not-accessible
    STATUS      current
    DESCRIPTION
        "Entry(s) for Vlan Pvid."
    INDEX {es2126VlanPvidPort}
    ::= { es2126VlanPvidTable 1 }

es2126VlanPvidPort  OBJECT-TYPE
    SYNTAX      INTEGER(1..26)
    MAX-ACCESS  not-accessible
    STATUS      current
    DESCRIPTION
        "The port number of pvid entry."
    ::= { es2126VlanPvidEntry 1 }

es2126VlanPvidValue  OBJECT-TYPE
    SYNTAX      INTEGER(1..4094)
    MAX-ACCESS  read-write
    STATUS      current
    DESCRIPTION
        "The pvid value of port."
    ::= { es2126VlanPvidEntry 2 }

es2126VlanPvidDefaultPriority  OBJECT-TYPE
    SYNTAX      INTEGER(0..7)
    MAX-ACCESS  read-write
    STATUS      current
    DESCRIPTION
        "The default priority of port ."
    ::= { es2126VlanPvidEntry 3 }

es2126VlanPvidDropUntag  OBJECT-TYPE
    SYNTAX      INTEGER(0..7)
    MAX-ACCESS  read-write
    STATUS      current
    DESCRIPTION
        "The drop untag of port ."
    ::= { es2126VlanPvidEntry 4 }

es2126PortBasedVlanGroup      OBJECT IDENTIFIER ::= { es2126Vlan 4 }

es2126PortBasedVlanNumbers  OBJECT-TYPE
    SYNTAX      INTEGER(1..26)
    MAX-ACCESS  read-only
    STATUS      current
    DESCRIPTION
        "Total numbers for tag-based vlan."
    ::= { es2126PortBasedVlanGroup 1 }

es2126PortBasedCreateStatus  OBJECT-TYPE
    SYNTAX      INTEGER(0|1)
    MAX-ACCESS  read-write
    STATUS      current
    DESCRIPTION
        "Creat a temp vlan in port-based vlan table.
         0 : none,
         1 : creat a new port-based vlan.
        "
    ::= { es2126PortBasedVlanGroup 2 }

es2126PortBasedVlanTable  OBJECT-TYPE
    SYNTAX      SEQUENCE OF ES2126PortBasedVlanEntry
    MAX-ACCESS  not-accessible
    STATUS      current
    DESCRIPTION
        " "
    ::= { es2126PortBasedVlanGroup 3 }

ES2126PortBasedVlanEntry ::=
SEQUENCE {
    es2126PortBasedVlanIndex                INTEGER,
    es2126PortBasedVlanName                 DisplayString,
    es2126PortBasedVlanMember               DisplayString,
    es2126PortBasedVlanRowStatus            INTEGER
}

es2126PortBasedVlanEntry OBJECT-TYPE
    SYNTAX      ES2126PortBasedVlanEntry
    MAX-ACCESS  not-accessible
    STATUS      current
    DESCRIPTION
        "Entry(s) for port-based vlan table."
    INDEX {es2126PortBasedVlanIndex}
    ::= { es2126PortBasedVlanTable 1 }

es2126PortBasedVlanIndex  OBJECT-TYPE
    SYNTAX      INTEGER(1..26)
    MAX-ACCESS  not-accessible
    STATUS      current
    DESCRIPTION
        "The index of vlan."
    ::= { es2126PortBasedVlanEntry 1 }

es2126PortBasedVlanName  OBJECT-TYPE
    SYNTAX      DisplayString
    MAX-ACCESS  read-write
    STATUS      current
    DESCRIPTION
        "The name of vlan."
    ::= { es2126PortBasedVlanEntry 2 }

es2126PortBasedVlanMember  OBJECT-TYPE
    SYNTAX      DisplayString
    MAX-ACCESS  read-write
    STATUS      current
    DESCRIPTION
        "The member of vlan."
    ::= { es2126PortBasedVlanEntry 3 }

es2126PortBasedVlanRowStatus  OBJECT-TYPE
    SYNTAX      INTEGER(1..3)
    MAX-ACCESS  read-write
    STATUS      current
    DESCRIPTION
        "The row status of vlan.
         1 : active,
         2 : not-inService,
         3 : delete
        "
    ::= { es2126PortBasedVlanEntry 4 }

es2126ManagementVlan      OBJECT IDENTIFIER ::= { es2126Vlan 5 }

es2126ManagementVlanState  OBJECT-TYPE
    SYNTAX      INTEGER(0|1)
    MAX-ACCESS  read-write
    STATUS      current
    DESCRIPTION
        "The stat of management vlan.
         0 : Disable,
         1 : Enable.
        "
    ::= { es2126ManagementVlan 1 }

es2126ManagementVlanVid  OBJECT-TYPE
    SYNTAX      INTEGER(1..4094)
    MAX-ACCESS  read-write
    STATUS      current
    DESCRIPTION
        "The vid value of management vlan."
    ::= { es2126ManagementVlan 2 }

es2126Dot1X        OBJECT IDENTIFIER ::= { es2126Produces 18 }

es2126Dot1XStateSetting      OBJECT IDENTIFIER ::= { es2126Dot1X 1 }

es2126RadiusServer OBJECT-TYPE
    SYNTAX         IpAddress
    MAX-ACCESS     read-write
    STATUS         current
    DESCRIPTION
        "Set radius server ip"
    ::= { es2126Dot1XStateSetting 1 }

es2126Dot1XPort OBJECT-TYPE
    SYNTAX         INTEGER(1..65535)
    MAX-ACCESS     read-write
    STATUS         current
    DESCRIPTION
        "Set 802.1X port number"
    ::= { es2126Dot1XStateSetting 2 }

es2126SecretKey  OBJECT-TYPE
    SYNTAX         DisplayString
    MAX-ACCESS     read-write
    STATUS         current
    DESCRIPTION
        "Set 802.1X secret key"
    ::= { es2126Dot1XStateSetting 3 }

es2126AccountingService  OBJECT-TYPE
    SYNTAX         INTEGER(0|1)
    MAX-ACCESS     read-write
    STATUS         current
    DESCRIPTION
        "Set 802.1X accounting service
         0 : disable
         1 : enable
        "
    ::= { es2126Dot1XStateSetting 4 }

es2126AccountingServer  OBJECT-TYPE
    SYNTAX         IpAddress
    MAX-ACCESS     read-write
    STATUS         current
    DESCRIPTION
        "Set 802.1X accounting server"
    ::= { es2126Dot1XStateSetting 5 }

es2126AccountingPort  OBJECT-TYPE
    SYNTAX         INTEGER(1..65535)
    MAX-ACCESS     read-write
    STATUS         current
    DESCRIPTION
        "Set 802.1X accounting port number"
    ::= { es2126Dot1XStateSetting 6 }

es2126Dot1XPortSecurityManagement      OBJECT IDENTIFIER ::= { es2126Dot1X 2 }

es2126Dot1XPortSecurityTable  OBJECT-TYPE
    SYNTAX      SEQUENCE OF ES2126Dot1XPortSecurityEntry
    MAX-ACCESS  not-accessible
    STATUS      current
    DESCRIPTION
        "This is a list of the 802.1x port security entry."
    ::= { es2126Dot1XPortSecurityManagement 1 }

ES2126Dot1XPortSecurityEntry ::=
SEQUENCE {
    es2126Dot1XPortSecurityPortIndex                INTEGER,
    es2126Dot1XPortSecurityMode                     INTEGER,
    es2126Dot1XPortSecurityPortControl              INTEGER,
    es2126Dot1XPortSecurityReAuthMax                INTEGER,
    es2126Dot1XPortSecurityTxPeriod                 INTEGER,
    es2126Dot1XPortSecurityQuietPeriod              INTEGER,
    es2126Dot1XPortSecurityReAuthEnabled            INTEGER,
    es2126Dot1XPortSecurityReAuthPeriod             INTEGER,
    es2126Dot1XPortSecurityMaxRequest               INTEGER,
    es2126Dot1XPortSecuritySuppTimeout              INTEGER,
    es2126Dot1XPortSecurityServerTimeout            INTEGER,
    es2126Dot1XPortSecurityStatus                   DisplayString
}

es2126Dot1XPortSecurityEntry OBJECT-TYPE
    SYNTAX      ES2126Dot1XPortSecurityEntry
    MAX-ACCESS  not-accessible
    STATUS      current
    DESCRIPTION
        "Entry(s) for 802.1x port security management table."
    INDEX {es2126Dot1XPortSecurityPortIndex}
    ::= { es2126Dot1XPortSecurityTable 1 }

es2126Dot1XPortSecurityPortIndex  OBJECT-TYPE
    SYNTAX      INTEGER(1..26)
    MAX-ACCESS  not-accessible
    STATUS      current
    DESCRIPTION
        "The port index of 802.1x port security."
    ::= { es2126Dot1XPortSecurityEntry 1 }

es2126Dot1XPortSecurityMode  OBJECT-TYPE
    SYNTAX      INTEGER(0..2)
    MAX-ACCESS  read-write
    STATUS      current
    DESCRIPTION
        "The mode of 802.1x port security.
         0 : Disable,
         1 : Normal,
         2 : Advanced 802.1X (Dual port no support)
        "
    ::= { es2126Dot1XPortSecurityEntry 2 }

es2126Dot1XPortSecurityPortControl  OBJECT-TYPE
    SYNTAX      INTEGER(0..2)
    MAX-ACCESS  read-write
    STATUS      current
    DESCRIPTION
        "The port control of 802.1x port security.
           0 : ForceUnauthorized,
           1 : ForceAuthorized,
           2 : Auto
        "
    ::= { es2126Dot1XPortSecurityEntry 3 }

es2126Dot1XPortSecurityReAuthMax  OBJECT-TYPE
    SYNTAX      INTEGER(1..10)
    MAX-ACCESS  read-write
    STATUS      current
    DESCRIPTION
        "The reAuthMax(1~10) of 802.1x port security."
    ::= { es2126Dot1XPortSecurityEntry 4 }

es2126Dot1XPortSecurityTxPeriod  OBJECT-TYPE
    SYNTAX      INTEGER(1..65535)
    MAX-ACCESS  read-write
    STATUS      current
    DESCRIPTION
        "The txPeriod(1~65535) of 802.1x port security."
    ::= { es2126Dot1XPortSecurityEntry 5 }

es2126Dot1XPortSecurityQuietPeriod  OBJECT-TYPE
    SYNTAX      INTEGER(0..65535)
    MAX-ACCESS  read-write
    STATUS      current
    DESCRIPTION
        "The quiet period(0~65535) of 802.1x port security."
    ::= { es2126Dot1XPortSecurityEntry 6 }

es2126Dot1XPortSecurityReAuthEnabled  OBJECT-TYPE
    SYNTAX      INTEGER(0|1)
    MAX-ACCESS  read-write
    STATUS      current
    DESCRIPTION
        "The reAuthEnabled of 802.1x port security.
         0 : off,
         1 : on.
        "
    ::= { es2126Dot1XPortSecurityEntry 7 }

es2126Dot1XPortSecurityReAuthPeriod  OBJECT-TYPE
    SYNTAX      INTEGER(1..65535)
    MAX-ACCESS  read-write
    STATUS      current
    DESCRIPTION
        "The reAuthPeriod(1~65535) of 802.1x port security."
    ::= { es2126Dot1XPortSecurityEntry 8 }

es2126Dot1XPortSecurityMaxRequest  OBJECT-TYPE
    SYNTAX      INTEGER(1..10)
    MAX-ACCESS  read-write
    STATUS      current
    DESCRIPTION
        "The max.request(1~10) of 802.1x port security."
    ::= { es2126Dot1XPortSecurityEntry 9 }

es2126Dot1XPortSecuritySuppTimeout  OBJECT-TYPE
    SYNTAX      INTEGER(1..65535)
    MAX-ACCESS  read-write
    STATUS      current
    DESCRIPTION
        "The suppTimeout(1~65535) of 802.1x port security."
    ::= { es2126Dot1XPortSecurityEntry 10 }

es2126Dot1XPortSecurityServerTimeout  OBJECT-TYPE
    SYNTAX      INTEGER(1..65535)
    MAX-ACCESS  read-write
    STATUS      current
    DESCRIPTION
        "The server timeout(1~65535) of 802.1x port security."
    ::= { es2126Dot1XPortSecurityEntry 11 }

es2126Dot1XPortSecurityStatus  OBJECT-TYPE
    SYNTAX      DisplayString
    MAX-ACCESS  read-only
    STATUS      current
    DESCRIPTION
        "The status of 802.1x port security."
    ::= { es2126Dot1XPortSecurityEntry 12 }

es2126TrunkInfo       OBJECT IDENTIFIER ::= { es2126Produces 19 }

es2126TrunkPort      OBJECT IDENTIFIER ::= { es2126TrunkInfo 1 }

es2126TrunkPortTable  OBJECT-TYPE
    SYNTAX      SEQUENCE OF ES2126TrunkPortEntry
    MAX-ACCESS  not-accessible
    STATUS      current
    DESCRIPTION
        " "
    ::= { es2126TrunkPort 1 }

ES2126TrunkPortEntry ::=
SEQUENCE {
    es2126TrunkPortIndex                INTEGER,
    es2126TrunkPortMethod                   INTEGER,
    es2126TrunkPortGroup                INTEGER,
    es2126TrunkPortActiveLacp               INTEGER,
    es2126TrunkPortAggtr                INTEGER,
    es2126TrunkPortStatus               INTEGER,
    es2126TrunkPortCurrentMode              INTEGER
}

es2126TrunkPortEntry OBJECT-TYPE
    SYNTAX      ES2126TrunkPortEntry
    MAX-ACCESS  not-accessible
    STATUS      current
    DESCRIPTION
        "Entry(s) for trunk table."
    INDEX {es2126TrunkPortIndex}
    ::= { es2126TrunkPortTable 1 }

es2126TrunkPortIndex  OBJECT-TYPE
    SYNTAX      INTEGER(1..26)
    MAX-ACCESS  not-accessible
    STATUS      current
    DESCRIPTION
        "The port index of trunk table."
    ::= { es2126TrunkPortEntry 1 }

es2126TrunkPortMethod  OBJECT-TYPE
    SYNTAX      INTEGER(0..2)
    MAX-ACCESS  read-write
    STATUS      current
    DESCRIPTION
        "The method of trunk port.
     0 : None,
     1 : LACP,
     2 : Static.
        "
    ::= { es2126TrunkPortEntry 2 }

es2126TrunkPortGroup  OBJECT-TYPE
    SYNTAX      INTEGER(0..3)
    MAX-ACCESS  read-write
    STATUS      current
    DESCRIPTION
        "The group(0~3) of trunk port."
    ::= { es2126TrunkPortEntry 3 }

es2126TrunkPortActiveLacp  OBJECT-TYPE
    SYNTAX      INTEGER(0|1)
    MAX-ACCESS  read-write
    STATUS      current
    DESCRIPTION
        "The active lacp mode of trunk port.
     0 : Passive,
     1 : Active.
        "
    ::= { es2126TrunkPortEntry 4 }

es2126TrunkPortAggtr  OBJECT-TYPE
    SYNTAX      INTEGER(1..26)
    MAX-ACCESS  read-only
    STATUS      current
    DESCRIPTION
        "The Aggtr of trunk port."
    ::= { es2126TrunkPortEntry 5 }

es2126TrunkPortStatus  OBJECT-TYPE
    SYNTAX      INTEGER(0|1)
    MAX-ACCESS  read-only
    STATUS      current
    DESCRIPTION
        "The status of trunk port.
         0 : None,
         1 : Ready.
        "
    ::= { es2126TrunkPortEntry 6 }

es2126TrunkPortCurrentMode  OBJECT-TYPE
    SYNTAX      INTEGER(0..2)
    MAX-ACCESS  read-write
    STATUS      current
    DESCRIPTION
        "The current mode of trunk port entry.
     0 : Active mode,
     1 : Edit mode,
     2 : Do edit.
        "
    ::= { es2126TrunkPortEntry 7 }

es2126AggregatorView      OBJECT IDENTIFIER ::= { es2126TrunkInfo 2 }

es2126AggregatorViewTable  OBJECT-TYPE
    SYNTAX      SEQUENCE OF ES2126AggregatorViewEntry
    MAX-ACCESS  not-accessible
    STATUS      current
    DESCRIPTION
        " "
    ::= { es2126AggregatorView 1 }

ES2126AggregatorViewEntry ::=
SEQUENCE {
    es2126AggregatorViewIndex               INTEGER,
    es2126AggregatorViewMethod              INTEGER,
    es2126AggregatorViewMemberPorts             DisplayString,
    es2126AggregatorViewReadyPorts          DisplayString
}

es2126AggregatorViewEntry OBJECT-TYPE
    SYNTAX      ES2126AggregatorViewEntry
    MAX-ACCESS  not-accessible
    STATUS      current
    DESCRIPTION
        "Entry(s) for aggregator view table."
    INDEX {es2126AggregatorViewIndex}
    ::= { es2126AggregatorViewTable 1 }

es2126AggregatorViewIndex  OBJECT-TYPE
    SYNTAX      INTEGER(1..26)
    MAX-ACCESS  not-accessible
    STATUS      current
    DESCRIPTION
        "The port index of aggregator view table."
    ::= { es2126AggregatorViewEntry 1 }

es2126AggregatorViewMethod  OBJECT-TYPE
    SYNTAX      INTEGER(0..2)
    MAX-ACCESS  read-only
    STATUS      current
    DESCRIPTION
        "The method of aggregator view table.
         0 : None,
     1 : LACP,
     2 : Static.
        "
    ::= { es2126AggregatorViewEntry 2 }

es2126AggregatorViewMemberPorts  OBJECT-TYPE
    SYNTAX      DisplayString
    MAX-ACCESS  read-only
    STATUS      current
    DESCRIPTION
        "The member ports of aggregator view table."
    ::= { es2126AggregatorViewEntry 3 }

es2126AggregatorViewReadyPorts  OBJECT-TYPE
    SYNTAX      DisplayString
    MAX-ACCESS  read-only
    STATUS      current
    DESCRIPTION
        "The ready ports of aggregator view table."
    ::= { es2126AggregatorViewEntry 4 }

es2126LacpSystemConfiguration     OBJECT IDENTIFIER ::= { es2126TrunkInfo 3 }

es2126LacpSystemPriority  OBJECT-TYPE
    SYNTAX      INTEGER(1..65535)
    MAX-ACCESS  read-write
    STATUS      current
    DESCRIPTION
        "The priority of LACP system."
    ::= { es2126LacpSystemConfiguration 1 }

es2126LacpSystemHashMethod  OBJECT-TYPE
    SYNTAX      INTEGER(0..2)
    MAX-ACCESS  read-write
    STATUS      current
    DESCRIPTION
        "The hash method of LACP system.
         0 : DA and SA
         1 : SA
         2 : DA
        "
    ::= { es2126LacpSystemConfiguration 2 }

es2126TrapEntry        OBJECT IDENTIFIER ::= { es2126Produces 20 }

es2126ModuleInserted NOTIFICATION-TYPE
    OBJECTS { ifIndex }
    STATUS    current
    DESCRIPTION
        "Send the trap when a module is inserted to the system. The OID value means
         the port number."
    ::= { es2126TrapEntry 1 }

es2126ModuleRemoved NOTIFICATION-TYPE
    OBJECTS { ifIndex }
    STATUS    current
    DESCRIPTION
        "Send the trap when a module is removed from the system. The OID value means
         the port number."
    ::= { es2126TrapEntry 2 }

es2126DualMediaSwapped NOTIFICATION-TYPE
    OBJECTS { ifIndex }
    STATUS    current
    DESCRIPTION
        "Send the trap when the dual media port changed. The OID value means the port number."
    ::= { es2126TrapEntry 3 }

es2126LoopDetected NOTIFICATION-TYPE
    OBJECTS { ifIndex }
    STATUS    current
    DESCRIPTION
        "Send the trap when loop condition has been detected. The OID value means the port number."
    ::= { es2126TrapEntry 4 }

es2126StpStateDisabled NOTIFICATION-TYPE
    STATUS      current
    DESCRIPTION
       "Send the trap when the operational state of STP is from enabled to disabled. "
    ::= { es2126TrapEntry 100 }

es2126StpStateEnabled NOTIFICATION-TYPE
    STATUS      current
    DESCRIPTION
       "Send the trap when the operational state of STP is from disabled to enabled. "
    ::= { es2126TrapEntry 101 }

es2126StpTopologyChanged NOTIFICATION-TYPE
    OBJECTS { ifIndex }
    STATUS      current
    DESCRIPTION
       "Send the trap when RSTP determines a port should enter the FORWARDING state
        (a topology change occurs). The OID value is the ifIndex of the port that
        produces the topology change."
    ::= { es2126TrapEntry 102 }

es2126RmonRisingAlarm NOTIFICATION-TYPE
    STATUS      current
    DESCRIPTION
       "Send the trap when an RMON rising alarm happened. The OID value is the value
        of another OID variable sampled by the RMON Alarm Group that exceeds its
        own RisingThreshold "
    ::= { es2126TrapEntry 110 }

es2126RmonFallingAlarm NOTIFICATION-TYPE
    STATUS      current
    DESCRIPTION
           "Send the trap when an RMON falling alarm happened. The OID value is the value
        of another OID variable sampled by the RMON Alarm Group that is smaller than its
        own FallingThreshold "
    ::= { es2126TrapEntry 111 }

es2126LacpStateDisabled NOTIFICATION-TYPE
    OBJECTS {ifIndex, groupId}
    STATUS      current
    DESCRIPTION
       "Send the trap when the operational state of LACP is from enabled to disabled.
        The OID value means the disabled Group ID."
    ::= { es2126TrapEntry 120 }

es2126LacpStateEnabled NOTIFICATION-TYPE
    OBJECTS {ifIndex, groupId}
    STATUS      current
    DESCRIPTION
       "Send the trap when the operational state of LACP is from disabled to enabled.
        The OID value means the disabled Group ID."
    ::= { es2126TrapEntry 121 }

es2126LacpPortAdded NOTIFICATION-TYPE
    OBJECTS   { ifIndex, actorkey, partnerkey }
    STATUS      current
    DESCRIPTION
       "Send the trap when the state of port is in 'trunk ready'."
    ::= { es2126TrapEntry 123 }

es2126LacpPortTrunkFailure NOTIFICATION-TYPE
    OBJECTS   { ifIndex, actorkey, partnerkey}
    STATUS      current
    DESCRIPTION
       "Send the trap when one port is not able to be aggregated
        due to duplex-mode of the port. "
    ::= { es2126TrapEntry 124 }

es2126GvrpStateDisabled NOTIFICATION-TYPE
    STATUS      current
    DESCRIPTION
       "Send the trap when the operational state of GVRP is from enabled to disabled. "
    ::= { es2126TrapEntry 140 }

es2126GvrpStateEnabled NOTIFICATION-TYPE
    STATUS      current
    DESCRIPTION
       "Send the trap when the operational state of LACP is from disabled to enabled. "
    ::= { es2126TrapEntry 141 }

es2126VlanPortBaseEnabled NOTIFICATION-TYPE
    STATUS      current
    DESCRIPTION
       "Send the trap when the operational state of vlan is changed to port-based vlan."
    ::= { es2126TrapEntry 151 }

es2126VlanTagBaseEnabled NOTIFICATION-TYPE
    STATUS      current
    DESCRIPTION
       "Send the trap when the operational state of vlan is changed to tag-based vlan."
    ::= { es2126TrapEntry 152 }

es2126VlanMetroBaseEnabled NOTIFICATION-TYPE
    STATUS      current
    DESCRIPTION
       "Send the trap when the operational state of vlan is changed to metro-based vlan."
    ::= { es2126TrapEntry 153 }

es2126UserLogin NOTIFICATION-TYPE
    OBJECTS   {username}
    STATUS      current
    DESCRIPTION
       "Send the trap when one user logins the system."
    ::= { es2126TrapEntry 200 }

es2126UserLogout NOTIFICATION-TYPE
    OBJECTS   {username}
    STATUS      current
    DESCRIPTION
       "Send the trap when one user logouts the system."
    ::= { es2126TrapEntry 201 }

es2126TrapVariable  OBJECT IDENTIFIER ::= { es2126Produces 21 }

username OBJECT-TYPE
    SYNTAX      DisplayString
    MAX-ACCESS  read-only
    STATUS      current
    DESCRIPTION
        "System account name."
    ::= { es2126TrapVariable 1 }

groupId OBJECT-TYPE
    SYNTAX      INTEGER(1..8)
    MAX-ACCESS  read-only
    STATUS      current
    DESCRIPTION
        "The Trunk group ID of LACP."
    ::= { es2126TrapVariable 2 }

actorkey OBJECT-TYPE
    SYNTAX  INTEGER(1..2147483647)
    MAX-ACCESS  read-only
    STATUS      current
    DESCRIPTION
        "The actor key information for LACP."
    ::= { es2126TrapVariable 3 }

partnerkey OBJECT-TYPE
    SYNTAX  INTEGER(1..2147483647)
    MAX-ACCESS  read-only
    STATUS      current
    DESCRIPTION
        "The partner key information for LACP."
    ::= { es2126TrapVariable 4 }

uplink OBJECT-TYPE
    SYNTAX  DisplayString
    MAX-ACCESS  read-only
    STATUS      current
    DESCRIPTION
        "Uplink port(s) in the metro-mode vlan."
    ::= { es2126TrapVariable 5 }

loginProtectInfo OBJECT-TYPE
    SYNTAX  DisplayString
    MAX-ACCESS  read-only
    STATUS      current
    DESCRIPTION
        "Loging protect information."
    ::= { es2126TrapVariable 6 }

es2126LoginProtect           OBJECT IDENTIFIER ::= { es2126Produces 22 }

es2126LockMinutes OBJECT-TYPE
    SYNTAX      INTEGER(0..10)
    MAX-ACCESS      read-write
    STATUS      current
    DESCRIPTION
        "Set the login lock time. Available from 0 to 10 (minutes)
         Set 0 as disabled.
        "
    ::= { es2126LoginProtect 1 }

es2126LoginErrors OBJECT-TYPE
    SYNTAX      INTEGER(0..10)
    MAX-ACCESS      read-write
    STATUS      current
    DESCRIPTION
        "Set login error count. Available from 0 to 10 (times)
         Set 0 as disabled.
        "
    ::= { es2126LoginProtect 2 }

END

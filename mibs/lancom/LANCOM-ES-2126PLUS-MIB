LANCOM-ES-2126PLUS-MIB DEFINITIONS ::= BEGIN

IMPORTS
    DisplayString FROM SNMPv2-TC
    MODULE-COMPLIANCE,OBJECT-GROUP, NOTIFICATION-GROUP       FROM SNMPv2-CONF
    enterprises,MODULE-IDENTITY,OBJECT-TYPE,NOTIFICATION-TYPE,Counter32,IpAddress        FROM SNMPv2-SMI
    MacAddress FROM BRIDGE-MIB
    ifIndex    FROM RFC1213-MIB;

-- @ENTERPRISE-SECTION-START
lancomSystems MODULE-IDENTITY
    LAST-UPDATED "200904010000Z"
        ORGANIZATION "LANCOM Systems GmbH"
        CONTACT-INFO
            "Adenauerstrasse 20 / B2, 52146 Wuerselen, Germany
                 Email: info@lancom.de
                 TEL: +49 (0)2405 49936 0
                 FAX: +49 (0)2405 49936 99"
        DESCRIPTION
                "The MIB module is for LANCOM Systems"
        ::= { enterprises 2356 }

switchingSystems               OBJECT IDENTIFIER ::= { lancomSystems 800 }

fastEthernetSwitches            OBJECT IDENTIFIER ::= { switchingSystems 2 }

lancomES2126PLUS            OBJECT IDENTIFIER ::= { fastEthernetSwitches 2128 }

-- @ENTERPRISE-SECTION-END
es2126plusProduces            OBJECT IDENTIFIER ::= { lancomES2126PLUS 1 }

es2126plusSystem            OBJECT IDENTIFIER ::= { es2126plusProduces 1 }

es2126plusCommonSys             OBJECT IDENTIFIER ::= { es2126plusSystem 1 }

es2126plusReboot OBJECT-TYPE
    SYNTAX      INTEGER(0|1|2)
    MAX-ACCESS      read-write
    STATUS      current
    DESCRIPTION
        "Reboot the system. Get this OID always return zero.
            0 - do nothing
            1 - Reboot without saving start
            2 - Reboot with saving start"
    ::= { es2126plusCommonSys 1 }

es2126plusBiosVsersion  OBJECT-TYPE
    SYNTAX      DisplayString
    MAX-ACCESS      read-only
    STATUS      current
    DESCRIPTION
        "Get the BIOS version of the system."
    ::= { es2126plusCommonSys 2 }

es2126plusFirmwareVersion   OBJECT-TYPE
    SYNTAX      DisplayString
    MAX-ACCESS      read-only
    STATUS      current
    DESCRIPTION
        "Get the firmware version of the system."
    ::= { es2126plusCommonSys 3 }

es2126plusHardwareVersion   OBJECT-TYPE
    SYNTAX      DisplayString
    MAX-ACCESS      read-only
    STATUS      current
    DESCRIPTION
        "Get the hardware version of the system."
    ::= { es2126plusCommonSys 4 }

es2126plusMechanicalVersion OBJECT-TYPE
    SYNTAX      DisplayString
    MAX-ACCESS      read-only
    STATUS      current
    DESCRIPTION
        "Get the mechanical version of the system."
    ::= { es2126plusCommonSys 5 }

es2126plusSerialNumber  OBJECT-TYPE
    SYNTAX      DisplayString
    MAX-ACCESS      read-only
    STATUS      current
    DESCRIPTION
        "Get the Serial number of the system."
    ::= { es2126plusCommonSys 6 }

es2126plusHostMacAddress    OBJECT-TYPE
    SYNTAX      DisplayString
    MAX-ACCESS      read-only
    STATUS      current
    DESCRIPTION
        "Get the MAC address of the system."
    ::= { es2126plusCommonSys 7 }

es2126plusDevicePort    OBJECT-TYPE
    SYNTAX      DisplayString
    MAX-ACCESS      read-only
    STATUS      current
    DESCRIPTION
        "Get the quantity of ports that this system owns now."
    ::= { es2126plusCommonSys 8 }

es2126plusRamSize  OBJECT-TYPE
    SYNTAX      DisplayString
    MAX-ACCESS      read-only
    STATUS      current
    DESCRIPTION
        "Get the RAM size of the system."
    ::= { es2126plusCommonSys 9 }

es2126plusFlashSize  OBJECT-TYPE
    SYNTAX      DisplayString
    MAX-ACCESS      read-only
    STATUS      current
    DESCRIPTION
        "Get the flash size of the system."
    ::= { es2126plusCommonSys 10 }

es2126plusSystemDescription  OBJECT-TYPE
    SYNTAX      DisplayString
    MAX-ACCESS      read-only
    STATUS      current
    DESCRIPTION
        "Get the system description."
    ::= { es2126plusCommonSys 11 }

es2126plusDeviceName  OBJECT-TYPE
    SYNTAX      DisplayString
    MAX-ACCESS      read-write
    STATUS      current
    DESCRIPTION
        "Get/Set the device Name."
    ::= { es2126plusCommonSys 12 }

es2126plusIP            OBJECT IDENTIFIER ::= { es2126plusSystem 2 }

es2126plusDhcpSetting OBJECT-TYPE
    SYNTAX          INTEGER(0|1)
    MAX-ACCESS          read-write
    STATUS          current
    DESCRIPTION
        "Get/Set DHCP status of the system.
            0 - DHCP disable
            1 - DHCP enable"
    ::= { es2126plusIP 1 }

es2126plusIPAddress OBJECT-TYPE
    SYNTAX      IpAddress
    MAX-ACCESS      read-write
    STATUS      current
    DESCRIPTION
        "Get/Set the IP address of the system.
         You can't set this OID if DHCP status is enabled."
    ::= { es2126plusIP 2 }

es2126plusNetMask OBJECT-TYPE
    SYNTAX      IpAddress
    MAX-ACCESS      read-write
    STATUS      current
    DESCRIPTION
        "Get/Set the subnet mask of the system.
         You can't set this OID if DHCP status is enabled."
    ::= { es2126plusIP 3 }

es2126plusDefaultGateway OBJECT-TYPE
    SYNTAX      IpAddress
    MAX-ACCESS      read-write
    STATUS      current
    DESCRIPTION
        "Get/Set the default gateway of the system.
         You can't set this OID if DHCP status is enabled."
    ::= { es2126plusIP 4 }

es2126plusDnsSetting OBJECT-TYPE
    SYNTAX      INTEGER(0|1)
    MAX-ACCESS      read-write
    STATUS      current
    DESCRIPTION
        "Get/Set the source of DNS server.
         You can't set this OID if DHCP status is disabled.
            0 - manual, the DNS server is from manual setting
            1 - Auto, the DNS server is assigned by DHCP server."
    ::= { es2126plusIP 5 }

es2126plusDnsServer OBJECT-TYPE
    SYNTAX      IpAddress
    MAX-ACCESS      read-write
    STATUS      current
    DESCRIPTION
        "Get/Set the DNS server of the system."
    ::= { es2126plusIP 6 }

es2126plusTime              OBJECT IDENTIFIER ::= { es2126plusSystem 3 }

es2126plusSystemCurrentTime OBJECT-TYPE
    SYNTAX      DisplayString
    MAX-ACCESS      read-only
    STATUS      current
    DESCRIPTION
        "Get the current time of the system."
    ::= { es2126plusTime 1 }

es2126plusManualTimeSetting OBJECT-TYPE
    SYNTAX      DisplayString
    MAX-ACCESS      read-write
    STATUS      current
    DESCRIPTION
        "Get/Set the system time of the device.
        The input format is 'Year/Month/Day/Hour/Minute/Second'.
        Ex: 2004/1/1/12/34/25 means 2004/1/1 - 12:24:25.
        Value range:
        Year    : 2000 - 2036,
        Mouth   : 1 - 12,
        Day     : 1 - 31,
        Hour    : 0 - 23,
        Minute  : 0 - 59,
        Sec     : 0 - 59."
    ::= { es2126plusTime 2 }

es2126plusNTPServer OBJECT-TYPE
    SYNTAX      DisplayString
    MAX-ACCESS      read-write
    STATUS      current
    DESCRIPTION
        "Get/Set the NTP Time Server. You can use the IP address or domain name."
    ::= { es2126plusTime 3 }

es2126plusNTPTimeZone OBJECT-TYPE
    SYNTAX      INTEGER(-12..13)
    MAX-ACCESS      read-write
    STATUS      current
    DESCRIPTION
        "Get/Set the NTP Time Zone.
        Value range is between -12 and 13
        -12 - GMT -12:00,
        -11 - GMT -11:00,
        -10 - GMT -10:00,
         -9 - GMT -09:00,
         -8 - GMT -08:00,
         -7 - GMT -07:00,
         -6 - GMT -06:00,
         -5 - GMT -05:00,
         -4 - GMT -04:00,
         -3 - GMT -03:00,
         -2 - GMT -02:00,
         -1 - GMT -01:00,
          0 - GMT +00:00,
          1 - GMT +01:00,
          2 - GMT +02:00,
          3 - GMT +03:00,
          4 - GMT +04:00,
          5 - GMT +05:00,
          6 - GMT +06:00,
          7 - GMT +07:00,
          8 - GMT +08:00,
          9 - GMT +09:00,
         10 - GMT +10:00,
         11 - GMT +11:00,
         12 - GMT +12:00,
         13 - GMT +13:00. "
    ::= { es2126plusTime 4 }

es2126plusNTPTimeSync OBJECT-TYPE
    SYNTAX      INTEGER(0|1)
    MAX-ACCESS      read-write
    STATUS      current
    DESCRIPTION
        "Sync time from NTP Server. Get this OID always return zero.
        Set the Time Server and Time Zone before doing time sync.
        Notice that time server must be correct!
        Value range (1|0):
        1 - Sync.
        0 - do nothing."
    ::= { es2126plusTime 5 }

es2126plusDaylightSavingTime OBJECT-TYPE
    SYNTAX      INTEGER(-5..5)
    MAX-ACCESS      read-write
    STATUS      current
    DESCRIPTION
        "Get/Set the daylight saving time.
        Value range is between -5 and 5. Unit: hour. "
    ::= { es2126plusTime 6 }

es2126plusDaylightStartTime OBJECT-TYPE
    SYNTAX      DisplayString
    MAX-ACCESS      read-write
    STATUS      current
    DESCRIPTION
        "Get/Set the Start time of Daylight Saving.
        The input format is 'MM/DD/HH',
        and daylight saving start month can't equal end month.
        Example: month/day/hour   10/01/00
        Month: 01~12, day: 01~31, hour: 00~23."
    ::= { es2126plusTime 7 }

es2126plusDaylightEndTime OBJECT-TYPE
    SYNTAX      DisplayString
    MAX-ACCESS      read-write
    STATUS      current
    DESCRIPTION
        "Get/Set the End time of Daylight Saving.
        The input format is 'MM/DD/HH',
        and daylight saving start month can't equal end month.
        Example: month/day/hour   04/01/00
        Month: 01~12, day: 01~31, hour: 00~23."
    ::= { es2126plusTime 8 }


es2126plusAccount               OBJECT IDENTIFIER ::= { es2126plusSystem 4 }

es2126plusAccountNumber OBJECT-TYPE
    SYNTAX      INTEGER(1..5)
    MAX-ACCESS      read-only
    STATUS      current
    DESCRIPTION
        "Get the current account number(s) of the system."
    ::= { es2126plusAccount 1 }

es2126plusAccountTable  OBJECT-TYPE
    SYNTAX      SEQUENCE OF ES2126PLUSAccountEntry
    MAX-ACCESS  not-accessible
    STATUS      current
    DESCRIPTION
        "This is a list of es2126plusAccountEntry. The numbers of entries are given by
        the value of es2126plusAccountNumber."
    ::= { es2126plusAccount 2 }

ES2126PLUSAccountEntry ::=
SEQUENCE {
    es2126plusAccountIndex          INTEGER,
    es2126plusAccountAuthorization  DisplayString,
    es2126plusAccountName             DisplayString,
    es2126plusAccountPassword         DisplayString
}

es2126plusAccountEntry  OBJECT-TYPE
    SYNTAX      ES2126PLUSAccountEntry
    MAX-ACCESS      not-accessible
    STATUS      current
    DESCRIPTION
        "This is the Entry(s) for account information."
    INDEX {es2126plusAccountIndex}
    ::= { es2126plusAccountTable 1 }

es2126plusAccountIndex  OBJECT-TYPE
    SYNTAX      INTEGER(1..5)
    MAX-ACCESS      read-only
    STATUS      current
    DESCRIPTION
        "This is the index of the account entry."
    ::= { es2126plusAccountEntry 1 }

es2126plusAccountAuthorization  OBJECT-TYPE
    SYNTAX      DisplayString
    MAX-ACCESS      read-only
    STATUS      current
    DESCRIPTION
        "This is the authorization of the account entry."
    ::= { es2126plusAccountEntry 2 }

es2126plusAccountName   OBJECT-TYPE
    SYNTAX      DisplayString
    MAX-ACCESS      read-write
    STATUS      current
    DESCRIPTION
        "This is the username of the account entry."
    ::= { es2126plusAccountEntry 3 }

es2126plusAccountPassword   OBJECT-TYPE
    SYNTAX      DisplayString
    MAX-ACCESS      read-write
    STATUS      current
    DESCRIPTION
        "This is the password of the account entry. The return value is always '********'."
    ::= { es2126plusAccountEntry 4 }

es2126plusAccountAddName OBJECT-TYPE
    SYNTAX      DisplayString
    MAX-ACCESS      read-write
    STATUS      current
    DESCRIPTION
        "This is the account name for adding operation."
    ::= { es2126plusAccount 3 }

es2126plusAccountAddPassword OBJECT-TYPE
    SYNTAX      DisplayString
    MAX-ACCESS      read-write
    STATUS      current
    DESCRIPTION
        "This is the account password for adding operation. The return value is always '********'."
    ::= { es2126plusAccount 4 }

es2126plusDoAccountAdd OBJECT-TYPE
    SYNTAX      INTEGER(0|1)
    MAX-ACCESS      read-write
    STATUS      current
    DESCRIPTION
        "Add account name. OID es2126plusAccountAddName and es2126plusAccountAddPassword must be
        filled first. Get this OID always return zero.
            1 - Add account.
            0 - do nothing."
    ::= { es2126plusAccount 5 }

es2126plusAccountDel    OBJECT-TYPE
    SYNTAX      INTEGER(2..5)
    MAX-ACCESS      read-write
    STATUS      current
    DESCRIPTION
        "Delete account. The value is valid es2126plusAccountIndex(Can't delete administrator)."
    ::= { es2126plusAccount 6 }


es2126plusSnmp              OBJECT IDENTIFIER ::= { es2126plusProduces 2 }

es2126plusGetCommunity OBJECT-TYPE
    SYNTAX      DisplayString
    MAX-ACCESS      read-write
    STATUS      current
    DESCRIPTION
        "Get/Set the get-community of the SNMP."
    ::= { es2126plusSnmp 1 }

es2126plusSetCommunity OBJECT-TYPE
    SYNTAX      DisplayString
    MAX-ACCESS      read-write
    STATUS      current
    DESCRIPTION
        "Get/Set the set-community of the SNMP."
    ::= { es2126plusSnmp 2 }

es2126plusTrapHostNumber OBJECT-TYPE
    SYNTAX      INTEGER(1..6)
    MAX-ACCESS      read-only
    STATUS      current
    DESCRIPTION
        "Get the number of trap hosts."
    ::= { es2126plusSnmp 3 }

es2126plusTrapHostTable OBJECT-TYPE
    SYNTAX      SEQUENCE OF ES2126PLUSTrapHostEntry
    MAX-ACCESS  not-accessible
    STATUS      current
    DESCRIPTION
        "This is a list of trap host entry. The numbers of entries are given by the value of es2126plusTrapHostNumber."
    ::= { es2126plusSnmp 4 }

ES2126PLUSTrapHostEntry ::=
SEQUENCE {
    es2126plusTrapHostIndex         INTEGER,
    es2126plusTrapHostIP            IpAddress,
    es2126plusTrapHostPort            INTEGER,
    es2126plusTrapHostCommunity       DisplayString
}

es2126plusTrapHostEntry OBJECT-TYPE
    SYNTAX      ES2126PLUSTrapHostEntry
    MAX-ACCESS      not-accessible
    STATUS      current
    DESCRIPTION
        "This is the Entry Information for trap host."
    INDEX {es2126plusTrapHostIndex}
    ::= { es2126plusTrapHostTable 1 }

es2126plusTrapHostIndex OBJECT-TYPE
    SYNTAX      INTEGER(1..6)
    MAX-ACCESS      read-only
    STATUS      current
    DESCRIPTION
        "The index of the trap host entry."
    ::= { es2126plusTrapHostEntry 1 }

es2126plusTrapHostIP    OBJECT-TYPE
    SYNTAX      IpAddress
    MAX-ACCESS      read-write
    STATUS      current
    DESCRIPTION
        "This is the IP of the trap host."
    ::= { es2126plusTrapHostEntry 2 }


es2126plusTrapHostPort  OBJECT-TYPE
    SYNTAX      INTEGER(1..65535)
    MAX-ACCESS      read-write
    STATUS      current
    DESCRIPTION
        "This is the receiving-port number of the trap host."
    ::= { es2126plusTrapHostEntry 3 }


es2126plusTrapHostCommunity OBJECT-TYPE
    SYNTAX      DisplayString
    MAX-ACCESS      read-write
    STATUS      current
    DESCRIPTION
        "The community name for the trap PDU."
    ::= { es2126plusTrapHostEntry 4 }

es2126plusRegisterMonitor OBJECT-TYPE
                SYNTAX DisplayString
                MAX-ACCESS read-write
                STATUS current
                DESCRIPTION "Register-Monitor"
                ::= {  es2126plusSnmp 5 }

es2126plusDeleteMonitor OBJECT-TYPE
               SYNTAX DisplayString
               MAX-ACCESS read-write
               STATUS current
               DESCRIPTION "Delete-Monitor"
               ::= {  es2126plusSnmp 6 }

es2126plusMonitorTable OBJECT-TYPE
                    SYNTAX SEQUENCE OF ES2126PLUSMonitorEntry
                    MAX-ACCESS not-accessible
                    STATUS current
                    DESCRIPTION "Monitor-Table"
                    ::= {  es2126plusSnmp 7 }

ES2126PLUSMonitorEntry ::= SEQUENCE {
                    es2126plusMonitorTableIp IpAddress,
                    es2126plusMonitorTableMac DisplayString
                   }

es2126plusMonitorEntry OBJECT-TYPE
                    SYNTAX ES2126PLUSMonitorEntry
                    MAX-ACCESS not-accessible
                    STATUS current
                    DESCRIPTION "entry in table"
                    INDEX { es2126plusMonitorTableIp }
                    ::= {  es2126plusMonitorTable 1 }

es2126plusMonitorTableIp OBJECT-TYPE
                  SYNTAX IpAddress
                  MAX-ACCESS read-only
                  STATUS current
                  DESCRIPTION "IP-Address"
                  ::= {  es2126plusMonitorEntry 1 }

es2126plusMonitorTableMac OBJECT-TYPE
                  SYNTAX DisplayString
                  MAX-ACCESS read-only
                  STATUS current
                  DESCRIPTION "MAC-Address"
                  ::= {  es2126plusMonitorEntry 2 }

es2126plusTrapBootDelayTime OBJECT-TYPE
    SYNTAX      INTEGER(0..120)
    MAX-ACCESS      read-write
    STATUS      current
    DESCRIPTION
        "Get/Set trap boot delay time in second. Default: 0"
    ::= { es2126plusSnmp 8 }

es2126plusAlarm             OBJECT IDENTIFIER ::= { es2126plusProduces 3 }

es2126plusEvent             OBJECT IDENTIFIER ::= { es2126plusAlarm 1 }

es2126plusEventNumber OBJECT-TYPE
    SYNTAX      INTEGER(1..2147483647)
    MAX-ACCESS      read-only
    STATUS      current
    DESCRIPTION
        "Get the total number of alarm events."
    ::= { es2126plusEvent 1 }

es2126plusEventTable    OBJECT-TYPE
    SYNTAX      SEQUENCE OF ES2126PLUSEventEntry
    MAX-ACCESS  not-accessible
    STATUS      current
    DESCRIPTION
        "This is a list of alarm event entry. The numbers of entries are given by the value of es2126plusEventNumber."
    ::= { es2126plusEvent 2 }

ES2126PLUSEventEntry ::=
SEQUENCE {
    es2126plusEventIndex            INTEGER,
    es2126plusEventName             DisplayString,
    es2126plusEventSendEmail      INTEGER,
    es2126plusEventSendTrap       INTEGER
}

es2126plusEventEntry    OBJECT-TYPE
    SYNTAX      ES2126PLUSEventEntry
    MAX-ACCESS      not-accessible
    STATUS      current
    DESCRIPTION
        "This is the entry information for alarm event."
    INDEX {es2126plusEventIndex}
    ::= { es2126plusEventTable 1 }

es2126plusEventIndex    OBJECT-TYPE
    SYNTAX      INTEGER(1..2147483647)
    MAX-ACCESS      read-only
    STATUS      current
    DESCRIPTION
        "This is the index of the alarm event entry."
    ::= { es2126plusEventEntry 1 }

es2126plusEventName OBJECT-TYPE
    SYNTAX      DisplayString
    MAX-ACCESS      read-only
    STATUS      current
    DESCRIPTION
        "This is the alarm event name."
    ::= { es2126plusEventEntry 2 }

es2126plusEventSendEmail    OBJECT-TYPE
    SYNTAX      INTEGER(0|1)
    MAX-ACCESS      read-write
    STATUS      current
    DESCRIPTION
        "Send email when alarm event is triggered."
    ::= { es2126plusEventEntry 3 }

es2126plusEventSendTrap OBJECT-TYPE
    SYNTAX      INTEGER(0|1)
    MAX-ACCESS      read-write
    STATUS      current
    DESCRIPTION
        "Send trap when alarm event is triggered."
    ::= { es2126plusEventEntry 4 }


es2126plusEmail             OBJECT IDENTIFIER ::= { es2126plusAlarm 2 }

es2126plusEmailServer OBJECT-TYPE
    SYNTAX      DisplayString
    MAX-ACCESS      read-write
    STATUS      current
    DESCRIPTION
        "This is the SMTP server for alarm event."
    ::= { es2126plusEmail 1 }

es2126plusEmailUsername OBJECT-TYPE
    SYNTAX      DisplayString
    MAX-ACCESS      read-write
    STATUS      current
    DESCRIPTION
        "This is the Username of SMTP server."
    ::= { es2126plusEmail 2 }

es2126plusEmailPassword OBJECT-TYPE
    SYNTAX      DisplayString
    MAX-ACCESS      read-write
    STATUS      current
    DESCRIPTION
        "This is the User Password of SMTP server."
    ::= { es2126plusEmail 3 }

es2126plusEmailSender OBJECT-TYPE
	SYNTAX      DisplayString
	MAX-ACCESS	    read-write
	STATUS		current
	DESCRIPTION
		"This is the Sender of SMTP server."
	::= { es2126plusEmail 4 }

es2126plusEmailReturnPath OBJECT-TYPE
	SYNTAX      DisplayString
	MAX-ACCESS	    read-write
	STATUS		current
	DESCRIPTION
		"This is the return path of mail."
	::= { es2126plusEmail 5 }

es2126plusEmailUserNumber OBJECT-TYPE
    SYNTAX      INTEGER(1..6)
    MAX-ACCESS      read-only
    STATUS      current
    DESCRIPTION
        "The number of the email users that you want to send the alarm notification."
    ::= { es2126plusEmail 6 }

es2126plusEmailUserTable    OBJECT-TYPE
    SYNTAX      SEQUENCE OF ES2126PLUSEmailUserEntry
    MAX-ACCESS  not-accessible
    STATUS      current
    DESCRIPTION
        "This is a list of email user entry. The numbers of entries are given by the value of es2126plusEmailUserNumber."
    ::= { es2126plusEmail 7 }

ES2126PLUSEmailUserEntry ::=
SEQUENCE {
    es2126plusEmailUserIndex            INTEGER,
    es2126plusEmailUserAddress          DisplayString
}

es2126plusEmailUserEntry    OBJECT-TYPE
    SYNTAX      ES2126PLUSEmailUserEntry
    MAX-ACCESS      not-accessible
    STATUS      current
    DESCRIPTION
        "This is the Entry information for email user entry."
    INDEX {es2126plusEmailUserIndex}
    ::= { es2126plusEmailUserTable 1 }

es2126plusEmailUserIndex    OBJECT-TYPE
    SYNTAX      INTEGER(1..6)
    MAX-ACCESS      read-only
    STATUS      current
    DESCRIPTION
        "This is the index of the email user entry."
    ::= { es2126plusEmailUserEntry 1 }

es2126plusEmailUserAddress  OBJECT-TYPE
    SYNTAX      DisplayString
    MAX-ACCESS      read-write
    STATUS      current
    DESCRIPTION
        "This is the email address of the email user entry."
    ::= { es2126plusEmailUserEntry 2 }

es2126plusTftp              OBJECT IDENTIFIER ::= { es2126plusProduces 4 }

es2126plusTftpRemoteServer OBJECT-TYPE
    SYNTAX      IpAddress
    MAX-ACCESS      read-write
    STATUS      current
    DESCRIPTION
        "Get/Set the remote tftp server."
    ::= { es2126plusTftp 1 }

es2126plusTftpInternalServerState OBJECT-TYPE
    SYNTAX      INTEGER(0|1)
    MAX-ACCESS      read-write
    STATUS      current
    DESCRIPTION
        "Get/Set internal tftp server state.
         0 : Disable
         1 : Enable
        "
    ::= { es2126plusTftp 2 }


es2126plusConfiguration             OBJECT IDENTIFIER ::= { es2126plusProduces 5 }

es2126plusSaveRestore               OBJECT IDENTIFIER ::= { es2126plusConfiguration 1 }

es2126plusSaveStart OBJECT-TYPE
    SYNTAX      INTEGER(0|1)
    MAX-ACCESS      read-write
    STATUS      current
    DESCRIPTION
        "Save current configuration into flash memory (Save as Start Configuration).
        Get this OID always return zero.
            1 - Save.
            0 - do nothing. "
    ::= { es2126plusSaveRestore 1 }

es2126plusSaveUser OBJECT-TYPE
    SYNTAX      INTEGER(0|1)
    MAX-ACCESS      read-write
    STATUS      current
    DESCRIPTION
        "Save current configuration into flash memory (Save as User Configuration).
        Get this OID always return zero.
            1 - Save.
            0 - do nothing. "
    ::= { es2126plusSaveRestore 2 }

es2126plusRestoreDefault OBJECT-TYPE
    SYNTAX      INTEGER(0|1|2)
    MAX-ACCESS      read-write
    STATUS      current
    DESCRIPTION
        "Restore factory default configuration.
        Get this OID always return zero.
            2 - Restore default included default ip address.
        1 - Restore default without changing current ip address.
            0 - do nothing. "
    ::= { es2126plusSaveRestore 3 }

es2126plusRestoreUser OBJECT-TYPE
    SYNTAX      INTEGER(0|1)
    MAX-ACCESS      read-write
    STATUS      current
    DESCRIPTION
        "Restore user configuration.
        Get this OID always return zero.
            1 - Restore.
            0 - do nothing. "
    ::= { es2126plusSaveRestore 4 }


es2126plusConfigFile            OBJECT IDENTIFIER ::= { es2126plusConfiguration 2 }

es2126plusExportConfigName OBJECT-TYPE
    SYNTAX      DisplayString
    MAX-ACCESS      read-write
    STATUS      current
    DESCRIPTION
        "Get/Set the export file path and name."
    ::= { es2126plusConfigFile 1 }

es2126plusDoExportConfig OBJECT-TYPE
    SYNTAX      INTEGER(1|2)
    MAX-ACCESS      read-write
    STATUS      current
    DESCRIPTION
        "Do export-config.
        Get this OID always return zero.
            1   -   Export start section.
            2   -   Export user-conf section."
    ::= { es2126plusConfigFile 2 }

es2126plusImportConfigName OBJECT-TYPE
    SYNTAX      DisplayString
    MAX-ACCESS      read-write
    STATUS      current
    DESCRIPTION
        "Get/Set the import file path and name."
    ::= { es2126plusConfigFile 3 }

es2126plusDoImportConfig OBJECT-TYPE
    SYNTAX      INTEGER(1|2)
    MAX-ACCESS      read-write
    STATUS      current
    DESCRIPTION
        "Do import-config.
        Get this OID always return zero.
            1   -   Import start section.
            2   -   Import user-conf section."
    ::= { es2126plusConfigFile 4 }

es2126plusDiagnostic            OBJECT IDENTIFIER ::= { es2126plusProduces 6 }

es2126plusInternalLoopbackTest OBJECT-TYPE
    SYNTAX      DisplayString
    MAX-ACCESS      read-only
    STATUS      current
    DESCRIPTION
        "Internal loop back test."
    ::= { es2126plusDiagnostic 1 }

es2126plusExternalLoopbackTest OBJECT-TYPE
    SYNTAX      DisplayString
    MAX-ACCESS      read-only
    STATUS      current
    DESCRIPTION
        "External loop back test."
    ::= { es2126plusDiagnostic 2 }

es2126plusPingTest OBJECT-TYPE
    SYNTAX      DisplayString
    MAX-ACCESS      read-write
    STATUS      current
    DESCRIPTION
        "Set the host address that you want to ping and the system will return the test result."
    ::= { es2126plusDiagnostic 3 }

es2126plusWatchdog               OBJECT IDENTIFIER ::= { es2126plusDiagnostic 4 }

es2126plusWatchdogState OBJECT-TYPE
    SYNTAX      INTEGER(0|1)
    MAX-ACCESS      read-write
    STATUS      current
    DESCRIPTION
        "Set the watchdog state.
            1 - Enable.
            0 - Disable."
    ::= { es2126plusWatchdog 1 }

es2126plusWatchdogTimeGap OBJECT-TYPE
    SYNTAX      INTEGER(0..100)
    MAX-ACCESS      read-write
    STATUS      current
    DESCRIPTION
        "Set the watchdog time gap, from 1 to 100."
    ::= { es2126plusWatchdog 2 }

es2126plusWatchdogHost OBJECT-TYPE
    SYNTAX      DisplayString
    MAX-ACCESS      read-write
    STATUS      current
    DESCRIPTION
        "Set the watchdog host"
    ::= { es2126plusWatchdog 3 }

es2126plusWatchdogResetMgtInf OBJECT-TYPE
    SYNTAX      INTEGER(0|1)
    MAX-ACCESS      read-write
    STATUS      current
    DESCRIPTION
        "Set the state of resetting the management cpu interface.
            1 - Enable.
            0 - Disable."
    ::= { es2126plusWatchdog 4 }

es2126plusWatchdogResetMgtInfCount OBJECT-TYPE
    SYNTAX      INTEGER(1..20)
    MAX-ACCESS      read-write
    STATUS      current
    DESCRIPTION
        "Set the count of resetting the management cpu interface."
    ::= { es2126plusWatchdog 5 }

es2126plusWatchdogResetSystem OBJECT-TYPE
    SYNTAX      INTEGER(0|1)
    MAX-ACCESS      read-write
    STATUS      current
    DESCRIPTION
        "Set the state of rebooting the system.
            1 - Enable.
            0 - Disable."
    ::= { es2126plusWatchdog 6 }

es2126plusWatchdogResetSystemCount OBJECT-TYPE
    SYNTAX      INTEGER(1..1000)
    MAX-ACCESS      read-write
    STATUS      current
    DESCRIPTION
        "Set the count of rebooting the system"
    ::= { es2126plusWatchdog 7 }

es2126plusLog               OBJECT IDENTIFIER ::= { es2126plusProduces 7 }

es2126plusClearLog OBJECT-TYPE
    SYNTAX      INTEGER(0|1)
    MAX-ACCESS      read-write
    STATUS      current
    DESCRIPTION
        "Clear system log.
        Get this OID always return zero.
            1 - Clear log.
            0 - do nothing. "
    ::= { es2126plusLog 1 }

es2126plusUploadLog OBJECT-TYPE
    SYNTAX      INTEGER(0|1)
    MAX-ACCESS      read-write
    STATUS      current
    DESCRIPTION
        "Upload current system log. Set the correct tftp server first.
        The format of log file is 'ModelName_SerialNumbuer_YYMMDD_HHMM'.
        Get this OID always return zero.
            1 - Upload log
            0 - do nothing. "
    ::= { es2126plusLog 2 }

es2126plusAutoUploadLogState OBJECT-TYPE
    SYNTAX      INTEGER(0|1)
    MAX-ACCESS      read-write
    STATUS      current
    DESCRIPTION
        "Enable auto-upload log function. Set the correct tftp server first.
        The format of log file is 'ModelName_SerialNumbuer_YYMMDD_HHMM'.
        Get this OID always return zero.
            1 - Enable auto-upload
            0 - do nothing. "
    ::= { es2126plusLog 3 }

es2126plusLogNumber OBJECT-TYPE
    SYNTAX      INTEGER(0..120)
    MAX-ACCESS      read-only
    STATUS      current
    DESCRIPTION
        "Get the number of current system log. "
    ::= { es2126plusLog 4 }

es2126plusLogTable  OBJECT-TYPE
    SYNTAX      SEQUENCE OF ES2126PLUSLogEntry
    MAX-ACCESS  not-accessible
    STATUS      current
    DESCRIPTION
        "This is a list of log entry. The numbers of entries are given by the value of es2126plusLogNumber."
    ::= { es2126plusLog 5 }

ES2126PLUSLogEntry ::=
SEQUENCE {
    es2126plusLogIndex          INTEGER,
    es2126plusLogEvent              DisplayString
}

es2126plusLogEntry  OBJECT-TYPE
    SYNTAX      ES2126PLUSLogEntry
    MAX-ACCESS      not-accessible
    STATUS      current
    DESCRIPTION
        "This is the Entry information for system log."
    INDEX {es2126plusLogIndex}
    ::= { es2126plusLogTable 1 }

es2126plusLogIndex  OBJECT-TYPE
    SYNTAX      INTEGER(1..120)
    MAX-ACCESS      read-only
    STATUS      current
    DESCRIPTION
        "This is the index of the log entry."
    ::= { es2126plusLogEntry 1 }

es2126plusLogEvent  OBJECT-TYPE
    SYNTAX      DisplayString
    MAX-ACCESS      read-only
    STATUS      current
    DESCRIPTION
        "This is the detail information of the log entry."
    ::= { es2126plusLogEntry 2 }

es2126plusFirmware              OBJECT IDENTIFIER ::= { es2126plusProduces 8 }

es2126plusFirmwareFileName OBJECT-TYPE
    SYNTAX      DisplayString
    MAX-ACCESS      read-write
    STATUS      current
    DESCRIPTION
        "Get/Set the path and filename for firmware upgrading."
    ::= { es2126plusFirmware 1 }

es2126plusDoFirmwareUpgrade OBJECT-TYPE
    SYNTAX      INTEGER(0|1)
    MAX-ACCESS      read-write
    STATUS      current
    DESCRIPTION
        "Do firmware upgrade. Get this OID always return zero.
            1 - Do firmware upgrade.
            0 - do nothing."
    ::= { es2126plusFirmware 2 }


es2126plusPort              OBJECT IDENTIFIER ::= { es2126plusProduces 9 }

es2126plusPortStatus            OBJECT IDENTIFIER ::= { es2126plusPort 1 }

es2126plusPortStatusNumber OBJECT-TYPE
    SYNTAX      INTEGER(1..2147483647)
    MAX-ACCESS      read-only
    STATUS      current
    DESCRIPTION
        "Get the number of port."
    ::= { es2126plusPortStatus 1 }

es2126plusPortStatusTable   OBJECT-TYPE
    SYNTAX      SEQUENCE OF ES2126PLUSPortStatusEntry
    MAX-ACCESS  not-accessible
    STATUS      current
    DESCRIPTION
        "This is a list of port status entry. The numbers of entries are given by the value of es2126plusPortStatusNumber."
    ::= { es2126plusPortStatus 2 }

ES2126PLUSPortStatusEntry ::=
SEQUENCE {
    es2126plusPortStatusIndex           INTEGER,
    es2126plusPortStatusMedia          DisplayString,
    es2126plusPortStatusLink           DisplayString,
    es2126plusPortStatusPortState      DisplayString,
    es2126plusPortStatusAutoNego       DisplayString,
    es2126plusPortStatusSpdDpx         DisplayString,
    es2126plusPortStatusRxPause        DisplayString,
    es2126plusPortStatusTxPause        DisplayString,
    es2126plusPortStatusDescription     DisplayString
}

es2126plusPortStatusEntry   OBJECT-TYPE
    SYNTAX      ES2126PLUSPortStatusEntry
    MAX-ACCESS      not-accessible
    STATUS      current
    DESCRIPTION
        "This is the entry(s) for port status information."
    INDEX {es2126plusPortStatusIndex}
    ::= { es2126plusPortStatusTable 1 }

es2126plusPortStatusIndex   OBJECT-TYPE
    SYNTAX      INTEGER(1..2147483647)
    MAX-ACCESS      read-only
    STATUS      current
    DESCRIPTION
        "This is the index of the port status entry."
    ::= { es2126plusPortStatusEntry 1 }

es2126plusPortStatusMedia   OBJECT-TYPE
    SYNTAX      DisplayString
    MAX-ACCESS      read-only
    STATUS      current
    DESCRIPTION
        "The port media type of the port status entry."
    ::= { es2126plusPortStatusEntry 2 }

es2126plusPortStatusLink    OBJECT-TYPE
    SYNTAX      DisplayString
    MAX-ACCESS      read-only
    STATUS      current
    DESCRIPTION
        "This is the port link of the port status entry."
    ::= { es2126plusPortStatusEntry 3 }

es2126plusPortStatusPortState   OBJECT-TYPE
    SYNTAX      DisplayString
    MAX-ACCESS      read-only
    STATUS      current
    DESCRIPTION
        "This is the port state of the port status entry."
    ::= { es2126plusPortStatusEntry 4 }

es2126plusPortStatusAutoNego    OBJECT-TYPE
    SYNTAX      DisplayString
    MAX-ACCESS      read-only
    STATUS      current
    DESCRIPTION
        "This is the auto negotiation of the port status entry."
    ::= { es2126plusPortStatusEntry 5 }

es2126plusPortStatusSpdDpx  OBJECT-TYPE
    SYNTAX      DisplayString
    MAX-ACCESS      read-only
    STATUS      current
    DESCRIPTION
        "This is the speed/duplex of the port status entry."
    ::= { es2126plusPortStatusEntry 6 }

es2126plusPortStatusRxPause     OBJECT-TYPE
    SYNTAX      DisplayString
    MAX-ACCESS      read-only
    STATUS      current
    DESCRIPTION
        "The Rx Pause of the port status entry."
    ::= { es2126plusPortStatusEntry 7 }

es2126plusPortStatusTxPause     OBJECT-TYPE
    SYNTAX      DisplayString
    MAX-ACCESS      read-only
    STATUS      current
    DESCRIPTION
        "The Tx Pause of the port status entry."
    ::= { es2126plusPortStatusEntry 8 }

es2126plusPortStatusDescription OBJECT-TYPE
    SYNTAX      DisplayString
    MAX-ACCESS      read-only
    STATUS      current
    DESCRIPTION
        "This is the description of port."
    ::= { es2126plusPortStatusEntry 9 }

es2126plusPortConf              OBJECT IDENTIFIER ::= { es2126plusPort 2 }

es2126plusPortConfNumber OBJECT-TYPE
    SYNTAX      INTEGER(1..2147483647)
    MAX-ACCESS      read-only
    STATUS      current
    DESCRIPTION
        "Get the number of port configuration."
    ::= { es2126plusPortConf 1 }

es2126plusPortConfTable OBJECT-TYPE
    SYNTAX      SEQUENCE OF ES2126PLUSPortConfEntry
    MAX-ACCESS  not-accessible
    STATUS      current
    DESCRIPTION
        "This is a list of port configuration entry. The numbers of entries are given by the value of es2126plusPortConfNumber."
    ::= { es2126plusPortConf 2 }

ES2126PLUSPortConfEntry ::=
SEQUENCE {
    es2126plusPortConfIndex        INTEGER,
    es2126plusPortConfPortState        INTEGER,
    es2126plusPortConfSpdDpx           INTEGER,
    es2126plusPortConfFlwCtrl          INTEGER,
    es2126plusPortConfDescription      DisplayString
}

es2126plusPortConfEntry OBJECT-TYPE
    SYNTAX      ES2126PLUSPortConfEntry
    MAX-ACCESS      not-accessible
    STATUS      current
    DESCRIPTION
        "This is the Entry(s) for port configuration information."
    INDEX {es2126plusPortConfIndex}
    ::= { es2126plusPortConfTable 1 }

es2126plusPortConfIndex OBJECT-TYPE
    SYNTAX      INTEGER(1..2147483647)
    MAX-ACCESS      read-only
    STATUS      current
    DESCRIPTION
        "This is the index of the port configuration entry."
    ::= { es2126plusPortConfEntry 1 }

es2126plusPortConfPortState OBJECT-TYPE
    SYNTAX      INTEGER(0|1)
    MAX-ACCESS      read-write
    STATUS      current
    DESCRIPTION
        "This is the port state of the port configuration entry.
         0 - disabled.
         1 - enabled. "
    ::= { es2126plusPortConfEntry 2 }

es2126plusPortConfSpdDpx    OBJECT-TYPE
    SYNTAX      INTEGER(0..5)
    MAX-ACCESS      read-write
    STATUS      current
    DESCRIPTION
        "This is the speed/duplex of the port configuration entry.
         0 - auto.
         1 - 10M/Half.
         2 - 10M/Full.
         3 - 100M/Half.
         4 - 100M/Full.
         5 - 1G/Full.  "
    ::= { es2126plusPortConfEntry 3 }

es2126plusPortConfFlwCtrl   OBJECT-TYPE
    SYNTAX      INTEGER(0|1)
    MAX-ACCESS      read-write
    STATUS      current
    DESCRIPTION
        "This is the flow control of the port configuration entry.
         0 - asymmetric.
         1 - symmetric.  "
    ::= { es2126plusPortConfEntry 4 }

es2126plusPortConfDescription   OBJECT-TYPE
    SYNTAX      DisplayString
    MAX-ACCESS      read-write
    STATUS      current
    DESCRIPTION
        "This is the description of port."
    ::= { es2126plusPortConfEntry 5 }

es2126plusPortBandwidth             OBJECT IDENTIFIER ::= { es2126plusPort 3 }

es2126plusPortBandwidthTable    OBJECT-TYPE
    SYNTAX      SEQUENCE OF ES2126PLUSPortBandwidthEntry
    MAX-ACCESS  not-accessible
    STATUS      current
    DESCRIPTION
        "This is a list of port bandwidth entry."
    ::= { es2126plusPortBandwidth 1 }

ES2126PLUSPortBandwidthEntry ::=
SEQUENCE {
    es2126plusPortBandwidthIndex                  INTEGER,
    es2126plusPortBandwidthIngressRate        INTEGER,
    es2126plusPortBandwidthEgressRate         INTEGER
}

es2126plusPortBandwidthEntry    OBJECT-TYPE
    SYNTAX      ES2126PLUSPortBandwidthEntry
    MAX-ACCESS      not-accessible
    STATUS      current
    DESCRIPTION
        "This is the Entry(s) for port bandwidth configuration."
    INDEX {es2126plusPortBandwidthIndex}
    ::= { es2126plusPortBandwidthTable 1 }

es2126plusPortBandwidthIndex    OBJECT-TYPE
    SYNTAX      INTEGER(1..26)
    MAX-ACCESS      read-only
    STATUS      current
    DESCRIPTION
        "This is the index of the port bandwidth entry."
    ::= { es2126plusPortBandwidthEntry 1 }

es2126plusPortBandwidthIngressRate  OBJECT-TYPE
    SYNTAX      INTEGER(66..1024000)
    MAX-ACCESS      read-write
    STATUS      current
    DESCRIPTION
        "Get/Set the port bandwidth ingress rate.
         Fast Ethernet port range: 66~102400(Kb)
         Gigabit Ethernet port range: 66~1024000(Kb)"
    ::= { es2126plusPortBandwidthEntry 2 }

es2126plusPortBandwidthEgressRate   OBJECT-TYPE
    SYNTAX      INTEGER(66..1024000)
    MAX-ACCESS      read-write
    STATUS      current
    DESCRIPTION
        "Get/Set the port bandwidth egress rate.
         Fast Ethernet port range: 66~102400(Kb)
         Gigabit Ethernet port range: 66~1024000(Kb)"
    ::= { es2126plusPortBandwidthEntry 3 }

es2126plusPortBandwidthStormType    OBJECT-TYPE
    SYNTAX      INTEGER(0..4)
    MAX-ACCESS      read-write
    STATUS      current
    DESCRIPTION
        "This is the bandwidth storm type.
        0:Disable
                1:Broadcast Storm Control
                2:Multicast Storm Control
                3:Unknown Unicast Storm Control
                4:Broadcast, Multicast, and Unknown Unicast Storm Control"
    ::= { es2126plusPortBandwidth 2 }

es2126plusPortBandwidthStormRate    OBJECT-TYPE
    SYNTAX      INTEGER(1..100)
    MAX-ACCESS      read-write
    STATUS      current
    DESCRIPTION
        "This is the storm rate."
    ::= { es2126plusPortBandwidth 3 }

es2126plusPortSFPInfo               OBJECT IDENTIFIER ::= { es2126plusPort 4 }

es2126plusPortSFPInfoNumber OBJECT-TYPE
    SYNTAX      INTEGER(1..2147483647)
    MAX-ACCESS      read-only
    STATUS      current
    DESCRIPTION
        "Get the number of sfp info entry."
    ::= { es2126plusPortSFPInfo 1 }

es2126plusPortSFPInfoTable  OBJECT-TYPE
    SYNTAX      SEQUENCE OF ES2126PLUSPORTSFPInfoEntry
    MAX-ACCESS  not-accessible
    STATUS      current
    DESCRIPTION
        "A list of sfp info entry. The numbers of entries are given by the value of es2126plusPortSFPInfoNumber."
    ::= { es2126plusPortSFPInfo 2 }

ES2126PLUSPORTSFPInfoEntry ::=
SEQUENCE {
    es2126plusPortSFPInfoIndex      INTEGER,
    es2126plusPortSFPConnectorType  DisplayString,
    es2126plusPortSFPFiberType      DisplayString,
    es2126plusPortSFPWavelength     DisplayString,
    es2126plusPortSFPBaudRate       DisplayString,
    es2126plusPortSFPVendorOUI      DisplayString,
    es2126plusPortSFPVendorName     DisplayString,
    es2126plusPortSFPVendorPN       DisplayString,
    es2126plusPortSFPVendorRev      DisplayString,
    es2126plusPortSFPVendorSN       DisplayString,
    es2126plusPortSFPDateCode       DisplayString,
    es2126plusPortSFPTemperature    DisplayString,
    es2126plusPortSFPVcc            DisplayString,
    es2126plusPortSFPTxBias         DisplayString,
    es2126plusPortSFPTxPWR          DisplayString,
    es2126plusPortSFPRxPWR          DisplayString
}

es2126plusPortSFPInfoEntry  OBJECT-TYPE
    SYNTAX      ES2126PLUSPORTSFPInfoEntry
    MAX-ACCESS      not-accessible
    STATUS      current
    DESCRIPTION
        "Entry(s) for SFP information."
    INDEX {es2126plusPortSFPInfoIndex}
    ::= { es2126plusPortSFPInfoTable 1 }

es2126plusPortSFPInfoIndex  OBJECT-TYPE
    SYNTAX      INTEGER(1..2147483647)
    MAX-ACCESS      read-only
    STATUS      current
    DESCRIPTION
        "The index of the sfp info entry."
    ::= { es2126plusPortSFPInfoEntry 1 }

es2126plusPortSFPConnectorType  OBJECT-TYPE
    SYNTAX      DisplayString
    MAX-ACCESS      read-only
    STATUS      current
    DESCRIPTION
        "Get connector type of the sfp."
    ::= { es2126plusPortSFPInfoEntry 2 }

es2126plusPortSFPFiberType  OBJECT-TYPE
    SYNTAX      DisplayString
    MAX-ACCESS      read-only
    STATUS      current
    DESCRIPTION
        "Get fiber type of the sfp."
    ::= { es2126plusPortSFPInfoEntry 3 }

es2126plusPortSFPWavelength OBJECT-TYPE
    SYNTAX      DisplayString
    MAX-ACCESS      read-only
    STATUS      current
    DESCRIPTION
        "Get tx central wavelength of the sfp."
    ::= { es2126plusPortSFPInfoEntry 4 }

es2126plusPortSFPBaudRate   OBJECT-TYPE
    SYNTAX      DisplayString
    MAX-ACCESS      read-only
    STATUS      current
    DESCRIPTION
        "Get baud rate of the sfp."
    ::= { es2126plusPortSFPInfoEntry 5 }

es2126plusPortSFPVendorOUI  OBJECT-TYPE
    SYNTAX      DisplayString
    MAX-ACCESS      read-only
    STATUS      current
    DESCRIPTION
        "Get vendor OUI of the sfp."
    ::= { es2126plusPortSFPInfoEntry 6 }

es2126plusPortSFPVendorName OBJECT-TYPE
    SYNTAX      DisplayString
    MAX-ACCESS      read-only
    STATUS      current
    DESCRIPTION
        "Get vendor name of the sfp."
    ::= { es2126plusPortSFPInfoEntry 7 }

es2126plusPortSFPVendorPN   OBJECT-TYPE
    SYNTAX      DisplayString
    MAX-ACCESS      read-only
    STATUS      current
    DESCRIPTION
        "Get vendor part number of the sfp."
    ::= { es2126plusPortSFPInfoEntry 8 }

es2126plusPortSFPVendorRev  OBJECT-TYPE
    SYNTAX      DisplayString
    MAX-ACCESS      read-only
    STATUS      current
    DESCRIPTION
        "Get vendor revision number of the sfp."
    ::= { es2126plusPortSFPInfoEntry 9 }

es2126plusPortSFPVendorSN   OBJECT-TYPE
    SYNTAX      DisplayString
    MAX-ACCESS      read-only
    STATUS      current
    DESCRIPTION
        "Get vendor serial number of the sfp."
    ::= { es2126plusPortSFPInfoEntry 10 }

es2126plusPortSFPDateCode   OBJECT-TYPE
    SYNTAX      DisplayString
    MAX-ACCESS      read-only
    STATUS      current
    DESCRIPTION
        "Get data code of the sfp."
    ::= { es2126plusPortSFPInfoEntry 11 }

es2126plusPortSFPTemperature    OBJECT-TYPE
    SYNTAX      DisplayString
    MAX-ACCESS      read-only
    STATUS      current
    DESCRIPTION
        "Get current temperature of the sfp."
    ::= { es2126plusPortSFPInfoEntry 12 }

es2126plusPortSFPVcc    OBJECT-TYPE
    SYNTAX      DisplayString
    MAX-ACCESS      read-only
    STATUS      current
    DESCRIPTION
        "Get current internal supply voltage of the sfp."
    ::= { es2126plusPortSFPInfoEntry 13 }

es2126plusPortSFPTxBias OBJECT-TYPE
    SYNTAX      DisplayString
    MAX-ACCESS      read-only
    STATUS      current
    DESCRIPTION
        "Get current TX Bias of the sfp."
    ::= { es2126plusPortSFPInfoEntry 14 }

es2126plusPortSFPTxPWR  OBJECT-TYPE
    SYNTAX      DisplayString
    MAX-ACCESS      read-only
    STATUS      current
    DESCRIPTION
        "Get current TX output power of the sfp."
    ::= { es2126plusPortSFPInfoEntry 15 }

es2126plusPortSFPRxPWR  OBJECT-TYPE
    SYNTAX      DisplayString
    MAX-ACCESS      read-only
    STATUS      current
    DESCRIPTION
        "Get current Received Power of the sfp."
    ::= { es2126plusPortSFPInfoEntry 16 }


es2126plusLoopDetectedConf              OBJECT IDENTIFIER ::= { es2126plusProduces 10 }

es2126plusLoopDetectedNumber OBJECT-TYPE
    SYNTAX      INTEGER(1..2147483647)
    MAX-ACCESS      read-only
    STATUS      current
    DESCRIPTION
        "Get the number of loop detected entry."
    ::= { es2126plusLoopDetectedConf 1 }

es2126plusLoopDetectedTable OBJECT-TYPE
    SYNTAX      SEQUENCE OF ES2126PLUSLoopDetectedEntry
    MAX-ACCESS  not-accessible
    STATUS      current
    DESCRIPTION
        "This is a list of loop detected entry. The number of entries are given by the value of es2126plusLoopDetectedNumber."
    ::= { es2126plusLoopDetectedConf 2 }

ES2126PLUSLoopDetectedEntry ::=
SEQUENCE {
    es2126plusLoopDetectedfIndex           INTEGER,
    es2126plusLoopDetectedStateEbl         INTEGER,
    es2126plusLoopDetectedCurrentStatus    INTEGER,
    es2126plusLoopDetectedRemoved          INTEGER
}

es2126plusLoopDetectedEntry OBJECT-TYPE
    SYNTAX      ES2126PLUSLoopDetectedEntry
    MAX-ACCESS      not-accessible
    STATUS      current
    DESCRIPTION
        "Entry(s) for loop detected information."
    INDEX {es2126plusLoopDetectedfIndex}
    ::= { es2126plusLoopDetectedTable 1 }

es2126plusLoopDetectedfIndex    OBJECT-TYPE
    SYNTAX      INTEGER(1..2147483647)
    MAX-ACCESS      read-only
    STATUS      current
    DESCRIPTION
        "This is the index of the loop detected entry."
    ::= { es2126plusLoopDetectedEntry 1 }

es2126plusLoopDetectedStateEbl  OBJECT-TYPE
    SYNTAX      INTEGER(0|1)
    MAX-ACCESS      read-write
    STATUS      current
    DESCRIPTION
        "The state of the loop detected entry.
         0 - disabled.
         1 - enabled. "
    ::= { es2126plusLoopDetectedEntry 2 }

es2126plusLoopDetectedCurrentStatus OBJECT-TYPE
    SYNTAX      INTEGER(0|1)
    MAX-ACCESS      read-only
    STATUS      current
    DESCRIPTION
        "The current status of the loop detected port.
         0 - Unlocked
         1 - Locked due to the loop condition "
    ::= { es2126plusLoopDetectedEntry 3 }

es2126plusLoopDetectedRemoved   OBJECT-TYPE
    SYNTAX      INTEGER(0|1)
    MAX-ACCESS      read-write
    STATUS      current
    DESCRIPTION
        "Unlock the port which is locked due to loop condition. Get this OID always return zero.
         1 - Unlock the port,
         0 - do nothing."
    ::= { es2126plusLoopDetectedEntry 4 }

es2126plusLoopDetectedAction OBJECT-TYPE
    SYNTAX      INTEGER(0|1)
    MAX-ACCESS      read-write
    STATUS      current
    DESCRIPTION
        "Set the corresponding action while loop is detected.
         1 - Lock the loop port,
         0 - do nothing."
    ::= { es2126plusLoopDetectedConf 3 }

es2126plusMacTableInfo              OBJECT IDENTIFIER ::= { es2126plusProduces 11 }

es2126plusMacTableMaintenance       OBJECT IDENTIFIER ::= { es2126plusMacTableInfo 1 }

es2126plusMacTableAgingTime  OBJECT-TYPE
    SYNTAX      INTEGER(0|10..1000000)
    MAX-ACCESS  read-write
    STATUS      current
    DESCRIPTION
        "Set the Mac Table Aging Time (10~1000000 Secs).
         0 : Disable.
        "
    ::= { es2126plusMacTableMaintenance 1 }

es2126plusMacTableFlush  OBJECT-TYPE
    SYNTAX      INTEGER(0|1)
    MAX-ACCESS  read-write
    STATUS      current
    DESCRIPTION
        "1 : Flush Mac Table."
    ::= { es2126plusMacTableMaintenance 2 }

es2126plusMacTableLearnPortLimitTable  OBJECT-TYPE
    SYNTAX      SEQUENCE OF ES2126PLUSMacTableLearnPortLimitEntry
    MAX-ACCESS  not-accessible
    STATUS      current
    DESCRIPTION
        "This is a list of MAC Learning Limitentry."
    ::= { es2126plusMacTableMaintenance 3 }

ES2126PLUSMacTableLearnPortLimitEntry ::=
SEQUENCE {
    es2126plusMacTableLearnPortLimitIndex   INTEGER,
    es2126plusMacTableLearnPortLimit        INTEGER
}

es2126plusMacTableLearnPortLimitEntry  OBJECT-TYPE
    SYNTAX      ES2126PLUSMacTableLearnPortLimitEntry
    MAX-ACCESS  not-accessible
    STATUS      current
    DESCRIPTION
        "Entry(s) for Mac Table Port Learning Limit."
    INDEX {es2126plusMacTableLearnPortLimitIndex}
    ::= { es2126plusMacTableLearnPortLimitTable 1 }

es2126plusMacTableLearnPortLimitIndex  OBJECT-TYPE
    SYNTAX      INTEGER(1..26)
    MAX-ACCESS  not-accessible
    STATUS      current
    DESCRIPTION
        "The index of the Mac Table Learning Limit entry."
    ::= { es2126plusMacTableLearnPortLimitEntry 1 }

es2126plusMacTableLearnPortLimit  OBJECT-TYPE
    SYNTAX      INTEGER(0..8191)
    MAX-ACCESS  read-write
    STATUS      current
    DESCRIPTION
        "Port Learning Limit (0~8191)."
    ::= { es2126plusMacTableLearnPortLimitEntry 2 }

es2126plusMacTableStaticMac       OBJECT IDENTIFIER ::= { es2126plusMacTableInfo 3 }

es2126plusMacTableStaticMacNumber  OBJECT-TYPE
    SYNTAX      INTEGER(0..1024)
    MAX-ACCESS  read-only
    STATUS      current
    DESCRIPTION
        "This is number of static Mac table entry"
    ::= { es2126plusMacTableStaticMac 1 }

es2126plusMacTableStaticMacEntryCreate  OBJECT-TYPE
    SYNTAX      INTEGER(0..1024)
    MAX-ACCESS  read-write
    STATUS      current
    DESCRIPTION
        "Creat a static mac entry."
    ::= { es2126plusMacTableStaticMac 2 }

es2126plusMacTableStaticMacTable  OBJECT-TYPE
    SYNTAX      SEQUENCE OF ES2126PLUSMacTableStaticMacEntry
    MAX-ACCESS  not-accessible
    STATUS      current
    DESCRIPTION
        "This is a list of static MAC table."
    ::= { es2126plusMacTableStaticMac 3 }

ES2126PLUSMacTableStaticMacEntry ::=
SEQUENCE {
    es2126plusMacTableStaticMacIndex        INTEGER,
    es2126plusMacTableStaticMacAddress      DisplayString,
    es2126plusMacTableStaticMacVid            INTEGER,
    es2126plusMacTableStaticMacQueue        INTEGER,
    es2126plusMacTableStaticMacFwRule       INTEGER,
    es2126plusMacTableStaticMacPort         INTEGER,
    es2126plusMacTableStaticMacEntryAction  INTEGER
}

es2126plusMacTableStaticMacEntry  OBJECT-TYPE
    SYNTAX      ES2126PLUSMacTableStaticMacEntry
    MAX-ACCESS  not-accessible
    STATUS      current
    DESCRIPTION
        "Entry(s) for Static Mac Table."
    INDEX {es2126plusMacTableStaticMacIndex}
    ::= { es2126plusMacTableStaticMacTable 1 }

es2126plusMacTableStaticMacIndex  OBJECT-TYPE
    SYNTAX      INTEGER(1..1024)
    MAX-ACCESS      not-accessible
    STATUS      current
    DESCRIPTION
        "The index of the static Mac Table."
    ::= { es2126plusMacTableStaticMacEntry 1 }

es2126plusMacTableStaticMacAddress  OBJECT-TYPE
    SYNTAX      DisplayString
    MAX-ACCESS  read-write
    STATUS      current
    DESCRIPTION
        "The mac address of the static mac table entry."
    ::= { es2126plusMacTableStaticMacEntry 2 }

es2126plusMacTableStaticMacVid  OBJECT-TYPE
    SYNTAX      INTEGER(1..4094)
    MAX-ACCESS  read-write
    STATUS      current
    DESCRIPTION
        "The vlan id of the static mac table entry."
    ::= { es2126plusMacTableStaticMacEntry 3 }

es2126plusMacTableStaticMacQueue  OBJECT-TYPE
    SYNTAX      INTEGER(0..3)
    MAX-ACCESS  read-write
    STATUS      current
    DESCRIPTION
        "The queue of the static mac table entry."
    ::= { es2126plusMacTableStaticMacEntry 4 }

es2126plusMacTableStaticMacFwRule  OBJECT-TYPE
    SYNTAX      INTEGER(0..2)
    MAX-ACCESS  read-write
    STATUS      current
    DESCRIPTION
        "The forwarding rule of the static mac table entry.
         0 : static
         1 : Static with Destination Drop
         2 : Static with Source Drop
        "
    ::= { es2126plusMacTableStaticMacEntry 5 }

es2126plusMacTableStaticMacPort  OBJECT-TYPE
    SYNTAX      INTEGER(1..26)
    MAX-ACCESS  read-write
    STATUS      current
    DESCRIPTION
        "The port of the static mac table entry."
    ::= { es2126plusMacTableStaticMacEntry 6 }

es2126plusMacTableStaticMacEntryAction  OBJECT-TYPE
    SYNTAX      INTEGER(1..3)
    MAX-ACCESS  read-write
    STATUS      current
    DESCRIPTION
        "The port of the static mac table entry."
    ::= { es2126plusMacTableStaticMacEntry 7 }

es2126plusMacTableMacAlias       OBJECT IDENTIFIER ::= { es2126plusMacTableInfo 4 }

es2126plusMacTableMacAliasNumber  OBJECT-TYPE
    SYNTAX      INTEGER(0..8192)
    MAX-ACCESS  read-only
    STATUS      current
    DESCRIPTION
        "This is number of static Mac table entry"
    ::= { es2126plusMacTableMacAlias 1 }

es2126plusMacTableMacAliasEntryCreate  OBJECT-TYPE
    SYNTAX      INTEGER(0..8192)
    MAX-ACCESS  read-write
    STATUS      current
    DESCRIPTION
        "Creat a static mac alias entry."
    ::= { es2126plusMacTableMacAlias 2 }

es2126plusMacTableMacAliasTable  OBJECT-TYPE
    SYNTAX      SEQUENCE OF ES2126PLUSMacTableMacAliasEntry
    MAX-ACCESS  not-accessible
    STATUS      current
    DESCRIPTION
        "This is a list of MAC Alias table."
    ::= { es2126plusMacTableMacAlias 3 }

ES2126PLUSMacTableMacAliasEntry ::=
SEQUENCE {
    es2126plusMacTableMacAliasIndex        INTEGER,
    es2126plusMacTableMacAliasAddress      DisplayString,
    es2126plusMacTableMacAliasAlias        DisplayString,
    es2126plusMacTableMacAliasEntryAction  INTEGER
}

es2126plusMacTableMacAliasEntry  OBJECT-TYPE
    SYNTAX      ES2126PLUSMacTableMacAliasEntry
    MAX-ACCESS  not-accessible
    STATUS      current
    DESCRIPTION
        "Entry(s) for Alias Mac Table."
    INDEX {es2126plusMacTableMacAliasIndex}
    ::= { es2126plusMacTableMacAliasTable 1 }

es2126plusMacTableMacAliasIndex  OBJECT-TYPE
    SYNTAX      INTEGER(1..1024)
    MAX-ACCESS      not-accessible
    STATUS      current
    DESCRIPTION
        "The index of the Alias Mac Table."
    ::= { es2126plusMacTableMacAliasEntry 1 }

es2126plusMacTableMacAliasAddress  OBJECT-TYPE
    SYNTAX      DisplayString
    MAX-ACCESS      read-write
    STATUS      current
    DESCRIPTION
        "The Mac address of the Alias Mac Table."
    ::= { es2126plusMacTableMacAliasEntry 2 }

es2126plusMacTableMacAliasAlias  OBJECT-TYPE
    SYNTAX      DisplayString
    MAX-ACCESS      read-write
    STATUS      current
    DESCRIPTION
        "The Mac Alias of the Alias Mac Table."
    ::= { es2126plusMacTableMacAliasEntry 3 }

es2126plusMacTableMacAliasEntryAction  OBJECT-TYPE
    SYNTAX      INTEGER(1..3)
    MAX-ACCESS  read-write
    STATUS      current
    DESCRIPTION
        "The action of the alias mac table entry."
    ::= { es2126plusMacTableMacAliasEntry 4 }

es2126plusGVRPInfo              OBJECT IDENTIFIER ::= { es2126plusProduces 12 }

es2126plusGvrpConf              OBJECT IDENTIFIER ::= { es2126plusGVRPInfo 1 }

es2126plusGvrpConfState OBJECT-TYPE
    SYNTAX      INTEGER(0|1)
    MAX-ACCESS      read-write
    STATUS      current
    DESCRIPTION
        "The state of GVRP.
         0 - Disable
         1 - Enable
    "
    ::= { es2126plusGvrpConf 1 }

es2126plusGvrpConfTable OBJECT-TYPE
    SYNTAX      SEQUENCE OF ES2126PLUSGvrpConfEntry
    MAX-ACCESS  not-accessible
    STATUS      current
    DESCRIPTION
        "This is a list of the GVRP conf table."
    ::= { es2126plusGvrpConf 2 }

ES2126PLUSGvrpConfEntry ::=
SEQUENCE {
    es2126plusGvrpConfIndex             INTEGER,
    es2126plusGvrpConfJoinTime          INTEGER,
    es2126plusGvrpConfLeaveTime         INTEGER,
    es2126plusGvrpConfLeaveAllTime      INTEGER,
    es2126plusGvrpConfDefaultAppMode    INTEGER,
    es2126plusGvrpConfDefaultRegMode    INTEGER,
    es2126plusGvrpConfRestrictedMode    INTEGER
}

es2126plusGvrpConfEntry OBJECT-TYPE
    SYNTAX      ES2126PLUSGvrpConfEntry
    MAX-ACCESS      not-accessible
    STATUS      current
    DESCRIPTION
        "Entry(s) for the GVRP conf table."
    INDEX {es2126plusGvrpConfIndex}
    ::= { es2126plusGvrpConfTable 1 }

es2126plusGvrpConfIndex OBJECT-TYPE
    SYNTAX      INTEGER(1..26)
    MAX-ACCESS      not-accessible
    STATUS      current
    DESCRIPTION
        "The index of the GVRP conf table."
    ::= { es2126plusGvrpConfEntry 1 }

es2126plusGvrpConfJoinTime  OBJECT-TYPE
    SYNTAX      INTEGER(20..100)
    MAX-ACCESS      read-write
    STATUS      current
    DESCRIPTION
        "The join time of the GVRP entry.
         range: 20~100
         default 20 centisecond"
    ::= { es2126plusGvrpConfEntry 2 }

es2126plusGvrpConfLeaveTime OBJECT-TYPE
    SYNTAX      INTEGER(60..300)
    MAX-ACCESS      read-write
    STATUS      current
    DESCRIPTION
        "The leave time of the GVRP entry.
         range: 60~300
        default:60 centisecond"
    ::= { es2126plusGvrpConfEntry 3 }

es2126plusGvrpConfLeaveAllTime  OBJECT-TYPE
    SYNTAX      INTEGER(1000..5000)
    MAX-ACCESS      read-write
    STATUS      current
    DESCRIPTION
        "The leave all time of the GVRP entry.
         range: 1000~5000
         default: 1000 unit time"
    ::= { es2126plusGvrpConfEntry 4 }

es2126plusGvrpConfDefaultAppMode    OBJECT-TYPE
    SYNTAX      INTEGER(0|1)
    MAX-ACCESS      read-write
    STATUS      current
    DESCRIPTION
        "The default application mode of the GVRP entry.
         0 - Normal
         1 - Non-Participant
         default: Normal"
    ::= { es2126plusGvrpConfEntry 5 }

es2126plusGvrpConfDefaultRegMode    OBJECT-TYPE
    SYNTAX      INTEGER(0|1|2)
    MAX-ACCESS      read-write
    STATUS      current
    DESCRIPTION
        "The default registrar mode of the GVRP entry.
         0 - Normal
         1 - Fixed
         2 - Forbidden
         default: Normal"
    ::= { es2126plusGvrpConfEntry 6 }

es2126plusGvrpConfRestrictedMode    OBJECT-TYPE
    SYNTAX      INTEGER(0|1)
    MAX-ACCESS      read-write
    STATUS      current
    DESCRIPTION
        "The restricted mode of the GVRP entry.
         0 - Disable
         1 - Enable
         default: Disable"
    ::= { es2126plusGvrpConfEntry 7 }

es2126plusGvrpCounter               OBJECT IDENTIFIER ::= { es2126plusGVRPInfo 2 }

es2126plusGvrpCounterTable  OBJECT-TYPE
    SYNTAX      SEQUENCE OF ES2126PLUSGvrpCounterEntry
    MAX-ACCESS  not-accessible
    STATUS      current
    DESCRIPTION
        "This is a list of the GVRP counter table."
    ::= { es2126plusGvrpCounter 1 }

ES2126PLUSGvrpCounterEntry ::=
SEQUENCE {
    es2126plusGvrpCounterIndex              INTEGER,
    es2126plusGvrpCounterRxTotalGvrpPkts    Counter32,
    es2126plusGvrpCounterRxInvalidGvrpPkts  Counter32,
    es2126plusGvrpCounterRxLeaveAllMsg      Counter32,
    es2126plusGvrpCounterRxJoinEmptyMsg     Counter32,
    es2126plusGvrpCounterRxJoinInMsg        Counter32,
    es2126plusGvrpCounterRxLeaveEmptyMsg    Counter32,
    es2126plusGvrpCounterRxEmptyMsg         Counter32,
    es2126plusGvrpCounterTxTotalGvrpPkts    Counter32,
    es2126plusGvrpCounterTxLeaveAllMsg      Counter32,
    es2126plusGvrpCounterTxJoinEmptyMsg     Counter32,
    es2126plusGvrpCounterTxJoinInMsg        Counter32,
    es2126plusGvrpCounterTxLeaveEmptyMsg    Counter32,
    es2126plusGvrpCounterTxEmptyMsg         Counter32
}

es2126plusGvrpCounterEntry  OBJECT-TYPE
    SYNTAX      ES2126PLUSGvrpCounterEntry
    MAX-ACCESS      not-accessible
    STATUS      current
    DESCRIPTION
        "Entry(s) for the GVRP counter table."
    INDEX {es2126plusGvrpCounterIndex}
    ::= { es2126plusGvrpCounterTable 1 }

es2126plusGvrpCounterIndex  OBJECT-TYPE
    SYNTAX      INTEGER(1..26)
    MAX-ACCESS      not-accessible
    STATUS      current
    DESCRIPTION
        "The port index of the GVRP counter table."
    ::= { es2126plusGvrpCounterEntry 1 }

es2126plusGvrpCounterRxTotalGvrpPkts    OBJECT-TYPE
    SYNTAX      Counter32
    MAX-ACCESS      read-only
    STATUS      current
    DESCRIPTION
        "This is Rx Total GVRP packet counters."
    ::= { es2126plusGvrpCounterEntry 2 }

es2126plusGvrpCounterRxInvalidGvrpPkts  OBJECT-TYPE
    SYNTAX      Counter32
    MAX-ACCESS      read-only
    STATUS      current
    DESCRIPTION
        "This is Rx Invalid GVRP packet counters."
    ::= { es2126plusGvrpCounterEntry 3 }

es2126plusGvrpCounterRxLeaveAllMsg  OBJECT-TYPE
    SYNTAX      Counter32
    MAX-ACCESS      read-only
    STATUS      current
    DESCRIPTION
        "This is Rx LeaveAll message packet counters."
    ::= { es2126plusGvrpCounterEntry 4 }

es2126plusGvrpCounterRxJoinEmptyMsg OBJECT-TYPE
    SYNTAX      Counter32
    MAX-ACCESS      read-only
    STATUS      current
    DESCRIPTION
        "This is Rx JoinEmpty message packet counters."
    ::= { es2126plusGvrpCounterEntry 5 }

es2126plusGvrpCounterRxJoinInMsg    OBJECT-TYPE
    SYNTAX      Counter32
    MAX-ACCESS      read-only
    STATUS      current
    DESCRIPTION
        "This is Rx JoinIn message packet counters."
    ::= { es2126plusGvrpCounterEntry 6 }

es2126plusGvrpCounterRxLeaveEmptyMsg    OBJECT-TYPE
    SYNTAX      Counter32
    MAX-ACCESS      read-only
    STATUS      current
    DESCRIPTION
        "This is Rx LeaveEmpty message packet counters."
    ::= { es2126plusGvrpCounterEntry 7 }

es2126plusGvrpCounterRxEmptyMsg OBJECT-TYPE
    SYNTAX      Counter32
    MAX-ACCESS      read-only
    STATUS      current
    DESCRIPTION
        "This is Rx Empty message packet counters."
    ::= { es2126plusGvrpCounterEntry 8 }

es2126plusGvrpCounterTxTotalGvrpPkts    OBJECT-TYPE
    SYNTAX      Counter32
    MAX-ACCESS      read-only
    STATUS      current
    DESCRIPTION
        "This is Tx Total GVRP packet counters."
    ::= { es2126plusGvrpCounterEntry 9 }

es2126plusGvrpCounterTxLeaveAllMsg  OBJECT-TYPE
    SYNTAX      Counter32
    MAX-ACCESS      read-only
    STATUS      current
    DESCRIPTION
        "This is Tx LeaveAll message packet counters."
    ::= { es2126plusGvrpCounterEntry 10 }

es2126plusGvrpCounterTxJoinEmptyMsg OBJECT-TYPE
    SYNTAX      Counter32
    MAX-ACCESS      read-only
    STATUS      current
    DESCRIPTION
        "This is Tx JoinEmpty message packet counters."
    ::= { es2126plusGvrpCounterEntry 11 }

es2126plusGvrpCounterTxJoinInMsg    OBJECT-TYPE
    SYNTAX      Counter32
    MAX-ACCESS      read-only
    STATUS      current
    DESCRIPTION
        "This is Tx JoinIn message packet counters."
    ::= { es2126plusGvrpCounterEntry 12 }

es2126plusGvrpCounterTxLeaveEmptyMsg    OBJECT-TYPE
    SYNTAX      Counter32
    MAX-ACCESS      read-only
    STATUS      current
    DESCRIPTION
        "This is Tx LeaveEmpty message packet counters."
    ::= { es2126plusGvrpCounterEntry 13 }

es2126plusGvrpCounterTxEmptyMsg OBJECT-TYPE
    SYNTAX      Counter32
    MAX-ACCESS      read-only
    STATUS      current
    DESCRIPTION
        "This is Tx Empty message packet counters."
    ::= { es2126plusGvrpCounterEntry 14 }

es2126plusGvrpGroup             OBJECT IDENTIFIER ::= { es2126plusGVRPInfo 3 }

es2126plusGvrpGroupNumber   OBJECT-TYPE
    SYNTAX      INTEGER(0..4094)
    MAX-ACCESS      read-only
    STATUS      current
    DESCRIPTION
        "This is number of the GVRP group table entry."
    ::= { es2126plusGvrpGroup 1 }

es2126plusGvrpGroupTable    OBJECT-TYPE
    SYNTAX      SEQUENCE OF ES2126PLUSGvrpGroupEntry
    MAX-ACCESS  not-accessible
    STATUS      current
    DESCRIPTION
        "This is a list of the GVRP group table."
    ::= { es2126plusGvrpGroup 2 }

ES2126PLUSGvrpGroupEntry ::=
SEQUENCE {
    es2126plusGvrpGroupId            INTEGER,
    es2126plusGvrpGroupVid           INTEGER,
    es2126plusGvrpGroupMemberPort    DisplayString
}

es2126plusGvrpGroupEntry    OBJECT-TYPE
    SYNTAX      ES2126PLUSGvrpGroupEntry
    MAX-ACCESS      not-accessible
    STATUS      current
    DESCRIPTION
        "Entry(s) for the GVRP group table."
    INDEX {es2126plusGvrpGroupId}
    ::= { es2126plusGvrpGroupTable 1 }

es2126plusGvrpGroupId   OBJECT-TYPE
    SYNTAX      INTEGER(1..4094)
    MAX-ACCESS      read-only
    STATUS      current
    DESCRIPTION
        "The index of the GVRP group table."
    ::= { es2126plusGvrpGroupEntry 1 }

es2126plusGvrpGroupVid  OBJECT-TYPE
    SYNTAX      INTEGER(1..4094)
    MAX-ACCESS      read-only
    STATUS      current
    DESCRIPTION
        "This is vid of GVRP group."
    ::= { es2126plusGvrpGroupEntry 2 }

es2126plusGvrpGroupMemberPort   OBJECT-TYPE
    SYNTAX      DisplayString
    MAX-ACCESS      read-only
    STATUS      current
    DESCRIPTION
        "This is the member port of GVRP group."
    ::= { es2126plusGvrpGroupEntry 3 }

es2126plusSecurity              OBJECT IDENTIFIER ::= { es2126plusProduces 13 }

es2126plusIsolatedPortGroup OBJECT-TYPE
    SYNTAX      DisplayString
    MAX-ACCESS      read-write
    STATUS      current
    DESCRIPTION
        "This is isolated group.
         0: Disable"
    ::= { es2126plusSecurity 1 }

es2126plusMirror            OBJECT IDENTIFIER ::= { es2126plusSecurity 2 }

es2126plusMirrorMode OBJECT-TYPE
    SYNTAX      INTEGER(0|1)
    MAX-ACCESS      read-write
    STATUS      current
    DESCRIPTION
        "This is mirror mode.
         0 - Disable
         1 - Enable
    "
    ::= { es2126plusMirror 1 }

es2126plusMonitoringPort OBJECT-TYPE
    SYNTAX      INTEGER(1..26)
    MAX-ACCESS      read-write
    STATUS      current
    DESCRIPTION
        "This is monitoring port."
    ::= { es2126plusMirror 2 }

es2126plusMonitoredIngressPort OBJECT-TYPE
    SYNTAX      DisplayString
    MAX-ACCESS      read-write
    STATUS      current
    DESCRIPTION
        "This is monitored ingress ports."
    ::= { es2126plusMirror 3 }

es2126plusMonitoredEgressPort OBJECT-TYPE
    SYNTAX      DisplayString
    MAX-ACCESS      read-write
    STATUS      current
    DESCRIPTION
        "This is monitored egress ports."
    ::= { es2126plusMirror 4 }

es2126plusRestrictedGroup               OBJECT IDENTIFIER ::= { es2126plusSecurity 3 }

es2126plusRestrictedGroupIngress OBJECT-TYPE
    SYNTAX      DisplayString
    MAX-ACCESS      read-write
    STATUS      current
    DESCRIPTION
        "This is the ingress port members of restricted group."
    ::= { es2126plusRestrictedGroup 1 }

es2126plusRestrictedGroupEgress OBJECT-TYPE
    SYNTAX      DisplayString
    MAX-ACCESS      read-write
    STATUS      current
    DESCRIPTION
        "This is the egress port members of restricted group."
    ::= { es2126plusRestrictedGroup 2 }

es2126plusVirtualStack        OBJECT IDENTIFIER ::= { es2126plusProduces 14 }

es2126plusVirtualStackState   OBJECT-TYPE
    SYNTAX      INTEGER(0|1)
    MAX-ACCESS  read-write
    STATUS      current
    DESCRIPTION
        "Set the Virtual Stack State.
         0 : disable,
         1 : enable
        "
    ::= { es2126plusVirtualStack 1 }

es2126plusVirtualStackRole   OBJECT-TYPE
    SYNTAX      INTEGER(0|1)
    MAX-ACCESS  read-write
    STATUS      current
    DESCRIPTION
        "Set the Virtual Stack Role.
         0 : slave,
         1 : master
        "
    ::= { es2126plusVirtualStack 2 }

es2126plusVirtualStackGroupID  OBJECT-TYPE
    SYNTAX      DisplayString
    MAX-ACCESS  read-write
    STATUS      current
    DESCRIPTION
        "Set the Virtual Stack Group ID."
    ::= { es2126plusVirtualStack 3 }

es2126plusManagementSecurity            OBJECT IDENTIFIER ::= { es2126plusProduces 15 }

es2126plusManagementSecurityNumber OBJECT-TYPE
    SYNTAX      INTEGER(0..64)
    MAX-ACCESS      read-only
    STATUS      current
    DESCRIPTION
        "This is number of the management security table entry."
    ::= { es2126plusManagementSecurity 1 }

es2126plusManagementSecurityEntryCreate OBJECT-TYPE
    SYNTAX      INTEGER(0..64)
    MAX-ACCESS      read-write
    STATUS      current
    DESCRIPTION
        "Creat a management security entry."
    ::= { es2126plusManagementSecurity 2 }

es2126plusManagementSecurityTable   OBJECT-TYPE
    SYNTAX      SEQUENCE OF ES2126PLUSManagementSecurityEntry
    MAX-ACCESS  not-accessible
    STATUS      current
    DESCRIPTION
        "This is a list of the management security table."
    ::= { es2126plusManagementSecurity 3 }

ES2126PLUSManagementSecurityEntry ::=
SEQUENCE {
    es2126plusManagementSecurityIndex          INTEGER,
    es2126plusManagementSecurityName           DisplayString,
    es2126plusManagementSecurityVid            INTEGER,
    es2126plusManagementSecurityIpRange        DisplayString,
    es2126plusManagementSecurityIncomigPort    DisplayString,
    es2126plusManagementSecurityAccessType     DisplayString,
    es2126plusManagementSecurityAction         INTEGER,
    es2126plusManagementSecurityEntryAction    INTEGER
}

es2126plusManagementSecurityEntry   OBJECT-TYPE
    SYNTAX      ES2126PLUSManagementSecurityEntry
    MAX-ACCESS      not-accessible
    STATUS      current
    DESCRIPTION
        "Entry(s) for the management security table."
    INDEX {es2126plusManagementSecurityIndex}
    ::= { es2126plusManagementSecurityTable 1 }

es2126plusManagementSecurityIndex   OBJECT-TYPE
    SYNTAX      INTEGER(1..64)
    MAX-ACCESS      not-accessible
    STATUS      current
    DESCRIPTION
        "The index of the management security table."
    ::= { es2126plusManagementSecurityEntry 1 }

es2126plusManagementSecurityName    OBJECT-TYPE
    SYNTAX      DisplayString
    MAX-ACCESS      read-write
    STATUS      current
    DESCRIPTION
        "The name of the management security entry."
    ::= { es2126plusManagementSecurityEntry 2 }

es2126plusManagementSecurityVid OBJECT-TYPE
    SYNTAX      INTEGER(0..4094)
    MAX-ACCESS      read-write
    STATUS      current
    DESCRIPTION
        "This is the vid of the management security entry.
         0: any VID."
    ::= { es2126plusManagementSecurityEntry 3 }

es2126plusManagementSecurityIpRange OBJECT-TYPE
    SYNTAX      DisplayString
    MAX-ACCESS      read-write
    STATUS      current
    DESCRIPTION
        "This is the IP range of the management security entry.
         0: any IP."
    ::= { es2126plusManagementSecurityEntry 4 }

es2126plusManagementSecurityIncomigPort OBJECT-TYPE
    SYNTAX      DisplayString
    MAX-ACCESS      read-write
    STATUS      current
    DESCRIPTION
        "This is the ports of the management security entry.
         0: any incoming port."
    ::= { es2126plusManagementSecurityEntry 5 }

es2126plusManagementSecurityAccessType  OBJECT-TYPE
    SYNTAX      DisplayString
    MAX-ACCESS      read-write
    STATUS      current
    DESCRIPTION
        "This is the access type of the management security entry.
         0: http, telnet, and SNMP."
    ::= { es2126plusManagementSecurityEntry 6 }

es2126plusManagementSecurityAction  OBJECT-TYPE
    SYNTAX      INTEGER(0|1)
    MAX-ACCESS      read-write
    STATUS      current
    DESCRIPTION
        "This is the action of the management security entry.
         0:deny
         1:accept"
    ::= { es2126plusManagementSecurityEntry 7 }

es2126plusManagementSecurityEntryAction OBJECT-TYPE
    SYNTAX      INTEGER(0..3)
    MAX-ACCESS      read-write
    STATUS      current
    DESCRIPTION
        "The action the management security entry."
    ::= { es2126plusManagementSecurityEntry 8 }

es2126plusQoS               OBJECT IDENTIFIER ::= { es2126plusProduces 16 }

es2126plusQoSGlobalConfig               OBJECT IDENTIFIER ::= { es2126plusQoS 1 }

es2126plusQoSMode OBJECT-TYPE
    SYNTAX      INTEGER(0|1)
    MAX-ACCESS      read-write
    STATUS      current
    DESCRIPTION
        "The mode of QoS.
         0 - Disable
         1 - Enable
    "
    ::= { es2126plusQoSGlobalConfig 1 }

es2126plusQosPriorityControl1p OBJECT-TYPE
    SYNTAX      INTEGER(0|1)
    MAX-ACCESS      read-write
    STATUS      current
    DESCRIPTION
        "This is the priority control for 802.1p.
         0 - Disable
         1 - Enable
    "
    ::= { es2126plusQoSGlobalConfig 2 }

es2126plusQosPriorityControlTOS OBJECT-TYPE
    SYNTAX      INTEGER(0|1)
    MAX-ACCESS      read-write
    STATUS      current
    DESCRIPTION
        "This is the priority control for TOS.
         0 - Disable
         1 - Enable
    "
    ::= { es2126plusQoSGlobalConfig 3 }

es2126plusQosPriorityControlDSCP OBJECT-TYPE
    SYNTAX      INTEGER(0|1)
    MAX-ACCESS      read-write
    STATUS      current
    DESCRIPTION
        "This is the priority control for DSCP.
         0 - Disable
         1 - Enable
    "
    ::= { es2126plusQoSGlobalConfig 4 }

es2126plusQoSSchedulingMethod OBJECT-TYPE
    SYNTAX      INTEGER(0|1)
    MAX-ACCESS      read-write
    STATUS      current
    DESCRIPTION
        "This is the scheduling method.
         0 - WRR
         1 - Strict
    "
    ::= { es2126plusQoSGlobalConfig 5 }

es2126plusQoSWeightQ0 OBJECT-TYPE
    SYNTAX      INTEGER(1..55)
    MAX-ACCESS      read-write
    STATUS      current
    DESCRIPTION
        "This is the weigtht of Queue0."
    ::= { es2126plusQoSGlobalConfig 6 }

es2126plusQoSWeightQ1 OBJECT-TYPE
    SYNTAX      INTEGER(1..55)
    MAX-ACCESS      read-write
    STATUS      current
    DESCRIPTION
        "This is the weigtht of Queue1."
    ::= { es2126plusQoSGlobalConfig 7 }

es2126plusQoSWeightQ2 OBJECT-TYPE
    SYNTAX      INTEGER(1..55)
    MAX-ACCESS      read-write
    STATUS      current
    DESCRIPTION
        "This is the weigtht of Queue2."
    ::= { es2126plusQoSGlobalConfig 8 }

es2126plusQoSWeightQ3 OBJECT-TYPE
    SYNTAX      INTEGER(1..55)
    MAX-ACCESS      read-write
    STATUS      current
    DESCRIPTION
        "This is the weigtht of Queue3."
    ::= { es2126plusQoSGlobalConfig 9 }

es2126plusQoSVIPPort OBJECT-TYPE
    SYNTAX      DisplayString
    MAX-ACCESS      read-write
    STATUS      current
    DESCRIPTION
        "This is the VIP group for QoS."
    ::= { es2126plusQoS 2 }

es2126plusQoS1pPriority             OBJECT IDENTIFIER ::= { es2126plusQoS 3 }

es2126plusQoS1pPriorityTable    OBJECT-TYPE
    SYNTAX      SEQUENCE OF ES2126PLUSQoS1pPriorityEntry
    MAX-ACCESS  not-accessible
    STATUS      current
    DESCRIPTION
        "This is a list of the 802.1p."
    ::= { es2126plusQoS1pPriority 1 }

ES2126PLUSQoS1pPriorityEntry ::=
SEQUENCE {
    es2126plusQoS1pPriorityIndex    INTEGER,
    es2126plusQoS1pPriorityValue    INTEGER,
    es2126plusQoS1pPriorityQueue    INTEGER
}

es2126plusQoS1pPriorityEntry    OBJECT-TYPE
    SYNTAX      ES2126PLUSQoS1pPriorityEntry
    MAX-ACCESS      not-accessible
    STATUS      current
    DESCRIPTION
        "Entry(s) for the 802.1p priority table."
    INDEX {es2126plusQoS1pPriorityIndex}
    ::= { es2126plusQoS1pPriorityTable 1 }

es2126plusQoS1pPriorityIndex    OBJECT-TYPE
    SYNTAX      INTEGER(1..8)
    MAX-ACCESS      not-accessible
    STATUS      current
    DESCRIPTION
        "The index of the 802.1p priority table."
    ::= { es2126plusQoS1pPriorityEntry 1 }

es2126plusQoS1pPriorityValue    OBJECT-TYPE
    SYNTAX      INTEGER(0..7)
    MAX-ACCESS      read-only
    STATUS      current
    DESCRIPTION
        "The value of 802.1p priority entry."
    ::= { es2126plusQoS1pPriorityEntry 2 }

es2126plusQoS1pPriorityQueue    OBJECT-TYPE
    SYNTAX      INTEGER(0..3)
    MAX-ACCESS      read-write
    STATUS      current
    DESCRIPTION
        "The queue of 802.1p priority entry."
    ::= { es2126plusQoS1pPriorityEntry 3 }

es2126plusQoSDTypeTOSPriority               OBJECT IDENTIFIER ::= { es2126plusQoS 4 }

es2126plusQoSDTypeTOSPriorityTable  OBJECT-TYPE
    SYNTAX      SEQUENCE OF ES2126PLUSQoSDTypeTOSPriorityEntry
    MAX-ACCESS  not-accessible
    STATUS      current
    DESCRIPTION
        "This is a list of the TOS delay priority mapping entry."
    ::= { es2126plusQoSDTypeTOSPriority 1 }

ES2126PLUSQoSDTypeTOSPriorityEntry ::=
SEQUENCE {
    es2126plusQoSDTypeTOSPriorityIndex    INTEGER,
    es2126plusQoSDTypeTOSPriorityValue    INTEGER,
    es2126plusQoSDTypeTOSPriorityQueue    INTEGER
}

es2126plusQoSDTypeTOSPriorityEntry  OBJECT-TYPE
    SYNTAX      ES2126PLUSQoSDTypeTOSPriorityEntry
    MAX-ACCESS      not-accessible
    STATUS      current
    DESCRIPTION
        "Entry(s) for the ToS delay priority mapping entry."
    INDEX {es2126plusQoSDTypeTOSPriorityIndex}
    ::= { es2126plusQoSDTypeTOSPriorityTable 1 }

es2126plusQoSDTypeTOSPriorityIndex  OBJECT-TYPE
    SYNTAX      INTEGER(1..8)
    MAX-ACCESS      not-accessible
    STATUS      current
    DESCRIPTION
        "The index of the ToS delay priority mapping table."
    ::= { es2126plusQoSDTypeTOSPriorityEntry 1 }

es2126plusQoSDTypeTOSPriorityValue  OBJECT-TYPE
    SYNTAX      INTEGER(0..7)
    MAX-ACCESS      read-only
    STATUS      current
    DESCRIPTION
        "The value of ToS delay priority mapping entry."
    ::= { es2126plusQoSDTypeTOSPriorityEntry 2 }

es2126plusQoSDTypeTOSPriorityQueue  OBJECT-TYPE
    SYNTAX      INTEGER(0..3)
    MAX-ACCESS      read-write
    STATUS      current
    DESCRIPTION
        "The queue of ToS delay priority mapping entry."
    ::= { es2126plusQoSDTypeTOSPriorityEntry 3 }

es2126plusQoSTTypeTOSPriority               OBJECT IDENTIFIER ::= { es2126plusQoS 5 }

es2126plusQoSTTypeTOSPriorityTable  OBJECT-TYPE
    SYNTAX      SEQUENCE OF ES2126PLUSQoSTTypeTOSPriorityEntry
    MAX-ACCESS  not-accessible
    STATUS      current
    DESCRIPTION
        "This is a list of the ToS throughput priority mapping entry."
    ::= { es2126plusQoSTTypeTOSPriority 1 }

ES2126PLUSQoSTTypeTOSPriorityEntry ::=
SEQUENCE {
    es2126plusQoSTTypeTOSPriorityIndex    INTEGER,
    es2126plusQoSTTypeTOSPriorityValue    INTEGER,
    es2126plusQoSTTypeTOSPriorityQueue    INTEGER
}

es2126plusQoSTTypeTOSPriorityEntry  OBJECT-TYPE
    SYNTAX      ES2126PLUSQoSTTypeTOSPriorityEntry
    MAX-ACCESS      not-accessible
    STATUS      current
    DESCRIPTION
        "Entry(s) for the TOS Throughput mapping entry."
    INDEX {es2126plusQoSTTypeTOSPriorityIndex}
    ::= { es2126plusQoSTTypeTOSPriorityTable 1 }

es2126plusQoSTTypeTOSPriorityIndex  OBJECT-TYPE
    SYNTAX      INTEGER(1..8)
    MAX-ACCESS      not-accessible
    STATUS      current
    DESCRIPTION
        "The index of the TOS throughput priority mapping table."
    ::= { es2126plusQoSTTypeTOSPriorityEntry 1 }

es2126plusQoSTTypeTOSPriorityValue  OBJECT-TYPE
    SYNTAX      INTEGER(0..7)
    MAX-ACCESS      read-only
    STATUS      current
    DESCRIPTION
        "The value of TOS throughput priority mapping entry."
    ::= { es2126plusQoSTTypeTOSPriorityEntry 2 }

es2126plusQoSTTypeTOSPriorityQueue  OBJECT-TYPE
    SYNTAX      INTEGER(0..3)
    MAX-ACCESS      read-write
    STATUS      current
    DESCRIPTION
        "The queue of TOS throughput priority mapping entry."
    ::= { es2126plusQoSTTypeTOSPriorityEntry 3 }

es2126plusQoSRTypeTOSPriority               OBJECT IDENTIFIER ::= { es2126plusQoS 6 }

es2126plusQoSRTypeTOSPriorityTable  OBJECT-TYPE
    SYNTAX      SEQUENCE OF ES2126PLUSQoSRTypeTOSPriorityEntry
    MAX-ACCESS  not-accessible
    STATUS      current
    DESCRIPTION
        "This is a list of the ToS reliability priority mapping entry."
    ::= { es2126plusQoSRTypeTOSPriority 1 }

ES2126PLUSQoSRTypeTOSPriorityEntry ::=
SEQUENCE {
    es2126plusQoSRTypeTOSPriorityIndex    INTEGER,
    es2126plusQoSRTypeTOSPriorityValue    INTEGER,
    es2126plusQoSRTypeTOSPriorityQueue    INTEGER
}

es2126plusQoSRTypeTOSPriorityEntry  OBJECT-TYPE
    SYNTAX      ES2126PLUSQoSRTypeTOSPriorityEntry
    MAX-ACCESS      not-accessible
    STATUS      current
    DESCRIPTION
        "Entry(s) for the TOS reliability mapping entry."
    INDEX {es2126plusQoSRTypeTOSPriorityIndex}
    ::= { es2126plusQoSRTypeTOSPriorityTable 1 }

es2126plusQoSRTypeTOSPriorityIndex  OBJECT-TYPE
    SYNTAX      INTEGER(1..8)
    MAX-ACCESS      not-accessible
    STATUS      current
    DESCRIPTION
        "The index of the TOS reliability priority mapping table."
    ::= { es2126plusQoSRTypeTOSPriorityEntry 1 }

es2126plusQoSRTypeTOSPriorityValue  OBJECT-TYPE
    SYNTAX      INTEGER(0..7)
    MAX-ACCESS      read-only
    STATUS      current
    DESCRIPTION
        "The value of TOS reliability priority mapping entry."
    ::= { es2126plusQoSRTypeTOSPriorityEntry 2 }

es2126plusQoSRTypeTOSPriorityQueue  OBJECT-TYPE
    SYNTAX      INTEGER(0..3)
    MAX-ACCESS      read-write
    STATUS      current
    DESCRIPTION
        "The queue of TOS reliability priority mapping entry."
    ::= { es2126plusQoSRTypeTOSPriorityEntry 3 }

es2126plusQoSMTypeTOSPriority               OBJECT IDENTIFIER ::= { es2126plusQoS 7 }

es2126plusQoSMTypeTOSPriorityTable  OBJECT-TYPE
    SYNTAX      SEQUENCE OF ES2126PLUSQoSMTypeTOSPriorityEntry
    MAX-ACCESS  not-accessible
    STATUS      current
    DESCRIPTION
        "This is a list of the ToS monetary cost priority mapping entry."
    ::= { es2126plusQoSMTypeTOSPriority 1 }

ES2126PLUSQoSMTypeTOSPriorityEntry ::=
SEQUENCE {
    es2126plusQoSMTypeTOSPriorityIndex    INTEGER,
    es2126plusQoSMTypeTOSPriorityValue    INTEGER,
    es2126plusQoSMTypeTOSPriorityQueue    INTEGER
}

es2126plusQoSMTypeTOSPriorityEntry  OBJECT-TYPE
    SYNTAX      ES2126PLUSQoSMTypeTOSPriorityEntry
    MAX-ACCESS      not-accessible
    STATUS      current
    DESCRIPTION
        "Entry(s) for the TOS monetary cost mapping entry."
    INDEX {es2126plusQoSMTypeTOSPriorityIndex}
    ::= { es2126plusQoSMTypeTOSPriorityTable 1 }

es2126plusQoSMTypeTOSPriorityIndex  OBJECT-TYPE
    SYNTAX      INTEGER(1..8)
    MAX-ACCESS      not-accessible
    STATUS      current
    DESCRIPTION
        "The index of the TOS monetary cost priority mapping table."
    ::= { es2126plusQoSMTypeTOSPriorityEntry 1 }

es2126plusQoSMTypeTOSPriorityValue  OBJECT-TYPE
    SYNTAX      INTEGER(0..7)
    MAX-ACCESS      read-only
    STATUS      current
    DESCRIPTION
        "The value of TOS monetary cost priority mapping entry."
    ::= { es2126plusQoSMTypeTOSPriorityEntry 2 }

es2126plusQoSMTypeTOSPriorityQueue  OBJECT-TYPE
    SYNTAX      INTEGER(0..3)
    MAX-ACCESS      read-write
    STATUS      current
    DESCRIPTION
        "The queue of TOS monetary cost priority mapping entry."
    ::= { es2126plusQoSMTypeTOSPriorityEntry 3 }

es2126plusQoSDSCPPriority               OBJECT IDENTIFIER ::= { es2126plusQoS 8 }

es2126plusQoSDSCPPriorityTable  OBJECT-TYPE
    SYNTAX      SEQUENCE OF ES2126PLUSQoSDSCPPriorityEntry
    MAX-ACCESS  not-accessible
    STATUS      current
    DESCRIPTION
        "This is a list of the DSCP priority entry."
    ::= { es2126plusQoSDSCPPriority 1 }

ES2126PLUSQoSDSCPPriorityEntry ::=
SEQUENCE {
    es2126plusQoSDSCPPriorityIndex    INTEGER,
    es2126plusQoSDSCPPriorityValue    INTEGER,
    es2126plusQoSDSCPPriorityQueue    INTEGER
}

es2126plusQoSDSCPPriorityEntry  OBJECT-TYPE
    SYNTAX      ES2126PLUSQoSDSCPPriorityEntry
    MAX-ACCESS      not-accessible
    STATUS      current
    DESCRIPTION
        "Entry(s) for the DSCP priority mapping entry."
    INDEX {es2126plusQoSDSCPPriorityIndex}
    ::= { es2126plusQoSDSCPPriorityTable 1 }

es2126plusQoSDSCPPriorityIndex  OBJECT-TYPE
    SYNTAX      INTEGER(1..64)
    MAX-ACCESS      not-accessible
    STATUS      current
    DESCRIPTION
        "The index of the DSCP priority priority mapping table."
    ::= { es2126plusQoSDSCPPriorityEntry 1 }

es2126plusQoSDSCPPriorityValue  OBJECT-TYPE
    SYNTAX      INTEGER(0..63)
    MAX-ACCESS      read-only
    STATUS      current
    DESCRIPTION
        "The value of DSCP priority priority mapping entry."
    ::= { es2126plusQoSDSCPPriorityEntry 2 }

es2126plusQoSDSCPPriorityQueue  OBJECT-TYPE
    SYNTAX      INTEGER(0..3)
    MAX-ACCESS      read-write
    STATUS      current
    DESCRIPTION
        "The queue of DSCP priority priority mapping entry."
    ::= { es2126plusQoSDSCPPriorityEntry 3 }

es2126plusVlan      OBJECT IDENTIFIER ::= { es2126plusProduces 17 }

es2126plusVlanModeConfig      OBJECT IDENTIFIER ::= { es2126plusVlan 1 }

es2126plusVlanMode  OBJECT-TYPE
    SYNTAX      INTEGER(0..2)
    MAX-ACCESS  read-write
    STATUS      current
    DESCRIPTION
        "0:Tag-based, 1:Port-based, 2:Metro mode"
    ::= { es2126plusVlanModeConfig 1 }

es2126plusSymmetricVlan  OBJECT-TYPE
    SYNTAX      INTEGER(0|1)
    MAX-ACCESS  read-write
    STATUS      current
    DESCRIPTION
        "Symmetric VLAN: for tag-based
        0:disable, 1:enable"
    ::= { es2126plusVlanModeConfig 2 }

es2126plusVlanSVL  OBJECT-TYPE
    SYNTAX      INTEGER(0|1)
    MAX-ACCESS  read-write
    STATUS      current
    DESCRIPTION
        "SVL: : for tag-based
        0:disable, 1:enable"
    ::= { es2126plusVlanModeConfig 3 }

es2126plusDoubleTag  OBJECT-TYPE
    SYNTAX      INTEGER(0|1)
    MAX-ACCESS  read-write
    STATUS      current
    DESCRIPTION
        "Double Tag: for tag-based
        0:disable, 1:enable"
    ::= { es2126plusVlanModeConfig 4 }

es2126plusUpLinkPort  OBJECT-TYPE
    SYNTAX      INTEGER(0..2)
    MAX-ACCESS  read-write
    STATUS      current
    DESCRIPTION
        "Up link Port: for Metro mode
        0:Port 25, 1:Port 26, 2:Port 25 & 26"
    ::= { es2126plusVlanModeConfig 5 }

es2126plusTagBasedVlanGroup      OBJECT IDENTIFIER ::= { es2126plusVlan 2 }

es2126plusTagBasedVlanNumbers  OBJECT-TYPE
    SYNTAX      INTEGER(1..4094)
    MAX-ACCESS  read-only
    STATUS      current
    DESCRIPTION
        "Total numbers for tag-based vlan."
    ::= { es2126plusTagBasedVlanGroup 1 }

es2126plusTagBasedCreateStatus  OBJECT-TYPE
    SYNTAX      INTEGER(0..4094)
    MAX-ACCESS  read-write
    STATUS      current
    DESCRIPTION
        "Creat a temp vlan in tag-based vlan table.
         0 : none,
         1~4094 : creat with this vid.
        "
    ::= { es2126plusTagBasedVlanGroup 2 }

es2126plusTagBasedVlanTable  OBJECT-TYPE
    SYNTAX      SEQUENCE OF ES2126PLUSTagBasedVlanEntry
    MAX-ACCESS  not-accessible
    STATUS      current
    DESCRIPTION
        " "
    ::= { es2126plusTagBasedVlanGroup 3 }

ES2126PLUSTagBasedVlanEntry ::=
SEQUENCE {
    es2126plusTagBasedVlanVid               INTEGER,
    es2126plusTagBasedVlanName                  DisplayString,
    es2126plusTagBasedVlanMember                DisplayString,
    es2126plusTagBasedVlanUntag                 DisplayString,
    es2126plusTagBasedVlanRowStatus             INTEGER
}

es2126plusTagBasedVlanEntry OBJECT-TYPE
    SYNTAX      ES2126PLUSTagBasedVlanEntry
    MAX-ACCESS  not-accessible
    STATUS      current
    DESCRIPTION
        "Entry(s) for tag-based vlan table."
    INDEX {es2126plusTagBasedVlanVid}
    ::= { es2126plusTagBasedVlanTable 1 }

es2126plusTagBasedVlanVid  OBJECT-TYPE
    SYNTAX      INTEGER(1..4094)
    MAX-ACCESS  not-accessible
    STATUS      current
    DESCRIPTION
        "The vid of vlan."
    ::= { es2126plusTagBasedVlanEntry 1 }

es2126plusTagBasedVlanName  OBJECT-TYPE
    SYNTAX      DisplayString
    MAX-ACCESS  read-write
    STATUS      current
    DESCRIPTION
        "The name of vlan."
    ::= { es2126plusTagBasedVlanEntry 2 }

es2126plusTagBasedVlanMember  OBJECT-TYPE
    SYNTAX      DisplayString
    MAX-ACCESS  read-write
    STATUS      current
    DESCRIPTION
        "The member of vlan."
    ::= { es2126plusTagBasedVlanEntry 3 }

es2126plusTagBasedVlanUntag  OBJECT-TYPE
    SYNTAX      DisplayString
    MAX-ACCESS  read-write
    STATUS      current
    DESCRIPTION
        "The untag port of vlan."
    ::= { es2126plusTagBasedVlanEntry 4 }

es2126plusTagBasedVlanRowStatus  OBJECT-TYPE
    SYNTAX      INTEGER(1..3)
    MAX-ACCESS  read-write
    STATUS      current
    DESCRIPTION
        "The row status of vlan.
         1 : active,
         2 : not-inService,
         3 : delete
        "
    ::= { es2126plusTagBasedVlanEntry 5 }

es2126plusVlanPvid      OBJECT IDENTIFIER ::= { es2126plusVlan 3 }

es2126plusVlanPvidTable  OBJECT-TYPE
    SYNTAX      SEQUENCE OF ES2126PLUSVlanPvidEntry
    MAX-ACCESS  not-accessible
    STATUS      current
    DESCRIPTION
        " "
    ::= { es2126plusVlanPvid 1 }

ES2126PLUSVlanPvidEntry ::=
SEQUENCE {
    es2126plusVlanPvidPort              INTEGER,
    es2126plusVlanPvidValue             INTEGER,
    es2126plusVlanPvidDefaultPriority           INTEGER,
    es2126plusVlanPvidDropUntag             INTEGER
}

es2126plusVlanPvidEntry OBJECT-TYPE
    SYNTAX      ES2126PLUSVlanPvidEntry
    MAX-ACCESS  not-accessible
    STATUS      current
    DESCRIPTION
        "Entry(s) for Vlan Pvid."
    INDEX {es2126plusVlanPvidPort}
    ::= { es2126plusVlanPvidTable 1 }

es2126plusVlanPvidPort  OBJECT-TYPE
    SYNTAX      INTEGER(1..26)
    MAX-ACCESS  not-accessible
    STATUS      current
    DESCRIPTION
        "The port number of pvid entry."
    ::= { es2126plusVlanPvidEntry 1 }

es2126plusVlanPvidValue  OBJECT-TYPE
    SYNTAX      INTEGER(1..4094)
    MAX-ACCESS  read-write
    STATUS      current
    DESCRIPTION
        "The pvid value of port."
    ::= { es2126plusVlanPvidEntry 2 }

es2126plusVlanPvidDefaultPriority  OBJECT-TYPE
    SYNTAX      INTEGER(0..7)
    MAX-ACCESS  read-write
    STATUS      current
    DESCRIPTION
        "The default priority of port ."
    ::= { es2126plusVlanPvidEntry 3 }

es2126plusVlanPvidDropUntag  OBJECT-TYPE
    SYNTAX      INTEGER(0..7)
    MAX-ACCESS  read-write
    STATUS      current
    DESCRIPTION
        "The drop untag of port ."
    ::= { es2126plusVlanPvidEntry 4 }

es2126plusPortBasedVlanGroup      OBJECT IDENTIFIER ::= { es2126plusVlan 4 }

es2126plusPortBasedVlanNumbers  OBJECT-TYPE
    SYNTAX      INTEGER(1..26)
    MAX-ACCESS  read-only
    STATUS      current
    DESCRIPTION
        "Total numbers for tag-based vlan."
    ::= { es2126plusPortBasedVlanGroup 1 }

es2126plusPortBasedCreateStatus  OBJECT-TYPE
    SYNTAX      INTEGER(0|1)
    MAX-ACCESS  read-write
    STATUS      current
    DESCRIPTION
        "Creat a temp vlan in port-based vlan table.
         0 : none,
         1 : creat a new port-based vlan.
        "
    ::= { es2126plusPortBasedVlanGroup 2 }

es2126plusPortBasedVlanTable  OBJECT-TYPE
    SYNTAX      SEQUENCE OF ES2126PLUSPortBasedVlanEntry
    MAX-ACCESS  not-accessible
    STATUS      current
    DESCRIPTION
        " "
    ::= { es2126plusPortBasedVlanGroup 3 }

ES2126PLUSPortBasedVlanEntry ::=
SEQUENCE {
    es2126plusPortBasedVlanIndex                INTEGER,
    es2126plusPortBasedVlanName                 DisplayString,
    es2126plusPortBasedVlanMember               DisplayString,
    es2126plusPortBasedVlanRowStatus            INTEGER
}

es2126plusPortBasedVlanEntry OBJECT-TYPE
    SYNTAX      ES2126PLUSPortBasedVlanEntry
    MAX-ACCESS  not-accessible
    STATUS      current
    DESCRIPTION
        "Entry(s) for port-based vlan table."
    INDEX {es2126plusPortBasedVlanIndex}
    ::= { es2126plusPortBasedVlanTable 1 }

es2126plusPortBasedVlanIndex  OBJECT-TYPE
    SYNTAX      INTEGER(1..26)
    MAX-ACCESS  not-accessible
    STATUS      current
    DESCRIPTION
        "The index of vlan."
    ::= { es2126plusPortBasedVlanEntry 1 }

es2126plusPortBasedVlanName  OBJECT-TYPE
    SYNTAX      DisplayString
    MAX-ACCESS  read-write
    STATUS      current
    DESCRIPTION
        "The name of vlan."
    ::= { es2126plusPortBasedVlanEntry 2 }

es2126plusPortBasedVlanMember  OBJECT-TYPE
    SYNTAX      DisplayString
    MAX-ACCESS  read-write
    STATUS      current
    DESCRIPTION
        "The member of vlan."
    ::= { es2126plusPortBasedVlanEntry 3 }

es2126plusPortBasedVlanRowStatus  OBJECT-TYPE
    SYNTAX      INTEGER(1..3)
    MAX-ACCESS  read-write
    STATUS      current
    DESCRIPTION
        "The row status of vlan.
         1 : active,
         2 : not-inService,
         3 : delete
        "
    ::= { es2126plusPortBasedVlanEntry 4 }

es2126plusManagementVlan      OBJECT IDENTIFIER ::= { es2126plusVlan 5 }

es2126plusManagementVlanState  OBJECT-TYPE
    SYNTAX      INTEGER(0|1)
    MAX-ACCESS  read-write
    STATUS      current
    DESCRIPTION
        "The stat of management vlan.
         0 : Disable,
         1 : Enable.
        "
    ::= { es2126plusManagementVlan 1 }

es2126plusManagementVlanVid  OBJECT-TYPE
    SYNTAX      INTEGER(1..4094)
    MAX-ACCESS  read-write
    STATUS      current
    DESCRIPTION
        "The vid value of management vlan."
    ::= { es2126plusManagementVlan 2 }

es2126plusDot1X        OBJECT IDENTIFIER ::= { es2126plusProduces 18 }

es2126plusDot1XStateSetting      OBJECT IDENTIFIER ::= { es2126plusDot1X 1 }

es2126plusRadiusServer OBJECT-TYPE
    SYNTAX         IpAddress
    MAX-ACCESS     read-write
    STATUS         current
    DESCRIPTION
        "Set radius server ip"
    ::= { es2126plusDot1XStateSetting 1 }

es2126plusDot1XPort OBJECT-TYPE
    SYNTAX         INTEGER(1..65535)
    MAX-ACCESS     read-write
    STATUS         current
    DESCRIPTION
        "Set 802.1X port number"
    ::= { es2126plusDot1XStateSetting 2 }

es2126plusSecretKey  OBJECT-TYPE
    SYNTAX         DisplayString
    MAX-ACCESS     read-write
    STATUS         current
    DESCRIPTION
        "Set 802.1X secret key"
    ::= { es2126plusDot1XStateSetting 3 }

es2126plusAccountingService  OBJECT-TYPE
    SYNTAX         INTEGER(0|1)
    MAX-ACCESS     read-write
    STATUS         current
    DESCRIPTION
        "Set 802.1X accounting service
         0 : disable
         1 : enable
        "
    ::= { es2126plusDot1XStateSetting 4 }

es2126plusAccountingServer  OBJECT-TYPE
    SYNTAX         IpAddress
    MAX-ACCESS     read-write
    STATUS         current
    DESCRIPTION
        "Set 802.1X accounting server"
    ::= { es2126plusDot1XStateSetting 5 }

es2126plusAccountingPort  OBJECT-TYPE
    SYNTAX         INTEGER(1..65535)
    MAX-ACCESS     read-write
    STATUS         current
    DESCRIPTION
        "Set 802.1X accounting port number"
    ::= { es2126plusDot1XStateSetting 6 }

es2126plusDot1XPortSecurityManagement      OBJECT IDENTIFIER ::= { es2126plusDot1X 2 }

es2126plusDot1XPortSecurityTable  OBJECT-TYPE
    SYNTAX      SEQUENCE OF ES2126PLUSDot1XPortSecurityEntry
    MAX-ACCESS  not-accessible
    STATUS      current
    DESCRIPTION
        "This is a list of the 802.1x port security entry."
    ::= { es2126plusDot1XPortSecurityManagement 1 }

ES2126PLUSDot1XPortSecurityEntry ::=
SEQUENCE {
    es2126plusDot1XPortSecurityPortIndex                INTEGER,
    es2126plusDot1XPortSecurityMode                     INTEGER,
    es2126plusDot1XPortSecurityPortControl              INTEGER,
    es2126plusDot1XPortSecurityReAuthMax                INTEGER,
    es2126plusDot1XPortSecurityTxPeriod                 INTEGER,
    es2126plusDot1XPortSecurityQuietPeriod              INTEGER,
    es2126plusDot1XPortSecurityReAuthEnabled            INTEGER,
    es2126plusDot1XPortSecurityReAuthPeriod             INTEGER,
    es2126plusDot1XPortSecurityMaxRequest               INTEGER,
    es2126plusDot1XPortSecuritySuppTimeout              INTEGER,
    es2126plusDot1XPortSecurityServerTimeout            INTEGER,
    es2126plusDot1XPortSecurityStatus                   DisplayString
}

es2126plusDot1XPortSecurityEntry OBJECT-TYPE
    SYNTAX      ES2126PLUSDot1XPortSecurityEntry
    MAX-ACCESS  not-accessible
    STATUS      current
    DESCRIPTION
        "Entry(s) for 802.1x port security management table."
    INDEX {es2126plusDot1XPortSecurityPortIndex}
    ::= { es2126plusDot1XPortSecurityTable 1 }

es2126plusDot1XPortSecurityPortIndex  OBJECT-TYPE
    SYNTAX      INTEGER(1..26)
    MAX-ACCESS  not-accessible
    STATUS      current
    DESCRIPTION
        "The port index of 802.1x port security."
    ::= { es2126plusDot1XPortSecurityEntry 1 }

es2126plusDot1XPortSecurityMode  OBJECT-TYPE
    SYNTAX      INTEGER(0..2)
    MAX-ACCESS  read-write
    STATUS      current
    DESCRIPTION
        "The mode of 802.1x port security.
         0 : Disable,
         1 : Normal,
         2 : Advanced 802.1X (Dual port no support)
        "
    ::= { es2126plusDot1XPortSecurityEntry 2 }

es2126plusDot1XPortSecurityPortControl  OBJECT-TYPE
    SYNTAX      INTEGER(0..2)
    MAX-ACCESS  read-write
    STATUS      current
    DESCRIPTION
        "The port control of 802.1x port security.
           0 : ForceUnauthorized,
           1 : ForceAuthorized,
           2 : Auto
        "
    ::= { es2126plusDot1XPortSecurityEntry 3 }

es2126plusDot1XPortSecurityReAuthMax  OBJECT-TYPE
    SYNTAX      INTEGER(1..10)
    MAX-ACCESS  read-write
    STATUS      current
    DESCRIPTION
        "The reAuthMax(1~10) of 802.1x port security."
    ::= { es2126plusDot1XPortSecurityEntry 4 }

es2126plusDot1XPortSecurityTxPeriod  OBJECT-TYPE
    SYNTAX      INTEGER(1..65535)
    MAX-ACCESS  read-write
    STATUS      current
    DESCRIPTION
        "The txPeriod(1~65535) of 802.1x port security."
    ::= { es2126plusDot1XPortSecurityEntry 5 }

es2126plusDot1XPortSecurityQuietPeriod  OBJECT-TYPE
    SYNTAX      INTEGER(0..65535)
    MAX-ACCESS  read-write
    STATUS      current
    DESCRIPTION
        "The quiet period(0~65535) of 802.1x port security."
    ::= { es2126plusDot1XPortSecurityEntry 6 }

es2126plusDot1XPortSecurityReAuthEnabled  OBJECT-TYPE
    SYNTAX      INTEGER(0|1)
    MAX-ACCESS  read-write
    STATUS      current
    DESCRIPTION
        "The reAuthEnabled of 802.1x port security.
         0 : off,
         1 : on.
        "
    ::= { es2126plusDot1XPortSecurityEntry 7 }

es2126plusDot1XPortSecurityReAuthPeriod  OBJECT-TYPE
    SYNTAX      INTEGER(1..65535)
    MAX-ACCESS  read-write
    STATUS      current
    DESCRIPTION
        "The reAuthPeriod(1~65535) of 802.1x port security."
    ::= { es2126plusDot1XPortSecurityEntry 8 }

es2126plusDot1XPortSecurityMaxRequest  OBJECT-TYPE
    SYNTAX      INTEGER(1..10)
    MAX-ACCESS  read-write
    STATUS      current
    DESCRIPTION
        "The max.request(1~10) of 802.1x port security."
    ::= { es2126plusDot1XPortSecurityEntry 9 }

es2126plusDot1XPortSecuritySuppTimeout  OBJECT-TYPE
    SYNTAX      INTEGER(1..65535)
    MAX-ACCESS  read-write
    STATUS      current
    DESCRIPTION
        "The suppTimeout(1~65535) of 802.1x port security."
    ::= { es2126plusDot1XPortSecurityEntry 10 }

es2126plusDot1XPortSecurityServerTimeout  OBJECT-TYPE
    SYNTAX      INTEGER(1..65535)
    MAX-ACCESS  read-write
    STATUS      current
    DESCRIPTION
        "The server timeout(1~65535) of 802.1x port security."
    ::= { es2126plusDot1XPortSecurityEntry 11 }

es2126plusDot1XPortSecurityStatus  OBJECT-TYPE
    SYNTAX      DisplayString
    MAX-ACCESS  read-only
    STATUS      current
    DESCRIPTION
        "The status of 802.1x port security."
    ::= { es2126plusDot1XPortSecurityEntry 12 }

es2126plusTrunkInfo       OBJECT IDENTIFIER ::= { es2126plusProduces 19 }

es2126plusTrunkPort      OBJECT IDENTIFIER ::= { es2126plusTrunkInfo 1 }

es2126plusTrunkPortTable  OBJECT-TYPE
    SYNTAX      SEQUENCE OF ES2126PLUSTrunkPortEntry
    MAX-ACCESS  not-accessible
    STATUS      current
    DESCRIPTION
        " "
    ::= { es2126plusTrunkPort 1 }

ES2126PLUSTrunkPortEntry ::=
SEQUENCE {
    es2126plusTrunkPortIndex                INTEGER,
    es2126plusTrunkPortMethod                   INTEGER,
    es2126plusTrunkPortGroup                INTEGER,
    es2126plusTrunkPortActiveLacp               INTEGER,
    es2126plusTrunkPortAggtr                INTEGER,
    es2126plusTrunkPortStatus               INTEGER,
    es2126plusTrunkPortCurrentMode              INTEGER
}

es2126plusTrunkPortEntry OBJECT-TYPE
    SYNTAX      ES2126PLUSTrunkPortEntry
    MAX-ACCESS  not-accessible
    STATUS      current
    DESCRIPTION
        "Entry(s) for trunk table."
    INDEX {es2126plusTrunkPortIndex}
    ::= { es2126plusTrunkPortTable 1 }

es2126plusTrunkPortIndex  OBJECT-TYPE
    SYNTAX      INTEGER(1..26)
    MAX-ACCESS  not-accessible
    STATUS      current
    DESCRIPTION
        "The port index of trunk table."
    ::= { es2126plusTrunkPortEntry 1 }

es2126plusTrunkPortMethod  OBJECT-TYPE
    SYNTAX      INTEGER(0..2)
    MAX-ACCESS  read-write
    STATUS      current
    DESCRIPTION
        "The method of trunk port.
     0 : None,
     1 : LACP,
     2 : Static.
        "
    ::= { es2126plusTrunkPortEntry 2 }

es2126plusTrunkPortGroup  OBJECT-TYPE
    SYNTAX      INTEGER(0..3)
    MAX-ACCESS  read-write
    STATUS      current
    DESCRIPTION
        "The group(0~3) of trunk port."
    ::= { es2126plusTrunkPortEntry 3 }

es2126plusTrunkPortActiveLacp  OBJECT-TYPE
    SYNTAX      INTEGER(0|1)
    MAX-ACCESS  read-write
    STATUS      current
    DESCRIPTION
        "The active lacp mode of trunk port.
     0 : Passive,
     1 : Active.
        "
    ::= { es2126plusTrunkPortEntry 4 }

es2126plusTrunkPortAggtr  OBJECT-TYPE
    SYNTAX      INTEGER(1..26)
    MAX-ACCESS  read-only
    STATUS      current
    DESCRIPTION
        "The Aggtr of trunk port."
    ::= { es2126plusTrunkPortEntry 5 }

es2126plusTrunkPortStatus  OBJECT-TYPE
    SYNTAX      INTEGER(0|1)
    MAX-ACCESS  read-only
    STATUS      current
    DESCRIPTION
        "The status of trunk port.
         0 : None,
         1 : Ready.
        "
    ::= { es2126plusTrunkPortEntry 6 }

es2126plusTrunkPortCurrentMode  OBJECT-TYPE
    SYNTAX      INTEGER(0..2)
    MAX-ACCESS  read-write
    STATUS      current
    DESCRIPTION
        "The current mode of trunk port entry.
     0 : Active mode,
     1 : Edit mode,
     2 : Do edit.
        "
    ::= { es2126plusTrunkPortEntry 7 }

es2126plusAggregatorView      OBJECT IDENTIFIER ::= { es2126plusTrunkInfo 2 }

es2126plusAggregatorViewTable  OBJECT-TYPE
    SYNTAX      SEQUENCE OF ES2126PLUSAggregatorViewEntry
    MAX-ACCESS  not-accessible
    STATUS      current
    DESCRIPTION
        " "
    ::= { es2126plusAggregatorView 1 }

ES2126PLUSAggregatorViewEntry ::=
SEQUENCE {
    es2126plusAggregatorViewIndex               INTEGER,
    es2126plusAggregatorViewMethod              INTEGER,
    es2126plusAggregatorViewMemberPorts             DisplayString,
    es2126plusAggregatorViewReadyPorts          DisplayString
}

es2126plusAggregatorViewEntry OBJECT-TYPE
    SYNTAX      ES2126PLUSAggregatorViewEntry
    MAX-ACCESS  not-accessible
    STATUS      current
    DESCRIPTION
        "Entry(s) for aggregator view table."
    INDEX {es2126plusAggregatorViewIndex}
    ::= { es2126plusAggregatorViewTable 1 }

es2126plusAggregatorViewIndex  OBJECT-TYPE
    SYNTAX      INTEGER(1..26)
    MAX-ACCESS  not-accessible
    STATUS      current
    DESCRIPTION
        "The port index of aggregator view table."
    ::= { es2126plusAggregatorViewEntry 1 }

es2126plusAggregatorViewMethod  OBJECT-TYPE
    SYNTAX      INTEGER(0..2)
    MAX-ACCESS  read-only
    STATUS      current
    DESCRIPTION
        "The method of aggregator view table.
         0 : None,
     1 : LACP,
     2 : Static.
        "
    ::= { es2126plusAggregatorViewEntry 2 }

es2126plusAggregatorViewMemberPorts  OBJECT-TYPE
    SYNTAX      DisplayString
    MAX-ACCESS  read-only
    STATUS      current
    DESCRIPTION
        "The member ports of aggregator view table."
    ::= { es2126plusAggregatorViewEntry 3 }

es2126plusAggregatorViewReadyPorts  OBJECT-TYPE
    SYNTAX      DisplayString
    MAX-ACCESS  read-only
    STATUS      current
    DESCRIPTION
        "The ready ports of aggregator view table."
    ::= { es2126plusAggregatorViewEntry 4 }

es2126plusLacpSystemConfiguration     OBJECT IDENTIFIER ::= { es2126plusTrunkInfo 3 }

es2126plusLacpSystemPriority  OBJECT-TYPE
    SYNTAX      INTEGER(1..65535)
    MAX-ACCESS  read-write
    STATUS      current
    DESCRIPTION
        "The priority of LACP system."
    ::= { es2126plusLacpSystemConfiguration 1 }

es2126plusLacpSystemHashMethod  OBJECT-TYPE
    SYNTAX      INTEGER(0..2)
    MAX-ACCESS  read-write
    STATUS      current
    DESCRIPTION
        "The hash method of LACP system.
         0 : DA and SA
         1 : SA
         2 : DA
        "
    ::= { es2126plusLacpSystemConfiguration 2 }

es2126plusTrapEntry        OBJECT IDENTIFIER ::= { es2126plusProduces 20 }

es2126plusModuleInserted NOTIFICATION-TYPE
    OBJECTS { ifIndex }
    STATUS    current
    DESCRIPTION
        "Send the trap when a module is inserted to the system. The OID value means
         the port number."
    ::= { es2126plusTrapEntry 1 }

es2126plusModuleRemoved NOTIFICATION-TYPE
    OBJECTS { ifIndex }
    STATUS    current
    DESCRIPTION
        "Send the trap when a module is removed from the system. The OID value means
         the port number."
    ::= { es2126plusTrapEntry 2 }

es2126plusDualMediaSwapped NOTIFICATION-TYPE
    OBJECTS { ifIndex }
    STATUS    current
    DESCRIPTION
        "Send the trap when the dual media port changed. The OID value means the port number."
    ::= { es2126plusTrapEntry 3 }

es2126plusLoopDetected NOTIFICATION-TYPE
    OBJECTS { ifIndex }
    STATUS    current
    DESCRIPTION
        "Send the trap when loop condition has been detected. The OID value means the port number."
    ::= { es2126plusTrapEntry 4 }

es2126plusLoginProtected NOTIFICATION-TYPE
    OBJECTS { ifIndex }
    STATUS    current
    DESCRIPTION
        "Send the trap when login protect has been detected."
    ::= { es2126plusTrapEntry 5 }

es2126plusStpStateDisabled NOTIFICATION-TYPE
    STATUS      current
    DESCRIPTION
       "Send the trap when the operational state of STP is from enabled to disabled. "
    ::= { es2126plusTrapEntry 100 }

es2126plusStpStateEnabled NOTIFICATION-TYPE
    STATUS      current
    DESCRIPTION
       "Send the trap when the operational state of STP is from disabled to enabled. "
    ::= { es2126plusTrapEntry 101 }

es2126plusStpTopologyChanged NOTIFICATION-TYPE
    OBJECTS { ifIndex }
    STATUS      current
    DESCRIPTION
       "Send the trap when RSTP determines a port should enter the FORWARDING state
        (a topology change occurs). The OID value is the ifIndex of the port that
        produces the topology change."
    ::= { es2126plusTrapEntry 102 }

es2126plusRmonRisingAlarm NOTIFICATION-TYPE
    STATUS      current
    DESCRIPTION
       "Send the trap when an RMON rising alarm happened. The OID value is the value
        of another OID variable sampled by the RMON Alarm Group that exceeds its
        own RisingThreshold "
    ::= { es2126plusTrapEntry 110 }

es2126plusRmonFallingAlarm NOTIFICATION-TYPE
    STATUS      current
    DESCRIPTION
           "Send the trap when an RMON falling alarm happened. The OID value is the value
        of another OID variable sampled by the RMON Alarm Group that is smaller than its
        own FallingThreshold "
    ::= { es2126plusTrapEntry 111 }

es2126plusLacpStateDisabled NOTIFICATION-TYPE
    OBJECTS {ifIndex, groupId}
    STATUS      current
    DESCRIPTION
       "Send the trap when the operational state of LACP is from enabled to disabled.
        The OID value means the disabled Group ID."
    ::= { es2126plusTrapEntry 120 }

es2126plusLacpStateEnabled NOTIFICATION-TYPE
    OBJECTS {ifIndex, groupId}
    STATUS      current
    DESCRIPTION
       "Send the trap when the operational state of LACP is from disabled to enabled.
        The OID value means the disabled Group ID."
    ::= { es2126plusTrapEntry 121 }

es2126plusLacpPortAdded NOTIFICATION-TYPE
    OBJECTS   { ifIndex, actorkey, partnerkey }
    STATUS      current
    DESCRIPTION
       "Send the trap when the state of port is in 'trunk ready'."
    ::= { es2126plusTrapEntry 123 }

es2126plusLacpPortTrunkFailure NOTIFICATION-TYPE
    OBJECTS   { ifIndex, actorkey, partnerkey}
    STATUS      current
    DESCRIPTION
       "Send the trap when one port is not able to be aggregated
        due to duplex-mode of the port. "
    ::= { es2126plusTrapEntry 124 }

es2126plusGvrpStateDisabled NOTIFICATION-TYPE
    STATUS      current
    DESCRIPTION
       "Send the trap when the operational state of GVRP is from enabled to disabled. "
    ::= { es2126plusTrapEntry 140 }

es2126plusGvrpStateEnabled NOTIFICATION-TYPE
    STATUS      current
    DESCRIPTION
       "Send the trap when the operational state of LACP is from disabled to enabled. "
    ::= { es2126plusTrapEntry 141 }

es2126plusVlanPortBaseEnabled NOTIFICATION-TYPE
    STATUS      current
    DESCRIPTION
       "Send the trap when the operational state of vlan is changed to port-based vlan."
    ::= { es2126plusTrapEntry 151 }

es2126plusVlanTagBaseEnabled NOTIFICATION-TYPE
    STATUS      current
    DESCRIPTION
       "Send the trap when the operational state of vlan is changed to tag-based vlan."
    ::= { es2126plusTrapEntry 152 }

es2126plusVlanMetroBaseEnabled NOTIFICATION-TYPE
    STATUS      current
    DESCRIPTION
       "Send the trap when the operational state of vlan is changed to metro-based vlan."
    ::= { es2126plusTrapEntry 153 }

es2126plusUserLogin NOTIFICATION-TYPE
    OBJECTS   {username}
    STATUS      current
    DESCRIPTION
       "Send the trap when one user logins the system."
    ::= { es2126plusTrapEntry 200 }

es2126plusUserLogout NOTIFICATION-TYPE
    OBJECTS   {username}
    STATUS      current
    DESCRIPTION
       "Send the trap when one user logouts the system."
    ::= { es2126plusTrapEntry 201 }

es2126plusTrapVariable  OBJECT IDENTIFIER ::= { es2126plusProduces 21 }

username OBJECT-TYPE
    SYNTAX      DisplayString
    MAX-ACCESS  read-only
    STATUS      current
    DESCRIPTION
        "System account name."
    ::= { es2126plusTrapVariable 1 }

groupId OBJECT-TYPE
    SYNTAX      INTEGER(1..8)
    MAX-ACCESS  read-only
    STATUS      current
    DESCRIPTION
        "The Trunk group ID of LACP."
    ::= { es2126plusTrapVariable 2 }

actorkey OBJECT-TYPE
    SYNTAX  INTEGER(1..2147483647)
    MAX-ACCESS  read-only
    STATUS      current
    DESCRIPTION
        "The actor key information for LACP."
    ::= { es2126plusTrapVariable 3 }

partnerkey OBJECT-TYPE
    SYNTAX  INTEGER(1..2147483647)
    MAX-ACCESS  read-only
    STATUS      current
    DESCRIPTION
        "The partner key information for LACP."
    ::= { es2126plusTrapVariable 4 }

uplink OBJECT-TYPE
    SYNTAX  DisplayString
    MAX-ACCESS  read-only
    STATUS      current
    DESCRIPTION
        "Uplink port(s) in the metro-mode vlan."
    ::= { es2126plusTrapVariable 5 }

loginProtectInfo OBJECT-TYPE
    SYNTAX  DisplayString
    MAX-ACCESS  read-only
    STATUS      current
    DESCRIPTION
        "Loging protect information."
    ::= { es2126plusTrapVariable 6 }

es2126plusLoginProtect           OBJECT IDENTIFIER ::= { es2126plusProduces 22 }

es2126plusLockTime OBJECT-TYPE
    SYNTAX      INTEGER(0..10)
    MAX-ACCESS      read-write
    STATUS      current
    DESCRIPTION
        "Set the login lock time. Available from 0 to 10 (minutes)
         Set 0 as disabled.
        "
    ::= { es2126plusLoginProtect 1 }

es2126plusErrorCount OBJECT-TYPE
    SYNTAX      INTEGER(0..10)
    MAX-ACCESS      read-write
    STATUS      current
    DESCRIPTION
        "Set login error count. Available from 0 to 10 (times)
         Set 0 as disabled.
        "
    ::= { es2126plusLoginProtect 2 }


END

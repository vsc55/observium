LANCOM-ES-2126PPLUS-MIB DEFINITIONS ::= BEGIN

IMPORTS
    DisplayString FROM SNMPv2-TC
    MODULE-COMPLIANCE,OBJECT-GROUP, NOTIFICATION-GROUP       FROM SNMPv2-CONF
    enterprises,MODULE-IDENTITY,OBJECT-TYPE,NOTIFICATION-TYPE,Counter32,IpAddress        FROM SNMPv2-SMI
    MacAddress FROM BRIDGE-MIB
    ifIndex    FROM RFC1213-MIB;

-- @ENTERPRISE-SECTION-START
lancomSystems MODULE-IDENTITY
    LAST-UPDATED "200806030000Z"
        ORGANIZATION "LANCOM Systems GmbH"
        CONTACT-INFO
            "Adenauerstrasse 20 / B2, 52146 Wuerselen, Germany
                 Email: info@lancom.de
                 TEL: +49 (0)2405 49936 0
                 FAX: +49 (0)2405 49936 99"
        DESCRIPTION
                "The MIB module is for LANCOM Systems"
        ::= { enterprises 2356 }

switchingSystems               OBJECT IDENTIFIER ::= { lancomSystems 800 }

fastEthernetSwitches            OBJECT IDENTIFIER ::= { switchingSystems 2 }

lancomES2126P           OBJECT IDENTIFIER ::= { fastEthernetSwitches 2129 }

-- @ENTERPRISE-SECTION-END
es2126PoEplusProduces            OBJECT IDENTIFIER ::= { lancomES2126P 1 }

es2126PoEplusSystem               OBJECT IDENTIFIER ::= { es2126PoEplusProduces 1 }

es2126PoEplusCommonSys            OBJECT IDENTIFIER ::= { es2126PoEplusSystem 1 }

es2126PoEplusReboot OBJECT-TYPE
    SYNTAX      INTEGER(0|1|2)
    MAX-ACCESS      read-write
    STATUS      current
    DESCRIPTION
        "Reboot the system. Get this OID always return zero.
            0 - do nothing
            1 - Reboot without saving start
            2 - Reboot with saving start"
    ::= { es2126PoEplusCommonSys 1 }

es2126PoEplusBiosVsersion OBJECT-TYPE
    SYNTAX      DisplayString
    MAX-ACCESS      read-only
    STATUS      current
    DESCRIPTION
        "Get the BIOS version of the system."
    ::= { es2126PoEplusCommonSys 2 }

es2126PoEplusFirmwareVersion  OBJECT-TYPE
    SYNTAX      DisplayString
    MAX-ACCESS      read-only
    STATUS      current
    DESCRIPTION
        "Get the firmware version of the system."
    ::= { es2126PoEplusCommonSys 3 }

es2126PoEplusHardwareVersion  OBJECT-TYPE
    SYNTAX      DisplayString
    MAX-ACCESS      read-only
    STATUS      current
    DESCRIPTION
        "Get the hardware version of the system."
    ::= { es2126PoEplusCommonSys 4 }

es2126PoEplusMechanicalVersion OBJECT-TYPE
    SYNTAX      DisplayString
    MAX-ACCESS      read-only
    STATUS      current
    DESCRIPTION
        "Get the mechanical version of the system."
    ::= { es2126PoEplusCommonSys 5 }

es2126PoEplusSerialNumber OBJECT-TYPE
    SYNTAX      DisplayString
    MAX-ACCESS      read-only
    STATUS      current
    DESCRIPTION
        "Get the Serial number of the system."
    ::= { es2126PoEplusCommonSys 6 }

es2126PoEplusHostMacAddress   OBJECT-TYPE
    SYNTAX      DisplayString
    MAX-ACCESS      read-only
    STATUS      current
    DESCRIPTION
        "Get the MAC address of the system."
    ::= { es2126PoEplusCommonSys 7 }

es2126PoEplusDevicePort   OBJECT-TYPE
    SYNTAX      DisplayString
    MAX-ACCESS      read-only
    STATUS      current
    DESCRIPTION
        "Get the quantity of ports that this system owns now."
    ::= { es2126PoEplusCommonSys 8 }

es2126PoEplusRamSize  OBJECT-TYPE
    SYNTAX      DisplayString
    MAX-ACCESS      read-only
    STATUS      current
    DESCRIPTION
        "Get the RAM size of the system."
    ::= { es2126PoEplusCommonSys 9 }

es2126PoEplusFlashSize  OBJECT-TYPE
    SYNTAX      DisplayString
    MAX-ACCESS      read-only
    STATUS      current
    DESCRIPTION
        "Get the flash size of the system."
    ::= { es2126PoEplusCommonSys 10 }

es2126PoEplusSystemDescription  OBJECT-TYPE
    SYNTAX      DisplayString
    MAX-ACCESS      read-only
    STATUS      current
    DESCRIPTION
        "Get the system description."
    ::= { es2126PoEplusCommonSys 11 }

es2126PoEplusDeviceName  OBJECT-TYPE
    SYNTAX      DisplayString
    MAX-ACCESS      read-write
    STATUS      current
    DESCRIPTION
        "Get/Set the device Name."
    ::= { es2126PoEplusCommonSys 12 }

es2126PoEplusIP               OBJECT IDENTIFIER ::= { es2126PoEplusSystem 2 }

es2126PoEplusDhcpSetting OBJECT-TYPE
    SYNTAX          INTEGER(0|1)
    MAX-ACCESS          read-write
    STATUS          current
    DESCRIPTION
        "Get/Set DHCP status of the system.
            0 - DHCP disable
            1 - DHCP enable"
    ::= { es2126PoEplusIP 1 }

es2126PoEplusIPAddress OBJECT-TYPE
    SYNTAX      IpAddress
    MAX-ACCESS      read-write
    STATUS      current
    DESCRIPTION
        "Get/Set the IP address of the system.
         You can't set this OID if DHCP status is enabled."
    ::= { es2126PoEplusIP 2 }

es2126PoEplusNetMask OBJECT-TYPE
    SYNTAX      IpAddress
    MAX-ACCESS      read-write
    STATUS      current
    DESCRIPTION
        "Get/Set the subnet mask of the system.
         You can't set this OID if DHCP status is enabled."
    ::= { es2126PoEplusIP 3 }

es2126PoEplusDefaultGateway OBJECT-TYPE
    SYNTAX      IpAddress
    MAX-ACCESS      read-write
    STATUS      current
    DESCRIPTION
        "Get/Set the default gateway of the system.
         You can't set this OID if DHCP status is enabled."
    ::= { es2126PoEplusIP 4 }

es2126PoEplusDnsSetting OBJECT-TYPE
    SYNTAX      INTEGER(0|1)
    MAX-ACCESS      read-write
    STATUS      current
    DESCRIPTION
        "Get/Set the source of DNS server.
         You can't set this OID if DHCP status is disabled.
            0 - manual, the DNS server is from manual setting
            1 - Auto, the DNS server is assigned by DHCP server."
    ::= { es2126PoEplusIP 5 }

es2126PoEplusDnsServer OBJECT-TYPE
    SYNTAX      IpAddress
    MAX-ACCESS      read-write
    STATUS      current
    DESCRIPTION
        "Get/Set the DNS server of the system."
    ::= { es2126PoEplusIP 6 }

es2126PoEplusTime             OBJECT IDENTIFIER ::= { es2126PoEplusSystem 3 }

es2126PoEplusSystemCurrentTime OBJECT-TYPE
    SYNTAX      DisplayString
    MAX-ACCESS      read-only
    STATUS      current
    DESCRIPTION
        "Get the current time of the system."
    ::= { es2126PoEplusTime 1 }

es2126PoEplusManualTimeSetting OBJECT-TYPE
    SYNTAX      DisplayString
    MAX-ACCESS      read-write
    STATUS      current
    DESCRIPTION
        "Get/Set the system time of the device.
        The input format is 'Year/Month/Day/Hour/Minute/Second'.
        Ex: 2004/1/1/12/34/25 means 2004/1/1 - 12:24:25.
        Value range:
        Year    : 2000 - 2036,
        Mouth   : 1 - 12,
        Day     : 1 - 31,
        Hour    : 0 - 23,
        Minute  : 0 - 59,
        Sec     : 0 - 59."
    ::= { es2126PoEplusTime 2 }

es2126PoEplusNTPServer OBJECT-TYPE
    SYNTAX      DisplayString
    MAX-ACCESS      read-write
    STATUS      current
    DESCRIPTION
        "Get/Set the NTP Time Server. You can use the IP address or domain name."
    ::= { es2126PoEplusTime 3 }

es2126PoEplusNTPTimeZone OBJECT-TYPE
    SYNTAX      INTEGER(-12..13)
    MAX-ACCESS      read-write
    STATUS      current
    DESCRIPTION
        "Get/Set the NTP Time Zone.
        Value range is between -12 and 13
        -12 - GMT -12:00,
        -11 - GMT -11:00,
        -10 - GMT -10:00,
         -9 - GMT -09:00,
         -8 - GMT -08:00,
         -7 - GMT -07:00,
         -6 - GMT -06:00,
         -5 - GMT -05:00,
         -4 - GMT -04:00,
         -3 - GMT -03:00,
         -2 - GMT -02:00,
         -1 - GMT -01:00,
          0 - GMT +00:00,
          1 - GMT +01:00,
          2 - GMT +02:00,
          3 - GMT +03:00,
          4 - GMT +04:00,
          5 - GMT +05:00,
          6 - GMT +06:00,
          7 - GMT +07:00,
          8 - GMT +08:00,
          9 - GMT +09:00,
         10 - GMT +10:00,
         11 - GMT +11:00,
         12 - GMT +12:00,
         13 - GMT +13:00. "
    ::= { es2126PoEplusTime 4 }

es2126PoEplusNTPTimeSync OBJECT-TYPE
    SYNTAX      INTEGER(0|1)
    MAX-ACCESS      read-write
    STATUS      current
    DESCRIPTION
        "Sync time from NTP Server. Get this OID always return zero.
        Set the Time Server and Time Zone before doing time sync.
        Notice that time server must be correct!
        Value range (1|0):
        1 - Sync.
        0 - do nothing."
    ::= { es2126PoEplusTime 5 }

es2126PoEplusDaylightSavingTime OBJECT-TYPE
    SYNTAX      INTEGER(-5..5)
    MAX-ACCESS      read-write
    STATUS      current
    DESCRIPTION
        "Get/Set the daylight saving time.
        Value range is between -5 and 5. Unit: hour. "
    ::= { es2126PoEplusTime 6 }

es2126PoEplusDaylightStartTime OBJECT-TYPE
    SYNTAX      DisplayString
    MAX-ACCESS      read-write
    STATUS      current
    DESCRIPTION
        "Get/Set the Start time of Daylight Saving.
        The input format is 'MM/DD/HH',
        and daylight saving start month can't equal end month.
        Example: month/day/hour   10/01/00
        Month: 01~12, day: 01~31, hour: 00~23."
    ::= { es2126PoEplusTime 7 }

es2126PoEplusDaylightEndTime OBJECT-TYPE
    SYNTAX      DisplayString
    MAX-ACCESS      read-write
    STATUS      current
    DESCRIPTION
        "Get/Set the End time of Daylight Saving.
        The input format is 'MM/DD/HH',
        and daylight saving start month can't equal end month.
        Example: month/day/hour   04/01/00
        Month: 01~12, day: 01~31, hour: 00~23."
    ::= { es2126PoEplusTime 8 }

es2126PoEplusAccount              OBJECT IDENTIFIER ::= { es2126PoEplusSystem 4 }

es2126PoEplusAccountNumber OBJECT-TYPE
    SYNTAX      INTEGER(1..5)
    MAX-ACCESS      read-only
    STATUS      current
    DESCRIPTION
        "Get the current account number(s) of the system."
    ::= { es2126PoEplusAccount 1 }

es2126PoEplusAccountTable OBJECT-TYPE
    SYNTAX      SEQUENCE OF ES2126POEPLUSAccountEntry
    MAX-ACCESS  not-accessible
    STATUS      current
    DESCRIPTION
        "This is a list of es2126PoEplusAccountEntry. The numbers of entries are given by
        the value of es2126PoEplusAccountNumber."
    ::= { es2126PoEplusAccount 2 }

es2126PoEplusAccountEntry OBJECT-TYPE
    SYNTAX      ES2126POEPLUSAccountEntry
    MAX-ACCESS      not-accessible
    STATUS      current
    DESCRIPTION
        "This is the Entry(s) for account information."
    INDEX {es2126PoEplusAccountIndex}
    ::= { es2126PoEplusAccountTable 1 }

ES2126POEPLUSAccountEntry ::=
SEQUENCE {
    es2126PoEplusAccountIndex         INTEGER,
    es2126PoEplusAccountAuthorization DisplayString,
    es2126PoEplusAccountName             DisplayString,
    es2126PoEplusAccountPassword         DisplayString
}

es2126PoEplusAccountIndex OBJECT-TYPE
    SYNTAX      INTEGER(1..5)
    MAX-ACCESS      read-only
    STATUS      current
    DESCRIPTION
        "This is the index of the account entry."
    ::= { es2126PoEplusAccountEntry 1 }

es2126PoEplusAccountAuthorization OBJECT-TYPE
    SYNTAX      DisplayString
    MAX-ACCESS      read-only
    STATUS      current
    DESCRIPTION
        "This is the authorization of the account entry."
    ::= { es2126PoEplusAccountEntry 2 }

es2126PoEplusAccountName  OBJECT-TYPE
    SYNTAX      DisplayString
    MAX-ACCESS      read-write
    STATUS      current
    DESCRIPTION
        "This is the username of the account entry."
    ::= { es2126PoEplusAccountEntry 3 }

es2126PoEplusAccountPassword  OBJECT-TYPE
    SYNTAX      DisplayString
    MAX-ACCESS      read-write
    STATUS      current
    DESCRIPTION
        "This is the password of the account entry. The return value is always '********'."
    ::= { es2126PoEplusAccountEntry 4 }

es2126PoEplusAccountAddName OBJECT-TYPE
    SYNTAX      DisplayString
    MAX-ACCESS      read-write
    STATUS      current
    DESCRIPTION
        "This is the account name for adding operation."
    ::= { es2126PoEplusAccount 3 }

es2126PoEplusAccountAddPassword OBJECT-TYPE
    SYNTAX      DisplayString
    MAX-ACCESS      read-write
    STATUS      current
    DESCRIPTION
        "This is the account password for adding operation. The return value is always '********'."
    ::= { es2126PoEplusAccount 4 }

es2126PoEplusDoAccountAdd OBJECT-TYPE
    SYNTAX      INTEGER(0|1)
    MAX-ACCESS      read-write
    STATUS      current
    DESCRIPTION
        "Add account name. OID es2126PoEplusAccountAddName and es2126PoEplusAccountAddPassword must be
        filled first. Get this OID always return zero.
            1 - Add account.
            0 - do nothing."
    ::= { es2126PoEplusAccount 5 }

es2126PoEplusAccountDel   OBJECT-TYPE
    SYNTAX      INTEGER(2..5)
    MAX-ACCESS      read-write
    STATUS      current
    DESCRIPTION
        "Delete account. The value is valid es2126PoEplusAccountIndex(Can't delete administrator)."
    ::= { es2126PoEplusAccount 6 }

es2126PoEplusSnmp             OBJECT IDENTIFIER ::= { es2126PoEplusProduces 2 }

es2126PoEplusGetCommunity OBJECT-TYPE
    SYNTAX      DisplayString
    MAX-ACCESS      read-write
    STATUS      current
    DESCRIPTION
        "Get/Set the get-community of the SNMP."
    ::= { es2126PoEplusSnmp 1 }

es2126PoEplusSetCommunity OBJECT-TYPE
    SYNTAX      DisplayString
    MAX-ACCESS      read-write
    STATUS      current
    DESCRIPTION
        "Get/Set the set-community of the SNMP."
    ::= { es2126PoEplusSnmp 2 }

es2126PoEplusTrapHostNumber OBJECT-TYPE
    SYNTAX      INTEGER(1..6)
    MAX-ACCESS      read-only
    STATUS      current
    DESCRIPTION
        "Get the number of trap hosts."
    ::= { es2126PoEplusSnmp 3 }

es2126PoEplusTrapHostTable    OBJECT-TYPE
    SYNTAX      SEQUENCE OF ES2126POEPLUSTrapHostEntry
    MAX-ACCESS  not-accessible
    STATUS      current
    DESCRIPTION
        "This is a list of trap host entry. The numbers of entries are given by the value of es2126PoEplusTrapHostNumber."
    ::= { es2126PoEplusSnmp 4 }

es2126PoEplusTrapHostEntry    OBJECT-TYPE
    SYNTAX      ES2126POEPLUSTrapHostEntry
    MAX-ACCESS      not-accessible
    STATUS      current
    DESCRIPTION
        "This is the Entry Information for trap host."
    INDEX {es2126PoEplusTrapHostIndex}
    ::= { es2126PoEplusTrapHostTable 1 }

ES2126POEPLUSTrapHostEntry ::=
SEQUENCE {
    es2126PoEplusTrapHostIndex            INTEGER,
    es2126PoEplusTrapHostIP           IpAddress,
    es2126PoEplusTrapHostPort            INTEGER,
    es2126PoEplusTrapHostCommunity       DisplayString
}

es2126PoEplusTrapHostIndex    OBJECT-TYPE
    SYNTAX      INTEGER(1..6)
    MAX-ACCESS      read-only
    STATUS      current
    DESCRIPTION
        "The index of the trap host entry."
    ::= { es2126PoEplusTrapHostEntry 1 }

es2126PoEplusTrapHostIP   OBJECT-TYPE
    SYNTAX      IpAddress
    MAX-ACCESS      read-write
    STATUS      current
    DESCRIPTION
        "This is the IP of the trap host."
    ::= { es2126PoEplusTrapHostEntry 2 }


es2126PoEplusTrapHostPort OBJECT-TYPE
    SYNTAX      INTEGER(1..65535)
    MAX-ACCESS      read-write
    STATUS      current
    DESCRIPTION
        "This is the receiving-port number of the trap host."
    ::= { es2126PoEplusTrapHostEntry 3 }


es2126PoEplusTrapHostCommunity    OBJECT-TYPE
    SYNTAX      DisplayString
    MAX-ACCESS      read-write
    STATUS      current
    DESCRIPTION
        "The community name for the trap PDU."
    ::= { es2126PoEplusTrapHostEntry 4 }

es2126PoEplusRegisterMonitor OBJECT-TYPE
                SYNTAX DisplayString
                MAX-ACCESS read-write
                STATUS current
                DESCRIPTION "Register-Monitor"
                ::= {  es2126PoEplusSnmp 5 }

es2126PoEplusDeleteMonitor OBJECT-TYPE
               SYNTAX DisplayString
               MAX-ACCESS read-write
               STATUS current
               DESCRIPTION "Delete-Monitor"
               ::= {  es2126PoEplusSnmp 6 }

es2126PoEplusMonitorTable OBJECT-TYPE
                    SYNTAX SEQUENCE OF ES2126POEPLUSMonitorEntry
                    MAX-ACCESS not-accessible
                    STATUS current
                    DESCRIPTION "Monitor-Table"
                    ::= {  es2126PoEplusSnmp 7 }

ES2126POEPLUSMonitorEntry ::= SEQUENCE {
                    es2126PoEplusMonitorTableIp IpAddress,
                    es2126PoEplusMonitorTableMac DisplayString
                   }

es2126PoEplusMonitorEntry OBJECT-TYPE
                    SYNTAX ES2126POEPLUSMonitorEntry
                    MAX-ACCESS not-accessible
                    STATUS current
                    DESCRIPTION "entry in table"
                    INDEX { es2126PoEplusMonitorTableIp }
                    ::= {  es2126PoEplusMonitorTable 1 }

es2126PoEplusMonitorTableIp OBJECT-TYPE
                  SYNTAX IpAddress
                  MAX-ACCESS read-only
                  STATUS current
                  DESCRIPTION "IP-Address"
                  ::= {  es2126PoEplusMonitorEntry 1 }

es2126PoEplusMonitorTableMac OBJECT-TYPE
                  SYNTAX DisplayString
                  MAX-ACCESS read-only
                  STATUS current
                  DESCRIPTION "MAC-Address"
                  ::= {  es2126PoEplusMonitorEntry 2 }

es2126PoEplusTrapBootDelayTime OBJECT-TYPE
    SYNTAX      INTEGER(0..120)
    MAX-ACCESS      read-write
    STATUS      current
    DESCRIPTION
        "Get/Set trap boot delay time in second. Default: 0"
    ::= { es2126PoEplusSnmp 8 }

es2126PoEplusAlarm            OBJECT IDENTIFIER ::= { es2126PoEplusProduces 3 }

es2126PoEplusEvent            OBJECT IDENTIFIER ::= { es2126PoEplusAlarm 1 }

es2126PoEplusEventNumber OBJECT-TYPE
    SYNTAX      INTEGER(1..2147483647)
    MAX-ACCESS      read-only
    STATUS      current
    DESCRIPTION
        "Get the total number of alarm events."
    ::= { es2126PoEplusEvent 1 }

es2126PoEplusEventTable   OBJECT-TYPE
    SYNTAX      SEQUENCE OF ES2126POEPLUSEventEntry
    MAX-ACCESS  not-accessible
    STATUS      current
    DESCRIPTION
        "This is a list of alarm event entry. The numbers of entries are given by the value of es2126PoEplusEventNumber."
    ::= { es2126PoEplusEvent 2 }

es2126PoEplusEventEntry   OBJECT-TYPE
    SYNTAX      ES2126POEPLUSEventEntry
    MAX-ACCESS      not-accessible
    STATUS      current
    DESCRIPTION
        "This is the entry information for alarm event."
    INDEX {es2126PoEplusEventIndex}
    ::= { es2126PoEplusEventTable 1 }

ES2126POEPLUSEventEntry ::=
SEQUENCE {
    es2126PoEplusEventIndex           INTEGER,
    es2126PoEplusEventName            DisplayString,
    es2126PoEplusEventSendEmail      INTEGER,
    es2126PoEplusEventSendTrap       INTEGER
}

es2126PoEplusEventIndex   OBJECT-TYPE
    SYNTAX      INTEGER(1..2147483647)
    MAX-ACCESS      read-only
    STATUS      current
    DESCRIPTION
        "This is the index of the alarm event entry."
    ::= { es2126PoEplusEventEntry 1 }

es2126PoEplusEventName    OBJECT-TYPE
    SYNTAX      DisplayString
    MAX-ACCESS      read-only
    STATUS      current
    DESCRIPTION
        "This is the alarm event name."
    ::= { es2126PoEplusEventEntry 2 }

es2126PoEplusEventSendEmail   OBJECT-TYPE
    SYNTAX      INTEGER(0|1)
    MAX-ACCESS      read-write
    STATUS      current
    DESCRIPTION
        "Send email when alarm event is triggered."
    ::= { es2126PoEplusEventEntry 3 }

es2126PoEplusEventSendTrap    OBJECT-TYPE
    SYNTAX      INTEGER(0|1)
    MAX-ACCESS      read-write
    STATUS      current
    DESCRIPTION
        "Send trap when alarm event is triggered."
    ::= { es2126PoEplusEventEntry 4 }


es2126PoEplusEmail            OBJECT IDENTIFIER ::= { es2126PoEplusAlarm 2 }

es2126PoEplusEmailServer OBJECT-TYPE
    SYNTAX      DisplayString
    MAX-ACCESS      read-write
    STATUS      current
    DESCRIPTION
        "This is the SMTP server for alarm event."
    ::= { es2126PoEplusEmail 1 }

es2126PoEplusEmailUsername OBJECT-TYPE
    SYNTAX      DisplayString
    MAX-ACCESS      read-write
    STATUS      current
    DESCRIPTION
        "This is the Username of SMTP server."
    ::= { es2126PoEplusEmail 2 }

es2126PoEplusEmailPassword OBJECT-TYPE
    SYNTAX      DisplayString
    MAX-ACCESS      read-write
    STATUS      current
    DESCRIPTION
        "This is the User Password of SMTP server."
    ::= { es2126PoEplusEmail 3 }

es2126PoEplusEmailSender OBJECT-TYPE
	SYNTAX      DisplayString
	MAX-ACCESS	    read-write
	STATUS		current
	DESCRIPTION
		"This is the Sender of SMTP server."
	::= { es2126PoEplusEmail 4 }

es2126PoEplusEmailReturnPath OBJECT-TYPE
	SYNTAX      DisplayString
	MAX-ACCESS	    read-write
	STATUS		current
	DESCRIPTION
		"This is the return path of mail."
	::= { es2126PoEplusEmail 5 }

es2126PoEplusEmailUserNumber OBJECT-TYPE
    SYNTAX      INTEGER(1..6)
    MAX-ACCESS      read-only
    STATUS      current
    DESCRIPTION
        "The number of the email users that you want to send the alarm notification."
    ::= { es2126PoEplusEmail 6 }

es2126PoEplusEmailUserTable   OBJECT-TYPE
    SYNTAX      SEQUENCE OF ES2126POEPLUSEmailUserEntry
    MAX-ACCESS  not-accessible
    STATUS      current
    DESCRIPTION
        "This is a list of email user entry. The numbers of entries are given by the value of es2126PoEplusEmailUserNumber."
    ::= { es2126PoEplusEmail 7 }

es2126PoEplusEmailUserEntry   OBJECT-TYPE
    SYNTAX      ES2126POEPLUSEmailUserEntry
    MAX-ACCESS      not-accessible
    STATUS      current
    DESCRIPTION
        "This is the Entry information for email user entry."
    INDEX {es2126PoEplusEmailUserIndex}
    ::= { es2126PoEplusEmailUserTable 1 }

ES2126POEPLUSEmailUserEntry ::=
SEQUENCE {
    es2126PoEplusEmailUserIndex           INTEGER,
    es2126PoEplusEmailUserAddress         DisplayString
}

es2126PoEplusEmailUserIndex   OBJECT-TYPE
    SYNTAX      INTEGER(1..6)
    MAX-ACCESS      read-only
    STATUS      current
    DESCRIPTION
        "This is the index of the email user entry."
    ::= { es2126PoEplusEmailUserEntry 1 }

es2126PoEplusEmailUserAddress OBJECT-TYPE
    SYNTAX      DisplayString
    MAX-ACCESS      read-write
    STATUS      current
    DESCRIPTION
        "This is the email address of the email user entry."
    ::= { es2126PoEplusEmailUserEntry 2 }

es2126PoEplusTftp             OBJECT IDENTIFIER ::= { es2126PoEplusProduces 4 }

es2126PoEplusRemoteTftpServer OBJECT-TYPE
    SYNTAX      IpAddress
    MAX-ACCESS      read-write
    STATUS      current
    DESCRIPTION
        "Get/Set the remote tftp server."
    ::= { es2126PoEplusTftp 1 }

es2126PoEplusInternalTftpServerState OBJECT-TYPE
    SYNTAX      INTEGER(0|1)
    MAX-ACCESS      read-write
    STATUS      current
    DESCRIPTION
        "Get/Set internal tftp server state.
         0 : Disable
         1 : Enable
        "
    ::= { es2126PoEplusTftp 2 }

es2126PoEplusConfiguration            OBJECT IDENTIFIER ::= { es2126PoEplusProduces 5 }

es2126PoEplusSaveRestore              OBJECT IDENTIFIER ::= { es2126PoEplusConfiguration 1 }

es2126PoEplusSaveStart OBJECT-TYPE
    SYNTAX      INTEGER(0|1)
    MAX-ACCESS      read-write
    STATUS      current
    DESCRIPTION
        "Save current configuration into flash memory (Save as Start Configuration).
        Get this OID always return zero.
            1 - Save.
            0 - do nothing. "
    ::= { es2126PoEplusSaveRestore 1 }

es2126PoEplusSaveUser OBJECT-TYPE
    SYNTAX      INTEGER(0|1)
    MAX-ACCESS      read-write
    STATUS      current
    DESCRIPTION
        "Save current configuration into flash memory (Save as User Configuration).
        Get this OID always return zero.
            1 - Save.
            0 - do nothing. "
    ::= { es2126PoEplusSaveRestore 2 }

es2126PoEplusRestoreDefault OBJECT-TYPE
    SYNTAX      INTEGER(0|1|2)
    MAX-ACCESS      read-write
    STATUS      current
    DESCRIPTION
        "Restore factory default configuration.
        Get this OID always return zero.
            2 - Restore default included default ip address.
        1 - Restore default without changing current ip address.
            0 - do nothing. "
    ::= { es2126PoEplusSaveRestore 3 }

es2126PoEplusRestoreUser OBJECT-TYPE
    SYNTAX      INTEGER(0|1)
    MAX-ACCESS      read-write
    STATUS      current
    DESCRIPTION
        "Restore user configuration.
        Get this OID always return zero.
            1 - Restore.
            0 - do nothing. "
    ::= { es2126PoEplusSaveRestore 4 }


es2126PoEplusConfigFile               OBJECT IDENTIFIER ::= { es2126PoEplusConfiguration 2 }

es2126PoEplusExportConfigName OBJECT-TYPE
    SYNTAX      DisplayString
    MAX-ACCESS      read-write
    STATUS      current
    DESCRIPTION
        "Get/Set the export file path and name."
    ::= { es2126PoEplusConfigFile 1 }

es2126PoEplusDoExportConfig OBJECT-TYPE
    SYNTAX      INTEGER(1|2)
    MAX-ACCESS      read-write
    STATUS      current
    DESCRIPTION
        "Do export-config.
        Get this OID always return zero.
            1   -   Export start section.
            2   -   Export user-conf section."
    ::= { es2126PoEplusConfigFile 2 }

es2126PoEplusImportConfigName OBJECT-TYPE
    SYNTAX      DisplayString
    MAX-ACCESS      read-write
    STATUS      current
    DESCRIPTION
        "Get/Set the import file path and name."
    ::= { es2126PoEplusConfigFile 3 }

es2126PoEplusDoImportConfig OBJECT-TYPE
    SYNTAX      INTEGER(1..3)
    MAX-ACCESS      read-write
    STATUS      current
    DESCRIPTION
        "Do import-config.
        Get this OID always return zero.
            1   -   Import start section.
            2   -   Import user-conf section.
            3   -   Import start and overwrite current ip."
    ::= { es2126PoEplusConfigFile 4 }

es2126PoEplusDiagnostic               OBJECT IDENTIFIER ::= { es2126PoEplusProduces 6 }

es2126PoEplusEEPROMTest OBJECT-TYPE
    SYNTAX      DisplayString
    MAX-ACCESS      read-only
    STATUS      current
    DESCRIPTION
        "EEPROM access test."
    ::= { es2126PoEplusDiagnostic 1 }

es2126PoEplusUartTest OBJECT-TYPE
    SYNTAX      DisplayString
    MAX-ACCESS      read-only
    STATUS      current
    DESCRIPTION
        "UART access test."
    ::= { es2126PoEplusDiagnostic 2 }

es2126PoEplusDramTest OBJECT-TYPE
    SYNTAX      DisplayString
    MAX-ACCESS      read-only
    STATUS      current
    DESCRIPTION
        "DRAM access test."
    ::= { es2126PoEplusDiagnostic 3 }

es2126PoEplusFlashTest OBJECT-TYPE
    SYNTAX      DisplayString
    MAX-ACCESS      read-only
    STATUS      current
    DESCRIPTION
        "Flash memory access test."
    ::= { es2126PoEplusDiagnostic 4 }

es2126PoEplusInternalLoopbackTest OBJECT-TYPE
    SYNTAX      DisplayString
    MAX-ACCESS      read-only
    STATUS      current
    DESCRIPTION
        "Internal loop back test."
    ::= { es2126PoEplusDiagnostic 5 }

es2126PoEplusExternalLoopbackTest OBJECT-TYPE
    SYNTAX      DisplayString
    MAX-ACCESS      read-only
    STATUS      current
    DESCRIPTION
        "External loop back test."
    ::= { es2126PoEplusDiagnostic 6 }

es2126PoEplusPingTest OBJECT-TYPE
    SYNTAX      DisplayString
    MAX-ACCESS      read-write
    STATUS      current
    DESCRIPTION
        "Set the host address that you want to ping and the system will return the test result."
    ::= { es2126PoEplusDiagnostic 7 }


es2126PoEplusLog              OBJECT IDENTIFIER ::= { es2126PoEplusProduces 7 }

es2126PoEplusClearLog OBJECT-TYPE
    SYNTAX      INTEGER(0|1)
    MAX-ACCESS      read-write
    STATUS      current
    DESCRIPTION
        "Clear system log.
        Get this OID always return zero.
            1 - Clear log.
            0 - do nothing. "
    ::= { es2126PoEplusLog 1 }

es2126PoEplusUploadLog OBJECT-TYPE
    SYNTAX      INTEGER(0|1)
    MAX-ACCESS      read-write
    STATUS      current
    DESCRIPTION
        "Upload current system log. Set the correct tftp server first.
        The format of log file is 'ModelName_SerialNumbuer_YYMMDD_HHMM'.
        Get this OID always return zero.
            1 - Upload log
            0 - do nothing. "
    ::= { es2126PoEplusLog 2 }

es2126PoEplusAutoUploadLogState OBJECT-TYPE
    SYNTAX      INTEGER(0|1)
    MAX-ACCESS      read-write
    STATUS      current
    DESCRIPTION
        "Enable auto-upload log function. Set the correct tftp server first.
        The format of log file is 'ModelName_SerialNumbuer_YYMMDD_HHMM'.
        Get this OID always return zero.
            1 - Enable auto-upload
            0 - do nothing. "
    ::= { es2126PoEplusLog 3 }

es2126PoEplusLogNumber OBJECT-TYPE
    SYNTAX      INTEGER(0..120)
    MAX-ACCESS      read-only
    STATUS      current
    DESCRIPTION
        "Get the number of current system log. "
    ::= { es2126PoEplusLog 4 }

es2126PoEplusLogTable OBJECT-TYPE
    SYNTAX      SEQUENCE OF ES2126POEPLUSLogEntry
    MAX-ACCESS  not-accessible
    STATUS      current
    DESCRIPTION
        "This is a list of log entry. The numbers of entries are given by the value of es2126PoEplusLogNumber."
    ::= { es2126PoEplusLog 5 }

es2126PoEplusLogEntry OBJECT-TYPE
    SYNTAX      ES2126POEPLUSLogEntry
    MAX-ACCESS      not-accessible
    STATUS      current
    DESCRIPTION
        "This is the Entry information for system log."
    INDEX {es2126PoEplusLogIndex}
    ::= { es2126PoEplusLogTable 1 }

ES2126POEPLUSLogEntry ::=
SEQUENCE {
    es2126PoEplusLogIndex         INTEGER,
    es2126PoEplusLogEvent             DisplayString
}

es2126PoEplusLogIndex OBJECT-TYPE
    SYNTAX      INTEGER(1..120)
    MAX-ACCESS      read-only
    STATUS      current
    DESCRIPTION
        "This is the index of the log entry."
    ::= { es2126PoEplusLogEntry 1 }

es2126PoEplusLogEvent OBJECT-TYPE
    SYNTAX      DisplayString
    MAX-ACCESS      read-only
    STATUS      current
    DESCRIPTION
        "This is the detail information of the log entry."
    ::= { es2126PoEplusLogEntry 2 }

es2126PoEplusFirmware             OBJECT IDENTIFIER ::= { es2126PoEplusProduces 8 }

es2126PoEplusFirmwareFileName OBJECT-TYPE
    SYNTAX      DisplayString
    MAX-ACCESS      read-write
    STATUS      current
    DESCRIPTION
        "Get/Set the path and filename for firmware upgrading."
    ::= { es2126PoEplusFirmware 1 }

es2126PoEplusDoFirmwareUpgrade OBJECT-TYPE
    SYNTAX      INTEGER(0|1)
    MAX-ACCESS      read-write
    STATUS      current
    DESCRIPTION
        "Do firmware upgrade. Get this OID always return zero.
            1 - Do firmware upgrade.
            0 - do nothing."
    ::= { es2126PoEplusFirmware 2 }

es2126PoEplusPort             OBJECT IDENTIFIER ::= { es2126PoEplusProduces 9 }

es2126PoEplusPortStatus               OBJECT IDENTIFIER ::= { es2126PoEplusPort 1 }

es2126PoEplusPortStatusNumber OBJECT-TYPE
    SYNTAX      INTEGER(1..2147483647)
    MAX-ACCESS      read-only
    STATUS      current
    DESCRIPTION
        "Get the number of port."
    ::= { es2126PoEplusPortStatus 1 }

es2126PoEplusPortStatusTable  OBJECT-TYPE
    SYNTAX      SEQUENCE OF ES2126POEPLUSPortStatusEntry
    MAX-ACCESS  not-accessible
    STATUS      current
    DESCRIPTION
        "This is a list of port status entry. The numbers of entries are given by the value of es2126PoEplusPortStatusNumber."
    ::= { es2126PoEplusPortStatus 2 }

es2126PoEplusPortStatusEntry  OBJECT-TYPE
    SYNTAX      ES2126POEPLUSPortStatusEntry
    MAX-ACCESS      not-accessible
    STATUS      current
    DESCRIPTION
        "This is the entry(s) for port status information."
    INDEX {es2126PoEplusPortStatusIndex}
    ::= { es2126PoEplusPortStatusTable 1 }

ES2126POEPLUSPortStatusEntry ::=
SEQUENCE {
    es2126PoEplusPortStatusIndex          INTEGER,
    es2126PoEplusPortStatusMedia          DisplayString,
    es2126PoEplusPortStatusLink           DisplayString,
    es2126PoEplusPortStatusPortState      DisplayString,
    es2126PoEplusPortStatusAutoNego       DisplayString,
    es2126PoEplusPortStatusSpdDpx         DisplayString,
    es2126PoEplusPortStatusRxPause        DisplayString,
    es2126PoEplusPortStatusTxPause        DisplayString,
    es2126PoEplusPortStatusDescription     DisplayString
}

es2126PoEplusPortStatusIndex  OBJECT-TYPE
    SYNTAX      INTEGER(1..2147483647)
    MAX-ACCESS      read-only
    STATUS      current
    DESCRIPTION
        "This is the index of the port status entry."
    ::= { es2126PoEplusPortStatusEntry 1 }

es2126PoEplusPortStatusMedia  OBJECT-TYPE
    SYNTAX      DisplayString
    MAX-ACCESS      read-only
    STATUS      current
    DESCRIPTION
        "The port media type of the port status entry."
    ::= { es2126PoEplusPortStatusEntry 2 }

es2126PoEplusPortStatusLink   OBJECT-TYPE
    SYNTAX      DisplayString
    MAX-ACCESS      read-only
    STATUS      current
    DESCRIPTION
        "This is the port link of the port status entry."
    ::= { es2126PoEplusPortStatusEntry 3 }

es2126PoEplusPortStatusPortState  OBJECT-TYPE
    SYNTAX      DisplayString
    MAX-ACCESS      read-only
    STATUS      current
    DESCRIPTION
        "This is the port state of the port status entry."
    ::= { es2126PoEplusPortStatusEntry 4 }

es2126PoEplusPortStatusAutoNego   OBJECT-TYPE
    SYNTAX      DisplayString
    MAX-ACCESS      read-only
    STATUS      current
    DESCRIPTION
        "This is the auto negotiation of the port status entry."
    ::= { es2126PoEplusPortStatusEntry 5 }

es2126PoEplusPortStatusSpdDpx     OBJECT-TYPE
    SYNTAX      DisplayString
    MAX-ACCESS      read-only
    STATUS      current
    DESCRIPTION
        "This is the speed/duplex of the port status entry."
    ::= { es2126PoEplusPortStatusEntry 6 }

es2126PoEplusPortStatusRxPause    OBJECT-TYPE
    SYNTAX      DisplayString
    MAX-ACCESS      read-only
    STATUS      current
    DESCRIPTION
        "The Rx Pause of the port status entry."
    ::= { es2126PoEplusPortStatusEntry 7 }

es2126PoEplusPortStatusTxPause    OBJECT-TYPE
    SYNTAX      DisplayString
    MAX-ACCESS      read-only
    STATUS      current
    DESCRIPTION
        "The Tx Pause of the port status entry."
    ::= { es2126PoEplusPortStatusEntry 8 }

es2126PoEplusPortStatusDescription    OBJECT-TYPE
    SYNTAX      DisplayString
    MAX-ACCESS      read-only
    STATUS      current
    DESCRIPTION
        "This is the description of port."
    ::= { es2126PoEplusPortStatusEntry 9 }

es2126PoEplusPortConf             OBJECT IDENTIFIER ::= { es2126PoEplusPort 2 }

es2126PoEplusPortConfNumber OBJECT-TYPE
    SYNTAX      INTEGER(1..2147483647)
    MAX-ACCESS      read-only
    STATUS      current
    DESCRIPTION
        "Get the number of port configuration."
    ::= { es2126PoEplusPortConf 1 }

es2126PoEplusPortConfTable    OBJECT-TYPE
    SYNTAX      SEQUENCE OF ES2126POEPLUSPortConfEntry
    MAX-ACCESS  not-accessible
    STATUS      current
    DESCRIPTION
        "This is a list of port configuration entry. The numbers of entries are given by the value of es2126PoEplusPortConfNumber."
    ::= { es2126PoEplusPortConf 2 }

es2126PoEplusPortConfEntry    OBJECT-TYPE
    SYNTAX      ES2126POEPLUSPortConfEntry
    MAX-ACCESS      not-accessible
    STATUS      current
    DESCRIPTION
        "This is the Entry(s) for port configuration information."
    INDEX {es2126PoEplusPortConfIndex}
    ::= { es2126PoEplusPortConfTable 1 }

ES2126POEPLUSPortConfEntry ::=
SEQUENCE {
    es2126PoEplusPortConfIndex        INTEGER,
    es2126PoEplusPortConfPortState        INTEGER,
    es2126PoEplusPortConfSpdDpx           INTEGER,
    es2126PoEplusPortConfFlwCtrl          INTEGER,
    es2126PoEplusPortConfDescription      DisplayString
}

es2126PoEplusPortConfIndex    OBJECT-TYPE
    SYNTAX      INTEGER(1..2147483647)
    MAX-ACCESS      read-only
    STATUS      current
    DESCRIPTION
        "This is the index of the port configuration entry."
    ::= { es2126PoEplusPortConfEntry 1 }

es2126PoEplusPortConfPortState    OBJECT-TYPE
    SYNTAX      INTEGER(0|1)
    MAX-ACCESS      read-write
    STATUS      current
    DESCRIPTION
        "This is the port state of the port configuration entry.
         0 - disabled.
         1 - enabled. "
    ::= { es2126PoEplusPortConfEntry 2 }

es2126PoEplusPortConfSpdDpx   OBJECT-TYPE
    SYNTAX      INTEGER(0..5)
    MAX-ACCESS      read-write
    STATUS      current
    DESCRIPTION
        "This is the speed/duplex of the port configuration entry.
         0 - auto.
         1 - 10M/Half.
         2 - 10M/Full.
         3 - 100M/Half.
         4 - 100M/Full.
         5 - 1G/Full.  "
    ::= { es2126PoEplusPortConfEntry 3 }

es2126PoEplusPortConfFlwCtrl  OBJECT-TYPE
    SYNTAX      INTEGER(0|1)
    MAX-ACCESS      read-write
    STATUS      current
    DESCRIPTION
        "This is the flow control of the port configuration entry.
         0 - asymmetric.
         1 - symmetric.  "
    ::= { es2126PoEplusPortConfEntry 4 }

es2126PoEplusPortConfDescription  OBJECT-TYPE
    SYNTAX      DisplayString
    MAX-ACCESS      read-write
    STATUS      current
    DESCRIPTION
        "This is the description of port."
    ::= { es2126PoEplusPortConfEntry 5 }


es2126PoEplusPortBandwidth            OBJECT IDENTIFIER ::= { es2126PoEplusPort 3 }

es2126PoEplusPortBandwidthTable   OBJECT-TYPE
    SYNTAX      SEQUENCE OF ES2126POEPLUSPortBandwidthEntry
    MAX-ACCESS  not-accessible
    STATUS      current
    DESCRIPTION
        "This is a list of port bandwidth entry."
    ::= { es2126PoEplusPortBandwidth 1 }

ES2126POEPLUSPortBandwidthEntry ::=
SEQUENCE {
    es2126PoEplusPortBandwidthIndex                 INTEGER,
    es2126PoEplusPortBandwidthIngressRate        INTEGER,
    es2126PoEplusPortBandwidthEgressRate         INTEGER
}

es2126PoEplusPortBandwidthEntry   OBJECT-TYPE
    SYNTAX      ES2126POEPLUSPortBandwidthEntry
    MAX-ACCESS      not-accessible
    STATUS      current
    DESCRIPTION
        "This is the Entry(s) for port bandwidth configuration."
    INDEX {es2126PoEplusPortBandwidthIndex}
    ::= { es2126PoEplusPortBandwidthTable 1 }

es2126PoEplusPortBandwidthIndex   OBJECT-TYPE
    SYNTAX      INTEGER(1..26)
    MAX-ACCESS      read-only
    STATUS      current
    DESCRIPTION
        "This is the index of the port bandwidth entry."
    ::= { es2126PoEplusPortBandwidthEntry 1 }

es2126PoEplusPortBandwidthIngressRate OBJECT-TYPE
    SYNTAX      INTEGER(66..1024000)
    MAX-ACCESS      read-write
    STATUS      current
    DESCRIPTION
        "Get/Set the port bandwidth ingress rate.
         Fast Ethernet port range: 66~102400(Kb)
         Gigabit Ethernet port range: 66~1024000(Kb)"
    ::= { es2126PoEplusPortBandwidthEntry 2 }

es2126PoEplusPortBandwidthEgressRate  OBJECT-TYPE
    SYNTAX      INTEGER(66..1024000)
    MAX-ACCESS      read-write
    STATUS      current
    DESCRIPTION
        "Get/Set the port bandwidth egress rate.
         Fast Ethernet port range: 66~102400(Kb)
         Gigabit Ethernet port range: 66~1024000(Kb)"
    ::= { es2126PoEplusPortBandwidthEntry 3 }

es2126PoEplusPortBandwidthStormType   OBJECT-TYPE
    SYNTAX      INTEGER(0..4)
    MAX-ACCESS      read-write
    STATUS      current
    DESCRIPTION
        "This is the bandwidth storm type.
        0:Disable
                1:Broadcast Storm Control
                2:Multicast Storm Control
                3:Unknown Unicast Storm Control
                4:Broadcast, Multicast, and Unknown Unicast Storm Control"
    ::= { es2126PoEplusPortBandwidth 2 }

es2126PoEplusPortBandwidthStormRate   OBJECT-TYPE
    SYNTAX      INTEGER(1..100)
    MAX-ACCESS      read-write
    STATUS      current
    DESCRIPTION
        "This is the storm rate."
    ::= { es2126PoEplusPortBandwidth 3 }

es2126PoEplusPortSFPInfo               OBJECT IDENTIFIER ::= { es2126PoEplusPort 4 }

es2126PoEplusPortSFPInfoNumber OBJECT-TYPE
    SYNTAX      INTEGER(1..2147483647)
    MAX-ACCESS      read-only
    STATUS      current
    DESCRIPTION
        "Get the number of sfp info entry."
    ::= { es2126PoEplusPortSFPInfo 1 }

es2126PoEplusPortSFPInfoTable  OBJECT-TYPE
    SYNTAX      SEQUENCE OF ES2126POEPLUSPORTSFPInfoEntry
    MAX-ACCESS  not-accessible
    STATUS      current
    DESCRIPTION
        "A list of sfp info entry. The numbers of entries are given by the value of es2126PoEplusPortSFPInfoNumber."
    ::= { es2126PoEplusPortSFPInfo 2 }

ES2126POEPLUSPORTSFPInfoEntry ::=
SEQUENCE {
    es2126PoEplusPortSFPInfoIndex      INTEGER,
    es2126PoEplusPortSFPConnectorType  DisplayString,
    es2126PoEplusPortSFPFiberType      DisplayString,
    es2126PoEplusPortSFPWavelength     DisplayString,
    es2126PoEplusPortSFPBaudRate       DisplayString,
    es2126PoEplusPortSFPVendorOUI      DisplayString,
    es2126PoEplusPortSFPVendorName     DisplayString,
    es2126PoEplusPortSFPVendorPN       DisplayString,
    es2126PoEplusPortSFPVendorRev      DisplayString,
    es2126PoEplusPortSFPVendorSN       DisplayString,
    es2126PoEplusPortSFPDateCode       DisplayString,
    es2126PoEplusPortSFPTemperature    DisplayString,
    es2126PoEplusPortSFPVcc            DisplayString,
    es2126PoEplusPortSFPTxBias         DisplayString,
    es2126PoEplusPortSFPTxPWR          DisplayString,
    es2126PoEplusPortSFPRxPWR          DisplayString
}

es2126PoEplusPortSFPInfoEntry  OBJECT-TYPE
    SYNTAX      ES2126POEPLUSPORTSFPInfoEntry
    MAX-ACCESS      not-accessible
    STATUS      current
    DESCRIPTION
        "Entry(s) for SFP information."
    INDEX {es2126PoEplusPortSFPInfoIndex}
    ::= { es2126PoEplusPortSFPInfoTable 1 }

es2126PoEplusPortSFPInfoIndex  OBJECT-TYPE
    SYNTAX      INTEGER(1..2147483647)
    MAX-ACCESS      read-only
    STATUS      current
    DESCRIPTION
        "The index of the sfp info entry."
    ::= { es2126PoEplusPortSFPInfoEntry 1 }

es2126PoEplusPortSFPConnectorType  OBJECT-TYPE
    SYNTAX      DisplayString
    MAX-ACCESS      read-only
    STATUS      current
    DESCRIPTION
        "Get connector type of the sfp."
    ::= { es2126PoEplusPortSFPInfoEntry 2 }

es2126PoEplusPortSFPFiberType  OBJECT-TYPE
    SYNTAX      DisplayString
    MAX-ACCESS      read-only
    STATUS      current
    DESCRIPTION
        "Get fiber type of the sfp."
    ::= { es2126PoEplusPortSFPInfoEntry 3 }

es2126PoEplusPortSFPWavelength OBJECT-TYPE
    SYNTAX      DisplayString
    MAX-ACCESS      read-only
    STATUS      current
    DESCRIPTION
        "Get tx central wavelength of the sfp."
    ::= { es2126PoEplusPortSFPInfoEntry 4 }

es2126PoEplusPortSFPBaudRate   OBJECT-TYPE
    SYNTAX      DisplayString
    MAX-ACCESS      read-only
    STATUS      current
    DESCRIPTION
        "Get baud rate of the sfp."
    ::= { es2126PoEplusPortSFPInfoEntry 5 }

es2126PoEplusPortSFPVendorOUI  OBJECT-TYPE
    SYNTAX      DisplayString
    MAX-ACCESS      read-only
    STATUS      current
    DESCRIPTION
        "Get vendor OUI of the sfp."
    ::= { es2126PoEplusPortSFPInfoEntry 6 }

es2126PoEplusPortSFPVendorName OBJECT-TYPE
    SYNTAX      DisplayString
    MAX-ACCESS      read-only
    STATUS      current
    DESCRIPTION
        "Get vendor name of the sfp."
    ::= { es2126PoEplusPortSFPInfoEntry 7 }

es2126PoEplusPortSFPVendorPN   OBJECT-TYPE
    SYNTAX      DisplayString
    MAX-ACCESS      read-only
    STATUS      current
    DESCRIPTION
        "Get vendor part number of the sfp."
    ::= { es2126PoEplusPortSFPInfoEntry 8 }

es2126PoEplusPortSFPVendorRev  OBJECT-TYPE
    SYNTAX      DisplayString
    MAX-ACCESS      read-only
    STATUS      current
    DESCRIPTION
        "Get vendor revision number of the sfp."
    ::= { es2126PoEplusPortSFPInfoEntry 9 }

es2126PoEplusPortSFPVendorSN   OBJECT-TYPE
    SYNTAX      DisplayString
    MAX-ACCESS      read-only
    STATUS      current
    DESCRIPTION
        "Get vendor serial number of the sfp."
    ::= { es2126PoEplusPortSFPInfoEntry 10 }

es2126PoEplusPortSFPDateCode   OBJECT-TYPE
    SYNTAX      DisplayString
    MAX-ACCESS      read-only
    STATUS      current
    DESCRIPTION
        "Get data code of the sfp."
    ::= { es2126PoEplusPortSFPInfoEntry 11 }

es2126PoEplusPortSFPTemperature    OBJECT-TYPE
    SYNTAX      DisplayString
    MAX-ACCESS      read-only
    STATUS      current
    DESCRIPTION
        "Get current temperature of the sfp."
    ::= { es2126PoEplusPortSFPInfoEntry 12 }

es2126PoEplusPortSFPVcc    OBJECT-TYPE
    SYNTAX      DisplayString
    MAX-ACCESS      read-only
    STATUS      current
    DESCRIPTION
        "Get current internal supply voltage of the sfp."
    ::= { es2126PoEplusPortSFPInfoEntry 13 }

es2126PoEplusPortSFPTxBias OBJECT-TYPE
    SYNTAX      DisplayString
    MAX-ACCESS      read-only
    STATUS      current
    DESCRIPTION
        "Get current TX Bias of the sfp."
    ::= { es2126PoEplusPortSFPInfoEntry 14 }

es2126PoEplusPortSFPTxPWR  OBJECT-TYPE
    SYNTAX      DisplayString
    MAX-ACCESS      read-only
    STATUS      current
    DESCRIPTION
        "Get current TX output power of the sfp."
    ::= { es2126PoEplusPortSFPInfoEntry 15 }

es2126PoEplusPortSFPRxPWR  OBJECT-TYPE
    SYNTAX      DisplayString
    MAX-ACCESS      read-only
    STATUS      current
    DESCRIPTION
        "Get current Received Power of the sfp."
    ::= { es2126PoEplusPortSFPInfoEntry 16 }


es2126PoEplusLoopDetectedConf             OBJECT IDENTIFIER ::= { es2126PoEplusProduces 10 }

es2126PoEplusLoopDetectedNumber OBJECT-TYPE
    SYNTAX      INTEGER(1..2147483647)
    MAX-ACCESS      read-only
    STATUS      current
    DESCRIPTION
        "Get the number of loop detected entry."
    ::= { es2126PoEplusLoopDetectedConf 1 }

es2126PoEplusLoopDetectedTable    OBJECT-TYPE
    SYNTAX      SEQUENCE OF ES2126POEPLUSLoopDetectedEntry
    MAX-ACCESS  not-accessible
    STATUS      current
    DESCRIPTION
        "This is a list of loop detected entry. The number of entries are given by the value of es2126PoEplusLoopDetectedNumber."
    ::= { es2126PoEplusLoopDetectedConf 2 }

es2126PoEplusLoopDetectedEntry    OBJECT-TYPE
    SYNTAX      ES2126POEPLUSLoopDetectedEntry
    MAX-ACCESS      not-accessible
    STATUS      current
    DESCRIPTION
        "Entry(s) for loop detected information."
    INDEX {es2126PoEplusLoopDetectedfIndex}
    ::= { es2126PoEplusLoopDetectedTable 1 }

ES2126POEPLUSLoopDetectedEntry ::=
SEQUENCE {
    es2126PoEplusLoopDetectedfIndex           INTEGER,
    es2126PoEplusLoopDetectedStateEbl         INTEGER,
    es2126PoEplusLoopDetectedCurrentStatus    INTEGER,
    es2126PoEplusLoopDetectedResumed          INTEGER
}

es2126PoEplusLoopDetectedfIndex   OBJECT-TYPE
    SYNTAX      INTEGER(1..2147483647)
    MAX-ACCESS      read-only
    STATUS      current
    DESCRIPTION
        "This is the index of the loop detected entry."
    ::= { es2126PoEplusLoopDetectedEntry 1 }

es2126PoEplusLoopDetectedStateEbl OBJECT-TYPE
    SYNTAX      INTEGER(0|1)
    MAX-ACCESS      read-write
    STATUS      current
    DESCRIPTION
        "The state of the loop detected entry.
         0 - disabled.
         1 - enabled. "
    ::= { es2126PoEplusLoopDetectedEntry 2 }

es2126PoEplusLoopDetectedCurrentStatus    OBJECT-TYPE
    SYNTAX      INTEGER(0|1)
    MAX-ACCESS      read-only
    STATUS      current
    DESCRIPTION
        "The current status of the loop detected port.
         0 - Unlocked
         1 - Locked due to the loop condition "
    ::= { es2126PoEplusLoopDetectedEntry 3 }

es2126PoEplusLoopDetectedResumed  OBJECT-TYPE
    SYNTAX      INTEGER(0|1)
    MAX-ACCESS      read-write
    STATUS      current
    DESCRIPTION
        "Unlock the port which is locked due to loop condition. Get this OID always return zero.
         1 - Unlock the port,
         0 - do nothing."
    ::= { es2126PoEplusLoopDetectedEntry 4 }

es2126PoEplusLoopDetectedAction OBJECT-TYPE
    SYNTAX      INTEGER(0|1)
    MAX-ACCESS      read-write
    STATUS      current
    DESCRIPTION
        "Set the corresponding action while loop is detected.
         1 - Lock the loop port,
         0 - do nothing."
    ::= { es2126PoEplusLoopDetectedConf 3 }

es2126PoEplusMacTableInfo             OBJECT IDENTIFIER ::= { es2126PoEplusProduces 11 }

es2126PoEplusMacTableMaintenance       OBJECT IDENTIFIER ::= { es2126PoEplusMacTableInfo 1 }

es2126PoEplusMacTableAgingTime  OBJECT-TYPE
    SYNTAX      INTEGER(0|10..1000000)
    MAX-ACCESS  read-write
    STATUS      current
    DESCRIPTION
        "Set the Mac Table Aging Time (10~1000000 Secs).
         0 : Disable.
        "
    ::= { es2126PoEplusMacTableMaintenance 1 }

es2126PoEplusMacTableFlush  OBJECT-TYPE
    SYNTAX      INTEGER(0|1)
    MAX-ACCESS  read-write
    STATUS      current
    DESCRIPTION
        "1 : Flush Mac Table."
    ::= { es2126PoEplusMacTableMaintenance 2 }

es2126PoEplusMacTableLearnPortLimitTable  OBJECT-TYPE
    SYNTAX      SEQUENCE OF ES2126POEPLUSMacTableLearnPortLimitEntry
    MAX-ACCESS  not-accessible
    STATUS      current
    DESCRIPTION
        "This is a list of MAC Learning Limitentry."
    ::= { es2126PoEplusMacTableMaintenance 3 }

ES2126POEPLUSMacTableLearnPortLimitEntry ::=
SEQUENCE {
    es2126PoEplusMacTableLearnPortLimitIndex   INTEGER,
    es2126PoEplusMacTableLearnPortLimit           INTEGER
}

es2126PoEplusMacTableLearnPortLimitEntry  OBJECT-TYPE
    SYNTAX      ES2126POEPLUSMacTableLearnPortLimitEntry
    MAX-ACCESS  not-accessible
    STATUS      current
    DESCRIPTION
        "Entry(s) for Mac Table Port Learning Limit."
    INDEX {es2126PoEplusMacTableLearnPortLimitIndex}
    ::= { es2126PoEplusMacTableLearnPortLimitTable 1 }

es2126PoEplusMacTableLearnPortLimitIndex  OBJECT-TYPE
    SYNTAX      INTEGER(1..26)
    MAX-ACCESS  not-accessible
    STATUS      current
    DESCRIPTION
        "The index of the Mac Table Learning Limit entry."
    ::= { es2126PoEplusMacTableLearnPortLimitEntry 1 }

es2126PoEplusMacTableLearnPortLimit  OBJECT-TYPE
    SYNTAX      INTEGER(0..8191)
    MAX-ACCESS  read-write
    STATUS      current
    DESCRIPTION
        "Port Learning Limit (0~8191)."
    ::= { es2126PoEplusMacTableLearnPortLimitEntry 2 }

es2126PoEplusMacTableStaticMac       OBJECT IDENTIFIER ::= { es2126PoEplusMacTableInfo 3 }

es2126PoEplusMacTableStaticMacNumber  OBJECT-TYPE
    SYNTAX      INTEGER(0..1024)
    MAX-ACCESS  read-only
    STATUS      current
    DESCRIPTION
        "This is number of static Mac table entry"
    ::= { es2126PoEplusMacTableStaticMac 1 }

es2126PoEplusMacTableStaticMacEntryCreate  OBJECT-TYPE
    SYNTAX      INTEGER(0..1024)
    MAX-ACCESS  read-write
    STATUS      current
    DESCRIPTION
        "Creat a static mac entry."
    ::= { es2126PoEplusMacTableStaticMac 2 }

es2126PoEplusMacTableStaticMacTable  OBJECT-TYPE
    SYNTAX      SEQUENCE OF ES2126POEPLUSMacTableStaticMacEntry
    MAX-ACCESS  not-accessible
    STATUS      current
    DESCRIPTION
        "This is a list of static MAC table."
    ::= { es2126PoEplusMacTableStaticMac 3 }

ES2126POEPLUSMacTableStaticMacEntry ::=
SEQUENCE {
    es2126PoEplusMacTableStaticMacIndex        INTEGER,
    es2126PoEplusMacTableStaticMacAddress      DisplayString,
    es2126PoEplusMacTableStaticMacVid           INTEGER,
    es2126PoEplusMacTableStaticMacQueue           INTEGER,
    es2126PoEplusMacTableStaticMacFwRule          INTEGER,
    es2126PoEplusMacTableStaticMacPort        INTEGER,
    es2126PoEplusMacTableStaticMacEntryAction     INTEGER
}

es2126PoEplusMacTableStaticMacEntry  OBJECT-TYPE
    SYNTAX      ES2126POEPLUSMacTableStaticMacEntry
    MAX-ACCESS  not-accessible
    STATUS      current
    DESCRIPTION
        "Entry(s) for Static Mac Table."
    INDEX {es2126PoEplusMacTableStaticMacIndex}
    ::= { es2126PoEplusMacTableStaticMacTable 1 }

es2126PoEplusMacTableStaticMacIndex  OBJECT-TYPE
    SYNTAX      INTEGER(1..1024)
    MAX-ACCESS      not-accessible
    STATUS      current
    DESCRIPTION
        "The index of the static Mac Table."
    ::= { es2126PoEplusMacTableStaticMacEntry 1 }

es2126PoEplusMacTableStaticMacAddress  OBJECT-TYPE
    SYNTAX      DisplayString
    MAX-ACCESS  read-write
    STATUS      current
    DESCRIPTION
        "The mac address of the static mac table entry."
    ::= { es2126PoEplusMacTableStaticMacEntry 2 }

es2126PoEplusMacTableStaticMacVid  OBJECT-TYPE
    SYNTAX      INTEGER(1..4094)
    MAX-ACCESS  read-write
    STATUS      current
    DESCRIPTION
        "The vlan id of the static mac table entry."
    ::= { es2126PoEplusMacTableStaticMacEntry 3 }

es2126PoEplusMacTableStaticMacQueue  OBJECT-TYPE
    SYNTAX      INTEGER(0..3)
    MAX-ACCESS  read-write
    STATUS      current
    DESCRIPTION
        "The queue of the static mac table entry."
    ::= { es2126PoEplusMacTableStaticMacEntry 4 }

es2126PoEplusMacTableStaticMacFwRule  OBJECT-TYPE
    SYNTAX      INTEGER(0..2)
    MAX-ACCESS  read-write
    STATUS      current
    DESCRIPTION
        "The forwarding rule of the static mac table entry.
         0 : static
         1 : Static with Destination Drop
         2 : Static with Source Drop
        "
    ::= { es2126PoEplusMacTableStaticMacEntry 5 }

es2126PoEplusMacTableStaticMacPort  OBJECT-TYPE
    SYNTAX      INTEGER(1..26)
    MAX-ACCESS  read-write
    STATUS      current
    DESCRIPTION
        "The port of the static mac table entry."
    ::= { es2126PoEplusMacTableStaticMacEntry 6 }

es2126PoEplusMacTableStaticMacEntryAction  OBJECT-TYPE
    SYNTAX      INTEGER(1..3)
    MAX-ACCESS  read-write
    STATUS      current
    DESCRIPTION
        "The port of the static mac table entry."
    ::= { es2126PoEplusMacTableStaticMacEntry 7 }

es2126PoEplusMacTableMacAlias       OBJECT IDENTIFIER ::= { es2126PoEplusMacTableInfo 4 }

es2126PoEplusMacTableMacAliasNumber  OBJECT-TYPE
    SYNTAX      INTEGER(0..8192)
    MAX-ACCESS  read-only
    STATUS      current
    DESCRIPTION
        "This is number of static Mac table entry"
    ::= { es2126PoEplusMacTableMacAlias 1 }

es2126PoEplusMacTableMacAliasEntryCreate  OBJECT-TYPE
    SYNTAX      INTEGER(0..8192)
    MAX-ACCESS  read-write
    STATUS      current
    DESCRIPTION
        "Creat a static mac alias entry."
    ::= { es2126PoEplusMacTableMacAlias 2 }

es2126PoEplusMacTableMacAliasTable  OBJECT-TYPE
    SYNTAX      SEQUENCE OF ES2126POEPLUSMacTableMacAliasEntry
    MAX-ACCESS  not-accessible
    STATUS      current
    DESCRIPTION
        "This is a list of MAC Alias table."
    ::= { es2126PoEplusMacTableMacAlias 3 }

ES2126POEPLUSMacTableMacAliasEntry ::=
SEQUENCE {
    es2126PoEplusMacTableMacAliasIndex        INTEGER,
    es2126PoEplusMacTableMacAliasAddress      DisplayString,
    es2126PoEplusMacTableMacAliasAlias        DisplayString,
    es2126PoEplusMacTableMacAliasEntryAction  INTEGER
}

es2126PoEplusMacTableMacAliasEntry  OBJECT-TYPE
    SYNTAX      ES2126POEPLUSMacTableMacAliasEntry
    MAX-ACCESS  not-accessible
    STATUS      current
    DESCRIPTION
        "Entry(s) for Alias Mac Table."
    INDEX {es2126PoEplusMacTableMacAliasIndex}
    ::= { es2126PoEplusMacTableMacAliasTable 1 }

es2126PoEplusMacTableMacAliasIndex  OBJECT-TYPE
    SYNTAX      INTEGER(1..1024)
    MAX-ACCESS      not-accessible
    STATUS      current
    DESCRIPTION
        "The index of the Alias Mac Table."
    ::= { es2126PoEplusMacTableMacAliasEntry 1 }

es2126PoEplusMacTableMacAliasAddress  OBJECT-TYPE
    SYNTAX      DisplayString
    MAX-ACCESS      read-write
    STATUS      current
    DESCRIPTION
        "The Mac address of the Alias Mac Table."
    ::= { es2126PoEplusMacTableMacAliasEntry 2 }

es2126PoEplusMacTableMacAliasAlias  OBJECT-TYPE
    SYNTAX      DisplayString
    MAX-ACCESS      read-write
    STATUS      current
    DESCRIPTION
        "The Mac Alias of the Alias Mac Table."
    ::= { es2126PoEplusMacTableMacAliasEntry 3 }

es2126PoEplusMacTableMacAliasEntryAction  OBJECT-TYPE
    SYNTAX      INTEGER(1..3)
    MAX-ACCESS  read-write
    STATUS      current
    DESCRIPTION
        "The action of the alias mac table entry."
    ::= { es2126PoEplusMacTableMacAliasEntry 4 }

es2126PoEplusGVRPInfo             OBJECT IDENTIFIER ::= { es2126PoEplusProduces 12 }

es2126PoEplusGvrpConf             OBJECT IDENTIFIER ::= { es2126PoEplusGVRPInfo 1 }

es2126PoEplusGvrpConfState OBJECT-TYPE
    SYNTAX      INTEGER(0|1)
    MAX-ACCESS      read-write
    STATUS      current
    DESCRIPTION
        "The state of GVRP.
         0 - Disable
         1 - Enable
    "
    ::= { es2126PoEplusGvrpConf 1 }

es2126PoEplusGvrpConfTable    OBJECT-TYPE
    SYNTAX      SEQUENCE OF ES2126POEPLUSGvrpConfEntry
    MAX-ACCESS  not-accessible
    STATUS      current
    DESCRIPTION
        "This is a list of the GVRP conf table."
    ::= { es2126PoEplusGvrpConf 2 }

ES2126POEPLUSGvrpConfEntry ::=
SEQUENCE {
    es2126PoEplusGvrpConfIndex             INTEGER,
    es2126PoEplusGvrpConfJoinTime          INTEGER,
    es2126PoEplusGvrpConfLeaveTime         INTEGER,
    es2126PoEplusGvrpConfLeaveAllTime      INTEGER,
    es2126PoEplusGvrpConfDefaultAppMode    INTEGER,
    es2126PoEplusGvrpConfDefaultRegMode    INTEGER,
    es2126PoEplusGvrpConfRestrictedMode    INTEGER
}

es2126PoEplusGvrpConfEntry    OBJECT-TYPE
    SYNTAX      ES2126POEPLUSGvrpConfEntry
    MAX-ACCESS      not-accessible
    STATUS      current
    DESCRIPTION
        "Entry(s) for the GVRP conf table."
    INDEX {es2126PoEplusGvrpConfIndex}
    ::= { es2126PoEplusGvrpConfTable 1 }

es2126PoEplusGvrpConfIndex    OBJECT-TYPE
    SYNTAX      INTEGER(1..26)
    MAX-ACCESS      not-accessible
    STATUS      current
    DESCRIPTION
        "The index of the GVRP conf table."
    ::= { es2126PoEplusGvrpConfEntry 1 }

es2126PoEplusGvrpConfJoinTime OBJECT-TYPE
    SYNTAX      INTEGER(20..100)
    MAX-ACCESS      read-write
    STATUS      current
    DESCRIPTION
        "The join time of the GVRP entry.
         range: 20~100
         default 20 centisecond"
    ::= { es2126PoEplusGvrpConfEntry 2 }

es2126PoEplusGvrpConfLeaveTime    OBJECT-TYPE
    SYNTAX      INTEGER(60..300)
    MAX-ACCESS      read-write
    STATUS      current
    DESCRIPTION
        "The leave time of the GVRP entry.
         range: 60~300
        default:60 centisecond"
    ::= { es2126PoEplusGvrpConfEntry 3 }

es2126PoEplusGvrpConfLeaveAllTime OBJECT-TYPE
    SYNTAX      INTEGER(1000..5000)
    MAX-ACCESS      read-write
    STATUS      current
    DESCRIPTION
        "The leave all time of the GVRP entry.
         range: 1000~5000
         default: 1000 unit time"
    ::= { es2126PoEplusGvrpConfEntry 4 }

es2126PoEplusGvrpConfDefaultAppMode   OBJECT-TYPE
    SYNTAX      INTEGER(0|1)
    MAX-ACCESS      read-write
    STATUS      current
    DESCRIPTION
        "The default application mode of the GVRP entry.
         0 - Normal
         1 - Non-Participant
         default: Normal"
    ::= { es2126PoEplusGvrpConfEntry 5 }

es2126PoEplusGvrpConfDefaultRegMode   OBJECT-TYPE
    SYNTAX      INTEGER(0|1|2)
    MAX-ACCESS      read-write
    STATUS      current
    DESCRIPTION
        "The default registrar mode of the GVRP entry.
         0 - Normal
         1 - Fixed
         2 - Forbidden
         default: Normal"
    ::= { es2126PoEplusGvrpConfEntry 6 }

es2126PoEplusGvrpConfRestrictedMode   OBJECT-TYPE
    SYNTAX      INTEGER(0|1)
    MAX-ACCESS      read-write
    STATUS      current
    DESCRIPTION
        "The restricted mode of the GVRP entry.
         0 - Disable
         1 - Enable
         default: Disable"
    ::= { es2126PoEplusGvrpConfEntry 7 }

es2126PoEplusGvrpCounter              OBJECT IDENTIFIER ::= { es2126PoEplusGVRPInfo 2 }

es2126PoEplusGvrpCounterTable OBJECT-TYPE
    SYNTAX      SEQUENCE OF ES2126POEPLUSGvrpCounterEntry
    MAX-ACCESS  not-accessible
    STATUS      current
    DESCRIPTION
        "This is a list of the GVRP counter table."
    ::= { es2126PoEplusGvrpCounter 1 }

ES2126POEPLUSGvrpCounterEntry ::=
SEQUENCE {
    es2126PoEplusGvrpCounterIndex              INTEGER,
    es2126PoEplusGvrpCounterRxTotalGvrpPkts    Counter32,
    es2126PoEplusGvrpCounterRxInvalidGvrpPkts  Counter32,
    es2126PoEplusGvrpCounterRxLeaveAllMsg      Counter32,
    es2126PoEplusGvrpCounterRxJoinEmptyMsg     Counter32,
    es2126PoEplusGvrpCounterRxJoinInMsg        Counter32,
    es2126PoEplusGvrpCounterRxLeaveEmptyMsg    Counter32,
    es2126PoEplusGvrpCounterRxEmptyMsg         Counter32,
    es2126PoEplusGvrpCounterTxTotalGvrpPkts    Counter32,
    es2126PoEplusGvrpCounterTxLeaveAllMsg      Counter32,
    es2126PoEplusGvrpCounterTxJoinEmptyMsg     Counter32,
    es2126PoEplusGvrpCounterTxJoinInMsg        Counter32,
    es2126PoEplusGvrpCounterTxLeaveEmptyMsg    Counter32,
    es2126PoEplusGvrpCounterTxEmptyMsg         Counter32
}

es2126PoEplusGvrpCounterEntry OBJECT-TYPE
    SYNTAX      ES2126POEPLUSGvrpCounterEntry
    MAX-ACCESS      not-accessible
    STATUS      current
    DESCRIPTION
        "Entry(s) for the GVRP counter table."
    INDEX {es2126PoEplusGvrpCounterIndex}
    ::= { es2126PoEplusGvrpCounterTable 1 }

es2126PoEplusGvrpCounterIndex OBJECT-TYPE
    SYNTAX      INTEGER(1..26)
    MAX-ACCESS      not-accessible
    STATUS      current
    DESCRIPTION
        "The port index of the GVRP counter table."
    ::= { es2126PoEplusGvrpCounterEntry 1 }

es2126PoEplusGvrpCounterRxTotalGvrpPkts   OBJECT-TYPE
    SYNTAX      Counter32
    MAX-ACCESS      read-only
    STATUS      current
    DESCRIPTION
        "This is Rx Total GVRP packet counters."
    ::= { es2126PoEplusGvrpCounterEntry 2 }

es2126PoEplusGvrpCounterRxInvalidGvrpPkts OBJECT-TYPE
    SYNTAX      Counter32
    MAX-ACCESS      read-only
    STATUS      current
    DESCRIPTION
        "This is Rx Invalid GVRP packet counters."
    ::= { es2126PoEplusGvrpCounterEntry 3 }

es2126PoEplusGvrpCounterRxLeaveAllMsg OBJECT-TYPE
    SYNTAX      Counter32
    MAX-ACCESS      read-only
    STATUS      current
    DESCRIPTION
        "This is Rx LeaveAll message packet counters."
    ::= { es2126PoEplusGvrpCounterEntry 4 }

es2126PoEplusGvrpCounterRxJoinEmptyMsg    OBJECT-TYPE
    SYNTAX      Counter32
    MAX-ACCESS      read-only
    STATUS      current
    DESCRIPTION
        "This is Rx JoinEmpty message packet counters."
    ::= { es2126PoEplusGvrpCounterEntry 5 }

es2126PoEplusGvrpCounterRxJoinInMsg   OBJECT-TYPE
    SYNTAX      Counter32
    MAX-ACCESS      read-only
    STATUS      current
    DESCRIPTION
        "This is Rx JoinIn message packet counters."
    ::= { es2126PoEplusGvrpCounterEntry 6 }

es2126PoEplusGvrpCounterRxLeaveEmptyMsg   OBJECT-TYPE
    SYNTAX      Counter32
    MAX-ACCESS      read-only
    STATUS      current
    DESCRIPTION
        "This is Rx LeaveEmpty message packet counters."
    ::= { es2126PoEplusGvrpCounterEntry 7 }

es2126PoEplusGvrpCounterRxEmptyMsg    OBJECT-TYPE
    SYNTAX      Counter32
    MAX-ACCESS      read-only
    STATUS      current
    DESCRIPTION
        "This is Rx Empty message packet counters."
    ::= { es2126PoEplusGvrpCounterEntry 8 }

es2126PoEplusGvrpCounterTxTotalGvrpPkts   OBJECT-TYPE
    SYNTAX      Counter32
    MAX-ACCESS      read-only
    STATUS      current
    DESCRIPTION
        "This is Tx Total GVRP packet counters."
    ::= { es2126PoEplusGvrpCounterEntry 9 }

es2126PoEplusGvrpCounterTxLeaveAllMsg OBJECT-TYPE
    SYNTAX      Counter32
    MAX-ACCESS      read-only
    STATUS      current
    DESCRIPTION
        "This is Tx LeaveAll message packet counters."
    ::= { es2126PoEplusGvrpCounterEntry 10 }

es2126PoEplusGvrpCounterTxJoinEmptyMsg    OBJECT-TYPE
    SYNTAX      Counter32
    MAX-ACCESS      read-only
    STATUS      current
    DESCRIPTION
        "This is Tx JoinEmpty message packet counters."
    ::= { es2126PoEplusGvrpCounterEntry 11 }

es2126PoEplusGvrpCounterTxJoinInMsg   OBJECT-TYPE
    SYNTAX      Counter32
    MAX-ACCESS      read-only
    STATUS      current
    DESCRIPTION
        "This is Tx JoinIn message packet counters."
    ::= { es2126PoEplusGvrpCounterEntry 12 }

es2126PoEplusGvrpCounterTxLeaveEmptyMsg   OBJECT-TYPE
    SYNTAX      Counter32
    MAX-ACCESS      read-only
    STATUS      current
    DESCRIPTION
        "This is Tx LeaveEmpty message packet counters."
    ::= { es2126PoEplusGvrpCounterEntry 13 }

es2126PoEplusGvrpCounterTxEmptyMsg    OBJECT-TYPE
    SYNTAX      Counter32
    MAX-ACCESS      read-only
    STATUS      current
    DESCRIPTION
        "This is Tx Empty message packet counters."
    ::= { es2126PoEplusGvrpCounterEntry 14 }

es2126PoEplusGvrpGroup            OBJECT IDENTIFIER ::= { es2126PoEplusGVRPInfo 3 }

es2126PoEplusGvrpGroupNumber  OBJECT-TYPE
    SYNTAX      INTEGER(0..4094)
    MAX-ACCESS      read-only
    STATUS      current
    DESCRIPTION
        "This is number of the GVRP group table entry."
    ::= { es2126PoEplusGvrpGroup 1 }

es2126PoEplusGvrpGroupTable   OBJECT-TYPE
    SYNTAX      SEQUENCE OF ES2126POEPLUSGvrpGroupEntry
    MAX-ACCESS  not-accessible
    STATUS      current
    DESCRIPTION
        "This is a list of the GVRP group table."
    ::= { es2126PoEplusGvrpGroup 2 }

ES2126POEPLUSGvrpGroupEntry ::=
SEQUENCE {
    es2126PoEplusGvrpGroupId            INTEGER,
    es2126PoEplusGvrpGroupVid           INTEGER,
    es2126PoEplusGvrpGroupMemberPort    DisplayString
}

es2126PoEplusGvrpGroupEntry   OBJECT-TYPE
    SYNTAX      ES2126POEPLUSGvrpGroupEntry
    MAX-ACCESS      not-accessible
    STATUS      current
    DESCRIPTION
        "Entry(s) for the GVRP group table."
    INDEX {es2126PoEplusGvrpGroupId}
    ::= { es2126PoEplusGvrpGroupTable 1 }

es2126PoEplusGvrpGroupId  OBJECT-TYPE
    SYNTAX      INTEGER(1..4094)
    MAX-ACCESS      read-only
    STATUS      current
    DESCRIPTION
        "The index of the GVRP group table."
    ::= { es2126PoEplusGvrpGroupEntry 1 }

es2126PoEplusGvrpGroupVid OBJECT-TYPE
    SYNTAX      INTEGER(1..4094)
    MAX-ACCESS      read-only
    STATUS      current
    DESCRIPTION
        "This is vid of GVRP group."
    ::= { es2126PoEplusGvrpGroupEntry 2 }

es2126PoEplusGvrpGroupMemberPort  OBJECT-TYPE
    SYNTAX      DisplayString
    MAX-ACCESS      read-only
    STATUS      current
    DESCRIPTION
        "This is the member port of GVRP group."
    ::= { es2126PoEplusGvrpGroupEntry 3 }

es2126PoEplusSecurity             OBJECT IDENTIFIER ::= { es2126PoEplusProduces 13 }

es2126PoEplusIsolatedPortGroup OBJECT-TYPE
    SYNTAX      DisplayString
    MAX-ACCESS      read-write
    STATUS      current
    DESCRIPTION
        "This is isolated group.
         0: Disable"
    ::= { es2126PoEplusSecurity 1 }

es2126PoEplusMirror               OBJECT IDENTIFIER ::= { es2126PoEplusSecurity 2 }

es2126PoEplusMirrorMode OBJECT-TYPE
    SYNTAX      INTEGER(0|1)
    MAX-ACCESS      read-write
    STATUS      current
    DESCRIPTION
        "This is mirror mode.
         0 - Disable
         1 - Enable
    "
    ::= { es2126PoEplusMirror 1 }

es2126PoEplusMonitoringPort OBJECT-TYPE
    SYNTAX      INTEGER(1..26)
    MAX-ACCESS      read-write
    STATUS      current
    DESCRIPTION
        "This is monitoring port."
    ::= { es2126PoEplusMirror 2 }

es2126PoEplusMonitoredIngressPort OBJECT-TYPE
    SYNTAX      DisplayString
    MAX-ACCESS      read-write
    STATUS      current
    DESCRIPTION
        "This is monitored ingress ports."
    ::= { es2126PoEplusMirror 3 }

es2126PoEplusMonitoredEgressPort OBJECT-TYPE
    SYNTAX      DisplayString
    MAX-ACCESS      read-write
    STATUS      current
    DESCRIPTION
        "This is monitored egress ports."
    ::= { es2126PoEplusMirror 4 }

es2126PoEplusRestrictedGroup              OBJECT IDENTIFIER ::= { es2126PoEplusSecurity 3 }

es2126PoEplusRestrictedGroupIngress OBJECT-TYPE
    SYNTAX      DisplayString
    MAX-ACCESS      read-write
    STATUS      current
    DESCRIPTION
        "This is the ingress port members of restricted group."
    ::= { es2126PoEplusRestrictedGroup 1 }

es2126PoEplusRestrictedGroupEgress OBJECT-TYPE
    SYNTAX      DisplayString
    MAX-ACCESS      read-write
    STATUS      current
    DESCRIPTION
        "This is the egress port members of restricted group."
    ::= { es2126PoEplusRestrictedGroup 2 }

es2126PoEplusVirtualStack        OBJECT IDENTIFIER ::= { es2126PoEplusProduces 14 }

es2126PoEplusVirtualStackState   OBJECT-TYPE
    SYNTAX      INTEGER(0|1)
    MAX-ACCESS  read-write
    STATUS      current
    DESCRIPTION
        "Set the Virtual Stack State.
         0 : disable,
         1 : enable
        "
    ::= { es2126PoEplusVirtualStack 1 }

es2126PoEplusVirtualStackRole   OBJECT-TYPE
    SYNTAX      INTEGER(0|1)
    MAX-ACCESS  read-write
    STATUS      current
    DESCRIPTION
        "Set the Virtual Stack Role.
         0 : slave,
         1 : master
        "
    ::= { es2126PoEplusVirtualStack 2 }

es2126PoEplusVirtualStackGroupID  OBJECT-TYPE
    SYNTAX      DisplayString
    MAX-ACCESS  read-write
    STATUS      current
    DESCRIPTION
        "Set the Virtual Stack Group ID."
    ::= { es2126PoEplusVirtualStack 3 }

es2126PoEplusManagementSecurity               OBJECT IDENTIFIER ::= { es2126PoEplusProduces 15 }

es2126PoEplusManagementSecurityNumber OBJECT-TYPE
    SYNTAX      INTEGER(0..64)
    MAX-ACCESS      read-only
    STATUS      current
    DESCRIPTION
        "This is number of the management security table entry."
    ::= { es2126PoEplusManagementSecurity 1 }

es2126PoEplusManagementSecurityEntryCreate OBJECT-TYPE
    SYNTAX      INTEGER(0..64)
    MAX-ACCESS      read-write
    STATUS      current
    DESCRIPTION
        "Creat a management security entry."
    ::= { es2126PoEplusManagementSecurity 2 }

es2126PoEplusManagementSecurityTable  OBJECT-TYPE
    SYNTAX      SEQUENCE OF ES2126POEPLUSManagementSecurityEntry
    MAX-ACCESS  not-accessible
    STATUS      current
    DESCRIPTION
        "This is a list of the management security table."
    ::= { es2126PoEplusManagementSecurity 3 }

ES2126POEPLUSManagementSecurityEntry ::=
SEQUENCE {
    es2126PoEplusManagementSecurityIndex          INTEGER,
    es2126PoEplusManagementSecurityName           DisplayString,
    es2126PoEplusManagementSecurityVid            INTEGER,
    es2126PoEplusManagementSecurityIpRange        DisplayString,
    es2126PoEplusManagementSecurityIncomigPort    DisplayString,
    es2126PoEplusManagementSecurityAccessType     DisplayString,
    es2126PoEplusManagementSecurityAction         INTEGER,
    es2126PoEplusManagementSecurityEntryAction    INTEGER
}

es2126PoEplusManagementSecurityEntry  OBJECT-TYPE
    SYNTAX      ES2126POEPLUSManagementSecurityEntry
    MAX-ACCESS      not-accessible
    STATUS      current
    DESCRIPTION
        "Entry(s) for the management security table."
    INDEX {es2126PoEplusManagementSecurityIndex}
    ::= { es2126PoEplusManagementSecurityTable 1 }

es2126PoEplusManagementSecurityIndex  OBJECT-TYPE
    SYNTAX      INTEGER(1..64)
    MAX-ACCESS      not-accessible
    STATUS      current
    DESCRIPTION
        "The index of the management security table."
    ::= { es2126PoEplusManagementSecurityEntry 1 }

es2126PoEplusManagementSecurityName   OBJECT-TYPE
    SYNTAX      DisplayString
    MAX-ACCESS      read-write
    STATUS      current
    DESCRIPTION
        "The name of the management security entry."
    ::= { es2126PoEplusManagementSecurityEntry 2 }

es2126PoEplusManagementSecurityVid    OBJECT-TYPE
    SYNTAX      INTEGER(0..4094)
    MAX-ACCESS      read-write
    STATUS      current
    DESCRIPTION
        "This is the vid of the management security entry.
         0: any VID."
    ::= { es2126PoEplusManagementSecurityEntry 3 }

es2126PoEplusManagementSecurityIpRange    OBJECT-TYPE
    SYNTAX      DisplayString
    MAX-ACCESS      read-write
    STATUS      current
    DESCRIPTION
        "This is the IP range of the management security entry.
         0: any IP."
    ::= { es2126PoEplusManagementSecurityEntry 4 }

es2126PoEplusManagementSecurityIncomigPort    OBJECT-TYPE
    SYNTAX      DisplayString
    MAX-ACCESS      read-write
    STATUS      current
    DESCRIPTION
        "This is the ports of the management security entry.
         0: any incoming port."
    ::= { es2126PoEplusManagementSecurityEntry 5 }

es2126PoEplusManagementSecurityAccessType OBJECT-TYPE
    SYNTAX      DisplayString
    MAX-ACCESS      read-write
    STATUS      current
    DESCRIPTION
        "This is the access type of the management security entry.
         0: http, telnet, and SNMP."
    ::= { es2126PoEplusManagementSecurityEntry 6 }

es2126PoEplusManagementSecurityAction OBJECT-TYPE
    SYNTAX      INTEGER(0|1)
    MAX-ACCESS      read-write
    STATUS      current
    DESCRIPTION
        "This is the action of the management security entry.
         0:deny
         1:accept"
    ::= { es2126PoEplusManagementSecurityEntry 7 }

es2126PoEplusManagementSecurityEntryAction    OBJECT-TYPE
    SYNTAX      INTEGER(0..3)
    MAX-ACCESS      read-write
    STATUS      current
    DESCRIPTION
        "The action the management security entry."
    ::= { es2126PoEplusManagementSecurityEntry 8 }

es2126PoEplusQoS              OBJECT IDENTIFIER ::= { es2126PoEplusProduces 16 }

es2126PoEplusQoSGlobalConfig              OBJECT IDENTIFIER ::= { es2126PoEplusQoS 1 }

es2126PoEplusQoSMode OBJECT-TYPE
    SYNTAX      INTEGER(0|1)
    MAX-ACCESS      read-write
    STATUS      current
    DESCRIPTION
        "The mode of QoS.
         0 - Disable
         1 - Enable
    "
    ::= { es2126PoEplusQoSGlobalConfig 1 }

es2126PoEplusQosPriorityControl1p OBJECT-TYPE
    SYNTAX      INTEGER(0|1)
    MAX-ACCESS      read-write
    STATUS      current
    DESCRIPTION
        "This is the priority control for 802.1p.
         0 - Disable
         1 - Enable
    "
    ::= { es2126PoEplusQoSGlobalConfig 2 }

es2126PoEplusQosPriorityControlTOS OBJECT-TYPE
    SYNTAX      INTEGER(0|1)
    MAX-ACCESS      read-write
    STATUS      current
    DESCRIPTION
        "This is the priority control for TOS.
         0 - Disable
         1 - Enable
    "
    ::= { es2126PoEplusQoSGlobalConfig 3 }

es2126PoEplusQosPriorityControlDSCP OBJECT-TYPE
    SYNTAX      INTEGER(0|1)
    MAX-ACCESS      read-write
    STATUS      current
    DESCRIPTION
        "This is the priority control for DSCP.
         0 - Disable
         1 - Enable
    "
    ::= { es2126PoEplusQoSGlobalConfig 4 }

es2126PoEplusQoSSchedulingMethod OBJECT-TYPE
    SYNTAX      INTEGER(0|1)
    MAX-ACCESS      read-write
    STATUS      current
    DESCRIPTION
        "This is the scheduling method.
         0 - WRR
         1 - Strict
    "
    ::= { es2126PoEplusQoSGlobalConfig 5 }

es2126PoEplusQoSWeightQ0 OBJECT-TYPE
    SYNTAX      INTEGER(1..55)
    MAX-ACCESS      read-write
    STATUS      current
    DESCRIPTION
        "This is the weigtht of Queue0."
    ::= { es2126PoEplusQoSGlobalConfig 6 }

es2126PoEplusQoSWeightQ1 OBJECT-TYPE
    SYNTAX      INTEGER(1..55)
    MAX-ACCESS      read-write
    STATUS      current
    DESCRIPTION
        "This is the weigtht of Queue1."
    ::= { es2126PoEplusQoSGlobalConfig 7 }

es2126PoEplusQoSWeightQ2 OBJECT-TYPE
    SYNTAX      INTEGER(1..55)
    MAX-ACCESS      read-write
    STATUS      current
    DESCRIPTION
        "This is the weigtht of Queue2."
    ::= { es2126PoEplusQoSGlobalConfig 8 }

es2126PoEplusQoSWeightQ3 OBJECT-TYPE
    SYNTAX      INTEGER(1..55)
    MAX-ACCESS      read-write
    STATUS      current
    DESCRIPTION
        "This is the weigtht of Queue3."
    ::= { es2126PoEplusQoSGlobalConfig 9 }

es2126PoEplusQoSVIPPort OBJECT-TYPE
    SYNTAX      DisplayString
    MAX-ACCESS      read-write
    STATUS      current
    DESCRIPTION
        "This is the VIP group for QoS."
    ::= { es2126PoEplusQoS 2 }

es2126PoEplusQoS1pPriority            OBJECT IDENTIFIER ::= { es2126PoEplusQoS 3 }

es2126PoEplusQoS1pPriorityTable   OBJECT-TYPE
    SYNTAX      SEQUENCE OF ES2126POEPLUSQoS1pPriorityEntry
    MAX-ACCESS  not-accessible
    STATUS      current
    DESCRIPTION
        "This is a list of the 802.1p."
    ::= { es2126PoEplusQoS1pPriority 1 }

ES2126POEPLUSQoS1pPriorityEntry ::=
SEQUENCE {
    es2126PoEplusQoS1pPriorityIndex    INTEGER,
    es2126PoEplusQoS1pPriorityValue    INTEGER,
    es2126PoEplusQoS1pPriorityQueue    INTEGER
}

es2126PoEplusQoS1pPriorityEntry   OBJECT-TYPE
    SYNTAX      ES2126POEPLUSQoS1pPriorityEntry
    MAX-ACCESS      not-accessible
    STATUS      current
    DESCRIPTION
        "Entry(s) for the 802.1p priority table."
    INDEX {es2126PoEplusQoS1pPriorityIndex}
    ::= { es2126PoEplusQoS1pPriorityTable 1 }

es2126PoEplusQoS1pPriorityIndex   OBJECT-TYPE
    SYNTAX      INTEGER(1..8)
    MAX-ACCESS      not-accessible
    STATUS      current
    DESCRIPTION
        "The index of the 802.1p priority table."
    ::= { es2126PoEplusQoS1pPriorityEntry 1 }

es2126PoEplusQoS1pPriorityValue   OBJECT-TYPE
    SYNTAX      INTEGER(0..7)
    MAX-ACCESS      read-only
    STATUS      current
    DESCRIPTION
        "The value of 802.1p priority entry."
    ::= { es2126PoEplusQoS1pPriorityEntry 2 }

es2126PoEplusQoS1pPriorityQueue   OBJECT-TYPE
    SYNTAX      INTEGER(0..3)
    MAX-ACCESS      read-write
    STATUS      current
    DESCRIPTION
        "The queue of 802.1p priority entry."
    ::= { es2126PoEplusQoS1pPriorityEntry 3 }

es2126PoEplusQoSDTypeTOSPriority              OBJECT IDENTIFIER ::= { es2126PoEplusQoS 4 }

es2126PoEplusQoSDTypeTOSPriorityTable OBJECT-TYPE
    SYNTAX      SEQUENCE OF ES2126POEPLUSQoSDTypeTOSPriorityEntry
    MAX-ACCESS  not-accessible
    STATUS      current
    DESCRIPTION
        "This is a list of the TOS delay priority mapping entry."
    ::= { es2126PoEplusQoSDTypeTOSPriority 1 }

ES2126POEPLUSQoSDTypeTOSPriorityEntry ::=
SEQUENCE {
    es2126PoEplusQoSDTypeTOSPriorityIndex    INTEGER,
    es2126PoEplusQoSDTypeTOSPriorityValue    INTEGER,
    es2126PoEplusQoSDTypeTOSPriorityQueue    INTEGER
}

es2126PoEplusQoSDTypeTOSPriorityEntry OBJECT-TYPE
    SYNTAX      ES2126POEPLUSQoSDTypeTOSPriorityEntry
    MAX-ACCESS      not-accessible
    STATUS      current
    DESCRIPTION
        "Entry(s) for the ToS delay priority mapping entry."
    INDEX {es2126PoEplusQoSDTypeTOSPriorityIndex}
    ::= { es2126PoEplusQoSDTypeTOSPriorityTable 1 }

es2126PoEplusQoSDTypeTOSPriorityIndex OBJECT-TYPE
    SYNTAX      INTEGER(1..8)
    MAX-ACCESS      not-accessible
    STATUS      current
    DESCRIPTION
        "The index of the ToS delay priority mapping table."
    ::= { es2126PoEplusQoSDTypeTOSPriorityEntry 1 }

es2126PoEplusQoSDTypeTOSPriorityValue OBJECT-TYPE
    SYNTAX      INTEGER(0..7)
    MAX-ACCESS      read-only
    STATUS      current
    DESCRIPTION
        "The value of ToS delay priority mapping entry."
    ::= { es2126PoEplusQoSDTypeTOSPriorityEntry 2 }

es2126PoEplusQoSDTypeTOSPriorityQueue OBJECT-TYPE
    SYNTAX      INTEGER(0..3)
    MAX-ACCESS      read-write
    STATUS      current
    DESCRIPTION
        "The queue of ToS delay priority mapping entry."
    ::= { es2126PoEplusQoSDTypeTOSPriorityEntry 3 }

es2126PoEplusQoSTTypeTOSPriority              OBJECT IDENTIFIER ::= { es2126PoEplusQoS 5 }

es2126PoEplusQoSTTypeTOSPriorityTable OBJECT-TYPE
    SYNTAX      SEQUENCE OF ES2126POEPLUSQoSTTypeTOSPriorityEntry
    MAX-ACCESS  not-accessible
    STATUS      current
    DESCRIPTION
        "This is a list of the ToS throughput priority mapping entry."
    ::= { es2126PoEplusQoSTTypeTOSPriority 1 }

ES2126POEPLUSQoSTTypeTOSPriorityEntry ::=
SEQUENCE {
    es2126PoEplusQoSTTypeTOSPriorityIndex    INTEGER,
    es2126PoEplusQoSTTypeTOSPriorityValue    INTEGER,
    es2126PoEplusQoSTTypeTOSPriorityQueue    INTEGER
}

es2126PoEplusQoSTTypeTOSPriorityEntry OBJECT-TYPE
    SYNTAX      ES2126POEPLUSQoSTTypeTOSPriorityEntry
    MAX-ACCESS      not-accessible
    STATUS      current
    DESCRIPTION
        "Entry(s) for the TOS Throughput mapping entry."
    INDEX {es2126PoEplusQoSTTypeTOSPriorityIndex}
    ::= { es2126PoEplusQoSTTypeTOSPriorityTable 1 }

es2126PoEplusQoSTTypeTOSPriorityIndex OBJECT-TYPE
    SYNTAX      INTEGER(1..8)
    MAX-ACCESS      not-accessible
    STATUS      current
    DESCRIPTION
        "The index of the TOS throughput priority mapping table."
    ::= { es2126PoEplusQoSTTypeTOSPriorityEntry 1 }

es2126PoEplusQoSTTypeTOSPriorityValue OBJECT-TYPE
    SYNTAX      INTEGER(0..7)
    MAX-ACCESS      read-only
    STATUS      current
    DESCRIPTION
        "The value of TOS throughput priority mapping entry."
    ::= { es2126PoEplusQoSTTypeTOSPriorityEntry 2 }

es2126PoEplusQoSTTypeTOSPriorityQueue OBJECT-TYPE
    SYNTAX      INTEGER(0..3)
    MAX-ACCESS      read-write
    STATUS      current
    DESCRIPTION
        "The queue of TOS throughput priority mapping entry."
    ::= { es2126PoEplusQoSTTypeTOSPriorityEntry 3 }

es2126PoEplusQoSRTypeTOSPriority              OBJECT IDENTIFIER ::= { es2126PoEplusQoS 6 }

es2126PoEplusQoSRTypeTOSPriorityTable OBJECT-TYPE
    SYNTAX      SEQUENCE OF ES2126POEPLUSQoSRTypeTOSPriorityEntry
    MAX-ACCESS  not-accessible
    STATUS      current
    DESCRIPTION
        "This is a list of the ToS reliability priority mapping entry."
    ::= { es2126PoEplusQoSRTypeTOSPriority 1 }

ES2126POEPLUSQoSRTypeTOSPriorityEntry ::=
SEQUENCE {
    es2126PoEplusQoSRTypeTOSPriorityIndex    INTEGER,
    es2126PoEplusQoSRTypeTOSPriorityValue    INTEGER,
    es2126PoEplusQoSRTypeTOSPriorityQueue    INTEGER
}

es2126PoEplusQoSRTypeTOSPriorityEntry OBJECT-TYPE
    SYNTAX      ES2126POEPLUSQoSRTypeTOSPriorityEntry
    MAX-ACCESS      not-accessible
    STATUS      current
    DESCRIPTION
        "Entry(s) for the TOS reliability mapping entry."
    INDEX {es2126PoEplusQoSRTypeTOSPriorityIndex}
    ::= { es2126PoEplusQoSRTypeTOSPriorityTable 1 }

es2126PoEplusQoSRTypeTOSPriorityIndex OBJECT-TYPE
    SYNTAX      INTEGER(1..8)
    MAX-ACCESS      not-accessible
    STATUS      current
    DESCRIPTION
        "The index of the TOS reliability priority mapping table."
    ::= { es2126PoEplusQoSRTypeTOSPriorityEntry 1 }

es2126PoEplusQoSRTypeTOSPriorityValue OBJECT-TYPE
    SYNTAX      INTEGER(0..7)
    MAX-ACCESS      read-only
    STATUS      current
    DESCRIPTION
        "The value of TOS reliability priority mapping entry."
    ::= { es2126PoEplusQoSRTypeTOSPriorityEntry 2 }

es2126PoEplusQoSRTypeTOSPriorityQueue OBJECT-TYPE
    SYNTAX      INTEGER(0..3)
    MAX-ACCESS      read-write
    STATUS      current
    DESCRIPTION
        "The queue of TOS reliability priority mapping entry."
    ::= { es2126PoEplusQoSRTypeTOSPriorityEntry 3 }

es2126PoEplusQoSMTypeTOSPriority              OBJECT IDENTIFIER ::= { es2126PoEplusQoS 7 }

es2126PoEplusQoSMTypeTOSPriorityTable OBJECT-TYPE
    SYNTAX      SEQUENCE OF ES2126POEPLUSQoSMTypeTOSPriorityEntry
    MAX-ACCESS  not-accessible
    STATUS      current
    DESCRIPTION
        "This is a list of the ToS monetary cost priority mapping entry."
    ::= { es2126PoEplusQoSMTypeTOSPriority 1 }

ES2126POEPLUSQoSMTypeTOSPriorityEntry ::=
SEQUENCE {
    es2126PoEplusQoSMTypeTOSPriorityIndex    INTEGER,
    es2126PoEplusQoSMTypeTOSPriorityValue    INTEGER,
    es2126PoEplusQoSMTypeTOSPriorityQueue    INTEGER
}

es2126PoEplusQoSMTypeTOSPriorityEntry OBJECT-TYPE
    SYNTAX      ES2126POEPLUSQoSMTypeTOSPriorityEntry
    MAX-ACCESS      not-accessible
    STATUS      current
    DESCRIPTION
        "Entry(s) for the TOS monetary cost mapping entry."
    INDEX {es2126PoEplusQoSMTypeTOSPriorityIndex}
    ::= { es2126PoEplusQoSMTypeTOSPriorityTable 1 }

es2126PoEplusQoSMTypeTOSPriorityIndex OBJECT-TYPE
    SYNTAX      INTEGER(1..8)
    MAX-ACCESS      not-accessible
    STATUS      current
    DESCRIPTION
        "The index of the TOS monetary cost priority mapping table."
    ::= { es2126PoEplusQoSMTypeTOSPriorityEntry 1 }

es2126PoEplusQoSMTypeTOSPriorityValue OBJECT-TYPE
    SYNTAX      INTEGER(0..7)
    MAX-ACCESS      read-only
    STATUS      current
    DESCRIPTION
        "The value of TOS monetary cost priority mapping entry."
    ::= { es2126PoEplusQoSMTypeTOSPriorityEntry 2 }

es2126PoEplusQoSMTypeTOSPriorityQueue OBJECT-TYPE
    SYNTAX      INTEGER(0..3)
    MAX-ACCESS      read-write
    STATUS      current
    DESCRIPTION
        "The queue of TOS monetary cost priority mapping entry."
    ::= { es2126PoEplusQoSMTypeTOSPriorityEntry 3 }

es2126PoEplusQoSDSCPPriority              OBJECT IDENTIFIER ::= { es2126PoEplusQoS 8 }

es2126PoEplusQoSDSCPPriorityTable OBJECT-TYPE
    SYNTAX      SEQUENCE OF ES2126POEPLUSQoSDSCPPriorityEntry
    MAX-ACCESS  not-accessible
    STATUS      current
    DESCRIPTION
        "This is a list of the DSCP priority entry."
    ::= { es2126PoEplusQoSDSCPPriority 1 }

ES2126POEPLUSQoSDSCPPriorityEntry ::=
SEQUENCE {
    es2126PoEplusQoSDSCPPriorityIndex    INTEGER,
    es2126PoEplusQoSDSCPPriorityValue    INTEGER,
    es2126PoEplusQoSDSCPPriorityQueue    INTEGER
}

es2126PoEplusQoSDSCPPriorityEntry OBJECT-TYPE
    SYNTAX      ES2126POEPLUSQoSDSCPPriorityEntry
    MAX-ACCESS      not-accessible
    STATUS      current
    DESCRIPTION
        "Entry(s) for the DSCP priority mapping entry."
    INDEX {es2126PoEplusQoSDSCPPriorityIndex}
    ::= { es2126PoEplusQoSDSCPPriorityTable 1 }

es2126PoEplusQoSDSCPPriorityIndex OBJECT-TYPE
    SYNTAX      INTEGER(1..64)
    MAX-ACCESS      not-accessible
    STATUS      current
    DESCRIPTION
        "The index of the DSCP priority priority mapping table."
    ::= { es2126PoEplusQoSDSCPPriorityEntry 1 }

es2126PoEplusQoSDSCPPriorityValue OBJECT-TYPE
    SYNTAX      INTEGER(0..63)
    MAX-ACCESS      read-only
    STATUS      current
    DESCRIPTION
        "The value of DSCP priority priority mapping entry."
    ::= { es2126PoEplusQoSDSCPPriorityEntry 2 }

es2126PoEplusQoSDSCPPriorityQueue OBJECT-TYPE
    SYNTAX      INTEGER(0..3)
    MAX-ACCESS      read-write
    STATUS      current
    DESCRIPTION
        "The queue of DSCP priority priority mapping entry."
    ::= { es2126PoEplusQoSDSCPPriorityEntry 3 }

es2126PoEplusVlan      OBJECT IDENTIFIER ::= { es2126PoEplusProduces 17 }

es2126PoEplusVlanModeConfig      OBJECT IDENTIFIER ::= { es2126PoEplusVlan 1 }

es2126PoEplusVlanMode  OBJECT-TYPE
    SYNTAX      INTEGER(0..2)
    MAX-ACCESS  read-write
    STATUS      current
    DESCRIPTION
        "0:Tag-based, 1:Port-based, 2:Metro mode"
    ::= { es2126PoEplusVlanModeConfig 1 }

es2126PoEplusSymmetricVlan  OBJECT-TYPE
    SYNTAX      INTEGER(0|1)
    MAX-ACCESS  read-write
    STATUS      current
    DESCRIPTION
        "Symmetric VLAN: for tag-based
        0:disable, 1:enable"
    ::= { es2126PoEplusVlanModeConfig 2 }

es2126PoEplusVlanSVL  OBJECT-TYPE
    SYNTAX      INTEGER(0|1)
    MAX-ACCESS  read-write
    STATUS      current
    DESCRIPTION
        "SVL: : for tag-based
        0:disable, 1:enable"
    ::= { es2126PoEplusVlanModeConfig 3 }

es2126PoEplusDoubleTag  OBJECT-TYPE
    SYNTAX      INTEGER(0|1)
    MAX-ACCESS  read-write
    STATUS      current
    DESCRIPTION
        "Double Tag: for tag-based
        0:disable, 1:enable"
    ::= { es2126PoEplusVlanModeConfig 4 }

es2126PoEplusUpLinkPort  OBJECT-TYPE
    SYNTAX      INTEGER(0..2)
    MAX-ACCESS  read-write
    STATUS      current
    DESCRIPTION
        "Up link Port: for Metro mode
        0:Port 25, 1:Port 26, 2:Port 25 & 26"
    ::= { es2126PoEplusVlanModeConfig 5 }

es2126PoEplusTagBasedVlanGroup      OBJECT IDENTIFIER ::= { es2126PoEplusVlan 2 }

es2126PoEplusTagBasedVlanNumbers  OBJECT-TYPE
    SYNTAX      INTEGER(1..4094)
    MAX-ACCESS  read-only
    STATUS      current
    DESCRIPTION
        "Total numbers for tag-based vlan."
    ::= { es2126PoEplusTagBasedVlanGroup 1 }

es2126PoEplusTagBasedCreateStatus  OBJECT-TYPE
    SYNTAX      INTEGER(0..4094)
    MAX-ACCESS  read-write
    STATUS      current
    DESCRIPTION
        "Creat a temp vlan in tag-based vlan table.
         0 : none,
         1~4094 : creat with this vid.
        "
    ::= { es2126PoEplusTagBasedVlanGroup 2 }

es2126PoEplusTagBasedVlanTable  OBJECT-TYPE
    SYNTAX      SEQUENCE OF ES2126POEPLUSTagBasedVlanEntry
    MAX-ACCESS  not-accessible
    STATUS      current
    DESCRIPTION
        " "
    ::= { es2126PoEplusTagBasedVlanGroup 3 }

ES2126POEPLUSTagBasedVlanEntry ::=
SEQUENCE {
    es2126PoEplusTagBasedVlanVid              INTEGER,
    es2126PoEplusTagBasedVlanName                 DisplayString,
    es2126PoEplusTagBasedVlanMember               DisplayString,
    es2126PoEplusTagBasedVlanUntag                DisplayString,
    es2126PoEplusTagBasedVlanRowStatus                INTEGER
}

es2126PoEplusTagBasedVlanEntry OBJECT-TYPE
    SYNTAX      ES2126POEPLUSTagBasedVlanEntry
    MAX-ACCESS  not-accessible
    STATUS      current
    DESCRIPTION
        "Entry(s) for tag-based vlan table."
    INDEX {es2126PoEplusTagBasedVlanVid}
    ::= { es2126PoEplusTagBasedVlanTable 1 }

es2126PoEplusTagBasedVlanVid  OBJECT-TYPE
    SYNTAX      INTEGER(1..4094)
    MAX-ACCESS  not-accessible
    STATUS      current
    DESCRIPTION
        "The vid of vlan."
    ::= { es2126PoEplusTagBasedVlanEntry 1 }

es2126PoEplusTagBasedVlanName  OBJECT-TYPE
    SYNTAX      DisplayString
    MAX-ACCESS  read-write
    STATUS      current
    DESCRIPTION
        "The name of vlan."
    ::= { es2126PoEplusTagBasedVlanEntry 2 }

es2126PoEplusTagBasedVlanMember  OBJECT-TYPE
    SYNTAX      DisplayString
    MAX-ACCESS  read-write
    STATUS      current
    DESCRIPTION
        "The member of vlan."
    ::= { es2126PoEplusTagBasedVlanEntry 3 }

es2126PoEplusTagBasedVlanUntag  OBJECT-TYPE
    SYNTAX      DisplayString
    MAX-ACCESS  read-write
    STATUS      current
    DESCRIPTION
        "The untag port of vlan."
    ::= { es2126PoEplusTagBasedVlanEntry 4 }

es2126PoEplusTagBasedVlanRowStatus  OBJECT-TYPE
    SYNTAX      INTEGER(1..3)
    MAX-ACCESS  read-write
    STATUS      current
    DESCRIPTION
        "The row status of vlan.
         1 : active,
         2 : not-inService,
         3 : delete
        "
    ::= { es2126PoEplusTagBasedVlanEntry 5 }

es2126PoEplusVlanPvid      OBJECT IDENTIFIER ::= { es2126PoEplusVlan 3 }

es2126PoEplusVlanPvidTable  OBJECT-TYPE
    SYNTAX      SEQUENCE OF ES2126POEPLUSVlanPvidEntry
    MAX-ACCESS  not-accessible
    STATUS      current
    DESCRIPTION
        " "
    ::= { es2126PoEplusVlanPvid 1 }

ES2126POEPLUSVlanPvidEntry ::=
SEQUENCE {
    es2126PoEplusVlanPvidPort             INTEGER,
    es2126PoEplusVlanPvidValue            INTEGER,
    es2126PoEplusVlanPvidDefaultPriority              INTEGER,
    es2126PoEplusVlanPvidDropUntag            INTEGER
}

es2126PoEplusVlanPvidEntry OBJECT-TYPE
    SYNTAX      ES2126POEPLUSVlanPvidEntry
    MAX-ACCESS  not-accessible
    STATUS      current
    DESCRIPTION
        "Entry(s) for Vlan Pvid."
    INDEX {es2126PoEplusVlanPvidPort}
    ::= { es2126PoEplusVlanPvidTable 1 }

es2126PoEplusVlanPvidPort  OBJECT-TYPE
    SYNTAX      INTEGER(1..26)
    MAX-ACCESS  not-accessible
    STATUS      current
    DESCRIPTION
        "The port number of pvid entry."
    ::= { es2126PoEplusVlanPvidEntry 1 }

es2126PoEplusVlanPvidValue  OBJECT-TYPE
    SYNTAX      INTEGER(1..4094)
    MAX-ACCESS  read-write
    STATUS      current
    DESCRIPTION
        "The pvid value of port."
    ::= { es2126PoEplusVlanPvidEntry 2 }

es2126PoEplusVlanPvidDefaultPriority  OBJECT-TYPE
    SYNTAX      INTEGER(0..7)
    MAX-ACCESS  read-write
    STATUS      current
    DESCRIPTION
        "The default priority of port ."
    ::= { es2126PoEplusVlanPvidEntry 3 }

es2126PoEplusVlanPvidDropUntag  OBJECT-TYPE
    SYNTAX      INTEGER(0..7)
    MAX-ACCESS  read-write
    STATUS      current
    DESCRIPTION
        "The drop untag of port ."
    ::= { es2126PoEplusVlanPvidEntry 4 }

es2126PoEplusPortBasedVlanGroup      OBJECT IDENTIFIER ::= { es2126PoEplusVlan 4 }

es2126PoEplusPortBasedVlanNumbers  OBJECT-TYPE
    SYNTAX      INTEGER(1..26)
    MAX-ACCESS  read-only
    STATUS      current
    DESCRIPTION
        "Total numbers for tag-based vlan."
    ::= { es2126PoEplusPortBasedVlanGroup 1 }

es2126PoEplusPortBasedCreateStatus  OBJECT-TYPE
    SYNTAX      INTEGER(0|1)
    MAX-ACCESS  read-write
    STATUS      current
    DESCRIPTION
        "Creat a temp vlan in port-based vlan table.
         0 : none,
         1 : creat a new port-based vlan.
        "
    ::= { es2126PoEplusPortBasedVlanGroup 2 }

es2126PoEplusPortBasedVlanTable  OBJECT-TYPE
    SYNTAX      SEQUENCE OF ES2126POEPLUSPortBasedVlanEntry
    MAX-ACCESS  not-accessible
    STATUS      current
    DESCRIPTION
        " "
    ::= { es2126PoEplusPortBasedVlanGroup 3 }

ES2126POEPLUSPortBasedVlanEntry ::=
SEQUENCE {
    es2126PoEplusPortBasedVlanIndex               INTEGER,
    es2126PoEplusPortBasedVlanName                DisplayString,
    es2126PoEplusPortBasedVlanMember                  DisplayString,
    es2126PoEplusPortBasedVlanRowStatus           INTEGER
}

es2126PoEplusPortBasedVlanEntry OBJECT-TYPE
    SYNTAX      ES2126POEPLUSPortBasedVlanEntry
    MAX-ACCESS  not-accessible
    STATUS      current
    DESCRIPTION
        "Entry(s) for port-based vlan table."
    INDEX {es2126PoEplusPortBasedVlanIndex}
    ::= { es2126PoEplusPortBasedVlanTable 1 }

es2126PoEplusPortBasedVlanIndex  OBJECT-TYPE
    SYNTAX      INTEGER(1..26)
    MAX-ACCESS  not-accessible
    STATUS      current
    DESCRIPTION
        "The index of vlan."
    ::= { es2126PoEplusPortBasedVlanEntry 1 }

es2126PoEplusPortBasedVlanName  OBJECT-TYPE
    SYNTAX      DisplayString
    MAX-ACCESS  read-write
    STATUS      current
    DESCRIPTION
        "The name of vlan."
    ::= { es2126PoEplusPortBasedVlanEntry 2 }

es2126PoEplusPortBasedVlanMember  OBJECT-TYPE
    SYNTAX      DisplayString
    MAX-ACCESS  read-write
    STATUS      current
    DESCRIPTION
        "The member of vlan."
    ::= { es2126PoEplusPortBasedVlanEntry 3 }

es2126PoEplusPortBasedVlanRowStatus  OBJECT-TYPE
    SYNTAX      INTEGER(1..3)
    MAX-ACCESS  read-write
    STATUS      current
    DESCRIPTION
        "The row status of vlan.
         1 : active,
         2 : not-inService,
         3 : delete
        "
    ::= { es2126PoEplusPortBasedVlanEntry 4 }

es2126PoEplusManagementVlan      OBJECT IDENTIFIER ::= { es2126PoEplusVlan 5 }

es2126PoEplusManagementVlanState  OBJECT-TYPE
    SYNTAX      INTEGER(0|1)
    MAX-ACCESS  read-write
    STATUS      current
    DESCRIPTION
        "The stat of management vlan. (for tag-base)
         0 : Disable,
         1 : Enable.
        "
    ::= { es2126PoEplusManagementVlan 1 }

es2126PoEplusManagementVlanVid  OBJECT-TYPE
    SYNTAX      INTEGER(1..4094)
    MAX-ACCESS  read-write
    STATUS      current
    DESCRIPTION
        "The vid value of management vlan."
    ::= { es2126PoEplusManagementVlan 2 }

es2126PoEplusDot1X        OBJECT IDENTIFIER ::= { es2126PoEplusProduces 18 }

es2126PoEplusDot1XStateSetting      OBJECT IDENTIFIER ::= { es2126PoEplusDot1X 1 }

es2126PoEplusRadiusServer OBJECT-TYPE
    SYNTAX         IpAddress
    MAX-ACCESS     read-write
    STATUS         current
    DESCRIPTION
        "Set radius server ip"
    ::= { es2126PoEplusDot1XStateSetting 1 }

es2126PoEplusDot1XPort OBJECT-TYPE
    SYNTAX         INTEGER(1..65535)
    MAX-ACCESS     read-write
    STATUS         current
    DESCRIPTION
        "Set 802.1X port number"
    ::= { es2126PoEplusDot1XStateSetting 2 }

es2126PoEplusSecretKey  OBJECT-TYPE
    SYNTAX         DisplayString
    MAX-ACCESS     read-write
    STATUS         current
    DESCRIPTION
        "Set 802.1X secret key"
    ::= { es2126PoEplusDot1XStateSetting 3 }

es2126PoEplusAccountingService  OBJECT-TYPE
    SYNTAX         INTEGER(0|1)
    MAX-ACCESS     read-write
    STATUS         current
    DESCRIPTION
        "Set 802.1X accounting service
         0 : disable
         1 : enable
        "
    ::= { es2126PoEplusDot1XStateSetting 4 }

es2126PoEplusAccountingServer  OBJECT-TYPE
    SYNTAX         IpAddress
    MAX-ACCESS     read-write
    STATUS         current
    DESCRIPTION
        "Set 802.1X accounting server"
    ::= { es2126PoEplusDot1XStateSetting 5 }

es2126PoEplusAccountingPort  OBJECT-TYPE
    SYNTAX         INTEGER(1..65535)
    MAX-ACCESS     read-write
    STATUS         current
    DESCRIPTION
        "Set 802.1X accounting port number"
    ::= { es2126PoEplusDot1XStateSetting 6 }

es2126PoEplusDot1XPortSecurityManagement      OBJECT IDENTIFIER ::= { es2126PoEplusDot1X 2 }

es2126PoEplusDot1XPortSecurityTable  OBJECT-TYPE
    SYNTAX      SEQUENCE OF ES2126POEPLUSDot1XPortSecurityEntry
    MAX-ACCESS  not-accessible
    STATUS      current
    DESCRIPTION
        "This is a list of the 802.1x port security entry."
    ::= { es2126PoEplusDot1XPortSecurityManagement 1 }

ES2126POEPLUSDot1XPortSecurityEntry ::=
SEQUENCE {
    es2126PoEplusDot1XPortSecurityPortIndex               INTEGER,
    es2126PoEplusDot1XPortSecurityMode                    INTEGER,
    es2126PoEplusDot1XPortSecurityPortControl             INTEGER,
    es2126PoEplusDot1XPortSecurityReAuthMax               INTEGER,
    es2126PoEplusDot1XPortSecurityTxPeriod                    INTEGER,
    es2126PoEplusDot1XPortSecurityQuietPeriod             INTEGER,
    es2126PoEplusDot1XPortSecurityReAuthEnabled           INTEGER,
    es2126PoEplusDot1XPortSecurityReAuthPeriod            INTEGER,
    es2126PoEplusDot1XPortSecurityMaxRequest              INTEGER,
    es2126PoEplusDot1XPortSecuritySuppTimeout             INTEGER,
    es2126PoEplusDot1XPortSecurityServerTimeout           INTEGER,
    es2126PoEplusDot1XPortSecurityStatus                  DisplayString
}

es2126PoEplusDot1XPortSecurityEntry OBJECT-TYPE
    SYNTAX      ES2126POEPLUSDot1XPortSecurityEntry
    MAX-ACCESS  not-accessible
    STATUS      current
    DESCRIPTION
        "Entry(s) for 802.1x port security management table."
    INDEX {es2126PoEplusDot1XPortSecurityPortIndex}
    ::= { es2126PoEplusDot1XPortSecurityTable 1 }

es2126PoEplusDot1XPortSecurityPortIndex  OBJECT-TYPE
    SYNTAX      INTEGER(1..26)
    MAX-ACCESS  not-accessible
    STATUS      current
    DESCRIPTION
        "The port index of 802.1x port security."
    ::= { es2126PoEplusDot1XPortSecurityEntry 1 }

es2126PoEplusDot1XPortSecurityMode  OBJECT-TYPE
    SYNTAX      INTEGER(0..2)
    MAX-ACCESS  read-write
    STATUS      current
    DESCRIPTION
        "The mode of 802.1x port security.
         0 : Disable,
         1 : Normal,
         2 : Advanced 802.1X
        "
    ::= { es2126PoEplusDot1XPortSecurityEntry 2 }

es2126PoEplusDot1XPortSecurityPortControl  OBJECT-TYPE
    SYNTAX      INTEGER(0..2)
    MAX-ACCESS  read-write
    STATUS      current
    DESCRIPTION
        "The port control of 802.1x port security.
           0 : ForceUnauthorized,
           1 : ForceAuthorized,
           2 : Auto
        "
    ::= { es2126PoEplusDot1XPortSecurityEntry 3 }

es2126PoEplusDot1XPortSecurityReAuthMax  OBJECT-TYPE
    SYNTAX      INTEGER(1..10)
    MAX-ACCESS  read-write
    STATUS      current
    DESCRIPTION
        "The reAuthMax(1~10) of 802.1x port security."
    ::= { es2126PoEplusDot1XPortSecurityEntry 4 }

es2126PoEplusDot1XPortSecurityTxPeriod  OBJECT-TYPE
    SYNTAX      INTEGER(1..65535)
    MAX-ACCESS  read-write
    STATUS      current
    DESCRIPTION
        "The txPeriod(1~65535) of 802.1x port security."
    ::= { es2126PoEplusDot1XPortSecurityEntry 5 }

es2126PoEplusDot1XPortSecurityQuietPeriod  OBJECT-TYPE
    SYNTAX      INTEGER(0..65535)
    MAX-ACCESS  read-write
    STATUS      current
    DESCRIPTION
        "The quiet period(0~65535) of 802.1x port security."
    ::= { es2126PoEplusDot1XPortSecurityEntry 6 }

es2126PoEplusDot1XPortSecurityReAuthEnabled  OBJECT-TYPE
    SYNTAX      INTEGER(0|1)
    MAX-ACCESS  read-write
    STATUS      current
    DESCRIPTION
        "The reAuthEnabled of 802.1x port security.
         0 : off,
         1 : on.
        "
    ::= { es2126PoEplusDot1XPortSecurityEntry 7 }

es2126PoEplusDot1XPortSecurityReAuthPeriod  OBJECT-TYPE
    SYNTAX      INTEGER(1..65535)
    MAX-ACCESS  read-write
    STATUS      current
    DESCRIPTION
        "The reAuthPeriod(1~65535) of 802.1x port security."
    ::= { es2126PoEplusDot1XPortSecurityEntry 8 }

es2126PoEplusDot1XPortSecurityMaxRequest  OBJECT-TYPE
    SYNTAX      INTEGER(1..10)
    MAX-ACCESS  read-write
    STATUS      current
    DESCRIPTION
        "The max.request(1~10) of 802.1x port security."
    ::= { es2126PoEplusDot1XPortSecurityEntry 9 }

es2126PoEplusDot1XPortSecuritySuppTimeout  OBJECT-TYPE
    SYNTAX      INTEGER(1..65535)
    MAX-ACCESS  read-write
    STATUS      current
    DESCRIPTION
        "The suppTimeout(1~65535) of 802.1x port security."
    ::= { es2126PoEplusDot1XPortSecurityEntry 10 }

es2126PoEplusDot1XPortSecurityServerTimeout  OBJECT-TYPE
    SYNTAX      INTEGER(1..65535)
    MAX-ACCESS  read-write
    STATUS      current
    DESCRIPTION
        "The server timeout(1~65535) of 802.1x port security."
    ::= { es2126PoEplusDot1XPortSecurityEntry 11 }

es2126PoEplusDot1XPortSecurityStatus  OBJECT-TYPE
    SYNTAX      DisplayString
    MAX-ACCESS  read-only
    STATUS      current
    DESCRIPTION
        "The status of 802.1x port security."
    ::= { es2126PoEplusDot1XPortSecurityEntry 12 }


es2126PoEplusTrunkInfo       OBJECT IDENTIFIER ::= { es2126PoEplusProduces 19 }

es2126PoEplusTrunkPort      OBJECT IDENTIFIER ::= { es2126PoEplusTrunkInfo 1 }

es2126PoEplusTrunkPortTable  OBJECT-TYPE
    SYNTAX      SEQUENCE OF ES2126POEPLUSTrunkPortEntry
    MAX-ACCESS  not-accessible
    STATUS      current
    DESCRIPTION
        " "
    ::= { es2126PoEplusTrunkPort 1 }

ES2126POEPLUSTrunkPortEntry ::=
SEQUENCE {
    es2126PoEplusTrunkPortIndex               INTEGER,
    es2126PoEplusTrunkPortMethod                  INTEGER,
    es2126PoEplusTrunkPortGroup               INTEGER,
    es2126PoEplusTrunkPortActiveLacp              INTEGER,
    es2126PoEplusTrunkPortAggtr               INTEGER,
    es2126PoEplusTrunkPortStatus              INTEGER,
    es2126PoEplusTrunkPortCurrentMode             INTEGER
}

es2126PoEplusTrunkPortEntry OBJECT-TYPE
    SYNTAX      ES2126POEPLUSTrunkPortEntry
    MAX-ACCESS  not-accessible
    STATUS      current
    DESCRIPTION
        "Entry(s) for trunk table."
    INDEX {es2126PoEplusTrunkPortIndex}
    ::= { es2126PoEplusTrunkPortTable 1 }

es2126PoEplusTrunkPortIndex  OBJECT-TYPE
    SYNTAX      INTEGER(1..26)
    MAX-ACCESS  not-accessible
    STATUS      current
    DESCRIPTION
        "The port index of trunk table."
    ::= { es2126PoEplusTrunkPortEntry 1 }

es2126PoEplusTrunkPortMethod  OBJECT-TYPE
    SYNTAX      INTEGER(0..2)
    MAX-ACCESS  read-write
    STATUS      current
    DESCRIPTION
        "The method of trunk port.
     0 : None,
     1 : LACP,
     2 : Static.
        "
    ::= { es2126PoEplusTrunkPortEntry 2 }

es2126PoEplusTrunkPortGroup  OBJECT-TYPE
    SYNTAX      INTEGER(0..3)
    MAX-ACCESS  read-write
    STATUS      current
    DESCRIPTION
        "The group(0~3) of trunk port."
    ::= { es2126PoEplusTrunkPortEntry 3 }

es2126PoEplusTrunkPortActiveLacp  OBJECT-TYPE
    SYNTAX      INTEGER(0|1)
    MAX-ACCESS  read-write
    STATUS      current
    DESCRIPTION
        "The active lacp mode of trunk port.
     0 : Passive,
     1 : Active.
        "
    ::= { es2126PoEplusTrunkPortEntry 4 }

es2126PoEplusTrunkPortAggtr  OBJECT-TYPE
    SYNTAX      INTEGER(1..26)
    MAX-ACCESS  read-only
    STATUS      current
    DESCRIPTION
        "The Aggtr of trunk port."
    ::= { es2126PoEplusTrunkPortEntry 5 }

es2126PoEplusTrunkPortStatus  OBJECT-TYPE
    SYNTAX      INTEGER(0|1)
    MAX-ACCESS  read-only
    STATUS      current
    DESCRIPTION
        "The status of trunk port.
         0 : None,
         1 : Ready.
        "
    ::= { es2126PoEplusTrunkPortEntry 6 }

es2126PoEplusTrunkPortCurrentMode  OBJECT-TYPE
    SYNTAX      INTEGER(0..2)
    MAX-ACCESS  read-write
    STATUS      current
    DESCRIPTION
        "The current mode of trunk port entry.
     0 : Active mode,
     1 : Edit mode,
     2 : Do edit.
        "
    ::= { es2126PoEplusTrunkPortEntry 7 }

es2126PoEplusAggregatorView      OBJECT IDENTIFIER ::= { es2126PoEplusTrunkInfo 2 }

es2126PoEplusAggregatorViewTable  OBJECT-TYPE
    SYNTAX      SEQUENCE OF ES2126POEPLUSAggregatorViewEntry
    MAX-ACCESS  not-accessible
    STATUS      current
    DESCRIPTION
        " "
    ::= { es2126PoEplusAggregatorView 1 }

ES2126POEPLUSAggregatorViewEntry ::=
SEQUENCE {
    es2126PoEplusAggregatorViewIndex              INTEGER,
    es2126PoEplusAggregatorViewMethod                 INTEGER,
    es2126PoEplusAggregatorViewMemberPorts            DisplayString,
    es2126PoEplusAggregatorViewReadyPorts         DisplayString
}

es2126PoEplusAggregatorViewEntry OBJECT-TYPE
    SYNTAX      ES2126POEPLUSAggregatorViewEntry
    MAX-ACCESS  not-accessible
    STATUS      current
    DESCRIPTION
        "Entry(s) for aggregator view table."
    INDEX {es2126PoEplusAggregatorViewIndex}
    ::= { es2126PoEplusAggregatorViewTable 1 }

es2126PoEplusAggregatorViewIndex  OBJECT-TYPE
    SYNTAX      INTEGER(1..26)
    MAX-ACCESS  not-accessible
    STATUS      current
    DESCRIPTION
        "The port index of aggregator view table."
    ::= { es2126PoEplusAggregatorViewEntry 1 }

es2126PoEplusAggregatorViewMethod  OBJECT-TYPE
    SYNTAX      INTEGER(0..2)
    MAX-ACCESS  read-only
    STATUS      current
    DESCRIPTION
        "The method of aggregator view table.
         0 : None,
     1 : LACP,
     2 : Static.
        "
    ::= { es2126PoEplusAggregatorViewEntry 2 }

es2126PoEplusAggregatorViewMemberPorts  OBJECT-TYPE
    SYNTAX      DisplayString
    MAX-ACCESS  read-only
    STATUS      current
    DESCRIPTION
        "The member ports of aggregator view table."
    ::= { es2126PoEplusAggregatorViewEntry 3 }

es2126PoEplusAggregatorViewReadyPorts  OBJECT-TYPE
    SYNTAX      DisplayString
    MAX-ACCESS  read-only
    STATUS      current
    DESCRIPTION
        "The ready ports of aggregator view table."
    ::= { es2126PoEplusAggregatorViewEntry 4 }

es2126PoEplusLacpSystemConfiguration     OBJECT IDENTIFIER ::= { es2126PoEplusTrunkInfo 3 }

es2126PoEplusLacpSystemPriority  OBJECT-TYPE
    SYNTAX      INTEGER(1..65535)
    MAX-ACCESS  read-write
    STATUS      current
    DESCRIPTION
        "The priority of LACP system."
    ::= { es2126PoEplusLacpSystemConfiguration 1 }

es2126PoEplusLacpSystemHashMethod  OBJECT-TYPE
    SYNTAX      INTEGER(0..2)
    MAX-ACCESS  read-write
    STATUS      current
    DESCRIPTION
        "The hash method of LACP system.
         0 : DA and SA
         1 : SA
         2 : DA
        "
    ::= { es2126PoEplusLacpSystemConfiguration 2 }

es2126PoEplusTrapEntry           OBJECT IDENTIFIER ::= { es2126PoEplusProduces 20 }

es2126PoEplusModuleInserted NOTIFICATION-TYPE
    OBJECTS { ifIndex }
    STATUS    current
    DESCRIPTION
        "Send the trap when a module is inserted to the system. The OID value means
         the port number."
    ::= { es2126PoEplusTrapEntry 1 }

es2126PoEplusModuleRemoved NOTIFICATION-TYPE
    OBJECTS { ifIndex }
    STATUS    current
    DESCRIPTION
        "Send the trap when a module is removed from the system. The OID value means
         the port number."
    ::= { es2126PoEplusTrapEntry 2 }

es2126PoEplusDualMediaSwapped NOTIFICATION-TYPE
    OBJECTS { ifIndex }
    STATUS    current
DESCRIPTION
        "Send the trap when the dual media port changed. The OID value means the port number."
    ::= { es2126PoEplusTrapEntry 3 }

es2126PoEplusPoEFailure NOTIFICATION-TYPE
    STATUS    current
    DESCRIPTION
        "Send the trap while detecting the malfunction of PoE chips."
    ::= { es2126PoEplusTrapEntry 4 }

es2126PoEplusLoopDetected NOTIFICATION-TYPE
    OBJECTS { ifIndex }
    STATUS    current
    DESCRIPTION
        "Send the trap when loop condition has been detected. The OID value means the port number."
    ::= { es2126PoEplusTrapEntry 5 }

es2126PoEplusLoginProtected NOTIFICATION-TYPE
    OBJECTS { ifIndex }
    STATUS    current
    DESCRIPTION
        "Send the trap when login protect has been detected."
    ::= { es2126PoEplusTrapEntry 6 }

es2126PoEplusStpStateDisabled NOTIFICATION-TYPE
    STATUS      current
    DESCRIPTION
       "Send the trap when the operational state of STP is from enabled to disabled. "
    ::= { es2126PoEplusTrapEntry 100 }

es2126PoEplusStpStateEnabled NOTIFICATION-TYPE
    STATUS      current
    DESCRIPTION
       "Send the trap when the operational state of STP is from disabled to enabled. "
    ::= { es2126PoEplusTrapEntry 101 }

es2126PoEplusStpTopologyChanged NOTIFICATION-TYPE
    OBJECTS { ifIndex }
    STATUS      current
    DESCRIPTION
       "Send the trap when RSTP determines a port should enter the FORWARDING state
        (a topology change occurs). The OID value is the ifIndex of the port that
        produces the topology change."
    ::= { es2126PoEplusTrapEntry 102 }

es2126PoEplusRmonRisingAlarm NOTIFICATION-TYPE
    STATUS      current
    DESCRIPTION
       "Send the trap when an RMON rising alarm happened. The OID value is the value
        of another OID variable sampled by the RMON Alarm Group that exceeds its
        own RisingThreshold "
    ::= { es2126PoEplusTrapEntry 110 }

es2126PoEplusRmonFallingAlarm NOTIFICATION-TYPE
    STATUS      current
    DESCRIPTION
           "Send the trap when an RMON falling alarm happened. The OID value is the value
        of another OID variable sampled by the RMON Alarm Group that is smaller than its
        own FallingThreshold "
    ::= { es2126PoEplusTrapEntry 111 }

es2126PoEplusLacpStateDisabled NOTIFICATION-TYPE
    OBJECTS {ifIndex, groupId}
    STATUS      current
    DESCRIPTION
       "Send the trap when the operational state of LACP is from enabled to disabled.
        The OID value means the disabled Group ID."
    ::= { es2126PoEplusTrapEntry 120 }

es2126PoEplusLacpStateEnabled NOTIFICATION-TYPE
    OBJECTS {ifIndex, groupId}
    STATUS      current
    DESCRIPTION
       "Send the trap when the operational state of LACP is from disabled to enabled.
        The OID value means the disabled Group ID."
    ::= { es2126PoEplusTrapEntry 121 }

es2126PoEplusLacpPortAdded NOTIFICATION-TYPE
    OBJECTS   { ifIndex, actorkey, partnerkey }
    STATUS      current
    DESCRIPTION
       "Send the trap when the state of port is in 'trunk ready'."
    ::= { es2126PoEplusTrapEntry 123 }

es2126PoEplusLacpPortTrunkFailure NOTIFICATION-TYPE
    OBJECTS   { ifIndex, actorkey, partnerkey}
    STATUS      current
    DESCRIPTION
       "Send the trap when one port is not able to be aggregated
        due to duplex-mode of the port. "
    ::= { es2126PoEplusTrapEntry 124 }

es2126PoEplusGvrpStateDisabled NOTIFICATION-TYPE
    STATUS      current
    DESCRIPTION
       "Send the trap when the operational state of GVRP is from enabled to disabled. "
    ::= { es2126PoEplusTrapEntry 140 }

es2126PoEplusGvrpStateEnabled NOTIFICATION-TYPE
    STATUS      current
    DESCRIPTION
       "Send the trap when the operational state of LACP is from disabled to enabled. "
    ::= { es2126PoEplusTrapEntry 141 }

es2126PoEplusVlanPortBaseEnabled NOTIFICATION-TYPE
    STATUS      current
    DESCRIPTION
       "Send the trap when the operational state of vlan is changed to port-based vlan."
    ::= { es2126PoEplusTrapEntry 151 }

es2126PoEplusVlanTagBaseEnabled NOTIFICATION-TYPE
    STATUS      current
    DESCRIPTION
       "Send the trap when the operational state of vlan is changed to tag-based vlan."
    ::= { es2126PoEplusTrapEntry 152 }

es2126PoEplusVlanMetroBaseEnabled NOTIFICATION-TYPE
    STATUS      current
    DESCRIPTION
       "Send this trap when the operational state of vlan is changed to metro-based vlan."
    ::= { es2126PoEplusTrapEntry 153 }

es2126PoEplusUserLogin NOTIFICATION-TYPE
    OBJECTS   {username}
    STATUS      current
    DESCRIPTION
       "Send the trap when one user logins the system."
    ::= { es2126PoEplusTrapEntry 200 }

es2126PoEplusUserLogout NOTIFICATION-TYPE
    OBJECTS   {username}
    STATUS      current
    DESCRIPTION
       "Send the trap when one user logouts the system."
    ::= { es2126PoEplusTrapEntry 201 }

es2126PoEplusTrapVariable OBJECT IDENTIFIER ::= { es2126PoEplusProduces 21 }

username OBJECT-TYPE
    SYNTAX      DisplayString
    MAX-ACCESS  read-only
    STATUS      current
    DESCRIPTION
        "System account name."
    ::= { es2126PoEplusTrapVariable 1 }

groupId OBJECT-TYPE
    SYNTAX      INTEGER(1..8)
    MAX-ACCESS  read-only
    STATUS      current
    DESCRIPTION
        "The Trunk group ID of LACP."
    ::= { es2126PoEplusTrapVariable 2 }

actorkey OBJECT-TYPE
    SYNTAX  INTEGER(1..2147483647)
    MAX-ACCESS  read-only
    STATUS      current
    DESCRIPTION
        "The actor key information for LACP."
    ::= { es2126PoEplusTrapVariable 3 }

partnerkey OBJECT-TYPE
    SYNTAX  INTEGER(1..2147483647)
    MAX-ACCESS  read-only
    STATUS      current
    DESCRIPTION
        "The partner key information for LACP."
    ::= { es2126PoEplusTrapVariable 4 }

uplink OBJECT-TYPE
    SYNTAX  DisplayString
    MAX-ACCESS  read-only
    STATUS      current
    DESCRIPTION
        "Uplink port(s) in the metro-mode vlan."
    ::= { es2126PoEplusTrapVariable 5 }

loginProtectInfo OBJECT-TYPE
    SYNTAX  DisplayString
    MAX-ACCESS  read-only
    STATUS      current
    DESCRIPTION
        "Loging protect information."
    ::= { es2126PoEplusTrapVariable 6 }

es2126PoEplusPoE              OBJECT IDENTIFIER ::= { es2126PoEplusProduces 22 }

es2126PoEplusPoEStatus            OBJECT IDENTIFIER ::= { es2126PoEplusPoE 1 }

es2126PoEplusPoEStatusVmain OBJECT-TYPE
    SYNTAX      DisplayString
    MAX-ACCESS  read-only
    STATUS      current
    DESCRIPTION
        "Current PoE Voltage status"
    ::= { es2126PoEplusPoEStatus 1 }

es2126PoEplusPoEStatusImain OBJECT-TYPE
    SYNTAX      DisplayString
    MAX-ACCESS  read-only
    STATUS      current
    DESCRIPTION
        "Current PoE Current status"
    ::= { es2126PoEplusPoEStatus 2 }

es2126PoEplusPoEStatusPconsume OBJECT-TYPE
    SYNTAX      DisplayString
    MAX-ACCESS  read-only
    STATUS      current
    DESCRIPTION
        "Current PoE consuming power status"
    ::= { es2126PoEplusPoEStatus 3 }

es2126PoEplusPoEStatusPowerLimit OBJECT-TYPE
    SYNTAX      DisplayString
    MAX-ACCESS  read-only
    STATUS      current
    DESCRIPTION
        "Current PoE power limit status"
    ::= { es2126PoEplusPoEStatus 4 }

es2126PoEplusPoEStatusTemperature OBJECT-TYPE
    SYNTAX      DisplayString
    MAX-ACCESS  read-only
    STATUS      current
    DESCRIPTION
        "Current PoE temperature status"
    ::= { es2126PoEplusPoEStatus 5 }


es2126PoEplusPoEStatusTable   OBJECT-TYPE
    SYNTAX      SEQUENCE OF ES2126POEPLUSPoEStatusEntry
    MAX-ACCESS  not-accessible
    STATUS      current
    DESCRIPTION
        "A list of PoE Status entry. The number of entries are given by Ports."
    ::= { es2126PoEplusPoEStatus 6 }

es2126PoEplusPoEStatusEntry   OBJECT-TYPE
    SYNTAX      ES2126POEPLUSPoEStatusEntry
    MAX-ACCESS      not-accessible
    STATUS      current
    DESCRIPTION
        "Entry(s) for PoE Status."
    INDEX {es2126PoEplusPoEStatusPortNum}
    ::= { es2126PoEplusPoEStatusTable 1 }

ES2126POEPLUSPoEStatusEntry ::=
SEQUENCE {
    es2126PoEplusPoEStatusPortNum                 INTEGER,
    es2126PoEplusPoEStatusPortOn                  INTEGER,
    es2126PoEplusPoEStatusACPortOff               INTEGER,
    es2126PoEplusPoEStatusDCPortOff           INTEGER,
    es2126PoEplusPoEStatusOverloadPortOff         INTEGER,
    es2126PoEplusPoEStatusShortCircuitPortOff     INTEGER,
    es2126PoEplusPoEStatusOverTemperature         INTEGER,
    es2126PoEplusPoEStatusPowerManagePortOff      INTEGER
}

es2126PoEplusPoEStatusPortNum OBJECT-TYPE
    SYNTAX      INTEGER(1..24)
    MAX-ACCESS  not-accessible
    STATUS      current
    DESCRIPTION
        "The index(Port number) of the PoE status entry."
    ::= { es2126PoEplusPoEStatusEntry 1 }

es2126PoEplusPoEStatusPortOn  OBJECT-TYPE
    SYNTAX      INTEGER(0|1)
    MAX-ACCESS      read-only
    STATUS      current
    DESCRIPTION
        "PD on this port is on."
    ::= { es2126PoEplusPoEStatusEntry 2 }

es2126PoEplusPoEStatusACPortOff   OBJECT-TYPE
    SYNTAX      INTEGER(0|8)
    MAX-ACCESS      read-only
    STATUS      current
    DESCRIPTION
        "Possitive value means PSE has been supplied power and is no supplying now, while zero
         means PSE has never supplied power or is supplying now."
    ::= { es2126PoEplusPoEStatusEntry 3 }

es2126PoEplusPoEStatusDCPortOff   OBJECT-TYPE
    SYNTAX      INTEGER(0|1)
    MAX-ACCESS      read-only
    STATUS      current
    DESCRIPTION
        "PD on this port is DC off."
    ::= { es2126PoEplusPoEStatusEntry 4 }

es2126PoEplusPoEStatusOverloadPortOff OBJECT-TYPE
    SYNTAX      INTEGER(0|32)
    MAX-ACCESS      read-only
    STATUS      current
    DESCRIPTION
        "Possitive value means PSE status overloaded now. Zero means PSE is not overloaded."
    ::= { es2126PoEplusPoEStatusEntry 5 }

es2126PoEplusPoEStatusShortCircuitPortOff OBJECT-TYPE
    SYNTAX      INTEGER(0|1)
    MAX-ACCESS      read-only
    STATUS      current
    DESCRIPTION
        "PD on this port is short circuit off."
    ::= { es2126PoEplusPoEStatusEntry 6 }

es2126PoEplusPoEStatusOverTemperature OBJECT-TYPE
    SYNTAX      INTEGER(0|1)
    MAX-ACCESS      read-only
    STATUS      current
    DESCRIPTION
        "PD on this port is over temperature."
    ::= { es2126PoEplusPoEStatusEntry 7 }

es2126PoEplusPoEStatusPowerManagePortOff  OBJECT-TYPE
    SYNTAX      INTEGER(0|1)
    MAX-ACCESS      read-only
    STATUS      current
    DESCRIPTION
        "PD on this port is powered off by management."
    ::= { es2126PoEplusPoEStatusEntry 8 }

es2126PoEplusPoEConfTable OBJECT-TYPE
    SYNTAX      SEQUENCE OF ES2126POEPLUSPoEConfEntry
    MAX-ACCESS  not-accessible
    STATUS      current
    DESCRIPTION
        "A list of PoE Configuration entry. The number of entries are given by Ports."
    ::= { es2126PoEplusPoE 2 }

es2126PoEplusPoEConfEntry OBJECT-TYPE
    SYNTAX      ES2126POEPLUSPoEConfEntry
    MAX-ACCESS      not-accessible
    STATUS      current
    DESCRIPTION
        "Entry(s) for PoE Configuration."
    INDEX {es2126PoEplusPoEConfPortNum}
    ::= { es2126PoEplusPoEConfTable 1 }

ES2126POEPLUSPoEConfEntry ::=
SEQUENCE {
    es2126PoEplusPoEConfPortNum                   INTEGER,
    es2126PoEplusPoEConfStatus                    INTEGER,
    es2126PoEplusPoEConfState                 INTEGER,
    es2126PoEplusPoEConfPriority                  INTEGER,
    es2126PoEplusPoEConfPower                 DisplayString,
    es2126PoEplusPoEConfCurrent                   INTEGER,
    es2126PoEplusPoEConfClass                 INTEGER
}

es2126PoEplusPoEConfPortNum   OBJECT-TYPE
    SYNTAX      INTEGER(1..24)
    MAX-ACCESS  not-accessible
    STATUS      current
    DESCRIPTION
        "The index(Port number) of the PoE Configuration entry."
    ::= { es2126PoEplusPoEConfEntry 1 }

es2126PoEplusPoEConfStatus    OBJECT-TYPE
    SYNTAX      INTEGER(0|1)
    MAX-ACCESS      read-only
    STATUS      current
    DESCRIPTION
        "0:Normal ; 1:Active"
    ::= { es2126PoEplusPoEConfEntry 2 }

es2126PoEplusPoEConfState OBJECT-TYPE
    SYNTAX      INTEGER(0|1)
    MAX-ACCESS      read-write
    STATUS      current
    DESCRIPTION
        "0:Disable ; 1:Enable"
    ::= { es2126PoEplusPoEConfEntry 3 }

es2126PoEplusPoEConfPriority  OBJECT-TYPE
    SYNTAX      INTEGER(0..2)
    MAX-ACCESS      read-write
    STATUS      current
    DESCRIPTION
        "0:Low ; 1:Normal ; 2:High"
    ::= { es2126PoEplusPoEConfEntry 4 }

es2126PoEplusPoEConfPower OBJECT-TYPE
    SYNTAX      DisplayString
    MAX-ACCESS      read-only
    STATUS      current
    DESCRIPTION
        "The power provides for the PD."
    ::= { es2126PoEplusPoEConfEntry 5 }

es2126PoEplusPoEConfCurrent   OBJECT-TYPE
    SYNTAX      INTEGER(0..2147483647)
    MAX-ACCESS      read-only
    STATUS      current
    DESCRIPTION
        "The current provides for the PD."
    ::= { es2126PoEplusPoEConfEntry 6 }

es2126PoEplusPoEConfClass OBJECT-TYPE
    SYNTAX      INTEGER(0..2147483647)
    MAX-ACCESS      read-only
    STATUS      current
    DESCRIPTION
        "The class of the PD."
    ::= { es2126PoEplusPoEConfEntry 7 }

es2126PoEplusLoginProtect           OBJECT IDENTIFIER ::= { es2126PoEplusProduces 23 }

es2126PoEplusLockMinutes OBJECT-TYPE
    SYNTAX      INTEGER(0..10)
    MAX-ACCESS      read-write
    STATUS      current
    DESCRIPTION
        "Set the login lock time. Available from 0 to 10 (minutes)
         Set 0 as disabled.
        "
    ::= { es2126PoEplusLoginProtect 1 }

es2126PoEplusLoginErrors OBJECT-TYPE
    SYNTAX      INTEGER(0..10)
    MAX-ACCESS      read-write
    STATUS      current
    DESCRIPTION
        "Set login error count. Available from 0 to 10 (times)
         Set 0 as disabled.
        "
    ::= { es2126PoEplusLoginProtect 2 }

END

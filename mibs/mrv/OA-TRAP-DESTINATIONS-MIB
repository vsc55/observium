--  =======================================================================
--  File        : OATRPDST.MIB
--  Description : Private MIB for Trap Destinations Table
--  By          : Yakov & Reuven
--  Version     : 0.1
--  Date        : 
--  =======================================================================
--
--
-- Copyright (c) 2006 MRV.  All Rights Reserved.
--
--
-- Reproduction of this document is authorized on condition that this
-- copyright notice is included.  This MRV SNMP MIB Specification
-- embodies MRV's proprietary intellectual property.  MRV
-- retains all title and ownership in the specification, including any
-- revisions.
--
-- It is MRV's intent to encourage the widespread use of this
-- specification in connection with the management of MRV's
-- products. MRV grants vendor, end-users, and other interested
-- parties a non-exclusive license to use this specification in
-- connection with the management of MRV's products.
--
-- This specification is supplied "AS IS," and MRV makes no
-- warranty, either express or implied, as to the use, operation,
-- condition, or performance of the specification.
--
-- Copyright text courtesy of MRV
--
-- If you have any questions about this MIB, please call MRV
-- Technical Support Center at 1-800-858-7815 from inside USA or
-- 1-818-773-0900 from outside USA.
--
--
-- MRV retains the right to change this MIB without notification.
--

OA-TRAP-DESTINATIONS-MIB DEFINITIONS ::= BEGIN

  IMPORTS
    MODULE-IDENTITY, OBJECT-TYPE, 
    Unsigned32                                   FROM SNMPv2-SMI    -- RFC2578
    MODULE-COMPLIANCE, OBJECT-GROUP              FROM SNMPv2-CONF   -- RFC2580
    nbSwitchG1Il                                 FROM OS-COMMON-TC-MIB
    DisplayString                                FROM SNMPv2-TC;    -- RFC2579

oaTrapDestinations  MODULE-IDENTITY
    LAST-UPDATED "201806100000Z" -- 22 Apr. 2012
    ORGANIZATION "MRV Communications, Inc."
    CONTACT-INFO
        "Yakov Vaisman
         MRV Communication, Inc
         http://www.mrv.com
         Email:  yvaisman@mrv.com,

         Reuven Putter
         MRV Communication, Inc
         http://www.mrv.com
         Email:  rputter@mrv.com
	"
    DESCRIPTION
        "Supports information about Trap destinations."

    -- Revision history

    REVISION     "201806100000Z"
    DESCRIPTION
    "New objects oaTrapDestInsertLogInfo, oaTrapDestInsertHostNameInfo were added."

    REVISION     "201204220000Z"
    DESCRIPTION
    "New object oaTrapDestMaxLimit was added."

    REVISION     "201104120000Z"
    DESCRIPTION
    "New object oaTrapDestEnableMode was added."

    REVISION "200612130000Z"
    DESCRIPTION
        "Initial edition."
    ::= { nbDevGen 21 }

-- ************************************************************
-- MRV Object Identifier Definition
-- ************************************************************

-- GROUPS for General Device Configuration
nbDeviceConfig     OBJECT IDENTIFIER ::= { nbSwitchG1Il 11}
nbDevGen           OBJECT IDENTIFIER ::= { nbDeviceConfig 1 }


oaTrapDestConformance   OBJECT IDENTIFIER ::= { oaTrapDestinations 101 }

-- ************************************************************
-- Objects in the Trap Destinations Group
-- ************************************************************

oaTrapDestGenSupport OBJECT-TYPE
    SYNTAX  INTEGER {
       notSupported (1),
       supported    (2)
    }       
    MAX-ACCESS  read-only
    STATUS  current
    DESCRIPTION
    "Traps destinations feature support."
    ::= { oaTrapDestinations 1 }

-- ************************************************************

oaTrapDestTable         OBJECT-TYPE
    SYNTAX  SEQUENCE OF OaTrapDestEntry
    MAX-ACCESS   not-accessible
    STATUS       current
    DESCRIPTION
    "This table configures Traps destinations."
    ::= { oaTrapDestinations 2 }

oaTrapDestEntry OBJECT-TYPE
    SYNTAX       OaTrapDestEntry
    MAX-ACCESS   not-accessible
    STATUS       current
    DESCRIPTION
    "Trap Destination entry."
    INDEX { oaTrapDestHostAddress }
    ::= { oaTrapDestTable 1 }

OaTrapDestEntry ::= SEQUENCE {
    oaTrapDestHostAddress     DisplayString,
    oaTrapDestVersion         INTEGER,
    oaTrapDestAuthentication  DisplayString,
    oaTrapDestTrapType        INTEGER,
    oaTrapDestAdminStatus     INTEGER
    }

oaTrapDestHostAddress     OBJECT-TYPE
    SYNTAX       DisplayString (SIZE (0..32))
    MAX-ACCESS   not-accessible
    STATUS       current
    DESCRIPTION
    "Specifies the host address to be used as a Trap destination.
     It could be DNS name or IPv4 address or IPv6 address
     in string format."
    ::= { oaTrapDestEntry 1 }

oaTrapDestVersion	OBJECT-TYPE
    SYNTAX       INTEGER {
       other    (0),
       snmpV1   (1),
       snmpV2C  (2),
       snmpV3   (3)
    }
    MAX-ACCESS   read-write
    STATUS       current
    DESCRIPTION
    "Trap SNMP Version: snmpV1  - send SNMPv1 traps,
                        snmpV2C - send SNMPv2c traps
                        snmpV3  - send SNMPv3 traps."
    DEFVAL { snmpV1 }
    ::= { oaTrapDestEntry 2 }

oaTrapDestAuthentication   OBJECT-TYPE
    SYNTAX       DisplayString (SIZE (0..32))
    MAX-ACCESS   read-write
    STATUS       current
    DESCRIPTION
    "SNMP Trap authentication string:
          - community name for SNMPv1 & SNMPv2c,
          - user      name for SNMPv3."
    ::= { oaTrapDestEntry 3 }

oaTrapDestTrapType   OBJECT-TYPE
    SYNTAX       INTEGER {
       other      (0),
       snmpTrap   (1),
       snmpInform (2)
    }
    MAX-ACCESS   read-write
    STATUS       current
    DESCRIPTION
    "Trap type:
          - SnmpTrap    - send SNMP TRAP,
          - SnmpInform  - send SNMP INFORM (for SNMPv2c & SNMPv3 only)."
    DEFVAL { snmpTrap }
    ::= { oaTrapDestEntry 4 }

oaTrapDestAdminStatus	OBJECT-TYPE
    SYNTAX       INTEGER {
       valid     (1),
       invalid   (2)
    }
    MAX-ACCESS   read-write
    STATUS  current
    DESCRIPTION
    "Controls creation/modification/invalidation of the entry."
    ::= { oaTrapDestEntry 5 }

-- ************************************************************

oaTrapDestEnableMode OBJECT-TYPE
    SYNTAX  INTEGER {
       enabled     (1),
       disabled    (2)
    }       
    MAX-ACCESS  read-write
    STATUS  current
    DESCRIPTION
        "Indicates whether the device will generate SNMP traps. 
        'Enabled' results in SNMP traps; 'disabled': no traps are sent."
    REFERENCE
        "CLI command: '[no] traps enable'"
    DEFVAL { enabled }
    ::= { oaTrapDestinations 3 }


-- ************************************************************

oaTrapDestMaxLimit OBJECT-TYPE
    SYNTAX      Unsigned32
    MAX-ACCESS  read-only
    STATUS      current
    DESCRIPTION
      "Maximun number of entries oaTrapDestTable."
    DEFVAL { 11 }
    ::= { oaTrapDestinations 4 }

oaTrapDestInsertLogInfo OBJECT-TYPE
    SYNTAX  INTEGER {
        enabled (1),
        disabled (2) 
    }
    MAX-ACCESS  read-write
    STATUS      current
    DESCRIPTION
       "When enabled(1), then all notifications will contain an extra parameter neEventLogTimeStamp.
       Corresponds to CLI command '[no ]bind-log-info-to-alarms'"
    DEFVAL { disabled }
    ::= { oaTrapDestinations 5 }

oaTrapDestInsertHostNameInfo OBJECT-TYPE
    SYNTAX  INTEGER {
        enabled (1),
        disabled (2) 
    }
    MAX-ACCESS  read-write
    STATUS      current
    DESCRIPTION
       "When enabled(1), then all notifications will contain an extra parameter sysName.
       Corresponds to CLI command '[no ]bind-hostname-to-alarms'"
    DEFVAL { disabled }
    ::= { oaTrapDestinations 6 }


-- *******************************************************************
--  Conformance Information 
-- ******************************************************************* 
 
oaTrapDestMIBCompliances  OBJECT IDENTIFIER ::= { oaTrapDestConformance 1 }
oaTrapDestMIBGroups       OBJECT IDENTIFIER ::= { oaTrapDestConformance 2 }

oaTrapDestMIBCompliance   MODULE-COMPLIANCE
    STATUS current 
    DESCRIPTION 
    "The core compliance statement for all
     'oaTrapDestinations' MIB implementations."

    MODULE -- this module

    MANDATORY-GROUPS { 
                      oaTrapDestGroup
                     } 

    ::= { oaTrapDestMIBCompliances 1 }

-- ...................................................................
-- Conformance Groups 
-- ................................................................... 
 
oaTrapDestGroup  OBJECT-GROUP
    OBJECTS { 
             oaTrapDestGenSupport,
             oaTrapDestVersion,
             oaTrapDestAuthentication,
             oaTrapDestTrapType,
             oaTrapDestAdminStatus,
             oaTrapDestEnableMode,
             oaTrapDestMaxLimit,
             oaTrapDestInsertLogInfo,
             oaTrapDestInsertHostNameInfo
            }
    STATUS current 
    DESCRIPTION 
    "Mandatory objects for grouping of Trap destinations parameters."
    ::= { oaTrapDestMIBGroups 1 }
 

END

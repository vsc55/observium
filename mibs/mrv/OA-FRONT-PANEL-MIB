--  =======================================================================
--  File        : OaFrPan.mib
--  Description : Private MIB for Device Front Panel.
--  By          : Ilan Weber, Yakov Vaisman, Asaf Henig.
--  Version       : Revision:   1.00
--  Original Date : June 5, 2008
--  Last Change   : Date:   June 5, 2008
--  Supports information about Device Front Panel
--  =======================================================================
--
--
-- Copyright (c) 2008 MRV.  All Rights Reserved.
--
--
-- Reproduction of this document is authorized on condition that this
-- copyright notice is included.  This MRV SNMP MIB Specification
-- embodies MRV's proprietary intellectual property.  MRV
-- retains all title and ownership in the specification, including any
-- revisions.
--
-- It is MRV's intent to encourage the widespread use of this
-- specification in connection with the management of MRV's
-- products. MRV grants vendor, end-users, and other interested
-- parties a non-exclusive license to use this specification in
-- connection with the management of MRV's products.
--
-- This specification is supplied "AS IS," and MRV makes no
-- warranty, either express or implied, as to the use, operation,
-- condition, or performance of the specification.
--
-- Copyright text courtesy of MRV
--
-- If you have any questions about this MIB, please call MRV
-- Technical Support Center at 1-800-858-7815 from inside USA or
-- 1-818-773-0900 from outside USA.
--
--
-- MRV retains the right to change this MIB without notification.

OA-FRONT-PANEL-MIB DEFINITIONS ::= BEGIN

IMPORTS
    MODULE-IDENTITY, OBJECT-TYPE, enterprises,
    Integer32                                    FROM SNMPv2-SMI  -- RFC2578
    MODULE-COMPLIANCE, OBJECT-GROUP              FROM SNMPv2-CONF -- RFC2580
    nbSwitchG1Il                                 FROM OS-COMMON-TC-MIB
    DisplayString                                FROM SNMPv2-TC;  -- RFC2579

------------------------------------------------------------------------------
-- Object Identifier Definition
------------------------------------------------------------------------------

oaFrPanel  MODULE-IDENTITY
    LAST-UPDATED "200806050000Z" -- June 5, 2008
    ORGANIZATION "MRV Communications, Inc."
    CONTACT-INFO "For technical support, please contact your service channel."

    DESCRIPTION
        "Supports information about Device Front Panel representation."

    -- Revision history

    REVISION "200806050000Z" -- June 5, 2008
    DESCRIPTION
        "Initial edition."
    ::= { nbDevId 20 }

---------------------------------------------------------------
-- MIB place Definition
---------------------------------------------------------------

nbDevId                OBJECT IDENTIFIER ::= { nbSwitchG1Il 16}

oaFrPanelGen           OBJECT IDENTIFIER ::= { oaFrPanel 1 }

oaFrPanelSlot          OBJECT IDENTIFIER ::= { oaFrPanel 5 }
oaFrPanelConformance   OBJECT IDENTIFIER ::= { oaFrPanel 101 }

---------------------------------------------------------------
-- Objects in the oaFrPanelGen Group
---------------------------------------------------------------

oaFrPanelGenSupport OBJECT-TYPE
    SYNTAX  INTEGER {
       notSupported (1),
       supported    (2)
    }       
    MAX-ACCESS  read-only
    STATUS  current
    DESCRIPTION
    "Device Front Panel feature support."
    ::= { oaFrPanelGen 1 }

---------------------------------------------------------------
-- oaFrPanelSlotTable
---------------------------------------------------------------

oaFrPanelSlotTable             OBJECT-TYPE
    SYNTAX       SEQUENCE OF OaFrPanelSlotEntry
    MAX-ACCESS   not-accessible
    STATUS       current
    DESCRIPTION
    "Table describes the changable components that
     can be shown on the Device Front Panel."
    ::= { oaFrPanelSlot 5 }

oaFrPanelSlotEntry             OBJECT-TYPE
    SYNTAX       OaFrPanelSlotEntry
    MAX-ACCESS   not-accessible
    STATUS       current
    DESCRIPTION  "."

    INDEX   { oaFrPanelSltShelfId,
              oaFrPanelSltSlotId
            }

    ::= { oaFrPanelSlotTable 1 }

OaFrPanelSlotEntry ::= SEQUENCE
            {
              oaFrPanelSltShelfId          Integer32,
              oaFrPanelSltSlotId           Integer32,
              oaFrPanelSltPortsNumber      Integer32,
              oaFrPanelSltLedsNumber       Integer32,
              oaFrPanelSltLedsVersion      Integer32,
              oaFrPanelSltLedStatuses      OCTET STRING,
              oaFrPanelSltPrtsConnector    OCTET STRING,
              oaFrPanelSltPrtsSubConnector OCTET STRING
            }

oaFrPanelSltShelfId  OBJECT-TYPE
    SYNTAX Integer32 (1..16)
    MAX-ACCESS  not-accessible
    STATUS  current
    DESCRIPTION
    "The Shelf Number the Slot belongs to.
     In case of Stand Alone device - always is equal to 1."

    ::= { oaFrPanelSlotEntry 1 }

oaFrPanelSltSlotId     OBJECT-TYPE
    SYNTAX Integer32 (1..64)
    MAX-ACCESS  not-accessible
    STATUS  current
    DESCRIPTION
    "The Slot Id into the corresponding Shelf."

    ::= { oaFrPanelSlotEntry 2 }

oaFrPanelSltPortsNumber  OBJECT-TYPE
    SYNTAX Integer32 (0..255)
    MAX-ACCESS  read-only
    STATUS  current
    DESCRIPTION
    "The Max. number of the Ports placed in the Slot Front Panel."

    ::= { oaFrPanelSlotEntry 3 }

oaFrPanelSltLedsNumber  OBJECT-TYPE
    SYNTAX Integer32 (0..255)
    MAX-ACCESS  read-only
    STATUS  current
    DESCRIPTION
    "The Max number of the Objects [LEDs,Ports,Labels,Pictures etc.]
     that must be drawn on the Slot Front Panel."

    ::= { oaFrPanelSlotEntry 4 }

oaFrPanelSltLedsVersion  OBJECT-TYPE
    SYNTAX Integer32 (1..4294967295)
    MAX-ACCESS  read-only
    STATUS  current
    DESCRIPTION
    "The Front Panel version.
     Indicates how to interpret this Table Objects Octet Strings.
     For example version=1 means that each byte in the Octet String
     stores the value of the corresponding Port parameter in the Slot."

    ::= { oaFrPanelSlotEntry 5 }

oaFrPanelSltLedStatuses  OBJECT-TYPE
    SYNTAX OCTET STRING (SIZE (0..255))
    MAX-ACCESS  read-only
    STATUS  current
    DESCRIPTION
    "The statuses of all Objects [LEDs,Ports,Labels,Pictures etc.]
     that must be drawn on the Slot Front Panel.
     Each byte of the Octet String can store such values:
     - in case of Colors:
       0 -             [unknown],
       1 - Light GREEN [on],
       2 - BLACK       [off],
       3 - YELLOW      [reserved],
       4 - RED         [disabled]."

    ::= { oaFrPanelSlotEntry 6 }

oaFrPanelSltPrtsConnector  OBJECT-TYPE
    SYNTAX OCTET STRING (SIZE (0..255))
    MAX-ACCESS  read-only
    STATUS  current
    DESCRIPTION
    "The Connector Types of the Ports placed in the Slot.
     Each byte of the Octet String can store such values: 
     other - 1 - Unknown type of connector,
     static- 2 - Not Changeable (fix) type of connector,
     gbic  - 3 - GBIC type of connector,
     sfp   - 4 - SFP  type of connector,
     xfp   - 5 - XFP  type of connector."

    ::= { oaFrPanelSlotEntry 7 }

oaFrPanelSltPrtsSubConnector  OBJECT-TYPE
    SYNTAX OCTET STRING (SIZE (0..255))
    MAX-ACCESS  read-only
    STATUS  current
    DESCRIPTION
    "The Connector Physical Sub Types of the Ports placed in the Slot.
     Each byte of the Octet String can store such values: 
     other - 1 - Unknown or N/A Connector's connectivity Type,
     rj45  - 2 - Copper RJ45,
     sc    - 3 - Regular Fibre Optic [FO],
     lc    - 4 - LC,
     mtrj  - 5 - MT-RJ,
     vf    - 6 - VF,
     mu    - 7 - MU."

    ::= { oaFrPanelSlotEntry 8 }

----------------------------------------------------------------------
--  Conformance Information 
----------------------------------------------------------------------

oaFrPanelCompliances  OBJECT IDENTIFIER ::= { oaFrPanelConformance 1 }
oaFrPanelGroups       OBJECT IDENTIFIER ::= { oaFrPanelConformance 2 }

oaFrPanelCompliance MODULE-COMPLIANCE
    STATUS current 
    DESCRIPTION 
        "The core compliance statement for all 'oaFrPanel' MIB implementations."
    MODULE -- this module 
     
        MANDATORY-GROUPS { 
                          oaFrPanelGroup
                         } 
--        DESCRIPTION
--        "."
    ::= { oaFrPanelCompliances 1 }
 
----------------------------------------------------------------------
-- Conformance Groups 
----------------------------------------------------------------------

oaFrPanelGroup  OBJECT-GROUP
    OBJECTS { 
             oaFrPanelGenSupport,

             oaFrPanelSltPortsNumber,
             oaFrPanelSltLedsNumber,
             oaFrPanelSltLedsVersion,
             oaFrPanelSltLedStatuses,
             oaFrPanelSltPrtsConnector,
             oaFrPanelSltPrtsSubConnector
            }
    STATUS current 
    DESCRIPTION 
        "Mandatory objects for grouping of Device Front Panel parameters."
    ::= { oaFrPanelGroups 1 }

END

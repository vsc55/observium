WebGraph-OLD-Thermo-Hygro-Barometer-US-MIB DEFINITIONS ::= BEGIN
----------------------------------------------------------------
-- Revison: 1.31
----------------------------------------------------------------
-- 03.09.2010 	New: wtWebGraphThermoBaroTempValuePkt
--		    Delimeter Dezimalpunkt        
----------------------------------------------------------------
-- Revison: 1.30
----------------------------------------------------------------
-- 14.12.2009 	RSS Feed
-- 08.02.2010 	Correction Graph Sensor Color Table
----------------------------------------------------------------
-- Revison: 1.29
----------------------------------------------------------------
-- 02.06.2008 	Correction wtWebGraphThermBaroHTTP
--		Correction wtWebGraphThermoBaroDiag            
----------------------------------------------------------------
-- Revison: 1.28
----------------------------------------------------------------
-- 19.01.2007 	Webio
--		New Graphics java script base parameter 
----------------------------------------------------------------
-- Revison: 1.27
----------------------------------------------------------------
-- 09.11.2006 	Webio
--		DHCP enable 
----------------------------------------------------------------
-- Revison: 1.26
----------------------------------------------------------------
-- 03.08.2006 	wtWebGraphThermoBaroSensorNo corrected
--	
----------------------------------------------------------------
-- Revison: 1.25
----------------------------------------------------------------
-- 28.06.2006 	New: Community String Trap
--		
----------------------------------------------------------------
-- Revison: 1.24
----------------------------------------------------------------
-- 26.07.2005 	#57606, WebGraph Thermo-Hygrometer
--		CRON timer function
----------------------------------------------------------------
-- Revison: 1.23
----------------------------------------------------------------
-- 14.07.2005 	#57606, WebGraph Thermo-Hygrometer
--		FTP functions
----------------------------------------------------------------
-- Revison: 1.22
----------------------------------------------------------------
-- 17.05.2005 	#57606, WebGraph Thermo-Hygrometer
--		Trap NMS annotations
----------------------------------------------------------------
-- Revison: 1.21
----------------------------------------------------------------
-- 19.04.2005 	#57606, WebGraph Themometer
--		Mail Authentication
----------------------------------------------------------------
-- Revison: 1.20
----------------------------------------------------------------
-- 05.11.2004 	#57606, WebGraph Thermo-Hygrometer
--		New: Syslog
--		     
----------------------------------------------------------------
-- Revison: 1.19
----------------------------------------------------------------
-- 08.09.2004 	#57606 WebGraph Thermo-Hygrometer
--		New: 
--			wtWebGraphThermoBaroAlarmRHMin
--			wtWebGraphThermoBaroAlarmRHMax
--			wtWebGraphThermoBaroAlarmRHHysteresis
--			wtWebGraphThermoBaroPortSensorSelect
--			wtWebGraphThermoBaroAlarmDeltaTemp		
--			wtWebGraphThermoBaroAlarmAHMin		
--			wtWebGraphThermoBaroAlarmAHMax		
----------------------------------------------------------------
-- Revison: 1.18
----------------------------------------------------------------
-- 21.07.2004 	#57601/3/4, Webio Anx
--		New: 
--		     Diagnosis
----------------------------------------------------------------
-- Revison: 1.17
----------------------------------------------------------------
-- 28.06.2004 	#57630/1/2, Webio Digital
--		Neu: Puls Mode
----------------------------------------------------------------
-- Revison: 1.16
----------------------------------------------------------------
-- 16.04.2004 	New: #57632, Webio Digital EA24x24
--
--		#57630/1, Webio Digital EA12x12
--		New:
--			wtWebioEA12x12InputCounterClear
----------------------------------------------------------------
-- Revison: 1.15
----------------------------------------------------------------
-- 27.02.2004 	#57630/1, Webio Digital EA12x12
--		New:
--		Length changed to 32 Bit:
--			wtWebioEA12x12InputValue
--			wtWebioEA12x12OutputValue
--			wtWebioEA12x12LoadControlView
--			wtWebioEA12x12LCShutDownView
--			wtWebioEA12x12SetOutput
--			wtWebioEA12x12AlarmInputTrigger
--			wtWebioEA12x12AlarmOutputTrigger
--			wtWebioEA12x12PortOutputSafetyState
----------------------------------------------------------------
-- Revison: 1.14
----------------------------------------------------------------
-- 16.02.2004 	#57630/1, Webio Digital EA12x12
--		New:
--		Text: Location, Contact
--		SNMP: ColdStart, WarmStart, ComunityString Read/RW
--		Alarm: ColdStart / WarmStart trigger
--
-- 	 	#57601, 1xWebThermometer
--		#57603, 2xWebThermometer		
--		#57604, 8xWebThermometer
--		New:
--		Alarm Hysteresis 
--		Alarm Clear Traps and Mails
----------------------------------------------------------------
-- Revison: 1.13
----------------------------------------------------------------
-- 05.02.2004 	#57601, 1xWebThermometer
--		#57603, 2xWebThermometer		
--		#57604, 8xWebThermometer
--		New:
--		Text: Location, Contact
--		SNMP: ColdStart, WarmStart, ComunityString Read/RW
--		Alarm: ColdStart / WarmStart trigger
----------------------------------------------------------------
-- Revison: 1.12
----------------------------------------------------------------
-- 05.11.2003 	#57601, 1xWebThermometer
--		#57603, 2xWebThermometer		
--		#57604, 8xWebThermometer
--		New features:
--		Mail  : Option CSV attachment
--		Port  : Offset calibration
--		Alarm : TCP Client mode		
----------------------------------------------------------------
-- Revison: 1.11
----------------------------------------------------------------
-- 28.10.2003 	#57630/1, Webio Digital EA12x12
--		New features:
--		Alarm : TCP Client mode		
--		Inputs: Puls filter
----------------------------------------------------------------
-- Revison: 1.10
----------------------------------------------------------------
-- 22.07.2003 	#57630, Webio Digital EA12x12
--		New navigation tree, new binary modes		
--
----------------------------------------------------------------
-- Revison: 1.09
----------------------------------------------------------------
-- 24.03.2003 	Trap Enterprise (Type 1, 2) corrected 
----------------------------------------------------------------
-- Revison: 1.08
----------------------------------------------------------------
-- 04.03.2003 	reconciled the language versions DE/US
----------------------------------------------------------------
-- Revison: 1.07
----------------------------------------------------------------
-- 25.02.2003 	Correction: wtWebioEA12x12LoadControl
----------------------------------------------------------------
-- Revison: 1.06
----------------------------------------------------------------
-- 24.02.2003 	New:
--		#57630, Webio EA12x12, LoadControl Group
--		Correction: Trap variable names
----------------------------------------------------------------
-- Revison: 1.05
----------------------------------------------------------------
-- 21.01.2003 	New:
--		#57630, Webio EA12x12
----------------------------------------------------------------
-- Revison: 1.04
----------------------------------------------------------------
-- 02.01.2003 	New:
--		#57601, 1xWebThermometer
--		#57603, 2xWebThermometer, 8 alarms
----------------------------------------------------------------
-- Revison: 1.03
----------------------------------------------------------------
-- 21.11.2002 	New:
--		#57604, 2xWebThermometer, BOOTP, StartupSite
--		#57603, 8xWebThermometer, BOOTP, StartupSite
----------------------------------------------------------------
-- Revison: 1.02
----------------------------------------------------------------
-- 26.07.2002 	New:
--		#57604, 2xWebThermometer
--		#57603, 8xWebThermometer
-- 		


    IMPORTS

    OBJECT-TYPE                                        FROM RFC-1212
    TRAP-TYPE                                          FROM RFC-1215
    DisplayString, PhysAddress                         FROM RFC1213-MIB
    enterprises, TimeTicks, IpAddress, NetworkAddress  FROM RFC1155-SMI;

 
--    IpAddress ::=
--        [APPLICATION 0]
--            IMPLICIT OCTET STRING (SIZE (4))
--    Counter ::=
--        [APPLICATION 1]
--            IMPLICIT INTEGER (0..4294967295)
--    Gauge ::=
--        [APPLICATION 2]
--            IMPLICIT INTEGER (0..4294967295)
--    TimeTicks ::=
--        [APPLICATION 3]
--            IMPLICIT INTEGER (0..4294967295)


--    DisplayString ::= OCTET STRING
--    PhysAddress   ::= OCTET STRING

--    internet         OBJECT IDENTIFIER ::= { iso org(3) dod(6) 1 }
--    privat           OBJECT IDENTIFIER ::= { internet 4 }
--    enterprises      OBJECT IDENTIFIER ::= { privat 1 }



--  Wiesemann & Theis Com-Server MIB

    wut                				OBJECT IDENTIFIER ::= { enterprises 5040 }
    wtComServer        				OBJECT IDENTIFIER ::= { wut 1 }
    wtWebio            				OBJECT IDENTIFIER ::= { wtComServer 2 }

--  wtWebGraph Tree

    wtWebGraphThermoBaro  			OBJECT IDENTIFIER ::= { wtWebio 16 }
    
--  wtWebGraphThermoBaro Tree

    wtWebGraphThermoBaroTemp      		OBJECT IDENTIFIER ::= { wtWebGraphThermoBaro 1 }
    wtWebGraphThermoBaroSessCntrl 		OBJECT IDENTIFIER ::= { wtWebGraphThermoBaro 2 }
    wtWebGraphThermoBaroConfig    		OBJECT IDENTIFIER ::= { wtWebGraphThermoBaro 3 }
    wtWebGraphThermoBaroDiag    		OBJECT IDENTIFIER ::= { wtWebGraphThermoBaro 4 }    
    
--  wtWebGraphThermoBaroConfig Tree

    wtWebGraphThermoBaroDevice    		OBJECT IDENTIFIER ::= { wtWebGraphThermoBaroConfig 1 }
    wtWebGraphThermoBaroPorts     		OBJECT IDENTIFIER ::= { wtWebGraphThermoBaroConfig 2 }	
    wtWebGraphThermoBaroManufact  		OBJECT IDENTIFIER ::= { wtWebGraphThermoBaroConfig 3 }	

--  wtWebGraphThermoBaroDevice Tree

    wtWebGraphThermoBaroText			OBJECT IDENTIFIER ::= { wtWebGraphThermoBaroDevice 1 }	
    wtWebGraphThermoBaroTimeDate 		OBJECT IDENTIFIER ::= { wtWebGraphThermoBaroDevice 2 }
    wtWebGraphThermoBaroBasic			OBJECT IDENTIFIER ::= { wtWebGraphThermoBaroDevice 3 }	
    wtWebGraphThermoBaroDatalogger		OBJECT IDENTIFIER ::= { wtWebGraphThermoBaroDevice 4 }	
    wtWebGraphThermoBaroAlarm			OBJECT IDENTIFIER ::= { wtWebGraphThermoBaroDevice 5 }
    wtWebGraphThermoBaroGraphics 		OBJECT IDENTIFIER ::= { wtWebGraphThermoBaroDevice 6 }
    
--  wtWebGraphThermoBaroTimeDate Tree

    wtWebGraphThermoBaroTimeZone		OBJECT IDENTIFIER ::= { wtWebGraphThermoBaroTimeDate 1 }
    wtWebGraphThermoBaroTimeServer		OBJECT IDENTIFIER ::= { wtWebGraphThermoBaroTimeDate 2 }	
    wtWebGraphThermoBaroDeviceClock		OBJECT IDENTIFIER ::= { wtWebGraphThermoBaroTimeDate 3 }

--  wtWebGraphThermoBaroBasic Tree
    
    wtWebGraphThermoBaroNetwork			OBJECT IDENTIFIER ::= { wtWebGraphThermoBaroBasic 1 }
    wtWebGraphThermoBaroHTTP			OBJECT IDENTIFIER ::= { wtWebGraphThermoBaroBasic 2 }
    wtWebGraphThermoBaroMail			OBJECT IDENTIFIER ::= { wtWebGraphThermoBaroBasic 3 }	
    wtWebGraphThermoBaroSNMP			OBJECT IDENTIFIER ::= { wtWebGraphThermoBaroBasic 4 }
    wtWebGraphThermoBaroUDP			OBJECT IDENTIFIER ::= { wtWebGraphThermoBaroBasic 5 }
    wtWebGraphThermoBaroSyslog			OBJECT IDENTIFIER ::= { wtWebGraphThermoBaroBasic 6 }    
    wtWebGraphThermoBaroFTP			OBJECT IDENTIFIER ::= { wtWebGraphThermoBaroBasic 7 }
    wtWebGraphThermoBaroRSS			OBJECT IDENTIFIER ::= { wtWebGraphThermoBaroBasic 8 }

    
--  wtWebGraphThermoBaroGraphics Tree
    
    wtWebGraphThermoBaroGraphicsBase 		OBJECT IDENTIFIER ::= { wtWebGraphThermoBaroGraphics 1 }
    wtWebGraphThermoBaroGraphicsSelect 		OBJECT IDENTIFIER ::= { wtWebGraphThermoBaroGraphics 2 }
    wtWebGraphThermoBaroGraphicsScale 		OBJECT IDENTIFIER ::= { wtWebGraphThermoBaroGraphics 3 }
        
-- wtWebGraphThermoBaroTemp Group
------------------------

wtWebGraphThermoBaroSensors OBJECT-TYPE
    SYNTAX INTEGER (1..2)
    ACCESS read-only
    STATUS mandatory
    DESCRIPTION
        "Number of sensors"
    ::= { wtWebGraphThermoBaroTemp 1 }

-- Interface Table

wtWebGraphThermoBaroSensorTable OBJECT-TYPE
    SYNTAX SEQUENCE OF WtWebGraphThermoBaroSensorEntry
    ACCESS not-accessible
    STATUS mandatory
    DESCRIPTION
        "List of sensors."
    ::= { wtWebGraphThermoBaroTemp 2 }

wtWebGraphThermoBaroSensorEntry OBJECT-TYPE
    SYNTAX WtWebGraphThermoBaroSensorEntry
    ACCESS not-accessible
    STATUS mandatory
    DESCRIPTION
        "List of sensor numbers."
    INDEX  { wtWebGraphThermoBaroSensorNo }
    ::= { wtWebGraphThermoBaroSensorTable 1 }

WtWebGraphThermoBaroSensorEntry ::= SEQUENCE {
    wtWebGraphThermoBaroSensorNo INTEGER
}

wtWebGraphThermoBaroSensorNo OBJECT-TYPE
    SYNTAX INTEGER (1..2)
    ACCESS read-only
    STATUS mandatory
    DESCRIPTION
        "Sensor number."
    ::= { wtWebGraphThermoBaroSensorEntry 1 }


-- wtWebGraphThermoBaroTempValue Table

wtWebGraphThermoBaroTempValueTable OBJECT-TYPE
    SYNTAX SEQUENCE OF WtWebGraphThermoBaroTempValueEntry
    ACCESS not-accessible
    STATUS mandatory
    DESCRIPTION
        "List of measurement values corresponding to the channel numbers."
    ::= { wtWebGraphThermoBaroTemp 3 }

wtWebGraphThermoBaroTempValueEntry OBJECT-TYPE
    SYNTAX WtWebGraphThermoBaroTempValueEntry
    ACCESS not-accessible
    STATUS mandatory
    DESCRIPTION
        "Measurement values of the sensors."
    INDEX  { wtWebGraphThermoBaroSensorNo }
    ::= { wtWebGraphThermoBaroTempValueTable 1 }

WtWebGraphThermoBaroTempValueEntry ::= SEQUENCE{
    wtWebGraphThermoBaroTempValue OCTET STRING
}

wtWebGraphThermoBaroTempValue OBJECT-TYPE
    SYNTAX OCTET STRING (SIZE (5))
    ACCESS read-only
    STATUS mandatory
    DESCRIPTION
        "Measurement value of the sensor, ASCII, 5 characters in length."
    ::= { wtWebGraphThermoBaroTempValueEntry 1 }

-- wtWebGraphThermoBaroBinaryTempValue Table

wtWebGraphThermoBaroBinaryTempValueTable OBJECT-TYPE
    SYNTAX SEQUENCE OF WtWebGraphThermoBaroBinaryTempValueEntry
    ACCESS not-accessible
    STATUS mandatory
    DESCRIPTION
        "List of binary measurement values corresponding to the channel numbers."
    ::= { wtWebGraphThermoBaroTemp 4 }

wtWebGraphThermoBaroBinaryTempValueEntry OBJECT-TYPE
    SYNTAX WtWebGraphThermoBaroBinaryTempValueEntry
    ACCESS not-accessible
    STATUS mandatory
    DESCRIPTION
        "Binary measurement values of the sensors."
    INDEX  { wtWebGraphThermoBaroSensorNo }
    ::= { wtWebGraphThermoBaroBinaryTempValueTable 1 }

WtWebGraphThermoBaroBinaryTempValueEntry ::= SEQUENCE{
    wtWebGraphThermoBaroBinaryTempValue INTEGER
}    

wtWebGraphThermoBaroBinaryTempValue OBJECT-TYPE
    SYNTAX INTEGER
    ACCESS read-only
    STATUS mandatory
    DESCRIPTION
        "Binary measurement value of the sensor in 1/10 degrees Celsius or 1/10 per cent,
        signed number, 0x4FFF6 indicates an 
        invalid measured value."
    ::= { wtWebGraphThermoBaroBinaryTempValueEntry 1 }

-- wtWebGraphThermoBaroTempValuePkt Table

wtWebGraphThermoBaroTempValuePktTable OBJECT-TYPE
    SYNTAX SEQUENCE OF WtWebGraphThermoBaroTempValuePktEntry
    ACCESS not-accessible
    STATUS mandatory
    DESCRIPTION
        "List of measurement values corresponding to the channel numbers."
    ::= { wtWebGraphThermoBaroTemp 8 }

wtWebGraphThermoBaroTempValuePktEntry OBJECT-TYPE
    SYNTAX WtWebGraphThermoBaroTempValuePktEntry
    ACCESS not-accessible
    STATUS mandatory
    DESCRIPTION
        "Measurement values of the sensors."
    INDEX  { wtWebGraphThermoBaroSensorNo }
    ::= { wtWebGraphThermoBaroTempValuePktTable 1 }

WtWebGraphThermoBaroTempValuePktEntry ::= SEQUENCE{
    wtWebGraphThermoBaroTempValuePkt OCTET STRING
}

wtWebGraphThermoBaroTempValuePkt OBJECT-TYPE
    SYNTAX OCTET STRING (SIZE (5))
    ACCESS read-only
    STATUS mandatory
    DESCRIPTION
        "Measurement value of the sensor, ASCII, 5 characters in length, delimeter is decimal point."
    ::= { wtWebGraphThermoBaroTempValuePktEntry 1 }    

-- wtWebGraphThermoBaroSessCntrl Group
--------------------------------

wtWebGraphThermoBaroSessCntrlPassword OBJECT-TYPE
    SYNTAX OCTET STRING 
    ACCESS read-write
    STATUS mandatory
    DESCRIPTION
        "Entering this password opens a session which is ended by writing a 1 to 
        wtWebGraphThermoBaroSessCntrlLogout. When read this variable provides a string of
        length zero."
    ::= { wtWebGraphThermoBaroSessCntrl 1 }

wtWebGraphThermoBaroSessCntrlConfigMode OBJECT-TYPE
    SYNTAX INTEGER {
    wtWebGraphThermoBaroSessCntrl-NoSession(0),
    wtWebGraphThermoBaroSessCntrl-Session(1)
    }
    ACCESS read-only
    STATUS mandatory
    DESCRIPTION
        "When the device is in SNMP configuration mode, the value 1 is
        returned, otherwise 0. If the read value is 0 even though the
        password was written, the device is already in config mode and the
        variables can only be read."
    ::= { wtWebGraphThermoBaroSessCntrl 2 }

wtWebGraphThermoBaroSessCntrlLogout OBJECT-TYPE
    SYNTAX INTEGER 
    ACCESS read-write
    STATUS mandatory
    DESCRIPTION
        "If the device is in configuration mode and the session was opened by
        this SNMP Manager, writing a 1 to this variable will end the session 
        and all parameters are stored.
        Writing a 2 discards all entries again.
        When read this variable provides the value 0."
    ::= { wtWebGraphThermoBaroSessCntrl 3 }

wtWebGraphThermoBaroSessCntrlAdminPassword OBJECT-TYPE
    SYNTAX OCTET STRING 
    ACCESS read-write
    STATUS mandatory
    DESCRIPTION
        "This password protects access to the variables with administrator rights.
        It can only be changed by the administrator. If no password was assigned,
        the valid password is public."
    ::= { wtWebGraphThermoBaroSessCntrl 4 }

wtWebGraphThermoBaroSessCntrlConfigPassword OBJECT-TYPE
    SYNTAX OCTET STRING 
    ACCESS read-write
    STATUS mandatory
    DESCRIPTION
        "This password protects access to the variables with configurator rights. It can
        be changed by the administrator and by the configurator. If no password was assigned, 
        the valid password is public. When read this variable provides a null-pointer."
    ::= { wtWebGraphThermoBaroSessCntrl 5 }
    

-- wtWebGraphThermoBaroText Group
------------------------

wtWebGraphThermoBaroDeviceName OBJECT-TYPE
    SYNTAX OCTET STRING 
    ACCESS read-write
    STATUS mandatory
    DESCRIPTION
        "Name of the Webio, which is user definable."
    ::= { wtWebGraphThermoBaroText 1 }

wtWebGraphThermoBaroDeviceText OBJECT-TYPE
    SYNTAX OCTET STRING 
    ACCESS read-write
    STATUS mandatory
    DESCRIPTION
        "Description of the Webio, which is user definable."
    ::= { wtWebGraphThermoBaroText 2 }

wtWebGraphThermoBaroDeviceLocation OBJECT-TYPE
    SYNTAX OCTET STRING 
    ACCESS read-write
    STATUS mandatory
    DESCRIPTION
        "Description of the location of the Webio, which is user definable."
    ::= { wtWebGraphThermoBaroText 3 }

wtWebGraphThermoBaroDeviceContact OBJECT-TYPE
    SYNTAX OCTET STRING 
    ACCESS read-write
    STATUS mandatory
    DESCRIPTION
        "Contact address of the system operator of the Webio, which is user definable."
    ::= { wtWebGraphThermoBaroText 4 }

-- wtWebGraphThermoBaroTimeZone Group
----------------------------

wtWebGraphThermoBaroTzOffsetHrs OBJECT-TYPE
    SYNTAX INTEGER 
    ACCESS read-write
    STATUS mandatory
    DESCRIPTION
        "Offset hours for the time zone (winter time) with respect to UTC."
    ::= { wtWebGraphThermoBaroTimeZone 1 }

wtWebGraphThermoBaroTzOffsetMin OBJECT-TYPE
    SYNTAX INTEGER 
    ACCESS read-write
    STATUS mandatory
    DESCRIPTION
        "Offset minutes for the time zone (winter time) with respect to UTC."
    ::= { wtWebGraphThermoBaroTimeZone 2 }

wtWebGraphThermoBaroTzEnable OBJECT-TYPE
    SYNTAX OCTET STRING (SIZE(4))
    ACCESS read-write
    STATUS mandatory
    DESCRIPTION
        "Binary coded conditions:
        Octet 1: unused
        Octet 2: unused
        Octet 3: unused
        Octet 4:
        	Bit 1-7: unused
	        Bit 0  : Apply Timezone"
    ::= { wtWebGraphThermoBaroTimeZone 3 }    
    
wtWebGraphThermoBaroStTzOffsetHrs OBJECT-TYPE
    SYNTAX INTEGER 
    ACCESS read-write
    STATUS mandatory
    DESCRIPTION
        "Offset hours of the time zone (summer time) with respect to UTC."
    ::= { wtWebGraphThermoBaroTimeZone 4 }

wtWebGraphThermoBaroStTzOffsetMin OBJECT-TYPE
    SYNTAX INTEGER 
    ACCESS read-write
    STATUS mandatory
    DESCRIPTION
        "Offset minutes of the time zone (summer time) with respect to UTC."
    ::= { wtWebGraphThermoBaroTimeZone 5 }
    
wtWebGraphThermoBaroStTzEnable OBJECT-TYPE
    SYNTAX OCTET STRING (SIZE(4))
    ACCESS read-write
    STATUS mandatory
    DESCRIPTION
        "Binary coded conditions:
        Octet 1: unused
        Octet 2: unused
        Octet 3: unused
        Octet 4:
        	Bit 1-7: unused
	        Bit 0  : Apply Summertime"
    ::= { wtWebGraphThermoBaroTimeZone 6 }       
    
wtWebGraphThermoBaroStTzStartMonth OBJECT-TYPE
    SYNTAX INTEGER {
    	wtWebGraphThermoBaroStartMonth-January(1),
    	wtWebGraphThermoBaroStartMonth-February(2),
    	wtWebGraphThermoBaroStartMonth-March(3),
    	wtWebGraphThermoBaroStartMonth-April(4),
    	wtWebGraphThermoBaroStartMonth-May(5),
    	wtWebGraphThermoBaroStartMonth-June(6),
    	wtWebGraphThermoBaroStartMonth-July(7),
    	wtWebGraphThermoBaroStartMonth-August(8),
    	wtWebGraphThermoBaroStartMonth-September(9),
    	wtWebGraphThermoBaroStartMonth-October(10),
    	wtWebGraphThermoBaroStartMonth-November(11),
    	wtWebGraphThermoBaroStartMonth-December(12)
    	}
    	
    ACCESS read-write
    STATUS mandatory
    DESCRIPTION
        "Month in which the change is made from winter time to summer time."
    ::= { wtWebGraphThermoBaroTimeZone 7 }

wtWebGraphThermoBaroStTzStartMode OBJECT-TYPE
    SYNTAX INTEGER {
    	wtWebGraphThermoBaroStartMode-first(1),
    	wtWebGraphThermoBaroStartMode-second(2),
    	wtWebGraphThermoBaroStartMode-third(3),
    	wtWebGraphThermoBaroStartMode-fourth(4),
    	wtWebGraphThermoBaroStartMode-last(5)
    	}
    	
    ACCESS read-write
    STATUS mandatory
    DESCRIPTION
        "Mode of the day of the week for which the change is made from winter time to summer time."
    ::= { wtWebGraphThermoBaroTimeZone 8 }

wtWebGraphThermoBaroStTzStartWday OBJECT-TYPE
    SYNTAX INTEGER {
    	wtWebGraphThermoBaroStartWday-Sunday(1),
    	wtWebGraphThermoBaroStartWday-Monday(2),
    	wtWebGraphThermoBaroStartWday-Tuesday(3),
    	wtWebGraphThermoBaroStartWday-Thursday(4),
    	wtWebGraphThermoBaroStartWday-Wednesday(5),
    	wtWebGraphThermoBaroStartWday-Friday(6),
    	wtWebGraphThermoBaroStartWday-Saturday(7)
    	}
    	
    ACCESS read-write
    STATUS mandatory
    DESCRIPTION
        "Day of the week on which the change is made from winter time to summer time"
    ::= { wtWebGraphThermoBaroTimeZone 9 }
    
wtWebGraphThermoBaroStTzStartHrs OBJECT-TYPE
    SYNTAX INTEGER 
    ACCESS read-write
    STATUS mandatory
    DESCRIPTION
        "Hour in which the time zone is changed from winter to summer time with
        respect to UTC."
    ::= { wtWebGraphThermoBaroTimeZone 10 }

wtWebGraphThermoBaroStTzStartMin OBJECT-TYPE
    SYNTAX INTEGER 
    ACCESS read-write
    STATUS mandatory
    DESCRIPTION
        "Minute in which the time zone is changed from winter to summer time with
        respect to UTC."
    ::= { wtWebGraphThermoBaroTimeZone 11 }
 
wtWebGraphThermoBaroStTzStopMonth OBJECT-TYPE
    SYNTAX INTEGER {
    	wtWebGraphThermoBaroStopMonth-January(1),
    	wtWebGraphThermoBaroStopMonth-February(2),
    	wtWebGraphThermoBaroStopMonth-March(3),
    	wtWebGraphThermoBaroStopMonth-April(4),
    	wtWebGraphThermoBaroStopMonth-May(5),
    	wtWebGraphThermoBaroStopMonth-June(6),
    	wtWebGraphThermoBaroStopMonth-July(7),
    	wtWebGraphThermoBaroStopMonth-August(8),
    	wtWebGraphThermoBaroStopMonth-September(9),
    	wtWebGraphThermoBaroStopMonth-October(10),
    	wtWebGraphThermoBaroStopMonth-November(11),
    	wtWebGraphThermoBaroStopMonth-December(12)
    	}
    ACCESS read-write
    STATUS mandatory
    DESCRIPTION
        "Month in which the change is made from summer time to winter time."
   ::= { wtWebGraphThermoBaroTimeZone 12 }

wtWebGraphThermoBaroStTzStopMode OBJECT-TYPE
    SYNTAX INTEGER {
    	wtWebGraphThermoBaroStopMode-first(1),
    	wtWebGraphThermoBaroStopMode-second(2),
    	wtWebGraphThermoBaroStopMode-third(3),
    	wtWebGraphThermoBaroStopMode-fourth(4),
    	wtWebGraphThermoBaroStopMode-last(5)
    	}
    ACCESS read-write
    STATUS mandatory
    DESCRIPTION
        "Mode of the week day on which the change is made from summer time to winter time."
    ::= { wtWebGraphThermoBaroTimeZone 13 }

wtWebGraphThermoBaroStTzStopWday OBJECT-TYPE
    SYNTAX INTEGER {
    	wtWebGraphThermoBaroStopWday-Sunday(1),
    	wtWebGraphThermoBaroStopWday-Monday(2),
    	wtWebGraphThermoBaroStopWday-Tuesday(3),
    	wtWebGraphThermoBaroStopWday-Thursday(4),
    	wtWebGraphThermoBaroStopWday-Wednesday(5),
    	wtWebGraphThermoBaroStopWday-Friday(6),
    	wtWebGraphThermoBaroStopWday-Saturday(7)
    	}
    ACCESS read-write
    STATUS mandatory
    DESCRIPTION
        "Day of the week on which the change is made from summer time to winter time."
    ::= { wtWebGraphThermoBaroTimeZone 14 }
    
wtWebGraphThermoBaroStTzStopHrs OBJECT-TYPE
    SYNTAX INTEGER 
    ACCESS read-write
    STATUS mandatory
    DESCRIPTION
        "Hour at which the time zone is changed from summer to winter time with
        respect to UTC."
    ::= { wtWebGraphThermoBaroTimeZone 15 }

wtWebGraphThermoBaroStTzStopMin OBJECT-TYPE
    SYNTAX INTEGER 
    ACCESS read-write
    STATUS mandatory
    DESCRIPTION
        "Minute at which the time zone is changed from summer to winter time with
        respect to UTC."
    ::= { wtWebGraphThermoBaroTimeZone 16 }

-- wtWebGraphThermoBaroTimeServer Group
----------------------------

wtWebGraphThermoBaroTimeServer1 OBJECT-TYPE
    SYNTAX OCTET STRING 
    ACCESS read-write
    STATUS mandatory
    DESCRIPTION
        "IP address or name of the 1st time server in ASCII"
    ::= { wtWebGraphThermoBaroTimeServer 1 }

wtWebGraphThermoBaroTimeServer2 OBJECT-TYPE
    SYNTAX OCTET STRING 
    ACCESS read-write
    STATUS mandatory
    DESCRIPTION
        "IP address or name of the 2nd time server in ASCII"
    ::= { wtWebGraphThermoBaroTimeServer 2 }
    
wtWebGraphThermoBaroTsEnable OBJECT-TYPE
    SYNTAX OCTET STRING (SIZE(4))
    ACCESS read-write
    STATUS mandatory
    DESCRIPTION
        "Binary coded conditions:
        Octet 1: unused
        Octet 2: unused
        Octet 3: unused
        Octet 4:
        	Bit 1-7: unused
	        Bit 0  : Apply Time Server"
    ::= { wtWebGraphThermoBaroTimeServer 3 }
    
wtWebGraphThermoBaroTsSyncTime OBJECT-TYPE
    SYNTAX INTEGER 
    ACCESS read-write
    STATUS mandatory
    DESCRIPTION
        "Daily synchronisation time with the time server (hour: 0-23)."
    ::= { wtWebGraphThermoBaroTimeServer 4 } 
    
-- wtWebGraphThermoBaroDeviceClock Group
----------------------------

wtWebGraphThermoBaroClockHrs OBJECT-TYPE
    SYNTAX INTEGER (0..23)
    ACCESS read-write
    STATUS mandatory
    DESCRIPTION
        "Clock hours taking into account the time zone settings."
    ::= { wtWebGraphThermoBaroDeviceClock 1 }

wtWebGraphThermoBaroClockMin OBJECT-TYPE
    SYNTAX INTEGER (0..59)
    ACCESS read-write
    STATUS mandatory
    DESCRIPTION
        "Clock minutes taking into account the time zone settings."
    ::= { wtWebGraphThermoBaroDeviceClock 2 }

wtWebGraphThermoBaroClockDay OBJECT-TYPE
    SYNTAX INTEGER (1..31)
    ACCESS read-write
    STATUS mandatory
    DESCRIPTION
        "Date: Day of the month, taking into account the time zone settings."
    ::= { wtWebGraphThermoBaroDeviceClock 3 }

wtWebGraphThermoBaroClockMonth OBJECT-TYPE
   SYNTAX INTEGER {
    	wtWebGraphThermoBaroClockMonth-January(1),
    	wtWebGraphThermoBaroClockMonth-February(2),
    	wtWebGraphThermoBaroClockMonth-March(3),
    	wtWebGraphThermoBaroClockMonth-April(4),
    	wtWebGraphThermoBaroClockMonth-May(5),
    	wtWebGraphThermoBaroClockMonth-June(6),
    	wtWebGraphThermoBaroClockMonth-July(7),
    	wtWebGraphThermoBaroClockMonth-August(8),
    	wtWebGraphThermoBaroClockMonth-September(9),
    	wtWebGraphThermoBaroClockMonth-October(10),
    	wtWebGraphThermoBaroClockMonth-November(11),
    	wtWebGraphThermoBaroClockMonth-December(12)
    	}
    ACCESS read-write
    STATUS mandatory
    DESCRIPTION
        "Date: Month, taking into account the time zone settings."
    ::= { wtWebGraphThermoBaroDeviceClock 4 }

wtWebGraphThermoBaroClockYear OBJECT-TYPE
    SYNTAX INTEGER (0..65535)
    ACCESS read-write
    STATUS mandatory
    DESCRIPTION
        "Date: Year, taking into account the time zone settings."
    ::= { wtWebGraphThermoBaroDeviceClock 5 }
    

-- wtWebGraphThermoBaroNetwork Group
------------------------

wtWebGraphThermoBaroIpAddress OBJECT-TYPE
    SYNTAX IpAddress
    ACCESS read-write
    STATUS mandatory
    DESCRIPTION
        "IP address of the Webio"
    ::= { wtWebGraphThermoBaroNetwork 1 }

wtWebGraphThermoBaroSubnetMask OBJECT-TYPE
    SYNTAX IpAddress
    ACCESS read-write
    STATUS mandatory
    DESCRIPTION
        "Subnet mask of the Webio"
    ::= { wtWebGraphThermoBaroNetwork 2 }

wtWebGraphThermoBaroGateway OBJECT-TYPE
    SYNTAX IpAddress
    ACCESS read-write
    STATUS mandatory
    DESCRIPTION
        "Gateway of the Webio"
    ::= { wtWebGraphThermoBaroNetwork 3 }

wtWebGraphThermoBaroDnsServer1 OBJECT-TYPE
    SYNTAX OCTET STRING 
    ACCESS read-write
    STATUS mandatory
    DESCRIPTION
        "IP address of the 1st DNS server in ASCII"
    ::= { wtWebGraphThermoBaroNetwork 4 }

wtWebGraphThermoBaroDnsServer2 OBJECT-TYPE
    SYNTAX OCTET STRING 
    ACCESS read-write
    STATUS mandatory
    DESCRIPTION
        "IP address of the 2nd DNS server in ASCII"
    ::= { wtWebGraphThermoBaroNetwork 5 }

wtWebGraphThermoBaroAddConfig OBJECT-TYPE
    SYNTAX OCTET STRING 
    ACCESS read-write
    STATUS mandatory
    DESCRIPTION
        "Additional configuration (1=ON):
        Octet 1: unused
        Octet 2: unused
        Octet 3: unused
        Octet 4:
	        Bit 1: DHCP disable
	        Bit 0: BOOTP disable
	        "
    ::= { wtWebGraphThermoBaroNetwork 6 }

--  wtWebGraphThermoBaroHTTP Group
--------------------------------

wtWebGraphThermoBaroStartup OBJECT-TYPE
    SYNTAX OCTET STRING 
    ACCESS read-write
    STATUS mandatory
    DESCRIPTION
        "Binary coded start page:
        Octet 1: unused
        Octet 2: unused
        Octet 3: unused
        Octet 4:
	        Bit 1: Index.htm
	        Bit 2: Home.htm
	        Bit 3: User.htm
	Only one page may be selected at a time."
    ::= { wtWebGraphThermoBaroHTTP 1 }

wtWebGraphThermoBaroGetHeaderEnable OBJECT-TYPE
    SYNTAX OCTET STRING 
    ACCESS read-write
    STATUS mandatory
    DESCRIPTION
        "If these bits are set, every answer of a short form GET question will be lead
        by the IP-address and name of the device and/or a HTTP header:
        Octet 1: unused
        Octet 2: unused
        Octet 3: unused
        Octet 4:
        	Bit 1-6: unused
        	Bit 1  : GET HTTP enable
                Bit 0  : GET Header enable"
    ::= { wtWebGraphThermoBaroHTTP 2 }  
    
wtWebGraphThermoBaroHttpPort OBJECT-TYPE
    SYNTAX INTEGER (1..65535)
    ACCESS read-write
    STATUS mandatory
    DESCRIPTION
        "Definition of the standard HTML port (Default: 80)."
    ::= { wtWebGraphThermoBaroHTTP 3 }    


-- wtWebGraphThermoBaroMail Group
--------------------------------

wtWebGraphThermoBaroMailAdName OBJECT-TYPE
    SYNTAX OCTET STRING 
    ACCESS read-write
    STATUS mandatory
    DESCRIPTION
        "Device name for mail administration."
    ::= { wtWebGraphThermoBaroMail 1 }
    
wtWebGraphThermoBaroMailReply OBJECT-TYPE
    SYNTAX OCTET STRING 
    ACCESS read-write
    STATUS mandatory
    DESCRIPTION
        "Reply address for the mail server."
    ::= { wtWebGraphThermoBaroMail 2 }
    
wtWebGraphThermoBaroMailServer OBJECT-TYPE
    SYNTAX OCTET STRING 
    ACCESS read-write
    STATUS mandatory
    DESCRIPTION
        "Name or IP address of the mail server."
    ::= { wtWebGraphThermoBaroMail 3 }
    
wtWebioAn1MailEnable OBJECT-TYPE
    SYNTAX OCTET STRING 
    ACCESS read-write
    STATUS mandatory
    DESCRIPTION
        "Set this bit to enable the sending of mails:
        Octet 1: unused
        Octet 2: unused
        Octet 3: unused
        Octet 4:
        	Bit 1-7: unused
                Bit 0  : Mail enable"
    ::= { wtWebGraphThermoBaroMail 4 }
    
wtWebGraphThermoBaroMailAuthentication OBJECT-TYPE
    SYNTAX OCTET STRING (SIZE (4))
    ACCESS read-write
    STATUS mandatory
    DESCRIPTION
        "Selection of the authentication modi:
        The OCTETS are interpreted bit-by-bit, with each bit corresponding to an output. 
        Bit 0 corresponds to the LSB.
        OCTET 1: unused
        OCTET 2: unused
        OCTET 3: unused
        OCTET 4: Bit 3-7: unused
        	 Bit 2  : POP3 before SMTP
        	 Bit 1  : ESMTP, authentication
        	 Bit 0  : SMTP, no authentication"
    ::= { wtWebGraphThermoBaroMail 5 }
    
wtWebGraphThermoBaroMailAuthUser OBJECT-TYPE
    SYNTAX OCTET STRING 
    ACCESS read-write
    STATUS mandatory
    DESCRIPTION
        "Name of the user to be authenticated."
    ::= { wtWebGraphThermoBaroMail 6 }    
    
wtWebGraphThermoBaroMailAuthPassword OBJECT-TYPE
    SYNTAX OCTET STRING 
    ACCESS read-write
    STATUS mandatory
    DESCRIPTION
        "Authentication password."
    ::= { wtWebGraphThermoBaroMail 7 }    
    
wtWebGraphThermoBaroMailPop3Server OBJECT-TYPE
    SYNTAX OCTET STRING 
    ACCESS read-write
    STATUS mandatory
    DESCRIPTION
        "Name or Ip-address of the POP3 Servers."
    ::= { wtWebGraphThermoBaroMail 8 }            

-- wtWebGraphThermoBaroSNMP Group
--------------------------------

wtWebGraphThermoBaroSnmpCommunityStringRead OBJECT-TYPE
    SYNTAX OCTET STRING
    ACCESS read-write
    STATUS mandatory
    DESCRIPTION
        "Community string read only"
    ::= { wtWebGraphThermoBaroSNMP 1 }

wtWebGraphThermoBaroSnmpCommunityStringReadWrite OBJECT-TYPE
    SYNTAX OCTET STRING
    ACCESS read-write
    STATUS mandatory
    DESCRIPTION
        "Community string read / write"
    ::= { wtWebGraphThermoBaroSNMP 2 }

wtWebGraphThermoBaroSystemTrapManagerIP OBJECT-TYPE
    SYNTAX OCTET STRING 
    ACCESS read-write
    STATUS mandatory
    DESCRIPTION
        "Name or IP address of the TCP server which accepts the system trap."
    ::= { wtWebGraphThermoBaroSNMP 3 }
    
wtWebGraphThermoBaroSystemTrapEnable OBJECT-TYPE
    SYNTAX OCTET STRING (SIZE(4))
    ACCESS read-write
    STATUS mandatory
    DESCRIPTION
        "Binary coded trigger conditions:
        Octet 1: unused
        Octet 2: unused
        Octet 3: unused
        Octet 4:
	        Bit 0:   ColdStart
	        Bit 1:   WarmStart
	        Bit 2-7: unused"
    ::= { wtWebGraphThermoBaroSNMP 4 }
    
wtWebGraphThermoBaroSnmpEnable OBJECT-TYPE
    SYNTAX OCTET STRING 
    ACCESS read-write
    STATUS mandatory
    DESCRIPTION
        "Set bit 0 to enable SNMP.
        If disabled, the device did not respond to any SNMP requests.
        Bit 1 decided wether the community string of read operations 
        is compared with the system password or not:
        Octet 1: unused
        Octet 2: unused
        Octet 3: unused
        Octet 4:
        	Bit 1-7: unused
        	Bit 0  : SNMP enable"
    ::= { wtWebGraphThermoBaroSNMP 5 }
    
wtWebGraphThermoBaroSnmpCommunityStringTrap OBJECT-TYPE
    SYNTAX OCTET STRING
    ACCESS read-write
    STATUS mandatory
    DESCRIPTION
        "Community string send within traps."
    ::= { wtWebGraphThermoBaroSNMP 6 }    
            
    
-- wtWebGraphThermoBaroUDP Group
--------------------------------
    
wtWebGraphThermoBaroUdpPort OBJECT-TYPE
    SYNTAX INTEGER (1..65535)
    ACCESS read-write
    STATUS mandatory
    DESCRIPTION
        "Udp port to which the Udp queries ( short form GET requests) can be sent. This
        port number must be unique within the device."
    ::= { wtWebGraphThermoBaroUDP 1 }
    
wtWebGraphThermoBaroUdpEnable OBJECT-TYPE
    SYNTAX OCTET STRING 
    ACCESS read-write
    STATUS mandatory
    DESCRIPTION
        "Set this bit to enable UDP support:
        Octet 1: unused
        Octet 2: unused
        Octet 3: unused
        Octet 4:
        	Bit 1-7: unused
                Bit 0  : UDP enable"
    ::= { wtWebGraphThermoBaroUDP 2 }
    
--  wtWebGraphThermoBaroSyslog Group
--------------------------------
    
wtWebGraphThermoBaroSyslogServerIP OBJECT-TYPE
    SYNTAX OCTET STRING 
    ACCESS read-write
    STATUS mandatory
    DESCRIPTION
        "Name or IP address of the Syslog server, which accepts the Syslog messgaes."
    ::= { wtWebGraphThermoBaroSyslog 1 }
    
wtWebGraphThermoBaroSyslogServerPort OBJECT-TYPE
    SYNTAX INTEGER
    ACCESS read-write
    STATUS mandatory
    DESCRIPTION
        "Portnumber of the Syslog servers, default 514."
    ::= { wtWebGraphThermoBaroSyslog 2 }

wtWebGraphThermoBaroSyslogSystemMessagesEnable OBJECT-TYPE
    SYNTAX OCTET STRING (SIZE(4))
    ACCESS read-write
    STATUS mandatory
    DESCRIPTION
        "Binary coded trigger conditions:
        Octet 1: unused
        Octet 2: unused
        Octet 3: unused
        Octet 4:
	        Bit 0:   ColdStart
	        Bit 1:   WarmStart
	        Bit 2:   Diag Messages
	        Bit 3-7: unused"
    ::= { wtWebGraphThermoBaroSyslog 3 }    

wtWebGraphThermoBaroSyslogEnable OBJECT-TYPE
    SYNTAX OCTET STRING 
    ACCESS read-write
    STATUS mandatory
    DESCRIPTION
        "Set bit 0to enable Syslog:
        Octet 1: unused
        Octet 2: unused
        Octet 3: unused
        Octet 4:
        	Bit 1-7: unused
                Bit 0  : Syslog enable"
    ::= { wtWebGraphThermoBaroSyslog 4 }
    
--  wtWebGraphThermoBaroFTP Group
--------------------------------

wtWebGraphThermoBaroFTPServerIP OBJECT-TYPE
    SYNTAX OCTET STRING 
    ACCESS read-write
    STATUS mandatory
    DESCRIPTION
        "Name or IP address of the FTP server, which accepts the FTP messages."
    ::= { wtWebGraphThermoBaroFTP 1 }
    
wtWebGraphThermoBaroFTPServerControlPort OBJECT-TYPE
    SYNTAX INTEGER
    ACCESS read-write
    STATUS mandatory
    DESCRIPTION
        "Portnumber of the control port of the FTP server, default 21."
    ::= { wtWebGraphThermoBaroFTP 2 }
    
wtWebGraphThermoBaroFTPUserName OBJECT-TYPE
    SYNTAX OCTET STRING 
    ACCESS read-write
    STATUS mandatory
    DESCRIPTION
        "FTP Loggin: user name."
    ::= { wtWebGraphThermoBaroFTP 3 }
    
wtWebGraphThermoBaroFTPPassword OBJECT-TYPE
    SYNTAX OCTET STRING 
    ACCESS read-write
    STATUS mandatory
    DESCRIPTION
        "FTP Loggin: user password."
    ::= { wtWebGraphThermoBaroFTP 4 }

wtWebGraphThermoBaroFTPAccount OBJECT-TYPE
    SYNTAX OCTET STRING 
    ACCESS read-write
    STATUS mandatory
    DESCRIPTION
        "FTP Loggin: name of account."
    ::= { wtWebGraphThermoBaroFTP 5 }

wtWebGraphThermoBaroFTPOption OBJECT-TYPE
    SYNTAX OCTET STRING 
    ACCESS read-write
    STATUS mandatory
    DESCRIPTION
        "Bit 0 switches the FTP Server in Passiv-Mode,
        the Client controls the data connection on its own:
        Octet 1: unused
        Octet 2: unused
        Octet 3: unused
        Octet 4:
        	Bit 1-7: unused
                Bit 0  : PASV enable"
    ::= { wtWebGraphThermoBaroFTP 6 }
    
wtWebGraphThermoBaroFTPEnable OBJECT-TYPE
    SYNTAX OCTET STRING 
    ACCESS read-write
    STATUS mandatory
    DESCRIPTION
        "Set Bit 0 to enable FTP:
        Octet 1: unused
        Octet 2: unused
        Octet 3: unused
        Octet 4:
        	Bit 1-7: unused
                Bit 0  : FTP enable"
    ::= { wtWebGraphThermoBaroFTP 7 }
    
    
-- wtWebGraphThermoBaroDatalogger Group
--------------------------------

wtWebGraphThermoBaroLoggerTimebase OBJECT-TYPE
    SYNTAX INTEGER {
    wtWebGraphThermoBaroDatalogger-1Min(1),
    wtWebGraphThermoBaroDatalogger-5Min(2),
    wtWebGraphThermoBaroDatalogger-15Min(3),
    wtWebGraphThermoBaroDatalogger-60Min(4)
    }
    ACCESS read-write
    STATUS mandatory
    DESCRIPTION
        "Time base of the data logger"
    ::= { wtWebGraphThermoBaroDatalogger 1 }

wtWebGraphThermoBaroLoggerSensorSel OBJECT-TYPE
    SYNTAX OCTET STRING (SIZE(4))
    ACCESS read-write
    STATUS mandatory
    DESCRIPTION
        "Binary coded trigger conditions:
        Octet 1: unused
        Octet 2: unused
        Octet 3: unused
        Octet 4:
        	Bit 0: Sensor 1
        	Bit 1: Sensor 2
        	Bit 2-7: unused"
    ::= { wtWebGraphThermoBaroDatalogger 2 }

--  wtWebGraphThermoBaroRSS Group
--------------------------------

wtWebGraphThermoBaroRSSChannelTitle OBJECT-TYPE
    SYNTAX OCTET STRING 
    ACCESS read-write
    STATUS mandatory
    DESCRIPTION
        "Name of the RSS Feed."
    ::= { wtWebGraphThermoBaroRSS 1 }
    
wtWebGraphThermoBaroRSSChannelLink OBJECT-TYPE
    SYNTAX OCTET STRING 
    ACCESS read-write
    STATUS mandatory
    DESCRIPTION
        "Link of the RSS Feed."
    ::= { wtWebGraphThermoBaroRSS 2 }

wtWebGraphThermoBaroRSSChannelDescription OBJECT-TYPE
    SYNTAX OCTET STRING 
    ACCESS read-write
    STATUS mandatory
    DESCRIPTION
        "Description of the RSS Feed."
    ::= { wtWebGraphThermoBaroRSS 3 }

wtWebGraphThermoBaroRSSChannelImage OBJECT-TYPE
    SYNTAX OCTET STRING 
    ACCESS read-write
    STATUS mandatory
    DESCRIPTION
        "Link of a picture, which will be shown at the headline of the output window."
    ::= { wtWebGraphThermoBaroRSS 4 }

wtWebGraphThermoBaroRSSChannelImageTitle OBJECT-TYPE
    SYNTAX OCTET STRING 
    ACCESS read-write
    STATUS mandatory
    DESCRIPTION
        "Alias Name of the picture."
    ::= { wtWebGraphThermoBaroRSS 5 }

wtWebGraphThermoBaroRSSChannelImageLink OBJECT-TYPE
    SYNTAX OCTET STRING 
    ACCESS read-write
    STATUS mandatory
    DESCRIPTION
        "Link, which can be selected by clicking on the picture."
    ::= { wtWebGraphThermoBaroRSS 6 }
    
wtWebGraphThermoBaroRSSChannelItemTitle OBJECT-TYPE
    SYNTAX OCTET STRING 
    ACCESS read-write
    STATUS mandatory
    DESCRIPTION
        "Title of the RSS Feed."
    ::= { wtWebGraphThermoBaroRSS 7 }

wtWebGraphThermoBaroRSSChannelItemLink OBJECT-TYPE
    SYNTAX OCTET STRING 
    ACCESS read-write
    STATUS mandatory
    DESCRIPTION
        "Link of the RSS Feed."
    ::= { wtWebGraphThermoBaroRSS 8 }

wtWebGraphThermoBaroRSSChannelItemDescription OBJECT-TYPE
    SYNTAX OCTET STRING 
    ACCESS read-write
    STATUS mandatory
    DESCRIPTION
        "Text of the RSS Feed."
    ::= { wtWebGraphThermoBaroRSS 9 }

wtWebGraphThermoBaroRSSChannelItemQuantity OBJECT-TYPE
    SYNTAX OCTET STRING 
    ACCESS read-write
    STATUS mandatory
    DESCRIPTION
        "Number of lines."
    ::= { wtWebGraphThermoBaroRSS 10 }

-- wtWebGraphThermoBaroAlarm Group
----------------------------

wtWebGraphThermoBaroAlarmCount OBJECT-TYPE
    SYNTAX INTEGER (1..8)
    ACCESS read-only
    STATUS mandatory
    DESCRIPTION
        "Number of independent alarms."
    ::= { wtWebGraphThermoBaroAlarm 1 }
    
-- Alarm Interface Table

wtWebGraphThermoBaroAlarmIfTable OBJECT-TYPE
    SYNTAX SEQUENCE OF WtWebGraphThermoBaroAlarmIfEntry
    ACCESS not-accessible
    STATUS mandatory
    DESCRIPTION
        "List of alarm indices."
    ::= { wtWebGraphThermoBaroAlarm 2 }

wtWebGraphThermoBaroAlarmIfEntry OBJECT-TYPE
    SYNTAX WtWebGraphThermoBaroAlarmIfEntry
    ACCESS not-accessible
    STATUS mandatory
    DESCRIPTION
        "Numbers of the alarms."
    INDEX  { wtWebGraphThermoBaroAlarmNo }
    ::= { wtWebGraphThermoBaroAlarmIfTable 1 }

WtWebGraphThermoBaroAlarmIfEntry ::= SEQUENCE {
    wtWebGraphThermoBaroAlarmNo INTEGER
}

wtWebGraphThermoBaroAlarmNo OBJECT-TYPE
    SYNTAX INTEGER (1..8)
    ACCESS read-only
    STATUS mandatory
    DESCRIPTION
        "Alarm number."
    ::= { wtWebGraphThermoBaroAlarmIfEntry 1 }

-- Alarm Table

wtWebGraphThermoBaroAlarmTable OBJECT-TYPE
    SYNTAX SEQUENCE OF WtWebGraphThermoBaroAlarmEntry
    ACCESS not-accessible
    STATUS mandatory
    DESCRIPTION
        "List of settings depending on the alarm number."
    ::= { wtWebGraphThermoBaroAlarm 3 }

wtWebGraphThermoBaroAlarmEntry OBJECT-TYPE
    SYNTAX WtWebGraphThermoBaroAlarmEntry
    ACCESS not-accessible
    STATUS mandatory
    DESCRIPTION
        "Alarm parameters of the individual alarms."
    INDEX  { wtWebGraphThermoBaroAlarmNo }
    ::= { wtWebGraphThermoBaroAlarmTable 1 }

WtWebGraphThermoBaroAlarmEntry ::= SEQUENCE {
    wtWebGraphThermoBaroAlarmTrigger		OCTET STRING,
    wtWebGraphThermoBaroAlarmMin		OCTET STRING,
    wtWebGraphThermoBaroAlarmMax		OCTET STRING,
    wtWebGraphThermoBaroAlarmHysteresis		OCTET STRING,
    wtWebGraphThermoBaroAlarmDelay		OCTET STRING,
    wtWebGraphThermoBaroAlarmInterval		OCTET STRING,
    wtWebGraphThermoBaroAlarmEnable		OCTET STRING,
    wtWebGraphThermoBaroAlarmEMailAddr		OCTET STRING,
    wtWebGraphThermoBaroAlarmMailSubject	OCTET STRING,
    wtWebGraphThermoBaroAlarmMailText		OCTET STRING,
    wtWebGraphThermoBaroAlarmManagerIP		OCTET STRING,
    wtWebGraphThermoBaroAlarmTrapText		OCTET STRING,
    wtWebGraphThermoBaroAlarmMailOptions	OCTET STRING,
    wtWebGraphThermoBaroAlarmTcpIpAddr		OCTET STRING,
    wtWebGraphThermoBaroAlarmTcpPort		INTEGER,
    wtWebGraphThermoBaroAlarmTcpText		OCTET STRING,
    wtWebGraphThermoBaroAlarmClearMailSubject	OCTET STRING,
    wtWebGraphThermoBaroAlarmClearMailText	OCTET STRING,
    wtWebGraphThermoBaroAlarmClearTrapText	OCTET STRING,
    wtWebGraphThermoBaroAlarmClearTcpText	OCTET STRING,
    wtWebGraphThermoBaroAlarmDeltaTemp		OCTET STRING,
    wtWebGraphThermoBaroAlarmRHMin		OCTET STRING,
    wtWebGraphThermoBaroAlarmRHMax		OCTET STRING,
    wtWebGraphThermoBaroAlarmRHHysteresis	OCTET STRING,
    wtWebGraphThermoBaroAlarmAHMin		OCTET STRING,
    wtWebGraphThermoBaroAlarmAHMax		OCTET STRING,    
    wtWebGraphThermoBaroAlarmSyslogIpAddr	OCTET STRING,
    wtWebGraphThermoBaroAlarmSyslogPort		INTEGER,
    wtWebGraphThermoBaroAlarmSyslogText		OCTET STRING,
    wtWebGraphThermoBaroAlarmSyslogClearText	OCTET STRING,
    wtWebGraphThermoBaroAlarmFtpDataPort	OCTET STRING,
    wtWebGraphThermoBaroAlarmFtpFileName	OCTET STRING,
    wtWebGraphThermoBaroAlarmFtpText		OCTET STRING,
    wtWebGraphThermoBaroAlarmFtpClearText	OCTET STRING,
    wtWebGraphThermoBaroAlarmFtpOption		OCTET STRING,
    wtWebGraphThermoBaroAlarmTimerCron		OCTET STRING
}

wtWebGraphThermoBaroAlarmTrigger OBJECT-TYPE
    SYNTAX OCTET STRING (SIZE(4))
    ACCESS read-write
    STATUS mandatory
    DESCRIPTION
        "Binary coded trigger conditions:
        Octet 1: unused
        Octet 2: unused
        Octet 3:
        	Bit 0: Timer
        	Bit 1: ColdStart
        	Bit 2: WarmStart
        	
        Octet 4:
        	Bit 0: Sensor 1
        	Bit 1: Sensor 2
        	Bit 2-7: unused"
    ::= { wtWebGraphThermoBaroAlarmEntry 1 }

wtWebGraphThermoBaroAlarmMin OBJECT-TYPE
    SYNTAX OCTET STRING 
    ACCESS read-write
    STATUS mandatory
    DESCRIPTION
        "Minimum temperature in degrees with maximum 2 decimal places."
    ::= { wtWebGraphThermoBaroAlarmEntry 2 }

wtWebGraphThermoBaroAlarmMax OBJECT-TYPE
    SYNTAX OCTET STRING 
    ACCESS read-write
    STATUS mandatory
    DESCRIPTION
        "Maximum temperature in degrees with maximum 2 decimal places."
    ::= { wtWebGraphThermoBaroAlarmEntry 3 }
    
wtWebGraphThermoBaroAlarmHysteresis OBJECT-TYPE
    SYNTAX OCTET STRING 
    ACCESS read-write
    STATUS mandatory
    DESCRIPTION
        "Temperature changes of this size clears the alarm state (MAX-hyst, MIN+hyst.)
        , in degrees with maximum 2 decimal places."
    ::= { wtWebGraphThermoBaroAlarmEntry 4 }

wtWebGraphThermoBaroAlarmDelay OBJECT-TYPE
    SYNTAX OCTET STRING 
    ACCESS read-write
    STATUS mandatory
    DESCRIPTION
        "Alarm will be delayed by setting this time while stable alarm 
        condition occur (time in minutes)."
    ::= { wtWebGraphThermoBaroAlarmEntry 5 }
        

wtWebGraphThermoBaroAlarmInterval OBJECT-TYPE
    SYNTAX OCTET STRING 
    ACCESS read-write
    STATUS mandatory
    DESCRIPTION
        "Send interval for alarm messages."
    ::= { wtWebGraphThermoBaroAlarmEntry 6 }

wtWebGraphThermoBaroAlarmEnable OBJECT-TYPE
    SYNTAX OCTET STRING (SIZE(4))
    ACCESS read-write
    STATUS mandatory
    DESCRIPTION
        "Binary coded alarm enable:
        Octet 1: unused
        Octet 2: unused
        Octet 3: unused
        Octet 4:
		Bit 0:	Mail Enable
        	Bit 1:	SNMP Trap enable
        	Bit 2:  TCP Client enable"
    ::= { wtWebGraphThermoBaroAlarmEntry 7 }

wtWebGraphThermoBaroAlarmEMailAddr OBJECT-TYPE
    SYNTAX OCTET STRING 
    ACCESS read-write
    STATUS mandatory
    DESCRIPTION
        "E-Mail address for sending the alarm mail to."
    ::= { wtWebGraphThermoBaroAlarmEntry 8 }

wtWebGraphThermoBaroAlarmMailSubject OBJECT-TYPE
    SYNTAX OCTET STRING 
    ACCESS read-write
    STATUS mandatory
    DESCRIPTION
        "Subject line for alarm mail."
    ::= { wtWebGraphThermoBaroAlarmEntry 9 }

wtWebGraphThermoBaroAlarmMailText OBJECT-TYPE
    SYNTAX OCTET STRING 
    ACCESS read-write
    STATUS mandatory
    DESCRIPTION
        "Alarm mail text: <Tn> provides the current temperature; n = 1..8.
        <Z> provides the current time."
    ::= { wtWebGraphThermoBaroAlarmEntry 10 }

wtWebGraphThermoBaroAlarmManagerIP OBJECT-TYPE
    SYNTAX OCTET STRING 
    ACCESS read-write
    STATUS mandatory
    DESCRIPTION
        "Name or IP address of the SNMP Manager which accepts the trap."
    ::= { wtWebGraphThermoBaroAlarmEntry 11 }

wtWebGraphThermoBaroAlarmTrapText OBJECT-TYPE
    SYNTAX OCTET STRING 
    ACCESS read-write
    STATUS mandatory
    DESCRIPTION
        "This text is sent in the trap body."
    ::= { wtWebGraphThermoBaroAlarmEntry 12 }
    
wtWebGraphThermoBaroAlarmMailOptions OBJECT-TYPE
    SYNTAX OCTET STRING (SIZE(4))
    ACCESS read-write
    STATUS mandatory
    DESCRIPTION
        "Binary coded options:
        Octet 1: unused
        Octet 2: unused
        Octet 3: unused
        Octet 4:
		Bit 0  :	Attach Thermo.csv Enable
		Bit 1  :	CSV-Data_since_last_report
        	Bit 2-7:	unused"
    ::= { wtWebGraphThermoBaroAlarmEntry 13 }    
    
wtWebGraphThermoBaroAlarmTcpIpAddr OBJECT-TYPE
    SYNTAX OCTET STRING 
    ACCESS read-write
    STATUS mandatory
    DESCRIPTION
        "Name or IP address of the TCP server which accepts the trap."
    ::= { wtWebGraphThermoBaroAlarmEntry 14 }    

wtWebGraphThermoBaroAlarmTcpPort OBJECT-TYPE
    SYNTAX INTEGER (1..65535) 
    ACCESS read-write
    STATUS mandatory
    DESCRIPTION
        "Port number of the TCP server which accepts the trap."
    ::= { wtWebGraphThermoBaroAlarmEntry 15 }    

wtWebGraphThermoBaroAlarmTcpText OBJECT-TYPE
    SYNTAX OCTET STRING 
    ACCESS read-write
    STATUS mandatory
    DESCRIPTION
        "This text is sent in the TCP trap body."
    ::= { wtWebGraphThermoBaroAlarmEntry 16 }

wtWebGraphThermoBaroAlarmClearMailSubject OBJECT-TYPE
    SYNTAX OCTET STRING 
    ACCESS read-write
    STATUS mandatory
    DESCRIPTION
        "Subject line for alarm clear mail."
    ::= { wtWebGraphThermoBaroAlarmEntry 17 }

wtWebGraphThermoBaroAlarmClearMailText OBJECT-TYPE
    SYNTAX OCTET STRING 
    ACCESS read-write
    STATUS mandatory
    DESCRIPTION
        "Alarm clear mail text: <Tn> provides the current temperature; n = 1..8.
        <Z> provides the current time."
    ::= { wtWebGraphThermoBaroAlarmEntry 18 }

wtWebGraphThermoBaroAlarmClearTrapText OBJECT-TYPE
    SYNTAX OCTET STRING 
    ACCESS read-write
    STATUS mandatory
    DESCRIPTION
        "This text is sent in the trap body."
    ::= { wtWebGraphThermoBaroAlarmEntry 19 }

wtWebGraphThermoBaroAlarmClearTcpText OBJECT-TYPE
    SYNTAX OCTET STRING 
    ACCESS read-write
    STATUS mandatory
    DESCRIPTION
        "This text is sent in the TCP trap body."
    ::= { wtWebGraphThermoBaroAlarmEntry 20 }
    
wtWebGraphThermoBaroAlarmDeltaTemp OBJECT-TYPE
    SYNTAX OCTET STRING 
    ACCESS read-write
    STATUS mandatory
    DESCRIPTION
        "Maximum rate of change  degrees/min with maximum 2 decimal places.
        Compared with the average of a period of 5 minutes."
    ::= { wtWebGraphThermoBaroAlarmEntry 21 }

wtWebGraphThermoBaroAlarmRHMin OBJECT-TYPE
    SYNTAX OCTET STRING 
    ACCESS read-write
    STATUS mandatory
    DESCRIPTION
        "Minimum rel. Humidity in percent with maximum 2 decimal places."
    ::= { wtWebGraphThermoBaroAlarmEntry 22 }

wtWebGraphThermoBaroAlarmRHMax OBJECT-TYPE
    SYNTAX OCTET STRING 
    ACCESS read-write
    STATUS mandatory
    DESCRIPTION
        "Maximum rel.Humidity in percent with maximum 2 decimal places."
    ::= { wtWebGraphThermoBaroAlarmEntry 23 }

wtWebGraphThermoBaroAlarmRHHysteresis OBJECT-TYPE
    SYNTAX OCTET STRING 
    ACCESS read-write
    STATUS mandatory
    DESCRIPTION
        "Hysterese rel. Humidity in percent with maximum 2 decimal places."
    ::= { wtWebGraphThermoBaroAlarmEntry 24 }

wtWebGraphThermoBaroAlarmAHMin OBJECT-TYPE
    SYNTAX OCTET STRING 
    ACCESS read-write
    STATUS mandatory
    DESCRIPTION
        "Minimum abs. Humidity in g/(m*m*m) with maximum 2 decimal places."
    ::= { wtWebGraphThermoBaroAlarmEntry 25 }

wtWebGraphThermoBaroAlarmAHMax OBJECT-TYPE
    SYNTAX OCTET STRING 
    ACCESS read-write
    STATUS mandatory
    DESCRIPTION
        "Maximum abs. Humidity in g/(m*m*m) with maximum 2 decimal places."
    ::= { wtWebGraphThermoBaroAlarmEntry 26 }

wtWebGraphThermoBaroAlarmSyslogIpAddr OBJECT-TYPE
    SYNTAX IpAddress 
    ACCESS read-write
    STATUS mandatory
    DESCRIPTION
        "IP address of the syslog server to which the Webio device should send syslog messages."
    ::= { wtWebGraphThermoBaroAlarmEntry 27 }    

wtWebGraphThermoBaroAlarmSyslogPort OBJECT-TYPE
    SYNTAX INTEGER (1..65535) 
    ACCESS read-write
    STATUS mandatory
    DESCRIPTION
        "Port number of the syslog server to which the Webio device should send syslog messages."
    ::= { wtWebGraphThermoBaroAlarmEntry 28 }    

wtWebGraphThermoBaroAlarmSyslogText OBJECT-TYPE
    SYNTAX OCTET STRING 
    ACCESS read-write
    STATUS mandatory
    DESCRIPTION
        "Every message starts with the priority key, a time stamp and the host ip address, according RFC3164.
        This text appears in the following syslog message body."
    ::= { wtWebGraphThermoBaroAlarmEntry 29 }
    
wtWebGraphThermoBaroAlarmSyslogClearText OBJECT-TYPE
    SYNTAX OCTET STRING 
    ACCESS read-write
    STATUS mandatory
    DESCRIPTION
        "Every message starts with the priority key, a time stamp and the host ip address, according RFC3164.
        This text appears in the following syslog message body."
    ::= { wtWebGraphThermoBaroAlarmEntry 30 } 
    
wtWebGraphThermoBaroAlarmFtpDataPort OBJECT-TYPE
    SYNTAX OCTET STRING 
    ACCESS read-write
    STATUS mandatory
    DESCRIPTION
        "Local data port: 1..65535 or AUTO: the next free port will be assigned."
    ::= { wtWebGraphThermoBaroAlarmEntry 31 }
    
wtWebGraphThermoBaroAlarmFtpFileName OBJECT-TYPE
    SYNTAX OCTET STRING 
    ACCESS read-write
    STATUS mandatory
    DESCRIPTION
        "Name of the file including path informations."
    ::= { wtWebGraphThermoBaroAlarmEntry 32 }
    
wtWebGraphThermoBaroAlarmFtpText OBJECT-TYPE
    SYNTAX OCTET STRING 
    ACCESS read-write
    STATUS mandatory
    DESCRIPTION
        "Message text to store on the FTP server."
    ::= { wtWebGraphThermoBaroAlarmEntry 33 }

wtWebGraphThermoBaroAlarmFtpClearText OBJECT-TYPE
    SYNTAX OCTET STRING 
    ACCESS read-write
    STATUS mandatory
    DESCRIPTION
        "Alarm clear message to store on the FTP server."
    ::= { wtWebGraphThermoBaroAlarmEntry 34 }
    
wtWebGraphThermoBaroAlarmFtpOptions OBJECT-TYPE
    SYNTAX OCTET STRING (SIZE(4))
    ACCESS read-write
    STATUS mandatory
    DESCRIPTION
        "Binary coded options, select only one option at the same time:
        STORE  = replace file
        APPEND = append message at the end of the file
        
        Octet 1: unused
        Octet 2: unused
        Octet 3: unused
        Octet 4:
		Bit 0  :	STORE
		Bit 1  :	APPEND
        	Bit 2-7:	unused"
    ::= { wtWebGraphThermoBaroAlarmEntry 35 }
    
wtWebGraphThermoBaroAlarmTimerCron OBJECT-TYPE
    SYNTAX OCTET STRING
    ACCESS read-write
    STATUS mandatory
    DESCRIPTION
        "This entry contains 5 space or tab seperated text fields for time trigger definition.
        Each field must match with the actual time to trigger a message, weekday and day of month
        are interpreted separatley.
        1: Minutes	Range 0-59
        2. Hours	Range 0-23, 0 is midnight
        3: Day of month	Range 1-31
        4: Month	Range 1-12
        5: Weekday	Range 0-6, 0 is sunday
        
        Syntax for every field:
         - an asterix (*) enables every possible setting of a field
         - single numbers seperated by commas
         - a partition within the allowed range (1-5)
         - step size within an partition of the allowed range (0-59/2: every second minute)."
    ::= { wtWebGraphThermoBaroAlarmEntry 36 }      
    
-- wtWebGraphThermoBaroGraphicsBase Group
----------------------------

wtWebGraphThermoBaroGraphicsBaseEnable OBJECT-TYPE
    SYNTAX OCTET STRING 
    ACCESS read-write
    STATUS mandatory
    DESCRIPTION
        "Defines the viewing options of the graphic:
        Octet 1: unused
        Octet 2: unused
        Octet 3: unused
        Octet 4:
                Bit 0  : Auto scroll enable
                Bit 1  : Show table
                Bit 2  : Show graph
                Bit 3  : Show control buttons
                Bit 4  : Show config menu
                Bit 5-7: unused"
    ::= { wtWebGraphThermoBaroGraphicsBase 1 }

wtWebGraphThermoBaroGraphicsBaseWidth OBJECT-TYPE
    SYNTAX INTEGER 
    ACCESS read-write
    STATUS mandatory
    DESCRIPTION
        "Defines the width of the graphic in pixels."
    ::= { wtWebGraphThermoBaroGraphicsBase 2 }
    
wtWebGraphThermoBaroGraphicsBaseHeight OBJECT-TYPE
        SYNTAX INTEGER 
        ACCESS read-write
        STATUS mandatory
        DESCRIPTION
            "Defines the height of the graphic in pixels."
        ::= { wtWebGraphThermoBaroGraphicsBase 3 }

wtWebGraphThermoBaroGraphicsBaseFrameColor OBJECT-TYPE
    SYNTAX OCTET STRING (SIZE(3))
    ACCESS read-write
    STATUS mandatory
    DESCRIPTION
        "Frame color definition in RGB."
    ::= { wtWebGraphThermoBaroGraphicsBase 4 }

wtWebGraphThermoBaroGraphicsBaseBackgroundColor OBJECT-TYPE
    SYNTAX OCTET STRING (SIZE(3))
    ACCESS read-write
    STATUS mandatory
    DESCRIPTION
        "Background color definition in RGB."
    ::= { wtWebGraphThermoBaroGraphicsBase 5 }
    
wtWebGraphThermoBaroGraphicsBasePollingrate OBJECT-TYPE
        SYNTAX INTEGER 
        ACCESS read-write
        STATUS mandatory
        DESCRIPTION
            "Defines the pollingrate in seconds, 
            which defines the refreshing intervall of the graphic."
        ::= { wtWebGraphThermoBaroGraphicsBase 6 }
   
-- wtWebGraphThermoBaroGraphicsSelect Group
----------------------------

wtWebGraphThermoBaroGraphicsSelectDisplaySensorSel OBJECT-TYPE
    SYNTAX OCTET STRING (SIZE(4))
    ACCESS read-write
    STATUS mandatory
    DESCRIPTION
        "Binary coded sensor selection:
        only selected sensors will be shown in the graphical presentation:
        Octet 1: unused
        Octet 2: unused
        Octet 3: unused
        Octet 4:
        	Bit 0: Sensor 1
        	Bit 1: Sensor 2
        	Bit 2: Sensor 3
        	Bit 3-7: unused"
    ::= { wtWebGraphThermoBaroGraphicsSelect 1 }   
    
wtWebGraphThermoBaroGraphicsSelectDisplayShowExtrem OBJECT-TYPE
    SYNTAX OCTET STRING (SIZE(4))
    ACCESS read-write
    STATUS mandatory
    DESCRIPTION
        "Binary coded sensor selection:
        only selected sensors will be shown with minima and maxima:
        Octet 1: unused
        Octet 2: unused
        Octet 3: unused
        Octet 4:
        	Bit 0: Sensor 1
        	Bit 1: Sensor 2
        	Bit 2: Sensor 3
        	Bit 3-7: unused"
     ::= { wtWebGraphThermoBaroGraphicsSelect 2 }   

-- Graph Sensor Color Table

wtWebGraphThermoBaroSensorColorTable OBJECT-TYPE
    SYNTAX SEQUENCE OF wtWebGraphThermoBaroSensorColorEntry
    ACCESS not-accessible
    STATUS mandatory
    DESCRIPTION
        "List of sensor colors for the praphical presentation."
    ::= { wtWebGraphThermoBaroGraphicsSelect 3 }

wtWebGraphThermoBaroSensorColorEntry OBJECT-TYPE
    SYNTAX wtWebGraphThermoBaroSensorColorEntry
    ACCESS not-accessible
    STATUS mandatory
    DESCRIPTION
        "Numbers of the sensors."
    INDEX  { wtWebGraphThermoBaroSensorNo }
    ::= { wtWebGraphThermoBaroSensorColorTable 1 }

WtWebGraphThermoBaroSensorColorEntry ::= SEQUENCE {
    wtWebGraphThermoBaroGraphicsSensorColor OCTET STRING,
    wtWebGraphThermoBaroGraphicsSelectScale OCTET STRING
}

wtWebGraphThermoBaroGraphicsSensorColor OBJECT-TYPE
    SYNTAX OCTET STRING (SIZE(3))
    ACCESS read-write
    STATUS mandatory
    DESCRIPTION
        "Color of the sensors at the praphical presention."
    ::= { wtWebGraphThermoBaroSensorColorEntry 1 }
    
wtWebGraphThermoBaroGraphicsSelectScale OBJECT-TYPE
    SYNTAX OCTET STRING 
    ACCESS read-write
    STATUS mandatory
    DESCRIPTION
        "Assignes one of 4 scales to a sensor:
        Octet 1: unused
        Octet 2: unused
        Octet 3: unused
        Octet 4:
                Bit 0  : Use Scale 1
                Bit 1  : Use Scale 2
                Bit 2  : Use Scale 3
                Bit 3-7: unused"
    ::= { wtWebGraphThermoBaroSensorColorEntry 2 }
   
-- wtWebGraphThermoBaroGraphicsScale Group
----------------------------

wtWebGraphThermoBaroGraphicsScaleAutoScaleEnable OBJECT-TYPE
    SYNTAX OCTET STRING 
    ACCESS read-write
    STATUS mandatory
    DESCRIPTION
        "Select the Auto Scale Mode:
        Octet 1: unused
        Octet 2: unused
        Octet 3: unused
        Octet 4:
                Bit 0  : Scale 1 Auto scale enable
                Bit 1  : Scale 2 Auto scale enable
                Bit 2  : Scale 3 Auto scale enable
                Bit 3-7: unused"
    ::= { wtWebGraphThermoBaroGraphicsScale 1 }


wtWebGraphThermoBaroGraphicsScaleAutoFitEnable OBJECT-TYPE
    SYNTAX OCTET STRING 
    ACCESS read-write
    STATUS mandatory
    DESCRIPTION
        "Select the Auto Fit Mode::
        Octet 1: unused
        Octet 2: unused
        Octet 3: unused
        Octet 4:
                Bit 0  : Scale 1 Auto fit enable
                Bit 1  : Scale 2 Auto fit enable
                Bit 2  : Scale 3 Auto fit enable
                Bit 3-7: unused"
    ::= { wtWebGraphThermoBaroGraphicsScale 2 }

wtWebGraphThermoBaroGraphicsScale1Min OBJECT-TYPE
    SYNTAX INTEGER
    ACCESS read-only
    STATUS mandatory
    DESCRIPTION
        "Scale 1: Minimum."
    ::= { wtWebGraphThermoBaroGraphicsScale 3 }
   
wtWebGraphThermoBaroGraphicsScale2Min OBJECT-TYPE
    SYNTAX INTEGER
    ACCESS read-only
    STATUS mandatory
    DESCRIPTION
        "Scale 2: Minimum."
    ::= { wtWebGraphThermoBaroGraphicsScale 4 }

wtWebGraphThermoBaroGraphicsScale3Min OBJECT-TYPE
    SYNTAX INTEGER
    ACCESS read-only
    STATUS mandatory
    DESCRIPTION
        "Scale 3: Minimum."
    ::= { wtWebGraphThermoBaroGraphicsScale 5 }

wtWebGraphThermoBaroGraphicsScale4Min OBJECT-TYPE
    SYNTAX INTEGER
    ACCESS read-only
    STATUS mandatory
    DESCRIPTION
        "Scale 4: Minimum."
    ::= { wtWebGraphThermoBaroGraphicsScale 6 }

wtWebGraphThermoBaroGraphicsScale1Max OBJECT-TYPE
    SYNTAX INTEGER
    ACCESS read-only
    STATUS mandatory
    DESCRIPTION
        "Scale 1: Maximum."
    ::= { wtWebGraphThermoBaroGraphicsScale 7 }

wtWebGraphThermoBaroGraphicsScale2Max OBJECT-TYPE
    SYNTAX INTEGER
    ACCESS read-only
    STATUS mandatory
    DESCRIPTION
        "Scale 2: Maximum."
    ::= { wtWebGraphThermoBaroGraphicsScale 8 }

wtWebGraphThermoBaroGraphicsScale3Max OBJECT-TYPE
    SYNTAX INTEGER
    ACCESS read-only
    STATUS mandatory
    DESCRIPTION
        "Scale 3: Maximum."
    ::= { wtWebGraphThermoBaroGraphicsScale 9 }

wtWebGraphThermoBaroGraphicsScale4Max OBJECT-TYPE
    SYNTAX INTEGER
    ACCESS read-only
    STATUS mandatory
    DESCRIPTION
        "Scale 4: Maximum."
    ::= { wtWebGraphThermoBaroGraphicsScale 10 }

wtWebGraphThermoBaroGraphicsScale1Unit OBJECT-TYPE
    SYNTAX OCTET STRING
    ACCESS read-only
    STATUS mandatory
    DESCRIPTION
        "Scale 1: Unit."
    ::= { wtWebGraphThermoBaroGraphicsScale 11 }

wtWebGraphThermoBaroGraphicsScale2Unit OBJECT-TYPE
    SYNTAX OCTET STRING
    ACCESS read-only
    STATUS mandatory
    DESCRIPTION
        "Scale 2: Unit."
    ::= { wtWebGraphThermoBaroGraphicsScale 12 }

wtWebGraphThermoBaroGraphicsScale3Unit OBJECT-TYPE
    SYNTAX OCTET STRING
    ACCESS read-only
    STATUS mandatory
    DESCRIPTION
        "Scale 3: Unit."
    ::= { wtWebGraphThermoBaroGraphicsScale 13 }

wtWebGraphThermoBaroGraphicsScale4Unit OBJECT-TYPE
    SYNTAX OCTET STRING
    ACCESS read-only
    STATUS mandatory
    DESCRIPTION
        "Scale 4: Unit."
    ::= { wtWebGraphThermoBaroGraphicsScale 14 }

    
-- wtWebGraphThermoBaroPorts Group
----------------------------

-- Table

wtWebGraphThermoBaroPortTable OBJECT-TYPE
    SYNTAX SEQUENCE OF WtWebGraphThermoBaroPortEntry
    ACCESS not-accessible
    STATUS mandatory
    DESCRIPTION
        "List of settings depending on the sensor number."
    ::= { wtWebGraphThermoBaroPorts 1 }

wtWebGraphThermoBaroPortEntry OBJECT-TYPE
    SYNTAX WtWebGraphThermoBaroPortEntry
    ACCESS not-accessible
    STATUS mandatory
    DESCRIPTION
        "Sensor parameters for the individual sensors."
    INDEX  { wtWebGraphThermoBaroSensorNo }
    ::= { wtWebGraphThermoBaroPortTable 1 }

WtWebGraphThermoBaroPortEntry ::= SEQUENCE {
    wtWebGraphThermoBaroPortName		OCTET STRING,
    wtWebGraphThermoBaroPortText		OCTET STRING,
    wtWebGraphThermoBaroPortOffset1		OCTET STRING,
    wtWebGraphThermoBaroPortTemperature1	OCTET STRING,
    wtWebGraphThermoBaroPortOffset2		OCTET STRING,
    wtWebGraphThermoBaroPortTemperature2	OCTET STRING,
    wtWebGraphThermoBaroPortComment		OCTET STRING
}

wtWebGraphThermoBaroPortName OBJECT-TYPE
    SYNTAX OCTET STRING 
    ACCESS read-write
    STATUS mandatory
    DESCRIPTION
        "Name of the sensor."
    ::= { wtWebGraphThermoBaroPortEntry 1 }

wtWebGraphThermoBaroPortText OBJECT-TYPE
    SYNTAX OCTET STRING 
    ACCESS read-write
    STATUS mandatory
    DESCRIPTION
        "Description of the sensor."
    ::= { wtWebGraphThermoBaroPortEntry 2 }

wtWebGraphThermoBaroPortOffset1 OBJECT-TYPE
    SYNTAX OCTET STRING 
    ACCESS read-write
    STATUS mandatory
    DESCRIPTION
        "Offset calibration: Offset in degrees with maximum 2 decimal places at temperature 1."
    ::= { wtWebGraphThermoBaroPortEntry 3 }

wtWebGraphThermoBaroPortTemperature1 OBJECT-TYPE
    SYNTAX OCTET STRING 
    ACCESS read-write
    STATUS mandatory
    DESCRIPTION
        "Offset calibration: Reference temperature 1 in degrees with maximum 2 decimal places."
    ::= { wtWebGraphThermoBaroPortEntry 4 }

wtWebGraphThermoBaroPortOffset2 OBJECT-TYPE
    SYNTAX OCTET STRING 
    ACCESS read-write
    STATUS mandatory
    DESCRIPTION
        "Offset calibration: Offset in degrees with maximum 2 decimal places at temperature 2."
    ::= { wtWebGraphThermoBaroPortEntry 5 }

wtWebGraphThermoBaroPortTemperature2 OBJECT-TYPE
    SYNTAX OCTET STRING 
    ACCESS read-write
    STATUS mandatory
    DESCRIPTION
        "Offset calibration: Reference temperature 1 in degrees with maximum 2 decimal places."
    ::= { wtWebGraphThermoBaroPortEntry 6 }

wtWebGraphThermoBaroPortComment OBJECT-TYPE
    SYNTAX OCTET STRING 
    ACCESS read-write
    STATUS mandatory
    DESCRIPTION
        "Offset calibration: informations of date, name of operator, reference devices."
    ::= { wtWebGraphThermoBaroPortEntry 7 }   

wtWebGraphThermoBaroPortAltidude OBJECT-TYPE
    SYNTAX OCTET STRING
    ACCESS read-write
    STATUS mandatory
    DESCRIPTION
        "Altidude oh the Sensor over mean sea level (MSL)."
    ::= { wtWebGraphThermoBaroPorts 2 }
    
-- wtWebGraphThermoBaroManufact Group
----------------------------

wtWebGraphThermoBaroMfName OBJECT-TYPE
    SYNTAX OCTET STRING 
    ACCESS read-write
    STATUS mandatory
    DESCRIPTION
        "Manufacturer company name"
    ::= { wtWebGraphThermoBaroManufact 1 }

wtWebGraphThermoBaroMfAddr OBJECT-TYPE
    SYNTAX OCTET STRING 
    ACCESS read-write
    STATUS mandatory
    DESCRIPTION
        "Manufacturer address."
    ::= { wtWebGraphThermoBaroManufact 2 }

wtWebGraphThermoBaroMfHotline OBJECT-TYPE
    SYNTAX OCTET STRING 
    ACCESS read-write
    STATUS mandatory
    DESCRIPTION
        "Manufacturer hotline."
    ::= { wtWebGraphThermoBaroManufact 3 }

wtWebGraphThermoBaroMfInternet OBJECT-TYPE
    SYNTAX OCTET STRING 
    ACCESS read-write
    STATUS mandatory
    DESCRIPTION
        "Manufacturer Internet address."
    ::= { wtWebGraphThermoBaroManufact 4 }

wtWebGraphThermoBaroMfDeviceTyp OBJECT-TYPE
    SYNTAX OCTET STRING 
    ACCESS read-write
    STATUS mandatory
    DESCRIPTION
        "Manufacturer device name (model number)."
    ::= { wtWebGraphThermoBaroManufact 5 }

wtWebGraphThermoBaroMfOrderNo OBJECT-TYPE
    SYNTAX OCTET STRING 
    ACCESS read-write
    STATUS mandatory
    DESCRIPTION
        "Manufacturer part number."
    ::= { wtWebGraphThermoBaroManufact 6 }

-- wtWebGraphThermoBaroDiag Group
----------------------------

wtWebGraphThermoBaroDiagErrorCount OBJECT-TYPE
    SYNTAX INTEGER
    ACCESS read-only
    STATUS mandatory
    DESCRIPTION
        "Number of entries in the error memory."
    ::= { wtWebGraphThermoBaroDiag 1 }

wtWebGraphThermoBaroDiagBinaryError OBJECT-TYPE
    SYNTAX OCTET STRING 
    ACCESS read-only
    STATUS mandatory
    DESCRIPTION
        "Error causes coded bit-by-bit."
    ::= { wtWebGraphThermoBaroDiag 2 }

wtWebGraphThermoBaroDiagErrorIndex OBJECT-TYPE
    SYNTAX INTEGER
    ACCESS read-write
    STATUS mandatory
    DESCRIPTION
        "The value of this variable is used as an index to read 
        an error massege from wtWebGraphThermoBaroDiagErrorMessage.
        Errors are numbered from 1 to wtWebGraphThermoBaroDiagErrorCount.
        Writing a valid value into this variable, making the appropriate 
        message readable from wtWebGraphThermoBaroDiagErrorMessage."
    ::= { wtWebGraphThermoBaroDiag 3 }

wtWebGraphThermoBaroDiagErrorMessage OBJECT-TYPE
    SYNTAX OCTET STRING 
    ACCESS read-only
    STATUS mandatory
    DESCRIPTION
        "Using wtWebGraphThermoBaroDiagErrorIndex as an index, the appropriate message is available."
    ::= { wtWebGraphThermoBaroDiag 4 }
    
wtWebGraphThermoBaroDiagErrorClear OBJECT-TYPE
    SYNTAX INTEGER
    ACCESS write-only
    STATUS mandatory
    DESCRIPTION
        "Writing 1 into this variable clears all diagnosis messages."
    ::= { wtWebGraphThermoBaroDiag 5 }

-- TRAP DEFINITIONS

-- Diese SNMP-Traps werden gesendet, wenn die Alarmtriggerbedingungen zutreffen 

wtWebGraphThermoBaroAlert1 TRAP-TYPE
    ENTERPRISE  wtWebGraphThermoBaro
    VARIABLES   { wtWebGraphThermoBaroAlarmTrapText }
    DESCRIPTION
        "This SNMP trap is generated when Alarm 1 was triggered,
        SNMP trap enable is set and
        SNMP is enabled."
    -- NMS trap annotation
    --#TYPE "Thermo-Hygrometer Alarm 1"
    --#SUMMARY "Alarm 1: %s"
    --#ARGUMENTS {0}
    --#SEVERITY INFORMATIONAL
    --#TIMEINDEX 99
    --#STATE OPERATIONAL    
    ::= 31

wtWebGraphThermoBaroAlert2 TRAP-TYPE
    ENTERPRISE  wtWebGraphThermoBaro
    VARIABLES   { wtWebGraphThermoBaroAlarmTrapText }
    DESCRIPTION
        "This SNMP trap is generated when Alarm 2 was triggered,
        SNMP trap enable is set and
        SNMP is enabled."
    -- NMS trap annotation
    --#TYPE "Thermo-Hygrometer Alarm 2"
    --#SUMMARY "Alarm 2: %s"
    --#ARGUMENTS {0}
    --#SEVERITY INFORMATIONAL
    --#TIMEINDEX 99
    --#STATE OPERATIONAL    
    ::= 32

wtWebGraphThermoBaroAlert3 TRAP-TYPE
    ENTERPRISE  wtWebGraphThermoBaro
    VARIABLES   { wtWebGraphThermoBaroAlarmTrapText }
    DESCRIPTION
        "This SNMP trap is generated when Alarm 3 was triggered,
        SNMP trap enable is set and
        SNMP is enabled."
    -- NMS trap annotation
    --#TYPE "Thermo-Hygrometer Alarm 3"
    --#SUMMARY "Alarm 3: %s"
    --#ARGUMENTS {0}
    --#SEVERITY INFORMATIONAL
    --#TIMEINDEX 99
    --#STATE OPERATIONAL    
    ::= 33

wtWebGraphThermoBaroAlert4 TRAP-TYPE
    ENTERPRISE  wtWebGraphThermoBaro
    VARIABLES   { wtWebGraphThermoBaroAlarmTrapText }
    DESCRIPTION
        "This SNMP trap is generated when Alarm 4 was triggered,
        SNMP trap enable is set and
        SNMP is enabled."
    -- NMS trap annotation
    --#TYPE "Thermo-Hygrometer Alarm 4"
    --#SUMMARY "Alarm 4: %s"
    --#ARGUMENTS {0}
    --#SEVERITY INFORMATIONAL
    --#TIMEINDEX 99
    --#STATE OPERATIONAL    
    ::= 34

wtWebGraphThermoBaroAlert5 TRAP-TYPE
    ENTERPRISE  wtWebGraphThermoBaro
    VARIABLES   { wtWebGraphThermoBaroAlarmTrapText }
    DESCRIPTION
        "This SNMP trap is generated when Alarm 5 was triggered,
        SNMP trap enable is set and
        SNMP is enabled."
    -- NMS trap annotation
    --#TYPE "Thermo-Hygrometer Alarm 5"
    --#SUMMARY "Alarm 5: %s"
    --#ARGUMENTS {0}
    --#SEVERITY INFORMATIONAL
    --#TIMEINDEX 99
    --#STATE OPERATIONAL    
    ::= 35

wtWebGraphThermoBaroAlert6 TRAP-TYPE
    ENTERPRISE  wtWebGraphThermoBaro
    VARIABLES   { wtWebGraphThermoBaroAlarmTrapText }
    DESCRIPTION
        "This SNMP trap is generated when Alarm 6 was triggered,
        SNMP trap enable is set and
        SNMP is enabled."
    -- NMS trap annotation
    --#TYPE "Thermo-Hygrometer Alarm 6"
    --#SUMMARY "Alarm 6: %s"
    --#ARGUMENTS {0}
    --#SEVERITY INFORMATIONAL
    --#TIMEINDEX 99
    --#STATE OPERATIONAL    
    ::= 36

wtWebGraphThermoBaroAlert7 TRAP-TYPE
    ENTERPRISE  wtWebGraphThermoBaro
    VARIABLES   { wtWebGraphThermoBaroAlarmTrapText }
    DESCRIPTION
        "This SNMP trap is generated when Alarm 7 was triggered,
        SNMP trap enable is set and
        SNMP is enabled."
    -- NMS trap annotation
    --#TYPE "Thermo-Hygrometer Alarm 7"
    --#SUMMARY "Alarm 7: %s"
    --#ARGUMENTS {0}
    --#SEVERITY INFORMATIONAL
    --#TIMEINDEX 99
    --#STATE OPERATIONAL    
    ::= 37

wtWebGraphThermoBaroAlert8 TRAP-TYPE
    ENTERPRISE  wtWebGraphThermoBaro
    VARIABLES   { wtWebGraphThermoBaroAlarmTrapText }
    DESCRIPTION
        "This SNMP trap is generated when Alarm 8 was triggered,
        SNMP trap enable is set and
        SNMP is enabled."
    -- NMS trap annotation
    --#TYPE "Thermo-Hygrometer Alarm 8"
    --#SUMMARY "Alarm 8: %s"
    --#ARGUMENTS {0}
    --#SEVERITY INFORMATIONAL
    --#TIMEINDEX 99
    --#STATE OPERATIONAL    
    ::= 38

    
wtWebGraphThermoBaroAlert9 TRAP-TYPE
    ENTERPRISE  wtWebGraphThermoBaro
    VARIABLES   { wtWebGraphThermoBaroAlarmClearTrapText }
    DESCRIPTION
        "This SNMP trap is generated when Alarm 1 was cleared,
        SNMP trap enable is set and
        SNMP is enabled."
    -- NMS trap annotation
    --#TYPE "Thermo-Hygrometer Release Alarm 1"
    --#SUMMARY "Release Alarm 1: %s"
    --#ARGUMENTS {0}
    --#SEVERITY INFORMATIONAL
    --#TIMEINDEX 99
    --#STATE OPERATIONAL    
    ::= 91

wtWebGraphThermoBaroAlert10 TRAP-TYPE
    ENTERPRISE  wtWebGraphThermoBaro
    VARIABLES   { wtWebGraphThermoBaroAlarmClearTrapText }
    DESCRIPTION
        "This SNMP trap is generated when Alarm 2 was cleared,
        SNMP trap enable is set and
        SNMP is enabled."
    -- NMS trap annotation
    --#TYPE "Thermo-Hygrometer Release Alarm 2"
    --#SUMMARY "Release Alarm 2: %s"
    --#ARGUMENTS {0}
    --#SEVERITY INFORMATIONAL
    --#TIMEINDEX 99
    --#STATE OPERATIONAL    
    ::= 92

wtWebGraphThermoBaroAlert11 TRAP-TYPE
    ENTERPRISE  wtWebGraphThermoBaro
    VARIABLES   { wtWebGraphThermoBaroAlarmClearTrapText }
    DESCRIPTION
        "This SNMP trap is generated when Alarm 3 was cleared,
        SNMP trap enable is set and
        SNMP is enabled."
    -- NMS trap annotation
    --#TYPE "Thermo-Hygrometer Release Alarm 3"
    --#SUMMARY "Release Alarm 3: %s"
    --#ARGUMENTS {0}
    --#SEVERITY INFORMATIONAL
    --#TIMEINDEX 99
    --#STATE OPERATIONAL    
    ::= 93

wtWebGraphThermoBaroAlert12 TRAP-TYPE
    ENTERPRISE  wtWebGraphThermoBaro
    VARIABLES   { wtWebGraphThermoBaroAlarmClearTrapText }
    DESCRIPTION
        "This SNMP trap is generated when Alarm 4 was cleared,
        SNMP trap enable is set and
        SNMP is enabled."
    -- NMS trap annotation
    --#TYPE "Thermo-Hygrometer Release Alarm 4"
    --#SUMMARY "Release Alarm 4: %s"
    --#ARGUMENTS {0}
    --#SEVERITY INFORMATIONAL
    --#TIMEINDEX 99
    --#STATE OPERATIONAL    
    ::= 94

wtWebGraphThermoBaroAlert13 TRAP-TYPE
    ENTERPRISE  wtWebGraphThermoBaro
    VARIABLES   { wtWebGraphThermoBaroAlarmClearTrapText }
    DESCRIPTION
        "This SNMP trap is generated when Alarm 5 was cleared,
        SNMP trap enable is set and
        SNMP is enabled."
    -- NMS trap annotation
    --#TYPE "Thermo-Hygrometer Release Alarm 5"
    --#SUMMARY "Release Alarm 5: %s"
    --#ARGUMENTS {0}
    --#SEVERITY INFORMATIONAL
    --#TIMEINDEX 99
    --#STATE OPERATIONAL    
    ::= 95

wtWebGraphThermoBaroAlert14 TRAP-TYPE
    ENTERPRISE  wtWebGraphThermoBaro
    VARIABLES   { wtWebGraphThermoBaroAlarmClearTrapText }
    DESCRIPTION
        "This SNMP trap is generated when Alarm 6 was cleared,
        SNMP trap enable is set and
        SNMP is enabled."
    -- NMS trap annotation
    --#TYPE "Thermo-Hygrometer Release Alarm 6"
    --#SUMMARY "Release Alarm 6: %s"
    --#ARGUMENTS {0}
    --#SEVERITY INFORMATIONAL
    --#TIMEINDEX 99
    --#STATE OPERATIONAL    
    ::= 96

wtWebGraphThermoBaroAlert15 TRAP-TYPE
    ENTERPRISE  wtWebGraphThermoBaro
    VARIABLES   { wtWebGraphThermoBaroAlarmClearTrapText }
    DESCRIPTION
        "This SNMP trap is generated when Alarm 7 was cleared,
        SNMP trap enable is set and
        SNMP is enabled."
    -- NMS trap annotation
    --#TYPE "Thermo-Hygrometer Release Alarm 7"
    --#SUMMARY "Release Alarm 7: %s"
    --#ARGUMENTS {0}
    --#SEVERITY INFORMATIONAL
    --#TIMEINDEX 99
    --#STATE OPERATIONAL    
    ::= 97

wtWebGraphThermoBaroAlert16 TRAP-TYPE
    ENTERPRISE  wtWebGraphThermoBaro
    VARIABLES   { wtWebGraphThermoBaroAlarmClearTrapText }
    DESCRIPTION
        "This SNMP trap is generated when Alarm 8 was cleared,
        SNMP trap enable is set and
        SNMP is enabled."
    -- NMS trap annotation
    --#TYPE "Thermo-Hygrometer Release Alarm 8"
    --#SUMMARY "Release Alarm 8: %s"
    --#ARGUMENTS {0}
    --#SEVERITY INFORMATIONAL
    --#TIMEINDEX 99
    --#STATE OPERATIONAL    
    ::= 98

wtWebGraphThermoBaroAlertDiag TRAP-TYPE
    ENTERPRISE  wtWebGraphThermoBaro
    VARIABLES   { 	
    		wtWebGraphThermoBaroDiagErrorIndex,
    	  	wtWebGraphThermoBaroDiagErrorMessage
    		}
    DESCRIPTION
        "This SNMP trap is generated when a diagnosis/error message was triggered,
        SNMP trap enable is set and
        SNMP is enabled."
    -- NMS trap annotation
    --#TYPE "Thermo-Hygrometer Diagnose Error"
    --#SUMMARY "Diagnose error index: %d, Message: %s."
    --#ARGUMENTS {0,1}
    --#SEVERITY MAJOR
    --#TIMEINDEX 99
    --#STATE DEGRADED    
    ::= 110 
 
END

WebGraph-2xThermometer-US-MIB DEFINITIONS ::= BEGIN
----------------------------------------------------------------
-- Revison: 1.35
----------------------------------------------------------------
-- 28.06.2018 	New: 
--		     systax errors corrected
----------------------------------------------------------------
-- Revison: 1.34
----------------------------------------------------------------
-- 12.12.2017 	New: 
--		     wtWebioAn2GraphMQTTLastWillEnable
--		     wtWebioAn2GraphMQTTLastWillTopic
--		     wtWebioAn2GraphMQTTLastWillMsg
--		     wtWebioAn2GraphMQTTLastWillQoS
--		     wtWebioAn2GraphMQTTLastWillRetain
--		     wtWebioAn2GraphMQTTLastWillConnectEnable
--		     wtWebioAn2GraphMQTTLastWillConnectMsg
----------------------------------------------------------------
-- Revison: 1.33
----------------------------------------------------------------
-- 07.09.2017 	New: wtWebioAnxGraphAlarmManagerPort
--		     wtWebioAnxGraphAlarmMQTT_QoS
--		     wtWebioAnxGraphAlarmMQTT_Retain
----------------------------------------------------------------
-- Revison: 1.32
----------------------------------------------------------------
-- 09.11.2016 	New: wtWebioAn2GraphMQTT group
--		     HTTP Request, MQTT Alarm, REST
----------------------------------------------------------------
-- Revison: 1.31
----------------------------------------------------------------
-- 15.07.2015 	Changes for new Navigation (__JB__)
----------------------------------------------------------------
-- Revison: 1.30
----------------------------------------------------------------
-- 22.06.2010 	Output with decimal point
--		
----------------------------------------------------------------
-- Revison: 1.29
----------------------------------------------------------------
-- 12.01.2009 	Webio
--		Trap numbering 
----------------------------------------------------------------
-- Revison: 1.28
----------------------------------------------------------------
-- 19.01.2007 	Webio
--		New Graphics java script base parameter 
----------------------------------------------------------------
-- Revison: 1.27
----------------------------------------------------------------
-- 09.11.2006 	Webio
--		DHCP enable 
----------------------------------------------------------------
-- Revison: 1.25
----------------------------------------------------------------
-- 28.06.2006 	New: Community String Trap
--		
----------------------------------------------------------------
-- Revison: 1.24
----------------------------------------------------------------
-- 23.12.2005 	#57607, WebGraph 2x Thermometer 
--		


    IMPORTS

    OBJECT-TYPE                                        FROM RFC-1212
    TRAP-TYPE                                          FROM RFC-1215
    DisplayString, PhysAddress                         FROM RFC1213-MIB
    enterprises, TimeTicks, IpAddress, NetworkAddress  FROM RFC1155-SMI;

 
--    IpAddress ::=
--        [APPLICATION 0]
--            IMPLICIT OCTET STRING (SIZE (4))
--    Counter ::=
--        [APPLICATION 1]
--            IMPLICIT INTEGER (0..4294967295)
--    Gauge ::=
--        [APPLICATION 2]
--            IMPLICIT INTEGER (0..4294967295)
--    TimeTicks ::=
--        [APPLICATION 3]
--            IMPLICIT INTEGER (0..4294967295)


--    DisplayString ::= OCTET STRING
--    PhysAddress   ::= OCTET STRING

--    internet         OBJECT IDENTIFIER ::= { iso org(3) dod(6) 1 }
--    privat           OBJECT IDENTIFIER ::= { internet 4 }
--    enterprises      OBJECT IDENTIFIER ::= { privat 1 }



--  Wiesemann & Theis Com-Server MIB

    wut                			OBJECT IDENTIFIER ::= { enterprises 5040 }
    wtComServer        			OBJECT IDENTIFIER ::= { wut 1 }
    wtWebio            			OBJECT IDENTIFIER ::= { wtComServer 2 }

--  wtWebio Tree

    wtWebioAn2Graph    			OBJECT IDENTIFIER ::= { wtWebio 43 }
    
--  wtWebioAn2Graph Tree

    wtWebioAn2GraphTemp      		OBJECT IDENTIFIER ::= { wtWebioAn2Graph 1 }
    wtWebioAn2GraphSessCntrl 		OBJECT IDENTIFIER ::= { wtWebioAn2Graph 2 }
    wtWebioAn2GraphConfig    		OBJECT IDENTIFIER ::= { wtWebioAn2Graph 3 }
    wtWebioAn2GraphDiag    		OBJECT IDENTIFIER ::= { wtWebioAn2Graph 4 }
    
--  wtWebioAn2GraphConfig Tree

    wtWebioAn2GraphDevice    		OBJECT IDENTIFIER ::= { wtWebioAn2GraphConfig 1 }
    wtWebioAn2GraphPorts     		OBJECT IDENTIFIER ::= { wtWebioAn2GraphConfig 2 }	
    wtWebioAn2GraphManufact  		OBJECT IDENTIFIER ::= { wtWebioAn2GraphConfig 3 }	

--  wtWebioAn2GraphDevice Tree

    wtWebioAn2GraphText			OBJECT IDENTIFIER ::= { wtWebioAn2GraphDevice 1 }	
    wtWebioAn2GraphTimeDate 		OBJECT IDENTIFIER ::= { wtWebioAn2GraphDevice 2 }
    wtWebioAn2GraphBasic		OBJECT IDENTIFIER ::= { wtWebioAn2GraphDevice 3 }	
    wtWebioAn2GraphDatalogger		OBJECT IDENTIFIER ::= { wtWebioAn2GraphDevice 4 }	
    wtWebioAn2GraphAlarm		OBJECT IDENTIFIER ::= { wtWebioAn2GraphDevice 5 }
    wtWebioAn2GraphGraphics 		OBJECT IDENTIFIER ::= { wtWebioAn2GraphDevice 6 }	
    
--  wtWebioAn2GraphTimeDate Tree

    wtWebioAn2GraphTimeZone		OBJECT IDENTIFIER ::= { wtWebioAn2GraphTimeDate 1 }
    wtWebioAn2GraphTimeServer		OBJECT IDENTIFIER ::= { wtWebioAn2GraphTimeDate 2 }	
    wtWebioAn2GraphDeviceClock		OBJECT IDENTIFIER ::= { wtWebioAn2GraphTimeDate 3 }

--  wtWebioAn2GraphBasic Tree
    
    wtWebioAn2GraphNetwork		OBJECT IDENTIFIER ::= { wtWebioAn2GraphBasic 1 }
    wtWebioAn2GraphHTTP			OBJECT IDENTIFIER ::= { wtWebioAn2GraphBasic 2 }
    wtWebioAn2GraphMail			OBJECT IDENTIFIER ::= { wtWebioAn2GraphBasic 3 }	
    wtWebioAn2GraphSNMP			OBJECT IDENTIFIER ::= { wtWebioAn2GraphBasic 4 }
    wtWebioAn2GraphUDP			OBJECT IDENTIFIER ::= { wtWebioAn2GraphBasic 5 }
    wtWebioAn2GraphSyslog		OBJECT IDENTIFIER ::= { wtWebioAn2GraphBasic 6 }    
    wtWebioAn2GraphFTP			OBJECT IDENTIFIER ::= { wtWebioAn2GraphBasic 7 }
    wtWebioAn2GraphLanguage		OBJECT IDENTIFIER ::= { wtWebioAn2GraphBasic 9 }
    wtWebioAn2GraphMQTT			OBJECT IDENTIFIER ::= { wtWebioAn2GraphBasic 12 }
    wtWebioAn2GraphREST			OBJECT IDENTIFIER ::= { wtWebioAn2GraphBasic 13 }
    
    
--  wtWebioAn2GraphGraphics Tree
           
    wtWebioAn2GraphGraphicsBase 	OBJECT IDENTIFIER ::= { wtWebioAn2GraphGraphics 1 }
    wtWebioAn2GraphGraphicsSelect 	OBJECT IDENTIFIER ::= { wtWebioAn2GraphGraphics 2 }
    wtWebioAn2GraphGraphicsScale 	OBJECT IDENTIFIER ::= { wtWebioAn2GraphGraphics 3 }
                  
-- wtWebioAn2GraphTemp Group
------------------------

wtWebioAn2GraphSensors OBJECT-TYPE
    SYNTAX INTEGER (1..2)
    ACCESS read-only
    STATUS mandatory
    DESCRIPTION
        "Number of temperature sensors"
    ::= { wtWebioAn2GraphTemp 1 }

-- Interface Table

wtWebioAn2GraphSensorTable OBJECT-TYPE
    SYNTAX SEQUENCE OF WtWebioAn2GraphSensorEntry
    ACCESS not-accessible
    STATUS mandatory
    DESCRIPTION
        "List of sensors."
    ::= { wtWebioAn2GraphTemp 2 }

wtWebioAn2GraphSensorEntry OBJECT-TYPE
    SYNTAX WtWebioAn2GraphSensorEntry
    ACCESS not-accessible
    STATUS mandatory
    DESCRIPTION
        "Temperature sensor numbers."
    INDEX  { wtWebioAn2GraphSensorNo }
    ::= { wtWebioAn2GraphSensorTable 1 }

WtWebioAn2GraphSensorEntry ::= SEQUENCE {
    wtWebioAn2GraphSensorNo INTEGER
}

wtWebioAn2GraphSensorNo OBJECT-TYPE
    SYNTAX INTEGER (1..2)
    ACCESS read-only
    STATUS mandatory
    DESCRIPTION
        "Temperature sensor number."
    ::= { wtWebioAn2GraphSensorEntry 1 }


-- wtWebioAn2GraphTempValue Table

wtWebioAn2GraphTempValueTable OBJECT-TYPE
    SYNTAX SEQUENCE OF WtWebioAn2GraphTempValueEntry
    ACCESS not-accessible
    STATUS mandatory
    DESCRIPTION
        "List of temperature values corresponding to the channel numbers."
    ::= { wtWebioAn2GraphTemp 3 }

wtWebioAn2GraphTempValueEntry OBJECT-TYPE
    SYNTAX WtWebioAn2GraphTempValueEntry
    ACCESS not-accessible
    STATUS mandatory
    DESCRIPTION
        "Temperatures of the sensors."
    INDEX  { wtWebioAn2GraphSensorNo }
    ::= { wtWebioAn2GraphTempValueTable 1 }

WtWebioAn2GraphTempValueEntry ::= SEQUENCE{
    wtWebioAn2GraphTempValue OCTET STRING
}

wtWebioAn2GraphTempValue OBJECT-TYPE
    SYNTAX OCTET STRING (SIZE (5))
    ACCESS read-only
    STATUS mandatory
    DESCRIPTION
        "Temperature value of the sensor, ASCII, 5 characters in length."
    ::= { wtWebioAn2GraphTempValueEntry 1 }

-- wtWebioAn2GraphBinaryTempValue Table

wtWebioAn2GraphBinaryTempValueTable OBJECT-TYPE
    SYNTAX SEQUENCE OF WtWebioAn2GraphBinaryTempValueEntry
    ACCESS not-accessible
    STATUS mandatory
    DESCRIPTION
        "List of binary temperature values corresponding to the channel numbers."
    ::= { wtWebioAn2GraphTemp 4 }

wtWebioAn2GraphBinaryTempValueEntry OBJECT-TYPE
    SYNTAX WtWebioAn2GraphBinaryTempValueEntry
    ACCESS not-accessible
    STATUS mandatory
    DESCRIPTION
        "Binary temperature values of the sensors."
    INDEX  { wtWebioAn2GraphSensorNo }
    ::= { wtWebioAn2GraphBinaryTempValueTable 1 }

WtWebioAn2GraphBinaryTempValueEntry ::= SEQUENCE{
    wtWebioAn2GraphBinaryTempValue INTEGER
}    

wtWebioAn2GraphBinaryTempValue OBJECT-TYPE
    SYNTAX INTEGER
    ACCESS read-only
    STATUS mandatory
    DESCRIPTION
        "Binary temperature value of the sensor in 1/10 degrees Celsius,
        signed number, 0x4FFF6 indicates an 
        invalid measured value."
    ::= { wtWebioAn2GraphBinaryTempValueEntry 1 }

-- wtWebioAn2GraphTempValuePkt Table

wtWebioAn2GraphTempValuePktTable OBJECT-TYPE
    SYNTAX SEQUENCE OF WtWebioAn2GraphTempValuePktEntry
    ACCESS not-accessible
    STATUS mandatory
    DESCRIPTION
        "List of temperature values corresponding to the channel numbers."
    ::= { wtWebioAn2GraphTemp 8 }

wtWebioAn2GraphTempValuePktEntry OBJECT-TYPE
    SYNTAX WtWebioAn2GraphTempValuePktEntry
    ACCESS not-accessible
    STATUS mandatory
    DESCRIPTION
        "Temperatures of the sensors."
    INDEX  { wtWebioAn2GraphSensorNo }
    ::= { wtWebioAn2GraphTempValuePktTable 1 }

WtWebioAn2GraphTempValuePktEntry ::= SEQUENCE{
    wtWebioAn2GraphTempValuePkt OCTET STRING
}

wtWebioAn2GraphTempValuePkt OBJECT-TYPE
    SYNTAX OCTET STRING (SIZE (5))
    ACCESS read-only
    STATUS mandatory
    DESCRIPTION
        "Temperature value of the sensor, ASCII, 5 characters in length, decimal point."
    ::= { wtWebioAn2GraphTempValuePktEntry 1 }  

-- wtWebioAn2GraphSessCntrl Group
--------------------------------

wtWebioAn2GraphSessCntrlPassword OBJECT-TYPE
    SYNTAX OCTET STRING 
    ACCESS read-write
    STATUS mandatory
    DESCRIPTION
        "Entering this password opens a session which is ended by writing a 1 to 
        wtWebioAn2GraphSessCntrlLogout. When read this variable provides a string of
        length zero."
    ::= { wtWebioAn2GraphSessCntrl 1 }

wtWebioAn2GraphSessCntrlConfigMode OBJECT-TYPE
    SYNTAX INTEGER {
    wtWebioAn2GraphSessCntrl-NoSession(0),
    wtWebioAn2GraphSessCntrl-Session(1)
    }
    ACCESS read-only
    STATUS mandatory
    DESCRIPTION
        "When the device is in SNMP configuration mode, the value 1 is
        returned, otherwise 0. If the read value is 0 even though the
        password was written, the device is already in config mode and the
        variables can only be read."
    ::= { wtWebioAn2GraphSessCntrl 2 }

wtWebioAn2GraphSessCntrlLogout OBJECT-TYPE
    SYNTAX INTEGER 
    ACCESS read-write
    STATUS mandatory
    DESCRIPTION
        "If the device is in configuration mode and the session was opened by
        this SNMP Manager, writing a 1 to this variable will end the session 
        and all parameters are stored.
        Writing a 2 discards all entries again.
        When read this variable provides the value 0."
    ::= { wtWebioAn2GraphSessCntrl 3 }

wtWebioAn2GraphSessCntrlAdminPassword OBJECT-TYPE
    SYNTAX OCTET STRING 
    ACCESS read-write
    STATUS mandatory
    DESCRIPTION
        "This password protects access to the variables with administrator rights.
        It can only be changed by the administrator. If no password was assigned,
        the valid password is public."
    ::= { wtWebioAn2GraphSessCntrl 4 }

wtWebioAn2GraphSessCntrlConfigPassword OBJECT-TYPE
    SYNTAX OCTET STRING 
    ACCESS read-write
    STATUS mandatory
    DESCRIPTION
        "This password protects access to the variables with configurator rights. It can
        be changed by the administrator and by the configurator. If no password was assigned, 
        the valid password is public. When read this variable provides a null-pointer."
    ::= { wtWebioAn2GraphSessCntrl 5 }
    

-- wtWebioAn2GraphText Group
------------------------

wtWebioAn2GraphDeviceName OBJECT-TYPE
    SYNTAX OCTET STRING 
    ACCESS read-write
    STATUS mandatory
    DESCRIPTION
        "Name of the Webio, which is user definable."
    ::= { wtWebioAn2GraphText 1 }

wtWebioAn2GraphDeviceText OBJECT-TYPE
    SYNTAX OCTET STRING 
    ACCESS read-write
    STATUS mandatory
    DESCRIPTION
        "Description of the Webio, which is user definable."
    ::= { wtWebioAn2GraphText 2 }

wtWebioAn2GraphDeviceLocation OBJECT-TYPE
    SYNTAX OCTET STRING 
    ACCESS read-write
    STATUS mandatory
    DESCRIPTION
        "Description of the location of the Webio, which is user definable."
    ::= { wtWebioAn2GraphText 3 }

wtWebioAn2GraphDeviceContact OBJECT-TYPE
    SYNTAX OCTET STRING 
    ACCESS read-write
    STATUS mandatory
    DESCRIPTION
        "Contact address of the system operator of the Webio, which is user definable."
    ::= { wtWebioAn2GraphText 4 }

-- wtWebioAn2GraphTimeZone Group
----------------------------

wtWebioAn2GraphTzOffsetHrs OBJECT-TYPE
    SYNTAX INTEGER 
    ACCESS read-write
    STATUS mandatory
    DESCRIPTION
        "Offset hours for the time zone (winter time) with respect to UTC."
    ::= { wtWebioAn2GraphTimeZone 1 }

wtWebioAn2GraphTzOffsetMin OBJECT-TYPE
    SYNTAX INTEGER 
    ACCESS read-write
    STATUS mandatory
    DESCRIPTION
        "Offset minutes for the time zone (winter time) with respect to UTC."
    ::= { wtWebioAn2GraphTimeZone 2 }

wtWebioAn2GraphTzEnable OBJECT-TYPE
    SYNTAX OCTET STRING (SIZE(4))
    ACCESS read-write
    STATUS mandatory
    DESCRIPTION
        "Binary coded conditions:
        Octet 1: unused
        Octet 2: unused
        Octet 3: unused
        Octet 4:
        	Bit 1-7: unused
	        Bit 0  : Apply Timezone"
    ::= { wtWebioAn2GraphTimeZone 3 }    
    
wtWebioAn2GraphStTzOffsetHrs OBJECT-TYPE
    SYNTAX INTEGER 
    ACCESS read-write
    STATUS mandatory
    DESCRIPTION
        "Offset hours of the time zone (summer time) with respect to UTC."
    ::= { wtWebioAn2GraphTimeZone 4 }

wtWebioAn2GraphStTzOffsetMin OBJECT-TYPE
    SYNTAX INTEGER 
    ACCESS read-write
    STATUS mandatory
    DESCRIPTION
        "Offset minutes of the time zone (summer time) with respect to UTC."
    ::= { wtWebioAn2GraphTimeZone 5 }
    
wtWebioAn2GraphStTzEnable OBJECT-TYPE
    SYNTAX OCTET STRING (SIZE(4))
    ACCESS read-write
    STATUS mandatory
    DESCRIPTION
        "Binary coded conditions:
        Octet 1: unused
        Octet 2: unused
        Octet 3: unused
        Octet 4:
        	Bit 1-7: unused
	        Bit 0  : Apply Summertime"
    ::= { wtWebioAn2GraphTimeZone 6 }       
    
wtWebioAn2GraphStTzStartMonth OBJECT-TYPE
    SYNTAX INTEGER {
    	wtWebioAn2GraphStartMonth-January(1),
    	wtWebioAn2GraphStartMonth-February(2),
    	wtWebioAn2GraphStartMonth-March(3),
    	wtWebioAn2GraphStartMonth-April(4),
    	wtWebioAn2GraphStartMonth-May(5),
    	wtWebioAn2GraphStartMonth-June(6),
    	wtWebioAn2GraphStartMonth-July(7),
    	wtWebioAn2GraphStartMonth-August(8),
    	wtWebioAn2GraphStartMonth-September(9),
    	wtWebioAn2GraphStartMonth-October(10),
    	wtWebioAn2GraphStartMonth-November(11),
    	wtWebioAn2GraphStartMonth-December(12)
    	}
    	
    ACCESS read-write
    STATUS mandatory
    DESCRIPTION
        "Month in which the change is made from winter time to summer time."
    ::= { wtWebioAn2GraphTimeZone 7 }

wtWebioAn2GraphStTzStartMode OBJECT-TYPE
    SYNTAX INTEGER {
    	wtWebioAn2GraphStartMode-first(1),
    	wtWebioAn2GraphStartMode-second(2),
    	wtWebioAn2GraphStartMode-third(3),
    	wtWebioAn2GraphStartMode-fourth(4),
    	wtWebioAn2GraphStartMode-last(5)
    	}
    	
    ACCESS read-write
    STATUS mandatory
    DESCRIPTION
        "Mode of the day of the week for which the change is made from winter time to summer time."
    ::= { wtWebioAn2GraphTimeZone 8 }

wtWebioAn2GraphStTzStartWday OBJECT-TYPE
    SYNTAX INTEGER {
    	wtWebioAn2GraphStartWday-Sunday(1),
    	wtWebioAn2GraphStartWday-Monday(2),
    	wtWebioAn2GraphStartWday-Tuesday(3),
    	wtWebioAn2GraphStartWday-Thursday(4),
    	wtWebioAn2GraphStartWday-Wednesday(5),
    	wtWebioAn2GraphStartWday-Friday(6),
    	wtWebioAn2GraphStartWday-Saturday(7)
    	}
    	
    ACCESS read-write
    STATUS mandatory
    DESCRIPTION
        "Day of the week on which the change is made from winter time to summer time"
    ::= { wtWebioAn2GraphTimeZone 9 }
    
wtWebioAn2GraphStTzStartHrs OBJECT-TYPE
    SYNTAX INTEGER 
    ACCESS read-write
    STATUS mandatory
    DESCRIPTION
        "Hour in which the time zone is changed from winter to summer time with
        respect to UTC."
    ::= { wtWebioAn2GraphTimeZone 10 }

wtWebioAn2GraphStTzStartMin OBJECT-TYPE
    SYNTAX INTEGER 
    ACCESS read-write
    STATUS mandatory
    DESCRIPTION
        "Minute in which the time zone is changed from winter to summer time with
        respect to UTC."
    ::= { wtWebioAn2GraphTimeZone 11 }
 
wtWebioAn2GraphStTzStopMonth OBJECT-TYPE
    SYNTAX INTEGER {
    	wtWebioAn2GraphStopMonth-January(1),
    	wtWebioAn2GraphStopMonth-February(2),
    	wtWebioAn2GraphStopMonth-March(3),
    	wtWebioAn2GraphStopMonth-April(4),
    	wtWebioAn2GraphStopMonth-May(5),
    	wtWebioAn2GraphStopMonth-June(6),
    	wtWebioAn2GraphStopMonth-July(7),
    	wtWebioAn2GraphStopMonth-August(8),
    	wtWebioAn2GraphStopMonth-September(9),
    	wtWebioAn2GraphStopMonth-October(10),
    	wtWebioAn2GraphStopMonth-November(11),
    	wtWebioAn2GraphStopMonth-December(12)
    	}
    ACCESS read-write
    STATUS mandatory
    DESCRIPTION
        "Month in which the change is made from summer time to winter time."
   ::= { wtWebioAn2GraphTimeZone 12 }

wtWebioAn2GraphStTzStopMode OBJECT-TYPE
    SYNTAX INTEGER {
    	wtWebioAn2GraphStopMode-first(1),
    	wtWebioAn2GraphStopMode-second(2),
    	wtWebioAn2GraphStopMode-third(3),
    	wtWebioAn2GraphStopMode-fourth(4),
    	wtWebioAn2GraphStopMode-last(5)
    	}
    ACCESS read-write
    STATUS mandatory
    DESCRIPTION
        "Mode of the week day on which the change is made from summer time to winter time."
    ::= { wtWebioAn2GraphTimeZone 13 }

wtWebioAn2GraphStTzStopWday OBJECT-TYPE
    SYNTAX INTEGER {
    	wtWebioAn2GraphStopWday-Sunday(1),
    	wtWebioAn2GraphStopWday-Monday(2),
    	wtWebioAn2GraphStopWday-Tuesday(3),
    	wtWebioAn2GraphStopWday-Thursday(4),
    	wtWebioAn2GraphStopWday-Wednesday(5),
    	wtWebioAn2GraphStopWday-Friday(6),
    	wtWebioAn2GraphStopWday-Saturday(7)
    	}
    ACCESS read-write
    STATUS mandatory
    DESCRIPTION
        "Day of the week on which the change is made from summer time to winter time."
    ::= { wtWebioAn2GraphTimeZone 14 }
    
wtWebioAn2GraphStTzStopHrs OBJECT-TYPE
    SYNTAX INTEGER 
    ACCESS read-write
    STATUS mandatory
    DESCRIPTION
        "Hour at which the time zone is changed from summer to winter time with
        respect to UTC."
    ::= { wtWebioAn2GraphTimeZone 15 }

wtWebioAn2GraphStTzStopMin OBJECT-TYPE
    SYNTAX INTEGER 
    ACCESS read-write
    STATUS mandatory
    DESCRIPTION
        "Minute at which the time zone is changed from summer to winter time with
        respect to UTC."
    ::= { wtWebioAn2GraphTimeZone 16 }

-- wtWebioAn2GraphTimeServer Group
----------------------------

wtWebioAn2GraphTimeServer1 OBJECT-TYPE
    SYNTAX OCTET STRING 
    ACCESS read-write
    STATUS mandatory
    DESCRIPTION
        "IP address or name of the 1st time server in ASCII"
    ::= { wtWebioAn2GraphTimeServer 1 }

wtWebioAn2GraphTimeServer2 OBJECT-TYPE
    SYNTAX OCTET STRING 
    ACCESS read-write
    STATUS mandatory
    DESCRIPTION
        "IP address or name of the 2nd time server in ASCII"
    ::= { wtWebioAn2GraphTimeServer 2 }
    
wtWebioAn2GraphTsEnable OBJECT-TYPE
    SYNTAX OCTET STRING (SIZE(4))
    ACCESS read-write
    STATUS mandatory
    DESCRIPTION
        "Binary coded conditions:
        Octet 1: unused
        Octet 2: unused
        Octet 3: unused
        Octet 4:
        	Bit 1-7: unused
	        Bit 0  : Apply Time Server"
    ::= { wtWebioAn2GraphTimeServer 3 }
    
wtWebioAn2GraphTsSyncTime OBJECT-TYPE
    SYNTAX INTEGER 
    ACCESS read-write
    STATUS mandatory
    DESCRIPTION
        "Daily synchronisation time with the time server (hour: 0-23)."
    ::= { wtWebioAn2GraphTimeServer 4 } 
    
-- wtWebioAn2GraphDeviceClock Group
----------------------------

wtWebioAn2GraphClockHrs OBJECT-TYPE
    SYNTAX INTEGER (0..23)
    ACCESS read-write
    STATUS mandatory
    DESCRIPTION
        "Clock hours taking into account the time zone settings."
    ::= { wtWebioAn2GraphDeviceClock 1 }

wtWebioAn2GraphClockMin OBJECT-TYPE
    SYNTAX INTEGER (0..59)
    ACCESS read-write
    STATUS mandatory
    DESCRIPTION
        "Clock minutes taking into account the time zone settings."
    ::= { wtWebioAn2GraphDeviceClock 2 }

wtWebioAn2GraphClockDay OBJECT-TYPE
    SYNTAX INTEGER (1..31)
    ACCESS read-write
    STATUS mandatory
    DESCRIPTION
        "Date: Day of the month, taking into account the time zone settings."
    ::= { wtWebioAn2GraphDeviceClock 3 }

wtWebioAn2GraphClockMonth OBJECT-TYPE
   SYNTAX INTEGER {
    	wtWebioAn2GraphClockMonth-January(1),
    	wtWebioAn2GraphClockMonth-February(2),
    	wtWebioAn2GraphClockMonth-March(3),
    	wtWebioAn2GraphClockMonth-April(4),
    	wtWebioAn2GraphClockMonth-May(5),
    	wtWebioAn2GraphClockMonth-June(6),
    	wtWebioAn2GraphClockMonth-July(7),
    	wtWebioAn2GraphClockMonth-August(8),
    	wtWebioAn2GraphClockMonth-September(9),
    	wtWebioAn2GraphClockMonth-October(10),
    	wtWebioAn2GraphClockMonth-November(11),
    	wtWebioAn2GraphClockMonth-December(12)
    	}
    ACCESS read-write
    STATUS mandatory
    DESCRIPTION
        "Date: Month, taking into account the time zone settings."
    ::= { wtWebioAn2GraphDeviceClock 4 }

wtWebioAn2GraphClockYear OBJECT-TYPE
    SYNTAX INTEGER (0..65535)
    ACCESS read-write
    STATUS mandatory
    DESCRIPTION
        "Date: Year, taking into account the time zone settings."
    ::= { wtWebioAn2GraphDeviceClock 5 }
    

-- wtWebioAn2GraphNetwork Group
------------------------

wtWebioAn2GraphIpAddress OBJECT-TYPE
    SYNTAX IpAddress
    ACCESS read-write
    STATUS mandatory
    DESCRIPTION
        "IP address of the Webio"
    ::= { wtWebioAn2GraphNetwork 1 }

wtWebioAn2GraphSubnetMask OBJECT-TYPE
    SYNTAX IpAddress
    ACCESS read-write
    STATUS mandatory
    DESCRIPTION
        "Subnet mask of the Webio"
    ::= { wtWebioAn2GraphNetwork 2 }

wtWebioAn2GraphGateway OBJECT-TYPE
    SYNTAX IpAddress
    ACCESS read-write
    STATUS mandatory
    DESCRIPTION
        "Gateway of the Webio"
    ::= { wtWebioAn2GraphNetwork 3 }

wtWebioAn2GraphDnsServer1 OBJECT-TYPE
    SYNTAX OCTET STRING 
    ACCESS read-write
    STATUS mandatory
    DESCRIPTION
        "IP address of the 1st DNS server in ASCII"
    ::= { wtWebioAn2GraphNetwork 4 }

wtWebioAn2GraphDnsServer2 OBJECT-TYPE
    SYNTAX OCTET STRING 
    ACCESS read-write
    STATUS mandatory
    DESCRIPTION
        "IP address of the 2nd DNS server in ASCII"
    ::= { wtWebioAn2GraphNetwork 5 }

wtWebioAn2GraphAddConfig OBJECT-TYPE
    SYNTAX OCTET STRING 
    ACCESS read-write
    STATUS mandatory
    DESCRIPTION
        "Additional configuration (1=ON):
        Octet 1: unused
        Octet 2: unused
        Octet 3: unused
        Octet 4:
	        Bit 0: BOOTP disable
	        Bit 1: DHCP disable
	        "
    ::= { wtWebioAn2GraphNetwork 6 }

--  wtWebioAn2GraphHTTP Group
--------------------------------

wtWebioAn2GraphStartup OBJECT-TYPE
    SYNTAX OCTET STRING 
    ACCESS read-write
    STATUS mandatory
    DESCRIPTION
        "Binary coded start page:
        Octet 1: unused
        Octet 2: unused
        Octet 3: unused
        Octet 4:
	        Bit 1: Index.htm
	        Bit 2: Home.htm
	        Bit 3: User.htm
	Only one page may be selected at a time."
    ::= { wtWebioAn2GraphHTTP 1 }

wtWebioAn2GraphGetHeaderEnable OBJECT-TYPE
    SYNTAX OCTET STRING 
    ACCESS read-write
    STATUS mandatory
    DESCRIPTION
        "If these bits are set, every answer of a short form GET question will be lead
        by the IP-address and name of the device and/or a HTTP header:
        Octet 1: unused
        Octet 2: unused
        Octet 3: unused
        Octet 4:
        	Bit 1-6: unused
        	Bit 1  : GET HTTP enable
                Bit 0  : GET Header enable"
    ::= { wtWebioAn2GraphHTTP 2 }  
    
wtWebioAn2GraphHttpPort OBJECT-TYPE
    SYNTAX INTEGER (1..65535)
    ACCESS read-write
    STATUS mandatory
    DESCRIPTION
        "Definition of the standard HTML port (Default: 80)."
    ::= { wtWebioAn2GraphHTTP 3 }    


-- wtWebioAn2GraphMail Group
--------------------------------

wtWebioAn2GraphMailAdName OBJECT-TYPE
    SYNTAX OCTET STRING 
    ACCESS read-write
    STATUS mandatory
    DESCRIPTION
        "Device name for mail administration."
    ::= { wtWebioAn2GraphMail 1 }
    
wtWebioAn2GraphMailReply OBJECT-TYPE
    SYNTAX OCTET STRING 
    ACCESS read-write
    STATUS mandatory
    DESCRIPTION
        "Reply address for the mail server."
    ::= { wtWebioAn2GraphMail 2 }
    
wtWebioAn2GraphMailServer OBJECT-TYPE
    SYNTAX OCTET STRING 
    ACCESS read-write
    STATUS mandatory
    DESCRIPTION
        "Name or IP address of the mail server."
    ::= { wtWebioAn2GraphMail 3 }
    
wtWebioAn1MailEnable OBJECT-TYPE
    SYNTAX OCTET STRING 
    ACCESS read-write
    STATUS mandatory
    DESCRIPTION
        "Set this bit to enable the sending of mails:
        Octet 1: unused
        Octet 2: unused
        Octet 3: unused
        Octet 4:
        	Bit 1-7: unused
                Bit 0  : Mail enable"
    ::= { wtWebioAn2GraphMail 4 }
    
wtWebioAn2GraphMailAuthentication OBJECT-TYPE
    SYNTAX OCTET STRING (SIZE (4))
    ACCESS read-write
    STATUS mandatory
    DESCRIPTION
        "Selection of the authentication modi:
        The OCTETS are interpreted bit-by-bit, with each bit corresponding to an output. 
        Bit 0 corresponds to the LSB.
        OCTET 1: unused
        OCTET 2: unused
        OCTET 3: unused
        OCTET 4: Bit 3-7: unused
        	 Bit 2  : POP3 before SMTP
        	 Bit 1  : ESMTP, authentication
        	 Bit 0  : SMTP, no authentication"
    ::= { wtWebioAn2GraphMail 5 }
    
wtWebioAn2GraphMailAuthUser OBJECT-TYPE
    SYNTAX OCTET STRING 
    ACCESS read-write
    STATUS mandatory
    DESCRIPTION
        "Name of the user to be authenticated."
    ::= { wtWebioAn2GraphMail 6 }    
    
wtWebioAn2GraphMailAuthPassword OBJECT-TYPE
    SYNTAX OCTET STRING 
    ACCESS read-write
    STATUS mandatory
    DESCRIPTION
        "Authentication password."
    ::= { wtWebioAn2GraphMail 7 }    
    
wtWebioAn2GraphMailPop3Server OBJECT-TYPE
    SYNTAX OCTET STRING 
    ACCESS read-write
    STATUS mandatory
    DESCRIPTION
        "Name or Ip-address of the POP3 Servers."
    ::= { wtWebioAn2GraphMail 8 }        
    

-- wtWebioAn2GraphSNMP Group
--------------------------------

wtWebioAn2GraphSnmpCommunityStringRead OBJECT-TYPE
    SYNTAX OCTET STRING
    ACCESS read-write
    STATUS mandatory
    DESCRIPTION
        "Community string read only"
    ::= { wtWebioAn2GraphSNMP 1 }

wtWebioAn2GraphSnmpCommunityStringReadWrite OBJECT-TYPE
    SYNTAX OCTET STRING
    ACCESS read-write
    STATUS mandatory
    DESCRIPTION
        "Community string read / write"
    ::= { wtWebioAn2GraphSNMP 2 }

wtWebioAn2GraphSystemTrapManagerIP OBJECT-TYPE
    SYNTAX OCTET STRING 
    ACCESS read-write
    STATUS mandatory
    DESCRIPTION
        "Name or IP address of the TCP server which accepts the system trap."
    ::= { wtWebioAn2GraphSNMP 3 }
    
wtWebioAn2GraphSystemTrapEnable OBJECT-TYPE
    SYNTAX OCTET STRING (SIZE(4))
    ACCESS read-write
    STATUS mandatory
    DESCRIPTION
        "Binary coded trigger conditions:
        Octet 1: unused
        Octet 2: unused
        Octet 3: unused
        Octet 4:
	        Bit 0:   ColdStart
	        Bit 1:   WarmStart
	        Bit 2-7: unused"
    ::= { wtWebioAn2GraphSNMP 4 }
    
wtWebioAn2GraphSnmpEnable OBJECT-TYPE
    SYNTAX OCTET STRING 
    ACCESS read-write
    STATUS mandatory
    DESCRIPTION
        "Set bit 0 to enable SNMP.
        If disabled, the device did not respond to any SNMP requests.
        Bit 1 decided wether the community string of read operations 
        is compared with the system password or not:
        Octet 1: unused
        Octet 2: unused
        Octet 3: unused
        Octet 4:
        	Bit 1-7: unused
        	Bit 0  : SNMP enable"
    ::= { wtWebioAn2GraphSNMP 5 }
    
wtWebioAn2GraphSnmpCommunityStringTrap OBJECT-TYPE
    SYNTAX OCTET STRING
    ACCESS read-write
    STATUS mandatory
    DESCRIPTION
        "Community string send within traps."
    ::= { wtWebioAn2GraphSNMP 6 }    
    
wtWebioAn2GraphSnmpSystemTrapManagerPort OBJECT-TYPE
    SYNTAX INTEGER 
    ACCESS read-write
    STATUS mandatory
    DESCRIPTION
        "Port number of the TCP server which accepts the system trap."
    ::= { wtWebioAn2GraphSNMP 7 }         
    
-- wtWebioAn2GraphUDP Group
--------------------------------
    
wtWebioAn2GraphUdpPort OBJECT-TYPE
    SYNTAX INTEGER (1..65535)
    ACCESS read-write
    STATUS mandatory
    DESCRIPTION
        "Udp port to which the Udp queries ( short form GET requests) can be sent. This
        port number must be unique within the device."
    ::= { wtWebioAn2GraphUDP 1 }
    
wtWebioAn2GraphUdpEnable OBJECT-TYPE
    SYNTAX OCTET STRING 
    ACCESS read-write
    STATUS mandatory
    DESCRIPTION
        "Set this bit to enable UDP support:
        Octet 1: unused
        Octet 2: unused
        Octet 3: unused
        Octet 4:
        	Bit 1-7: unused
                Bit 0  : UDP enable"
    ::= { wtWebioAn2GraphUDP 2 }

    
--  wtWebioAn2GraphSyslog Group
--------------------------------
    
wtWebioAn2GraphSyslogServerIP OBJECT-TYPE
    SYNTAX OCTET STRING 
    ACCESS read-write
    STATUS mandatory
    DESCRIPTION
        "Name or IP address of the Syslog server, which accepts the Syslog messgaes."
    ::= { wtWebioAn2GraphSyslog 1 }
    
wtWebioAn2GraphSyslogServerPort OBJECT-TYPE
    SYNTAX INTEGER
    ACCESS read-write
    STATUS mandatory
    DESCRIPTION
        "Portnumber of the Syslog servers, default 514."
    ::= { wtWebioAn2GraphSyslog 2 }

wtWebioAn2GraphSyslogSystemMessagesEnable OBJECT-TYPE
    SYNTAX OCTET STRING (SIZE(4))
    ACCESS read-write
    STATUS mandatory
    DESCRIPTION
        "Binary coded trigger conditions:
        Octet 1: unused
        Octet 2: unused
        Octet 3: unused
        Octet 4:
	        Bit 0:   ColdStart
	        Bit 1:   WarmStart
	        Bit 2:   Diag Messages
	        Bit 3-7: unused"
    ::= { wtWebioAn2GraphSyslog 3 }    

wtWebioAn2GraphSyslogEnable OBJECT-TYPE
    SYNTAX OCTET STRING 
    ACCESS read-write
    STATUS mandatory
    DESCRIPTION
        "Set bit 0 to enable Syslog:
        Octet 1: unused
        Octet 2: unused
        Octet 3: unused
        Octet 4:
        	Bit 1-7: unused
                Bit 0  : Syslog enable"
    ::= { wtWebioAn2GraphSyslog 4 }
    
--  wtWebioAn2GraphFTP Group
--------------------------------

wtWebioAn2GraphFTPServerIP OBJECT-TYPE
    SYNTAX OCTET STRING 
    ACCESS read-write
    STATUS mandatory
    DESCRIPTION
        "Name or IP address of the FTP server, which accepts the FTP messages."
    ::= { wtWebioAn2GraphFTP 1 }
    
wtWebioAn2GraphFTPServerControlPort OBJECT-TYPE
    SYNTAX INTEGER
    ACCESS read-write
    STATUS mandatory
    DESCRIPTION
        "Portnumber of the control port of the FTP server, default 21."
    ::= { wtWebioAn2GraphFTP 2 }
    
wtWebioAn2GraphFTPUserName OBJECT-TYPE
    SYNTAX OCTET STRING 
    ACCESS read-write
    STATUS mandatory
    DESCRIPTION
        "FTP Loggin: user name."
    ::= { wtWebioAn2GraphFTP 3 }
    
wtWebioAn2GraphFTPPassword OBJECT-TYPE
    SYNTAX OCTET STRING 
    ACCESS read-write
    STATUS mandatory
    DESCRIPTION
        "FTP Loggin: user password."
    ::= { wtWebioAn2GraphFTP 4 }

wtWebioAn2GraphFTPAccount OBJECT-TYPE
    SYNTAX OCTET STRING 
    ACCESS read-write
    STATUS mandatory
    DESCRIPTION
        "FTP Loggin: name of account."
    ::= { wtWebioAn2GraphFTP 5 }

wtWebioAn2GraphFTPOption OBJECT-TYPE
    SYNTAX OCTET STRING 
    ACCESS read-write
    STATUS mandatory
    DESCRIPTION
        "Bit 0 switches the FTP Server in Passiv-Mode,
        the Client controls the data connection on its own:
        Octet 1: unused
        Octet 2: unused
        Octet 3: unused
        Octet 4:
        	Bit 1-7: unused
                Bit 0  : PASV enable"
    ::= { wtWebioAn2GraphFTP 6 }
    
wtWebioAn2GraphFTPEnable OBJECT-TYPE
    SYNTAX OCTET STRING 
    ACCESS read-write
    STATUS mandatory
    DESCRIPTION
        "Set Bit 0 to enable FTP:
        Octet 1: unused
        Octet 2: unused
        Octet 3: unused
        Octet 4:
        	Bit 1-7: unused
                Bit 0  : FTP enable"
    ::= { wtWebioAn2GraphFTP 7 }

--  wtWebioAn2GraphLanguage Group
--------------------------------

wtWebioAn2GraphLanguageSelect OBJECT-TYPE
    SYNTAX OCTET STRING 
    ACCESS read-write
    STATUS mandatory
    DESCRIPTION
        "Language selection:
        Octet 1: unused
        Octet 2: unused
        Octet 3: unused
        Octet 4:
        	Bit 2-7: unused
        	Bit 1  : English
                Bit 0  : German"
    ::= { wtWebioAn2GraphLanguage 1 }  
  	
--  wtWebioAn2GraphMQTT Group
--------------------------------

wtWebioAn2GraphMQTTEnable OBJECT-TYPE
    SYNTAX OCTET STRING 
    ACCESS read-write
    STATUS mandatory
    DESCRIPTION
        "Bit 7 schaltet MQTT frei:
        Octet 1: ungenutzt
        Octet 2: ungenutzt
        Octet 3: ungenutzt
        Octet 4:
        	Bit 0-6: ungenutzt
                Bit 7  : MQTT enable"
    ::= { wtWebioAn2GraphMQTT 1 }  

wtWebioAn2GraphMQTTBrockerIP OBJECT-TYPE
    SYNTAX OCTET STRING 
    ACCESS read-write
    STATUS mandatory
    DESCRIPTION
        "Name or IP-address of the MQTT-Server."
    ::= { wtWebioAn2GraphMQTT 2 }

wtWebioAn2GraphMQTTUserName OBJECT-TYPE
    SYNTAX OCTET STRING 
    ACCESS read-write
    STATUS mandatory
    DESCRIPTION
        "MQTT login  user name."
    ::= { wtWebioAn2GraphMQTT 3 }

wtWebioAn2GraphMQTTPassword OBJECT-TYPE
    SYNTAX OCTET STRING 
    ACCESS read-write
    STATUS mandatory
    DESCRIPTION
        "MQTT login password."
    ::= { wtWebioAn2GraphMQTT 4 }

wtWebioAn2GraphMQTTLocalPort OBJECT-TYPE
    SYNTAX INTEGER
    ACCESS read-write
    STATUS mandatory
    DESCRIPTION
        "Local port number."
    ::= { wtWebioAn2GraphMQTT 5 }
    
wtWebioAn2GraphMQTTBrokerServerPort OBJECT-TYPE
    SYNTAX INTEGER
    ACCESS read-write
    STATUS mandatory
    DESCRIPTION
        "MQTT Server port number."
    ::= { wtWebioAn2GraphMQTT 6 }
    
wtWebioAn2GraphMQTTInterval OBJECT-TYPE
    SYNTAX INTEGER
    ACCESS read-write
    STATUS mandatory
    DESCRIPTION
        "Ping intervall, if no data has to be send: time in seconds."
    ::= { wtWebioAn2GraphMQTT 7 }
	
wtWebioAn2GraphMQTTLastWillEnable OBJECT-TYPE
    SYNTAX OCTET STRING 
    ACCESS read-write
    STATUS mandatory
    DESCRIPTION
        "Bit 0 activate MQTT LastWill message:
        Octet 1: unused
        Octet 2: unused
        Octet 3: unused
        Octet 4:
        	Bit 1-7: unused
            Bit 0  : MQTT Last will enable"
    ::= { wtWebioAn2GraphMQTT 8 }  

wtWebioAn2GraphMQTTLastWillTopic OBJECT-TYPE
    SYNTAX OCTET STRING 
    ACCESS read-write
    STATUS mandatory
    DESCRIPTION
        "MQTT Last Will Topic."
    ::= { wtWebioAn2GraphMQTT 9 }
	
wtWebioAn2GraphMQTTLastWillMsg OBJECT-TYPE
    SYNTAX OCTET STRING 
    ACCESS read-write
    STATUS mandatory
    DESCRIPTION
        "MQTT Last Will message."
    ::= { wtWebioAn2GraphMQTT 10 }

wtWebioAn2GraphMQTTLastWillQoS OBJECT-TYPE
    SYNTAX OCTET STRING (SIZE(4))
    ACCESS read-write
    STATUS mandatory
    DESCRIPTION
        "Binary coded MQTT Publish QoS:
        Octet 1: unused
        Octet 2: unused
        Octet 3: unused
        Octet 4:
		Bit 0:	QoS 0
        Bit 1:	QoS 1
        Bit 2:  QoS 2
        Bit 3-7:unused"
    ::= { wtWebioAn2GraphMQTT 11 }
    
wtWebioAn2GraphMQTTLastWillRetain OBJECT-TYPE
    SYNTAX OCTET STRING (SIZE(4))
    ACCESS read-write
    STATUS mandatory
    DESCRIPTION
        "Binary coded MQTT Publish Retain properties:
        Octet 1: unused
        Octet 2: unused
        Octet 3: unused
        Octet 4:
		Bit 0	: retain enable
        Bit 1-7	: unused"
    ::= { wtWebioAn2GraphMQTT 12 }  
	
wtWebioAn2GraphMQTTLastWillConnectEnable OBJECT-TYPE
    SYNTAX OCTET STRING 
    ACCESS read-write
    STATUS mandatory
    DESCRIPTION
        "Bit 0 activate MQTT LastWill Connect message:
        Octet 1: unused
        Octet 2: unused
        Octet 3: unused
        Octet 4:
        	Bit 1-7: unused
            Bit 0  : MQTT Last will connect message enable"
    ::= { wtWebioAn2GraphMQTT 13 }

wtWebioAn2GraphMQTTLastWillConnectMsg OBJECT-TYPE
    SYNTAX OCTET STRING 
    ACCESS read-write
    STATUS mandatory
    DESCRIPTION
        "MQTT Last Will Connect message will be send with the QoS and Retain settings
		of the LastWill message."
    ::= { wtWebioAn2GraphMQTT 14 }
		
    	
--  wtWebioAn2GraphREST Group
--------------------------------

wtWebioAn2GraphRESTEnable OBJECT-TYPE
    SYNTAX OCTET STRING 
    ACCESS read-write
    STATUS mandatory
    DESCRIPTION
        "Bit 0 activates REST :
        Octet 1: unused
        Octet 2: unused
        Octet 3: unused
        Octet 4:
        	Bit 1-7: unused
            Bit 0  : REST enable"
    ::= { wtWebioAn2GraphREST 1 }  

wtWebioAn2GraphRESTDigestAuthEnable OBJECT-TYPE
    SYNTAX OCTET STRING 
    ACCESS read-write
    STATUS mandatory
    DESCRIPTION
        "Bit 0 activates Digest-Authentification:
        Octet 1: unused
        Octet 2: unused
        Octet 3: unused
        Octet 4:
        	Bit 1-7: unused
            Bit 0  : Digest Auth enable"
    ::= { wtWebioAn2GraphREST 2 }  	
            
-- wtWebioAn2GraphDatalogger Group
--------------------------------

wtWebioAn2GraphLoggerTimebase OBJECT-TYPE
    SYNTAX INTEGER {
    wtWebioAn2GraphDatalogger-1Min(1),
    wtWebioAn2GraphDatalogger-5Min(2),
    wtWebioAn2GraphDatalogger-15Min(3),
    wtWebioAn2GraphDatalogger-60Min(4)
    }
    ACCESS read-write
    STATUS mandatory
    DESCRIPTION
        "Time base of the data logger"
    ::= { wtWebioAn2GraphDatalogger 1 }

wtWebioAn2GraphLoggerSensorSel OBJECT-TYPE
    SYNTAX OCTET STRING (SIZE(4))
    ACCESS read-write
    STATUS mandatory
    DESCRIPTION
        "Binary coded trigger conditions:
        Octet 1: unused
        Octet 2: unused
        Octet 3: unused
        Octet 4:
        	Bit 0: Sensor 1
        	Bit 1: Sensor 2
        	Bit 2: Sensor 3
        	Bit 3: Sensor 4
        	Bit 4: Sensor 5
        	Bit 5: Sensor 6
        	Bit 6: Sensor 7
        	Bit 7: Sensor 8"
    ::= { wtWebioAn2GraphDatalogger 2 }

wtWebioAn2GraphDisplaySensorSel OBJECT-TYPE
    SYNTAX OCTET STRING (SIZE(4))
    ACCESS read-write
    STATUS mandatory
    DESCRIPTION
        "Binary coded sensor selection:
        only selected sensors will be shown in the graphical presentation:
        Octet 1: unused
        Octet 2: unused
        Octet 3: unused
        Octet 4:
        	Bit 0: Sensor 1
        	Bit 1: Sensor 2
        	Bit 2: Sensor 3
        	Bit 3: Sensor 4
        	Bit 4: Sensor 5
        	Bit 5: Sensor 6
        	Bit 6: Sensor 7
        	Bit 7: Sensor 8"
    ::= { wtWebioAn2GraphDatalogger 3 }    
    
-- Graph Sensor Color Table

wtWebioAn2GraphSensorColorTable OBJECT-TYPE
    SYNTAX SEQUENCE OF WtWebioAn2GraphSensorColorEntry
    ACCESS not-accessible
    STATUS mandatory
    DESCRIPTION
        "List of sensor colors for the praphical presentation."
    ::= { wtWebioAn2GraphDatalogger 4 }

wtWebioAn2GraphSensorColorEntry OBJECT-TYPE
    SYNTAX WtWebioAn2GraphSensorColorEntry
    ACCESS not-accessible
    STATUS mandatory
    DESCRIPTION
        "Index numbers of the sensors."
    INDEX  { wtWebioAn2GraphSensorNo }
    ::= { wtWebioAn2GraphSensorColorTable 1 }

WtWebioAn2GraphSensorColorEntry ::= SEQUENCE {
    wtWebioAn2GraphSensorColor OCTET STRING
}

wtWebioAn2GraphSensorColor OBJECT-TYPE
    SYNTAX OCTET STRING (SIZE(3))
    ACCESS read-write
    STATUS mandatory
    DESCRIPTION
        "Color of the sensors at the praphical presention."
    ::= { wtWebioAn2GraphSensorColorEntry 1 }
    
wtWebioAn2GraphAutoScaleEnable OBJECT-TYPE
    SYNTAX OCTET STRING 
    ACCESS read-write
    STATUS mandatory
    DESCRIPTION
        "If bit 0 is set, vertical auto scale is enabled:
        Octet 1: unused
        Octet 2: unused
        Octet 3: unused
        Octet 4:
        	Bit 1-7: unused
                Bit 0  : Auto Scale enable"
    ::= { wtWebioAn2GraphDatalogger 5 }
    
wtWebioAn2GraphVerticalUpperLimit OBJECT-TYPE
    SYNTAX OCTET STRING 
    ACCESS read-write
    STATUS mandatory
    DESCRIPTION
        "This value defines the maximum temperature shown in the graphical presentation,
        if no auto scaling is selected.
        Temperature in degrees with maximum 2 decimal places."
    ::= { wtWebioAn2GraphDatalogger 6 }

wtWebioAn2GraphVerticalLowerLimit OBJECT-TYPE
    SYNTAX OCTET STRING 
    ACCESS read-write
    STATUS mandatory
    DESCRIPTION
        "This value defines the minimum temperature shown in the graphical presentation,
        if no auto scaling is selected.
        Temperature in degrees with maximum 2 decimal places."
    ::= { wtWebioAn2GraphDatalogger 7 }
    
wtWebioAn2GraphHorizontalZoom OBJECT-TYPE
    SYNTAX INTEGER {
    wtWebioAn2GraphZoom-25min(1),
    wtWebioAn2GraphZoom-75min(2),
    wtWebioAn2GraphZoom-5hrs(3),
    wtWebioAn2GraphZoom-30hrs(4),
    wtWebioAn2GraphZoom-5days(5),
    wtWebioAn2GraphZoom-25days(6)
    }
    ACCESS read-write
    STATUS mandatory
    DESCRIPTION
        "Defines the default zoom stage, if no auto scaling is selected."
    ::= { wtWebioAn2GraphDatalogger 8 }    

-- wtWebioAn2GraphAlarm Group
----------------------------

wtWebioAn2GraphAlarmCount OBJECT-TYPE
    SYNTAX INTEGER (1..2)
    ACCESS read-only
    STATUS mandatory
    DESCRIPTION
        "Number of independent alarms."
    ::= { wtWebioAn2GraphAlarm 1 }
    
-- Alarm Interface Table

wtWebioAn2GraphAlarmIfTable OBJECT-TYPE
    SYNTAX SEQUENCE OF WtWebioAn2GraphAlarmIfEntry
    ACCESS not-accessible
    STATUS mandatory
    DESCRIPTION
        "List of alarm indices."
    ::= { wtWebioAn2GraphAlarm 2 }

wtWebioAn2GraphAlarmIfEntry OBJECT-TYPE
    SYNTAX WtWebioAn2GraphAlarmIfEntry
    ACCESS not-accessible
    STATUS mandatory
    DESCRIPTION
        "Numbers of the alarms."
    INDEX  { wtWebioAn2GraphAlarmNo }
    ::= { wtWebioAn2GraphAlarmIfTable 1 }

WtWebioAn2GraphAlarmIfEntry ::= SEQUENCE {
    wtWebioAn2GraphAlarmNo INTEGER
}

wtWebioAn2GraphAlarmNo OBJECT-TYPE
    SYNTAX INTEGER (1..2)
    ACCESS read-only
    STATUS mandatory
    DESCRIPTION
        "Alarm number."
    ::= { wtWebioAn2GraphAlarmIfEntry 1 }

-- Alarm Table

wtWebioAn2GraphAlarmTable OBJECT-TYPE
    SYNTAX SEQUENCE OF WtWebioAn2GraphAlarmEntry
    ACCESS not-accessible
    STATUS mandatory
    DESCRIPTION
        "List of settings depending on the alarm number."
    ::= { wtWebioAn2GraphAlarm 3 }

wtWebioAn2GraphAlarmEntry OBJECT-TYPE
    SYNTAX WtWebioAn2GraphAlarmEntry
    ACCESS not-accessible
    STATUS mandatory
    DESCRIPTION
        "Alarm parameters of the individual alarms."
    INDEX  { wtWebioAn2GraphAlarmNo }
    ::= { wtWebioAn2GraphAlarmTable 1 }

WtWebioAn2GraphAlarmEntry ::= SEQUENCE {
    wtWebioAn2GraphAlarmTrigger				OCTET STRING,
    wtWebioAn2GraphAlarmMin				OCTET STRING,
    wtWebioAn2GraphAlarmMax				OCTET STRING,
    wtWebioAn2GraphAlarmHysteresis			OCTET STRING,
    wtWebioAn2GraphAlarmDelay				OCTET STRING,
    wtWebioAn2GraphAlarmInterval			OCTET STRING,
    wtWebioAn2GraphAlarmEnable				OCTET STRING,
    wtWebioAn2GraphAlarmEMailAddr			OCTET STRING,
    wtWebioAn2GraphAlarmMailSubject			OCTET STRING,
    wtWebioAn2GraphAlarmMailText			OCTET STRING,
    wtWebioAn2GraphAlarmManagerIP			OCTET STRING,
    wtWebioAn2GraphAlarmTrapText			OCTET STRING,
    wtWebioAn2GraphAlarmMailOptions			OCTET STRING,
    wtWebioAn2GraphAlarmTcpIpAddr			OCTET STRING,
    wtWebioAn2GraphAlarmTcpPort				INTEGER,
    wtWebioAn2GraphAlarmTcpText				OCTET STRING,
    wtWebioAn2GraphAlarmClearMailSubject		OCTET STRING,
    wtWebioAn2GraphAlarmClearMailText			OCTET STRING,
    wtWebioAn2GraphAlarmClearTrapText			OCTET STRING,
    wtWebioAn2GraphAlarmClearTcpText			OCTET STRING,    
    wtWebioAn2GraphAlarmSyslogIpAddr			OCTET STRING,
    wtWebioAn2GraphAlarmSyslogPort			INTEGER,
    wtWebioAn2GraphAlarmSyslogText			OCTET STRING,
    wtWebioAn2GraphAlarmSyslogClearText			OCTET STRING,
    wtWebioAn2GraphAlarmFtpDataPort			OCTET STRING,
    wtWebioAn2GraphAlarmFtpFileName			OCTET STRING,
    wtWebioAn2GraphAlarmFtpText				OCTET STRING,
    wtWebioAn2GraphAlarmFtpClearText			OCTET STRING,
    wtWebioAn2GraphAlarmFtpOption			OCTET STRING,
    wtWebioAn2GraphAlarmTimerCron			OCTET STRING,
    wtWebioAn2GraphAlarmName 				OCTET STRING,
    wtWebioAn2GraphAlarmActive 				OCTET STRING,
    wtWebioAn2GraphAlarmHttpReqAuthEnable		OCTET STRING,
    wtWebioAn2GraphAlarmHttpReqAuthUser			OCTET STRING,
    wtWebioAn2GraphAlarmHttpReqAuthPassword		OCTET STRING,
    wtWebioAn2GraphAlarmHttpReqSetUrl			OCTET STRING,
    wtWebioAn2GraphAlarmHttpReqClearUrl			OCTET STRING,
    wtWebioAn2GraphAlarmHttpReqServerPort		INTEGER,
    wtWebioAn2GraphAlarmMqttTopicPath			OCTET STRING,
    wtWebioAn2GraphAlarmMqttTopicSetTopic		OCTET STRING,
    wtWebioAn2GraphAlarmMqttTopicClear			OCTET STRING,
    wtWebioAn2GraphAlarmSensorLostSelection		OCTET STRING,
    wtWebioAn2GraphAlarmLimitWindow			OCTET STRING,
    wtWebioAn2GraphAlarmSnmpManagerPort			INTEGER,
    wtWebioAn2GraphAlarmMqttQoS				OCTET STRING,
    wtWebioAn2GraphAlarmMqttRetain			OCTET STRING    
    
}

wtWebioAn2GraphAlarmTrigger OBJECT-TYPE
    SYNTAX OCTET STRING (SIZE(4))
    ACCESS read-write
    STATUS mandatory
    DESCRIPTION
        "Binary coded trigger conditions:
        Octet 1: unused
        Octet 2: unused
        Octet 3:
        	Bit 0: Timer
        	Bit 1: ColdStart
        	Bit 2: WarmStart
        	
        Octet 4:
        	Bit 0: Sensor 1
        	Bit 1: Sensor 2
        	Bit 2: Sensor 3
        	Bit 3: Sensor 4
        	Bit 4: Sensor 5
        	Bit 5: Sensor 6
        	Bit 6: Sensor 7
        	Bit 7: Sensor 8"
    ::= { wtWebioAn2GraphAlarmEntry 1 }

wtWebioAn2GraphAlarmMin OBJECT-TYPE
    SYNTAX OCTET STRING 
    ACCESS read-write
    STATUS mandatory
    DESCRIPTION
        "Minimum temperature in degrees with maximum 2 decimal places."
    ::= { wtWebioAn2GraphAlarmEntry 2 }

wtWebioAn2GraphAlarmMax OBJECT-TYPE
    SYNTAX OCTET STRING 
    ACCESS read-write
    STATUS mandatory
    DESCRIPTION
        "Maximum temperature in degrees with maximum 2 decimal places."
    ::= { wtWebioAn2GraphAlarmEntry 3 }
    
wtWebioAn2GraphAlarmHysteresis OBJECT-TYPE
    SYNTAX OCTET STRING 
    ACCESS read-write
    STATUS mandatory
    DESCRIPTION
        "Temperature changes of this size clears the alarm state (MAX-hyst, MIN+hyst.)
        , in degrees with maximum 2 decimal places."
    ::= { wtWebioAn2GraphAlarmEntry 4 }

wtWebioAn2GraphAlarmDelay OBJECT-TYPE
    SYNTAX OCTET STRING 
    ACCESS read-write
    STATUS mandatory
    DESCRIPTION
        "Alarm will be delayed by setting this time while stable alarm 
        condition occur (time in minutes)."
    ::= { wtWebioAn2GraphAlarmEntry 5 }
        

wtWebioAn2GraphAlarmInterval OBJECT-TYPE
    SYNTAX OCTET STRING 
    ACCESS read-write
    STATUS mandatory
    DESCRIPTION
        "Send interval for alarm messages."
    ::= { wtWebioAn2GraphAlarmEntry 6 }

wtWebioAn2GraphAlarmEnable OBJECT-TYPE
    SYNTAX OCTET STRING (SIZE(4))
    ACCESS read-write
    STATUS mandatory
    DESCRIPTION
        "Binary coded alarm enable:
        Octet 1: unused
        Octet 2: unused
        Octet 3: unused
        Octet 4:
		Bit 0:	Mail Enable
        	Bit 1:	SNMP Trap enable
        	Bit 2:  TCP Client enable"
    ::= { wtWebioAn2GraphAlarmEntry 7 }

wtWebioAn2GraphAlarmEMailAddr OBJECT-TYPE
    SYNTAX OCTET STRING 
    ACCESS read-write
    STATUS mandatory
    DESCRIPTION
        "E-Mail address for sending the alarm mail to."
    ::= { wtWebioAn2GraphAlarmEntry 8 }

wtWebioAn2GraphAlarmMailSubject OBJECT-TYPE
    SYNTAX OCTET STRING 
    ACCESS read-write
    STATUS mandatory
    DESCRIPTION
        "Subject line for alarm mail."
    ::= { wtWebioAn2GraphAlarmEntry 9 }

wtWebioAn2GraphAlarmMailText OBJECT-TYPE
    SYNTAX OCTET STRING 
    ACCESS read-write
    STATUS mandatory
    DESCRIPTION
        "Alarm mail text: <Tn> provides the current temperature; n = 1..2.
        <Z> provides the current time."
    ::= { wtWebioAn2GraphAlarmEntry 10 }

wtWebioAn2GraphAlarmManagerIP OBJECT-TYPE
    SYNTAX OCTET STRING 
    ACCESS read-write
    STATUS mandatory
    DESCRIPTION
        "Name or IP address of the SNMP Manager which accepts the trap."
    ::= { wtWebioAn2GraphAlarmEntry 11 }

wtWebioAn2GraphAlarmTrapText OBJECT-TYPE
    SYNTAX OCTET STRING 
    ACCESS read-write
    STATUS mandatory
    DESCRIPTION
        "This text is sent in the trap body."
    ::= { wtWebioAn2GraphAlarmEntry 12 }
    
wtWebioAn2GraphAlarmMailOptions OBJECT-TYPE
    SYNTAX OCTET STRING (SIZE(4))
    ACCESS read-write
    STATUS mandatory
    DESCRIPTION
        "Binary coded options:
        Octet 1: unused
        Octet 2: unused
        Octet 3: unused
        Octet 4:
		Bit 0  :	Attach Thermo.csv Enable
		Bit 1  :	CSV-Data_since_last_report
        	Bit 2-7:	unused"
    ::= { wtWebioAn2GraphAlarmEntry 13 }    
    
wtWebioAn2GraphAlarmTcpIpAddr OBJECT-TYPE
    SYNTAX OCTET STRING 
    ACCESS read-write
    STATUS mandatory
    DESCRIPTION
        "Name or IP address of the TCP server which accepts the trap."
    ::= { wtWebioAn2GraphAlarmEntry 14 }    

wtWebioAn2GraphAlarmTcpPort OBJECT-TYPE
    SYNTAX INTEGER (1..65535) 
    ACCESS read-write
    STATUS mandatory
    DESCRIPTION
        "Port number of the TCP server which accepts the trap."
    ::= { wtWebioAn2GraphAlarmEntry 15 }    

wtWebioAn2GraphAlarmTcpText OBJECT-TYPE
    SYNTAX OCTET STRING 
    ACCESS read-write
    STATUS mandatory
    DESCRIPTION
        "This text is sent in the TCP trap body."
    ::= { wtWebioAn2GraphAlarmEntry 16 }

wtWebioAn2GraphAlarmClearMailSubject OBJECT-TYPE
    SYNTAX OCTET STRING 
    ACCESS read-write
    STATUS mandatory
    DESCRIPTION
        "Subject line for alarm clear mail."
    ::= { wtWebioAn2GraphAlarmEntry 17 }

wtWebioAn2GraphAlarmClearMailText OBJECT-TYPE
    SYNTAX OCTET STRING 
    ACCESS read-write
    STATUS mandatory
    DESCRIPTION
        "Alarm clear mail text: <Tn> provides the current temperature; n = 1..2.
        <Z> provides the current time."
    ::= { wtWebioAn2GraphAlarmEntry 18 }

wtWebioAn2GraphAlarmClearTrapText OBJECT-TYPE
    SYNTAX OCTET STRING 
    ACCESS read-write
    STATUS mandatory
    DESCRIPTION
        "This text is sent in the trap body."
    ::= { wtWebioAn2GraphAlarmEntry 19 }

wtWebioAn2GraphAlarmClearTcpText OBJECT-TYPE
    SYNTAX OCTET STRING 
    ACCESS read-write
    STATUS mandatory
    DESCRIPTION
        "This text is sent in the TCP trap body."
    ::= { wtWebioAn2GraphAlarmEntry 20 }
    
wtWebioAn2GraphAlarmSyslogIpAddr OBJECT-TYPE
    SYNTAX OCTET STRING 
    ACCESS read-write
    STATUS mandatory
    DESCRIPTION
        "IP address of the syslog server to which the Webio device should send syslog messages."
    ::= { wtWebioAn2GraphAlarmEntry 21 }    

wtWebioAn2GraphAlarmSyslogPort OBJECT-TYPE
    SYNTAX INTEGER (1..65535) 
    ACCESS read-write
    STATUS mandatory
    DESCRIPTION
        "Port number of the syslog server to which the Webio device should send syslog messages."
    ::= { wtWebioAn2GraphAlarmEntry 22 }    

wtWebioAn2GraphAlarmSyslogText OBJECT-TYPE
    SYNTAX OCTET STRING 
    ACCESS read-write
    STATUS mandatory
    DESCRIPTION
        "Every message starts with the priority key, a time stamp and the host ip address, according RFC3164.
        This text appears in the following syslog message body."
    ::= { wtWebioAn2GraphAlarmEntry 23 }    
    
wtWebioAn2GraphAlarmSyslogClearText OBJECT-TYPE
    SYNTAX OCTET STRING 
    ACCESS read-write
    STATUS mandatory
    DESCRIPTION
        "Every message starts with the priority key, a time stamp and the host ip address, according RFC3164.
        This text appears in the following syslog message body."
    ::= { wtWebioAn2GraphAlarmEntry 24 } 
    
wtWebioAn2GraphAlarmFtpDataPort OBJECT-TYPE
    SYNTAX OCTET STRING 
    ACCESS read-write
    STATUS mandatory
    DESCRIPTION
        "Local data port: 1..65535 or AUTO: the next free port will be assigned."
    ::= { wtWebioAn2GraphAlarmEntry 25 }
    
wtWebioAn2GraphAlarmFtpFileName OBJECT-TYPE
    SYNTAX OCTET STRING 
    ACCESS read-write
    STATUS mandatory
    DESCRIPTION
        "Name of the file including path informations."
    ::= { wtWebioAn2GraphAlarmEntry 26 }
    
wtWebioAn2GraphAlarmFtpText OBJECT-TYPE
    SYNTAX OCTET STRING 
    ACCESS read-write
    STATUS mandatory
    DESCRIPTION
        "Message text to store on the FTP server."
    ::= { wtWebioAn2GraphAlarmEntry 27 }

wtWebioAn2GraphAlarmFtpClearText OBJECT-TYPE
    SYNTAX OCTET STRING 
    ACCESS read-write
    STATUS mandatory
    DESCRIPTION
        "Alarm clear message to store on the FTP server."
    ::= { wtWebioAn2GraphAlarmEntry 28 }
    
wtWebioAn2GraphAlarmFtpOption OBJECT-TYPE
    SYNTAX OCTET STRING (SIZE(4))
    ACCESS read-write
    STATUS mandatory
    DESCRIPTION
        "Binary coded options, select only one option at the same time:
        STORE  = replace file
        APPEND = append message at the end of the file
        
        Octet 1: unused
        Octet 2: unused
        Octet 3: unused
        Octet 4:
		Bit 0  :	STORE
		Bit 1  :	APPEND
        	Bit 2-7:	unused"
    ::= { wtWebioAn2GraphAlarmEntry 29 }      
    
wtWebioAn2GraphAlarmTimerCron OBJECT-TYPE
    SYNTAX OCTET STRING
    ACCESS read-write
    STATUS mandatory
    DESCRIPTION
        "This entry contains 5 text fields space or tab seperated for time trigger definition.
        Each field must match with the actual time to trigger a message, weekday and day of month
        are interpreted separatley.
        1: Minutes	Range 0-59
        2. Hours	Range 0-23, 0 is midnight
        3: Day of month	Range 1-31
        4: Month	Range 1-12
        5: Weekday	Range 0-6, 0 is sunday
        
        Syntax for every field:
         - an asterix (*) enables every possible setting of a field
         - single numbers seperated by commas
         - a partition within the allowed range (1-5)
         - step size within an partition of the allowed range (0-59/2: every second minute)."
    ::= { wtWebioAn2GraphAlarmEntry 30 } 

-- __JB__
wtWebioAn2GraphAlarmName OBJECT-TYPE
    SYNTAX OCTET STRING
    ACCESS read-write
    STATUS mandatory
    DESCRIPTION
        "Alert name"
    ::= { wtWebioAn2GraphAlarmEntry 39 } 
	
-- __JB__
wtWebioAn2GraphAlarmActive OBJECT-TYPE
    SYNTAX OCTET STRING
    ACCESS read-write
    STATUS mandatory
    DESCRIPTION
        "Alert active
			1 = ON
			0 = OFF"
    ::= { wtWebioAn2GraphAlarmEntry 40 }
    
wtWebioAn2GraphAlarmHttpReqAuthEnable OBJECT-TYPE
    SYNTAX OCTET STRING 
    ACCESS read-write
    STATUS mandatory
    DESCRIPTION
        "Binary coded options, select only one option at the same time:
        OCTET 1: unused
        OCTET 2: unused
        OCTET 3: unused
        OCTET 4, Bit 1-7: unused
        Bit 0  : HHTP Request Authentication enable"
    ::= { wtWebioAn2GraphAlarmEntry 61 }

wtWebioAn2GraphAlarmHttpReqAuthUser OBJECT-TYPE
    SYNTAX OCTET STRING 
    ACCESS read-write
    STATUS mandatory
    DESCRIPTION
	"HTTP Request: User"
    ::= { wtWebioAn2GraphAlarmEntry 62 }

wtWebioAn2GraphAlarmHttpReqAuthPassword OBJECT-TYPE
    SYNTAX OCTET STRING 
    ACCESS read-write
    STATUS mandatory
    DESCRIPTION
	"HTTP Request: Password"
    ::= { wtWebioAn2GraphAlarmEntry 63 }

wtWebioAn2GraphAlarmHttpReqSetUrl OBJECT-TYPE
    SYNTAX OCTET STRING 
    ACCESS read-write
    STATUS mandatory
    DESCRIPTION
	"HTTP Request: Set URL"
    ::= { wtWebioAn2GraphAlarmEntry 64 }

wtWebioAn2GraphAlarmHttpReqClearUrl OBJECT-TYPE
    SYNTAX OCTET STRING 
    ACCESS read-write
    STATUS mandatory
    DESCRIPTION
	"HTTP Request: Clear URL"
    ::= { wtWebioAn2GraphAlarmEntry 65 }

wtWebioAn2GraphAlarmHttpReqServerPort OBJECT-TYPE
    SYNTAX INTEGER (1..65535) 
    ACCESS read-write
    STATUS mandatory
    DESCRIPTION
	"HTTP Request: Server Port"
    ::= { wtWebioAn2GraphAlarmEntry 66 }

wtWebioAn2GraphAlarmMqttTopicPath OBJECT-TYPE
    SYNTAX OCTET STRING 
    ACCESS read-write
    STATUS mandatory
    DESCRIPTION
	"MQTT Publish: Topic path"
    ::= { wtWebioAn2GraphAlarmEntry 67 }

wtWebioAn2GraphAlarmMqttTopicSetTopic OBJECT-TYPE
    SYNTAX OCTET STRING 
    ACCESS read-write
    STATUS mandatory
    DESCRIPTION
	"MQTT Publish: Topic SET message"
    ::= { wtWebioAn2GraphAlarmEntry 68 }

wtWebioAn2GraphAlarmMqttTopicClear OBJECT-TYPE
    SYNTAX OCTET STRING 
    ACCESS read-write
    STATUS mandatory
    DESCRIPTION
	"MQTT Publish: Topic CLEAR message"
    ::= { wtWebioAn2GraphAlarmEntry 69 }    
    
wtWebioAn2GraphAlarmSensorLostSelection OBJECT-TYPE
    SYNTAX OCTET STRING 
    ACCESS read-write
    STATUS mandatory
    DESCRIPTION
        "Binary coded options:
        OCTET 1: unused
        OCTET 2: unused
        OCTET 3: unused
        OCTET 4: 
		Bit 2-7: unused
		Bit 1  : Sensor 1
       		 Bit 0  : Sensor 0 "
    ::= { wtWebioAn2GraphAlarmEntry 70 }
	
wtWebioAn2GraphAlarmLimitWindow OBJECT-TYPE
    SYNTAX OCTET STRING
    ACCESS read-write
    STATUS mandatory
    DESCRIPTION
        "If window type is INSIDE the alarm is genereted when the temperature
        is greater minumum value and lower than maximum value. If window type is OUTSIDE
        the alarm is generated when the measured value is lower than the minimum value
        or greater than the maximum value.
		Binary coded options, select only one option at the same time:
        OCTET 1: unused
        OCTET 2: unused
        OCTET 3: unused
        OCTET 4, Bit 2-7: unused
		Bit 1  : inside window
        Bit 0  : outside window"
    ::= { wtWebioAn2GraphAlarmEntry 71 }
    
wtWebioAn2GraphAlarmSnmpManagerPort OBJECT-TYPE
    SYNTAX INTEGER 
    ACCESS read-write
    STATUS mandatory
    DESCRIPTION
        "Port number of the SNMP Manager to which the Webio device should send SNMP traps."
    ::= { wtWebioAn2GraphAlarmEntry 76 }     
    
wtWebioAn2GraphAlarmMqttQoS OBJECT-TYPE
    SYNTAX OCTET STRING (SIZE(4))
    ACCESS read-write
    STATUS mandatory
    DESCRIPTION
        "Binary coded value:
        Octet 1: unused
        Octet 2: unused
        Octet 3: unused
        Octet 4:
		Bit 0:	QoS 0
        	Bit 1:	QoS 1
        	Bit 2:  QoS 2
        	Bit 3-7:unused"
    ::= { wtWebioAn2GraphAlarmEntry 77 }
    
wtWebioAn2GraphAlarmMqttRetain OBJECT-TYPE
    SYNTAX OCTET STRING (SIZE(4))
    ACCESS read-write
    STATUS mandatory
    DESCRIPTION
        "Binary coded value:
        Octet 1: unused
        Octet 2: unused
        Octet 3: unused
        Octet 4:
		Bit 0	: retain enable
        	Bit 1-7	: unused"
    ::= { wtWebioAn2GraphAlarmEntry 78 }    
	    
-- wtWebioAn2GraphGraphicsBase Group
----------------------------

wtWebioAn2GraphGraphicsBaseEnable OBJECT-TYPE
    SYNTAX OCTET STRING 
    ACCESS read-write
    STATUS mandatory
    DESCRIPTION
        "Defines the viewing options of the graphic:
        Octet 1: unused
        Octet 2: unused
        Octet 3: unused
        Octet 4:
                Bit 0  : Auto scroll enable
                Bit 1  : Show table
                Bit 2  : Show graph
                Bit 3  : Show control buttons
                Bit 4  : Show config menu
                Bit 5-7: unused"
    ::= { wtWebioAn2GraphGraphicsBase 1 }

wtWebioAn2GraphGraphicsBaseWidth OBJECT-TYPE
    SYNTAX INTEGER 
    ACCESS read-write
    STATUS mandatory
    DESCRIPTION
        "Defines the width of the graphic in pixels."
    ::= { wtWebioAn2GraphGraphicsBase 2 }
    
wtWebioAn2GraphGraphicsBaseHeight OBJECT-TYPE
        SYNTAX INTEGER 
        ACCESS read-write
        STATUS mandatory
        DESCRIPTION
            "Defines the height of the graphic in pixels."
        ::= { wtWebioAn2GraphGraphicsBase 3 }

wtWebioAn2GraphGraphicsBaseFrameColor OBJECT-TYPE
    SYNTAX OCTET STRING (SIZE(3))
    ACCESS read-write
    STATUS mandatory
    DESCRIPTION
        "Frame color definition in RGB."
    ::= { wtWebioAn2GraphGraphicsBase 4 }

wtWebioAn2GraphGraphicsBaseBackgroundColor OBJECT-TYPE
    SYNTAX OCTET STRING (SIZE(3))
    ACCESS read-write
    STATUS mandatory
    DESCRIPTION
        "Background color definition in RGB."
    ::= { wtWebioAn2GraphGraphicsBase 5 }
    
wtWebioAn2GraphGraphicsBasePollingrate OBJECT-TYPE
        SYNTAX INTEGER 
        ACCESS read-write
        STATUS mandatory
        DESCRIPTION
            "Defines the pollingrate in seconds, 
            which defines the refreshing intervall of the graphic."
        ::= { wtWebioAn2GraphGraphicsBase 6 }
   
-- wtWebioAn2GraphGraphicsSelect Group
----------------------------

wtWebioAn2GraphGraphicsSelectDisplaySensorSel OBJECT-TYPE
    SYNTAX OCTET STRING (SIZE(4))
    ACCESS read-write
    STATUS mandatory
    DESCRIPTION
        "Binary coded sensor selection:
        only selected sensors will be shown in the graphical presentation:
        Octet 1: unused
        Octet 2: unused
        Octet 3: unused
        Octet 4:
        	Bit 0: Sensor 1
        	Bit 1: Sensor 2
        	Bit 2: Sensor 3
        	Bit 3: Sensor 4
        	Bit 4: Sensor 5
        	Bit 5: Sensor 6
        	Bit 6: Sensor 7
        	Bit 7: Sensor 8"
    ::= { wtWebioAn2GraphGraphicsSelect 1 }   
    
wtWebioAn2GraphGraphicsSelectDisplayShowExtrem OBJECT-TYPE
    SYNTAX OCTET STRING (SIZE(4))
    ACCESS read-write
    STATUS mandatory
    DESCRIPTION
        "Binary coded sensor selection:
        only selected sensors will be shown with minima and maxima:
        Octet 1: unused
        Octet 2: unused
        Octet 3: unused
        Octet 4:
        	Bit 0: Sensor 1
        	Bit 1: Sensor 2
        	Bit 2: Sensor 3
        	Bit 3: Sensor 4
        	Bit 4: Sensor 5
        	Bit 5: Sensor 6
        	Bit 6: Sensor 7
        	Bit 7: Sensor 8"
     ::= { wtWebioAn2GraphGraphicsSelect 2 }   

-- Graph Sensor Color Table

wtWebioAn2GraphSelectSensorColorTable OBJECT-TYPE
    SYNTAX SEQUENCE OF WtWebioAn2GraphSelectSensorColorEntry
    ACCESS not-accessible
    STATUS mandatory
    DESCRIPTION
        "List of sensor colors for the praphical presentation."
    ::= { wtWebioAn2GraphGraphicsSelect 3 }

wtWebioAn2GraphSelectSensorColorEntry OBJECT-TYPE
    SYNTAX WtWebioAn2GraphSelectSensorColorEntry
    ACCESS not-accessible
    STATUS mandatory
    DESCRIPTION
        "Numbers of the sensors."
    INDEX  { wtWebioAn2GraphSensorNo }
    ::= { wtWebioAn2GraphSelectSensorColorTable 1 }

WtWebioAn2GraphSelectSensorColorEntry ::= SEQUENCE {
    wtWebioAn2GraphSelectGraphicsSensorColor OCTET STRING,
    wtWebioAn2GraphSelectGraphicsSelectScale OCTET STRING
}

wtWebioAn2GraphSelectGraphicsSensorColor OBJECT-TYPE
    SYNTAX OCTET STRING (SIZE(3))
    ACCESS read-write
    STATUS mandatory
    DESCRIPTION
        "Color of the sensors at the praphical presention."
    ::= { wtWebioAn2GraphSelectSensorColorEntry 1 }
    
wtWebioAn2GraphSelectGraphicsSelectScale OBJECT-TYPE
    SYNTAX OCTET STRING 
    ACCESS read-write
    STATUS mandatory
    DESCRIPTION
        "Assignes one of 4 scales to a sensor:
        Octet 1: unused
        Octet 2: unused
        Octet 3: unused
        Octet 4:
                Bit 0  : Use Scale 1
                Bit 1  : Use Scale 2
                Bit 2  : Use Scale 3
                Bit 3  : Use Scale 4
                Bit 4-7: unused"
    ::= { wtWebioAn2GraphSelectSensorColorEntry 2 }
   
-- wtWebioAn2GraphGraphicsScale Group
----------------------------

wtWebioAn2GraphGraphicsScaleAutoScaleEnable OBJECT-TYPE
    SYNTAX OCTET STRING 
    ACCESS read-write
    STATUS mandatory
    DESCRIPTION
        "Select the Auto Scale Mode:
        Octet 1: unused
        Octet 2: unused
        Octet 3: unused
        Octet 4:
                Bit 0  : Scale 1 Auto scale enable
                Bit 1  : Scale 2 Auto scale enable
                Bit 2  : Scale 3 Auto scale enable
                Bit 3  : Scale 4 Auto scale enable
                Bit 4-7: unused"
    ::= { wtWebioAn2GraphGraphicsScale 1 }


wtWebioAn2GraphGraphicsScaleAutoFitEnable OBJECT-TYPE
    SYNTAX OCTET STRING 
    ACCESS read-write
    STATUS mandatory
    DESCRIPTION
        "Select the Auto Fit Mode::
        Octet 1: unused
        Octet 2: unused
        Octet 3: unused
        Octet 4:
                Bit 0  : Scale 1 Auto fit enable
                Bit 1  : Scale 2 Auto fit enable
                Bit 2  : Scale 3 Auto fit enable
                Bit 3  : Scale 4 Auto fit enable
                Bit 4-7: unused"
    ::= { wtWebioAn2GraphGraphicsScale 2 }

wtWebioAn2GraphGraphicsScale1Min OBJECT-TYPE
    SYNTAX INTEGER
    ACCESS read-only
    STATUS mandatory
    DESCRIPTION
        "Scale 1: Minimum."
    ::= { wtWebioAn2GraphGraphicsScale 3 }
   
wtWebioAn2GraphGraphicsScale2Min OBJECT-TYPE
    SYNTAX INTEGER
    ACCESS read-only
    STATUS mandatory
    DESCRIPTION
        "Scale 2: Minimum."
    ::= { wtWebioAn2GraphGraphicsScale 4 }

wtWebioAn2GraphGraphicsScale3Min OBJECT-TYPE
    SYNTAX INTEGER
    ACCESS read-only
    STATUS mandatory
    DESCRIPTION
        "Scale 3: Minimum."
    ::= { wtWebioAn2GraphGraphicsScale 5 }

wtWebioAn2GraphGraphicsScale4Min OBJECT-TYPE
    SYNTAX INTEGER
    ACCESS read-only
    STATUS mandatory
    DESCRIPTION
        "Scale 4: Minimum."
    ::= { wtWebioAn2GraphGraphicsScale 6 }

wtWebioAn2GraphGraphicsScale1Max OBJECT-TYPE
    SYNTAX INTEGER
    ACCESS read-only
    STATUS mandatory
    DESCRIPTION
        "Scale 1: Maximum."
    ::= { wtWebioAn2GraphGraphicsScale 7 }

wtWebioAn2GraphGraphicsScale2Max OBJECT-TYPE
    SYNTAX INTEGER
    ACCESS read-only
    STATUS mandatory
    DESCRIPTION
        "Scale 2: Maximum."
    ::= { wtWebioAn2GraphGraphicsScale 8 }

wtWebioAn2GraphGraphicsScale3Max OBJECT-TYPE
    SYNTAX INTEGER
    ACCESS read-only
    STATUS mandatory
    DESCRIPTION
        "Scale 3: Maximum."
    ::= { wtWebioAn2GraphGraphicsScale 9 }

wtWebioAn2GraphGraphicsScale4Max OBJECT-TYPE
    SYNTAX INTEGER
    ACCESS read-only
    STATUS mandatory
    DESCRIPTION
        "Scale 4: Maximum."
    ::= { wtWebioAn2GraphGraphicsScale 10 }

wtWebioAn2GraphGraphicsScale1Unit OBJECT-TYPE
    SYNTAX OCTET STRING
    ACCESS read-only
    STATUS mandatory
    DESCRIPTION
        "Scale 1: Unit."
    ::= { wtWebioAn2GraphGraphicsScale 11 }

wtWebioAn2GraphGraphicsScale2Unit OBJECT-TYPE
    SYNTAX OCTET STRING
    ACCESS read-only
    STATUS mandatory
    DESCRIPTION
        "Scale 2: Unit."
    ::= { wtWebioAn2GraphGraphicsScale 12 }

wtWebioAn2GraphGraphicsScale3Unit OBJECT-TYPE
    SYNTAX OCTET STRING
    ACCESS read-only
    STATUS mandatory
    DESCRIPTION
        "Scale 3: Unit."
    ::= { wtWebioAn2GraphGraphicsScale 13 }

wtWebioAn2GraphGraphicsScale4Unit OBJECT-TYPE
    SYNTAX OCTET STRING
    ACCESS read-only
    STATUS mandatory
    DESCRIPTION
        "Scale 4: Unit."
    ::= { wtWebioAn2GraphGraphicsScale 14 }    

-- wtWebioAn2GraphPorts Group
----------------------------

-- Table

wtWebioAn2GraphPortTable OBJECT-TYPE
    SYNTAX SEQUENCE OF WtWebioAn2GraphPortEntry
    ACCESS not-accessible
    STATUS mandatory
    DESCRIPTION
        "List of settings depending on the sensor number."
    ::= { wtWebioAn2GraphPorts 1 }

wtWebioAn2GraphPortEntry OBJECT-TYPE
    SYNTAX WtWebioAn2GraphPortEntry
    ACCESS not-accessible
    STATUS mandatory
    DESCRIPTION
        "Sensor parameters for the individual sensors."
    INDEX  { wtWebioAn2GraphSensorNo }
    ::= { wtWebioAn2GraphPortTable 1 }

WtWebioAn2GraphPortEntry ::= SEQUENCE {
    wtWebioAn2GraphPortName		OCTET STRING,
    wtWebioAn2GraphPortText		OCTET STRING,
    wtWebioAn2GraphPortOffset1		OCTET STRING,
    wtWebioAn2GraphPortTemperature1	OCTET STRING,
    wtWebioAn2GraphPortOffset2		OCTET STRING,
    wtWebioAn2GraphPortTemperature2	OCTET STRING,
    wtWebioAn2GraphPortComment		OCTET STRING,
    wtWebioAn2GraphPortSensorSelect	OCTET STRING

    
}

wtWebioAn2GraphPortName OBJECT-TYPE
    SYNTAX OCTET STRING 
    ACCESS read-write
    STATUS mandatory
    DESCRIPTION
        "Name of the sensor."
    ::= { wtWebioAn2GraphPortEntry 1 }

wtWebioAn2GraphPortText OBJECT-TYPE
    SYNTAX OCTET STRING 
    ACCESS read-write
    STATUS mandatory
    DESCRIPTION
        "Description of the sensor."
    ::= { wtWebioAn2GraphPortEntry 2 }

wtWebioAn2GraphPortOffset1 OBJECT-TYPE
    SYNTAX OCTET STRING 
    ACCESS read-write
    STATUS mandatory
    DESCRIPTION
        "Offset calibration: Offset in degrees with maximum 2 decimal places at temperature 1."
    ::= { wtWebioAn2GraphPortEntry 3 }

wtWebioAn2GraphPortTemperature1 OBJECT-TYPE
    SYNTAX OCTET STRING 
    ACCESS read-write
    STATUS mandatory
    DESCRIPTION
        "Offset calibration: Reference temperature 1 in degrees with maximum 2 decimal places."
    ::= { wtWebioAn2GraphPortEntry 4 }

wtWebioAn2GraphPortOffset2 OBJECT-TYPE
    SYNTAX OCTET STRING 
    ACCESS read-write
    STATUS mandatory
    DESCRIPTION
        "Offset calibration: Offset in degrees with maximum 2 decimal places at temperature 2."
    ::= { wtWebioAn2GraphPortEntry 5 }

wtWebioAn2GraphPortTemperature2 OBJECT-TYPE
    SYNTAX OCTET STRING 
    ACCESS read-write
    STATUS mandatory
    DESCRIPTION
        "Offset calibration: Reference temperature 1 in degrees with maximum 2 decimal places."
    ::= { wtWebioAn2GraphPortEntry 6 }

wtWebioAn2GraphPortComment OBJECT-TYPE
    SYNTAX OCTET STRING 
    ACCESS read-write
    STATUS mandatory
    DESCRIPTION
        "Offset calibration: informations of date, name of operator, reference devices."
    ::= { wtWebioAn2GraphPortEntry 7 }

wtWebioAn2GraphPortSensorSelect OBJECT-TYPE
    SYNTAX OCTET STRING (SIZE(4))
    ACCESS read-write
    STATUS mandatory
    DESCRIPTION
        "Binär kodierte Optionen für Sensor:
        Octet 1: ungenutzt
        Octet 2: ungenutzt
        Octet 3: ungenutzt
        Octet 4:
		Bit 0  :	PT100
		Bit 1  :	PT1000 (default)
        	Bit 2-7:	ungenutzt"
    ::= { wtWebioAn2GraphPortEntry 8 }        
    
-- wtWebioAn2GraphManufact Group
----------------------------

wtWebioAn2GraphMfName OBJECT-TYPE
    SYNTAX OCTET STRING 
    ACCESS read-write
    STATUS mandatory
    DESCRIPTION
        "Manufacturer company name"
    ::= { wtWebioAn2GraphManufact 1 }

wtWebioAn2GraphMfAddr OBJECT-TYPE
    SYNTAX OCTET STRING 
    ACCESS read-write
    STATUS mandatory
    DESCRIPTION
        "Manufacturer address."
    ::= { wtWebioAn2GraphManufact 2 }

wtWebioAn2GraphMfHotline OBJECT-TYPE
    SYNTAX OCTET STRING 
    ACCESS read-write
    STATUS mandatory
    DESCRIPTION
        "Manufacturer hotline."
    ::= { wtWebioAn2GraphManufact 3 }

wtWebioAn2GraphMfInternet OBJECT-TYPE
    SYNTAX OCTET STRING 
    ACCESS read-write
    STATUS mandatory
    DESCRIPTION
        "Manufacturer Internet address."
    ::= { wtWebioAn2GraphManufact 4 }

wtWebioAn2GraphMfDeviceTyp OBJECT-TYPE
    SYNTAX OCTET STRING 
    ACCESS read-write
    STATUS mandatory
    DESCRIPTION
        "Manufacturer device name (model number)."
    ::= { wtWebioAn2GraphManufact 5 }

wtWebioAn2GraphMfOrderNo OBJECT-TYPE
    SYNTAX OCTET STRING 
    ACCESS read-write
    STATUS mandatory
    DESCRIPTION
        "Manufacturer part number."
    ::= { wtWebioAn2GraphManufact 6 }

-- wtWebioAn2GraphDiag Group
----------------------------

wtWebioAn2GraphDiagErrorCount OBJECT-TYPE
    SYNTAX INTEGER
    ACCESS read-only
    STATUS mandatory
    DESCRIPTION
        "Number of entries in the error memory."
    ::= { wtWebioAn2GraphDiag 1 }

wtWebioAn2GraphDiagBinaryError OBJECT-TYPE
    SYNTAX OCTET STRING 
    ACCESS read-only
    STATUS mandatory
    DESCRIPTION
        "Error causes coded bit-by-bit."
    ::= { wtWebioAn2GraphDiag 2 }

wtWebioAn2GraphDiagErrorIndex OBJECT-TYPE
    SYNTAX INTEGER
    ACCESS read-write
    STATUS mandatory
    DESCRIPTION
        "The value of this variable is used as an index to read 
        an error massege from wtWebioAn2GraphDiagErrorMessage.
        Errors are numbered from 1 to wtWebioAn2GraphDiagErrorCount.
        Writing a valid value into this variable, making the appropriate 
        message readable from wtWebioAn2GraphDiagErrorMessage."
    ::= { wtWebioAn2GraphDiag 3 }

wtWebioAn2GraphDiagErrorMessage OBJECT-TYPE
    SYNTAX OCTET STRING 
    ACCESS read-only
    STATUS mandatory
    DESCRIPTION
        "Using wtWebioAn2GraphDiagErrorIndex as an index, the appropriate message is available."
    ::= { wtWebioAn2GraphDiag 4 }
    
wtWebioAn2GraphDiagErrorClear OBJECT-TYPE
    SYNTAX INTEGER
    ACCESS write-only
    STATUS mandatory
    DESCRIPTION
        "Writing 1 into this variable clears all diagnosis messages."
    ::= { wtWebioAn2GraphDiag 5 }

-- TRAP DEFINITIONS

-- Diese SNMP-Traps werden gesendet, wenn die Alarmtriggerbedingungen zutreffen 

wtWebioAn2GraphAlert1 TRAP-TYPE
    ENTERPRISE  wtWebioAn2Graph
    VARIABLES   { wtWebioAn2GraphAlarmTrapText }
    DESCRIPTION
        "This SNMP trap is generated when Alarm 1 was triggered,
        SNMP trap enable is set and
        SNMP is enabled."
    -- NMS trap annotation
    --#TYPE "Web-Thermograph Alarm 1"
    --#SUMMARY "Alarm 1: %s"
    --#ARGUMENTS {0}
    --#SEVERITY INFORMATIONAL
    --#TIMEINDEX 99
    --#STATE OPERATIONAL    
    ::= 21

wtWebioAn2GraphAlert2 TRAP-TYPE
    ENTERPRISE  wtWebioAn2Graph
    VARIABLES   { wtWebioAn2GraphAlarmTrapText }
    DESCRIPTION
        "This SNMP trap is generated when Alarm 2 was triggered,
        SNMP trap enable is set and
        SNMP is enabled."
    -- NMS trap annotation
    --#TYPE "Web-Thermograph Alarm 2"
    --#SUMMARY "Alarm 2: %s"
    --#ARGUMENTS {0}
    --#SEVERITY INFORMATIONAL
    --#TIMEINDEX 99
    --#STATE OPERATIONAL    
    ::= 22

wtWebioAn2GraphAlert3 TRAP-TYPE
    ENTERPRISE  wtWebioAn2Graph
    VARIABLES   { wtWebioAn2GraphAlarmTrapText }
    DESCRIPTION
        "This SNMP trap is generated when Alarm 3 was triggered,
        SNMP trap enable is set and
        SNMP is enabled."
    -- NMS trap annotation
    --#TYPE "Web-Thermograph Alarm 3"
    --#SUMMARY "Alarm 3: %s"
    --#ARGUMENTS {0}
    --#SEVERITY INFORMATIONAL
    --#TIMEINDEX 99
    --#STATE OPERATIONAL    
    ::= 23

wtWebioAn2GraphAlert4 TRAP-TYPE
    ENTERPRISE  wtWebioAn2Graph
    VARIABLES   { wtWebioAn2GraphAlarmTrapText }
    DESCRIPTION
        "This SNMP trap is generated when Alarm 4 was triggered,
        SNMP trap enable is set and
        SNMP is enabled."
    -- NMS trap annotation
    --#TYPE "Web-Thermograph Alarm 4"
    --#SUMMARY "Alarm 4: %s"
    --#ARGUMENTS {0}
    --#SEVERITY INFORMATIONAL
    --#TIMEINDEX 99
    --#STATE OPERATIONAL    
    ::= 24

wtWebioAn2GraphAlert5 TRAP-TYPE
    ENTERPRISE  wtWebioAn2Graph
    VARIABLES   { wtWebioAn2GraphAlarmTrapText }
    DESCRIPTION
        "This SNMP trap is generated when Alarm 5 was triggered,
        SNMP trap enable is set and
        SNMP is enabled."
    -- NMS trap annotation
    --#TYPE "Web-Thermograph Alarm 5"
    --#SUMMARY "Alarm 5: %s"
    --#ARGUMENTS {0}
    --#SEVERITY INFORMATIONAL
    --#TIMEINDEX 99
    --#STATE OPERATIONAL    
    ::= 25

wtWebioAn2GraphAlert6 TRAP-TYPE
    ENTERPRISE  wtWebioAn2Graph
    VARIABLES   { wtWebioAn2GraphAlarmTrapText }
    DESCRIPTION
        "This SNMP trap is generated when Alarm 6 was triggered,
        SNMP trap enable is set and
        SNMP is enabled."
    -- NMS trap annotation
    --#TYPE "Web-Thermograph Alarm 6"
    --#SUMMARY "Alarm 6: %s"
    --#ARGUMENTS {0}
    --#SEVERITY INFORMATIONAL
    --#TIMEINDEX 99
    --#STATE OPERATIONAL    
    ::= 26

wtWebioAn2GraphAlert7 TRAP-TYPE
    ENTERPRISE  wtWebioAn2Graph
    VARIABLES   { wtWebioAn2GraphAlarmTrapText }
    DESCRIPTION
        "This SNMP trap is generated when Alarm 7 was triggered,
        SNMP trap enable is set and
        SNMP is enabled."
    -- NMS trap annotation
    --#TYPE "Web-Thermograph Alarm 7"
    --#SUMMARY "Alarm 7: %s"
    --#ARGUMENTS {0}
    --#SEVERITY INFORMATIONAL
    --#TIMEINDEX 99
    --#STATE OPERATIONAL    
    ::= 27

wtWebioAn2GraphAlert8 TRAP-TYPE
    ENTERPRISE  wtWebioAn2Graph
    VARIABLES   { wtWebioAn2GraphAlarmTrapText }
    DESCRIPTION
        "This SNMP trap is generated when Alarm 8 was triggered,
        SNMP trap enable is set and
        SNMP is enabled."
    -- NMS trap annotation
    --#TYPE "Web-Thermograph Alarm 8"
    --#SUMMARY "Alarm 8: %s"
    --#ARGUMENTS {0}
    --#SEVERITY INFORMATIONAL
    --#TIMEINDEX 99
    --#STATE OPERATIONAL    
    ::= 28

    
wtWebioAn2GraphAlert9 TRAP-TYPE
    ENTERPRISE  wtWebioAn2Graph
    VARIABLES   { wtWebioAn2GraphAlarmClearTrapText }
    DESCRIPTION
        "This SNMP trap is generated when Alarm 1 was cleared,
        SNMP trap enable is set and
        SNMP is enabled."
    -- NMS trap annotation
    --#TYPE "Web-Thermograph Release Alarm 1"
    --#SUMMARY "Release Alarm 1: %s"
    --#ARGUMENTS {0}
    --#SEVERITY INFORMATIONAL
    --#TIMEINDEX 99
    --#STATE OPERATIONAL    
    ::= 81

wtWebioAn2GraphAlert10 TRAP-TYPE
    ENTERPRISE  wtWebioAn2Graph
    VARIABLES   { wtWebioAn2GraphAlarmClearTrapText }
    DESCRIPTION
        "This SNMP trap is generated when Alarm 2 was cleared,
        SNMP trap enable is set and
        SNMP is enabled."
    -- NMS trap annotation
    --#TYPE "Web-Thermograph Release Alarm 2"
    --#SUMMARY "Release Alarm 2: %s"
    --#ARGUMENTS {0}
    --#SEVERITY INFORMATIONAL
    --#TIMEINDEX 99
    --#STATE OPERATIONAL    
    ::= 82

wtWebioAn2GraphAlert11 TRAP-TYPE
    ENTERPRISE  wtWebioAn2Graph
    VARIABLES   { wtWebioAn2GraphAlarmClearTrapText }
    DESCRIPTION
        "This SNMP trap is generated when Alarm 3 was cleared,
        SNMP trap enable is set and
        SNMP is enabled."
    -- NMS trap annotation
    --#TYPE "Web-Thermograph Release Alarm 3"
    --#SUMMARY "Release Alarm 3: %s"
    --#ARGUMENTS {0}
    --#SEVERITY INFORMATIONAL
    --#TIMEINDEX 99
    --#STATE OPERATIONAL    
    ::= 83

wtWebioAn2GraphAlert12 TRAP-TYPE
    ENTERPRISE  wtWebioAn2Graph
    VARIABLES   { wtWebioAn2GraphAlarmClearTrapText }
    DESCRIPTION
        "This SNMP trap is generated when Alarm 4 was cleared,
        SNMP trap enable is set and
        SNMP is enabled."
    -- NMS trap annotation
    --#TYPE "Web-Thermograph Release Alarm 4"
    --#SUMMARY "Release Alarm 4: %s"
    --#ARGUMENTS {0}
    --#SEVERITY INFORMATIONAL
    --#TIMEINDEX 99
    --#STATE OPERATIONAL    
    ::= 84

wtWebioAn2GraphAlert13 TRAP-TYPE
    ENTERPRISE  wtWebioAn2Graph
    VARIABLES   { wtWebioAn2GraphAlarmClearTrapText }
    DESCRIPTION
        "This SNMP trap is generated when Alarm 5 was cleared,
        SNMP trap enable is set and
        SNMP is enabled."
    -- NMS trap annotation
    --#TYPE "Web-Thermograph Release Alarm 5"
    --#SUMMARY "Release Alarm 5: %s"
    --#ARGUMENTS {0}
    --#SEVERITY INFORMATIONAL
    --#TIMEINDEX 99
    --#STATE OPERATIONAL    
    ::= 85

wtWebioAn2GraphAlert14 TRAP-TYPE
    ENTERPRISE  wtWebioAn2Graph
    VARIABLES   { wtWebioAn2GraphAlarmClearTrapText }
    DESCRIPTION
        "This SNMP trap is generated when Alarm 6 was cleared,
        SNMP trap enable is set and
        SNMP is enabled."
    -- NMS trap annotation
    --#TYPE "Web-Thermograph Release Alarm 6"
    --#SUMMARY "Release Alarm 6: %s"
    --#ARGUMENTS {0}
    --#SEVERITY INFORMATIONAL
    --#TIMEINDEX 99
    --#STATE OPERATIONAL    
    ::= 86

wtWebioAn2GraphAlert15 TRAP-TYPE
    ENTERPRISE  wtWebioAn2Graph
    VARIABLES   { wtWebioAn2GraphAlarmClearTrapText }
    DESCRIPTION
        "This SNMP trap is generated when Alarm 7 was cleared,
        SNMP trap enable is set and
        SNMP is enabled."
    -- NMS trap annotation
    --#TYPE "Web-Thermograph Release Alarm 7"
    --#SUMMARY "Release Alarm 7: %s"
    --#ARGUMENTS {0}
    --#SEVERITY INFORMATIONAL
    --#TIMEINDEX 99
    --#STATE OPERATIONAL    
    ::= 87

wtWebioAn2GraphAlert16 TRAP-TYPE
    ENTERPRISE  wtWebioAn2Graph
    VARIABLES   { wtWebioAn2GraphAlarmClearTrapText }
    DESCRIPTION
        "This SNMP trap is generated when Alarm 8 was cleared,
        SNMP trap enable is set and
        SNMP is enabled."
    -- NMS trap annotation
    --#TYPE "Web-Thermograph Release Alarm 8"
    --#SUMMARY "Release Alarm 8: %s"
    --#ARGUMENTS {0}
    --#SEVERITY INFORMATIONAL
    --#TIMEINDEX 99
    --#STATE OPERATIONAL    
    ::= 88

wtWebioAn2GraphAlertDiag TRAP-TYPE
    ENTERPRISE  wtWebioAn2Graph
    VARIABLES   { 	
    		wtWebioAn2GraphDiagErrorIndex,
    	  	wtWebioAn2GraphDiagErrorMessage
    		}
    DESCRIPTION
        "This SNMP trap is generated when a diagnosis/error message was triggered,
        SNMP trap enable is set and
        SNMP is enabled."
    -- NMS trap annotation
    --#TYPE "Web-Thermograph Diagnose Error"
    --#SUMMARY "Diagnose error index: %d, Message: %s."
    --#ARGUMENTS {0,1}
    --#SEVERITY MAJOR
    --#TIMEINDEX 99
    --#STATE DEGRADED    
    ::= 110 

END

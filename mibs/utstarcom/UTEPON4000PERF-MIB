-- *****************************************************************************
-- Filename:        ut-epon-4000-perf.mib
-- Description:     Contains iSwitch MIB Extension.
-- MIB Version:     1.00
-- 
-- Copyright (C) 2001 by UTStarcom, Inc. All rights reserved.
-- Reproduction of this document is authorized on the condition that
-- the foregoing copyright notice is included.
--
-- NOTE:  The contents of this document are subject to change without notice
-- *****************************************************************************

-- *****************************************************************************
-- Version:        $Id:  $
-- Last Modified:  $DateTime:  $
-- Change List #:  $Change:  $
-- *****************************************************************************

UTEPON4000PERF-MIB DEFINITIONS ::= BEGIN

    IMPORTS
        MODULE-IDENTITY, OBJECT-TYPE, IpAddress,
        Counter64                               FROM SNMPv2-SMI
        Counter, TimeTicks                      FROM RFC1155-SMI            
        RowStatus, TruthValue                   FROM SNMPv2-TC
        DisplayString                           FROM RFC1213-MIB
        ifIndex                                 FROM IF-MIB
        MacAddress, BridgeId, Timeout           FROM BRIDGE-MIB
        utsGeponBBS4000      FROM UTS-BBS-COMMON-MIB;


   utsGeponBBS4000Performance  MODULE-IDENTITY
        LAST-UPDATED "9407272253Z"      -- Wed Jul 27 22:53:04 PDT 1994
        ORGANIZATION "UTStarcom Inc"
        CONTACT-INFO
            "Postal: UTStarcom Inc
             Alameda, California 9xxxx
             Tel:    +1 510 555 1212
             E-Mail: mibs@utstar.com "
      DESCRIPTION
         "Contains UT EPON MIB Extensions."
     ::= { utsGeponBBS4000 4   }


--
--  epon objects extersion
--

utsEthIfPerfExt     OBJECT IDENTIFIER ::= { utsGeponBBS4000Performance 1 }
utsEfmPonPerfExt     OBJECT IDENTIFIER ::= { utsGeponBBS4000Performance 2 }
utsLayer3PerfExt     OBJECT IDENTIFIER ::= { utsGeponBBS4000Performance 3 }
utsSystemPerfExt     OBJECT IDENTIFIER ::= { utsGeponBBS4000Performance 4 }
--
--  ethernet interface extersion
--


utsEthIfStatsExtObjects OBJECT IDENTIFIER ::= { utsEthIfPerfExt 1 }

--
-- Ether-like interface extension private MIB objects--        


utsSystemStatsExtObjects OBJECT IDENTIFIER ::= { utsSystemPerfExt 1 }

--
-- System perf extension private MIB objects--

--
--  CPU and Mem Util, temperature for each board info
--
   utsSystemPerfTable  OBJECT-TYPE
        SYNTAX      SEQUENCE OF UtsSystemPerfEntry
        MAX-ACCESS  not-accessible
        STATUS      current
        DESCRIPTION
            "A table of the util of cpu and memory, and temperature information in each board."
       ::= { utsSystemStatsExtObjects 1 }


   utsSystemPerfEntry OBJECT-TYPE
       SYNTAX       UtsSystemPerfEntry
       MAX-ACCESS   not-accessible
       STATUS       current
       DESCRIPTION
          "An entry contains the util of cpu, memory, and temperature on each board."
      INDEX { utsSystemPerfBoardPhyId }
      ::= { utsSystemPerfTable 1 }


    UtsSystemPerfEntry ::=
        SEQUENCE {
            utsSystemPerfBoardPhyId
                INTEGER,
            utsSystemPerfBoardType
                INTEGER,
  	        utsSystemPerfCpuUtil
                INTEGER,
            utsSystemPerfMemUtil
                INTEGER,
            utsSystemPerfTemperature
                INTEGER            
        }

    utsSystemPerfBoardPhyId OBJECT-TYPE
        SYNTAX      INTEGER (1..14)
        MAX-ACCESS  read-only
        STATUS      current
        DESCRIPTION
           "The physical module number, 1-12 means service card, 13 means CSM A, 14 means CSM B. "
       ::= { utsSystemPerfEntry 1 }

    utsSystemPerfBoardType OBJECT-TYPE
        SYNTAX      INTEGER
        {
			other(1),
			csm(2),
			epm04a(3),
			epm04b(4),
			epm04c(5),
			gem04a(6), 		
			gem04b(7)
        }
        MAX-ACCESS  read-only
        STATUS      current
        DESCRIPTION
           "The line card type. In bbs4000, current 4 kind board are supported:
            csm(2) -- controller and switch fabric card,
            epm04a(3) -- epon service access line card using the Passave Chip,
            epm04b(4) -- epon service access line card using the ImmenStar Chip,
            epm04c(5) -- epon service access line card(reserved),
            gem04(6) -- giga Ethernet service card,            
            gem04a(8) -- giga Ethernet service card with opper port only.
            "
       ::= { utsSystemPerfEntry 2 } 
       
    utsSystemPerfCpuUtil OBJECT-TYPE
        SYNTAX      INTEGER
        MAX-ACCESS  read-only
        STATUS      current
        DESCRIPTION
           "The util of cpu, the value should be from 0 to 1000."
       ::= { utsSystemPerfEntry 3 }
   
    utsSystemPerfMemUtil OBJECT-TYPE
        SYNTAX      INTEGER
        MAX-ACCESS  read-only
        STATUS      current
        DESCRIPTION
           "The util of memory, the value should be from 0 to 1000."
       ::= { utsSystemPerfEntry 4 }  
    
    utsSystemPerfTemperature OBJECT-TYPE
        SYNTAX      INTEGER
        MAX-ACCESS  read-only
        STATUS      current
        DESCRIPTION
           "The temperature of the board."
       ::= { utsSystemPerfEntry 5 }      
                              
END

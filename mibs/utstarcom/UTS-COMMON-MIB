-- This MIB file defines UTStarcom's generic management object model. PDS Handle: UTSI-NJTC-200411800100

UTS-COMMON-MIB DEFINITIONS ::= BEGIN

IMPORTS
	MODULE-IDENTITY, OBJECT-IDENTITY, enterprises
		FROM SNMPv2-SMI;

utCommonMib MODULE-IDENTITY
	LAST-UPDATED "200204280000Z"
	ORGANIZATION 
		"UTStarcom, Inc."
	CONTACT-INFO 
		"	UTStarcom Inc., Corporate Headquarters
			1275 Harbor Bay Parkway
			Alameda, CA 94502 USA
			Phone: 1 (510) 864-8800
			Fax: 1 (510) 864-8802


			UTStarcom Inc., New Jersey R&D Center
			33 Wood Avenue South 3rd floor
			Iselin, NJ 08830 USA
			Phone: 1 (732) 767-5200
			Fax: 1 (732) 548-1099 
			
			
			UTStarcom (China) Ltd.
			10F, Tower E2, The Towers, Oriental Plaza
			No. 1 East Chang An Ave
			DongCheng district, Beijing, China
			Post code: 100738
			Phone: +86-10-8520-5588
			Fax: +86-10-8520-5599 
			

			UTStarcom Hangzhou R&D Center
			Building 3, Yile Industrial Park
			No. 129, Wenyi Road
			Hangzhou 310012, P.R. China
			Phone: 86-571-88862342
			Fax: 86-571-88862349


			UTStarcom Shenzhen R&D Center
			3/F, Legend Building,
		        High-tech Industrial Park,
		        Nanshan Shenzhen, 518057, PRC
		        Phone: 86-755-6983555
		        Fax: 86-755-6983786
		        
		        http://www.utstar.com
		        "
	DESCRIPTION 
		"The root MIB module for UTStarcom, Inc.
		
		        Copyright (c) 2002 UTStarcom, Inc.
		        All rights reserved.
		
		        Reproduction of this document is authorized on the condition that the 
		        foregoing copyright notice is included.
		
		        This SNMP MIB module (Specification) embodies UTStarcom proprietary 
		        intellectual property.  UTStarcom retains all title and ownership in 
		        the Specification, including any revisions.
		
		        UTStarcom grants all interested parties a non-exclusive license to use 
		        and distribute an unmodified copy of this Specification in connection 
		        with management of UTStarcom products, and without fee, provided this 
		        copyright notice and license appear on all copies.
		
		        This Specification is supplied 'AS IS' and UTStarcom makes no warranty, 
		        either express or implied, as to the use, operation, condition, or 
		        performance of the Specification."

	REVISION "200204280000Z"
	DESCRIPTION 
		"Initial version of the root MIB module UTS-COMMON-MIB."

	REVISION "200408190000Z"
	DESCRIPTION 
		"The people who have been involved in this changes:
		    UNMS committee
		
		The following changes are made:
		    1. Add 'utsCdma2000 (17)' and 'utsMsan (18)' under the node 'utsProducts'.
		    2. Add 'utiAN8000 (1)' under the node 'utsMsan'.
		The updated MIB file has been uploaded to PDS (UTSI-NJTC-200411800100).
		"

	REVISION "200409210000Z"
	DESCRIPTION 
		"The people who have been involved in this changes:
		    UNMS committee
		
		The following changes are made:
		    1. Add 'utDslamCommon (2)' under the node 'utsDslam';
		    2. Add 'utsPwlan (19)' under the node 'utsProducts';
		"

	REVISION "200505080000Z"
	DESCRIPTION 
		"The people who have been involved in this changes:
		    Bingjun Li
		
		The following changes are made:
		    1. Add 'utsRfOverlay (20)' under the node 'utsProducts';
		"
		
			
::= { utModules 1 }


-- ********************
-- *   UTSTARCOM ROOT *
-- ********************

utstarcom            OBJECT IDENTIFIER ::= { enterprises 1949 }

utsRoot  OBJECT-IDENTITY
	STATUS     current
	DESCRIPTION 
		"Root for Utstarcom MIB tree."
	::= { utstarcom 1 }

-- ********************
-- *   Registration   *
-- ********************
-- Midnight 28 April 2002
-- **************************************************
-- * The top level registrations for the enterprise *
-- **************************************************

utsReg  OBJECT-IDENTITY
	STATUS     current
	DESCRIPTION 
		"Sub-tree for registering UTStarcom MIB administration entitities, 
		         including MIB modules, products, product components, and other MIB 
		         related items (like Agent capabilities, etc.)."
	::= { utsRoot 1 }

utModules  OBJECT-IDENTITY
	STATUS     current
	DESCRIPTION 
		"Sub-tree to register the values assigned to modules with the 
		        MODULE-IDENTITY construct.
		
		        The MODULE-IDENTITY construct, like the MODULE-COMPLIANCE, and 
		        AGENT-CAPABILITIES constructs, is expanded during the implementation,
		        not at runtime. 
		
		        The modules can be arranged in a hierarchical structure. The sub-oid
		        1 is used by this module, as defined in the MODULE-IDENTITY construct
		        of this file.
		        "
	::= { utsReg 1 }

utUmtsModules  OBJECT-IDENTITY
	STATUS     current
	DESCRIPTION 
		"Sub-tree to register the MIB modules under UMTS product line."
	::= { utModules 2 }

utEmbeddedPlatformModules  OBJECT-IDENTITY
	STATUS     current
	DESCRIPTION 
		"Sub-tree to register the MIB modules for Embedded common platform."
	::= { utModules 5 }

utServerPlatformModules  OBJECT-IDENTITY
	STATUS     current
	DESCRIPTION 
		"Sub-tree to register the MIB modules for Serrver common platform."
	::= { utModules 6 }

utCommonPlatformModules  OBJECT-IDENTITY
	STATUS     current
	DESCRIPTION 
		"Sub-tree to register the MIB modules for common protocols."
	::= { utModules 7 }

utBroadbandModules  OBJECT-IDENTITY
	STATUS     current
	DESCRIPTION 
		""
	::= { utModules 8 }

utMediaSwitchModules  OBJECT-IDENTITY
	STATUS     current
	DESCRIPTION 
		""
	::= { utModules 9 }

utMswitchModules  OBJECT-IDENTITY
	STATUS     current
	DESCRIPTION 
		""
	::= { utModules 10 }

utAgentCap  OBJECT-IDENTITY
	STATUS     current
	DESCRIPTION 
		"Sub-tree for identifying agent implementation profiles."
	::= { utsReg 2 }

utsGeneric  OBJECT-IDENTITY
	STATUS     current
	DESCRIPTION 
		"Sub-tree for generic properties of UTStarcom MIB tree."
	::= { utsRoot 2 }

utsProducts  OBJECT-IDENTITY
	STATUS     current
	DESCRIPTION 
		"Sub-tree for defining objects and events that are specific to 
		        particular UTStarcom product lines.
		
		        Each product line is partitioned into a functional view and a service 
		        view. The functional view is mainly for Element Management, while the
		        service view is mainly for Service Management (which may span across
		        multiple Network Elements)."
	::= { utsRoot 3 }

utsAn2K  OBJECT-IDENTITY
	STATUS     current
	DESCRIPTION 
		"Sub-tree for products AN2000."
	::= { utsProducts 1 }

utsWll  OBJECT-IDENTITY
	STATUS     current
	DESCRIPTION 
		"Sub-tree for products WLL."
	::= { utsProducts 2 }

utsIpDslam  OBJECT-IDENTITY
	STATUS     current
	DESCRIPTION 
		"Sub-tree for products IP DSLAM."
	::= { utsProducts 3 }

utsiAN4000  OBJECT-IDENTITY
	STATUS     current
	DESCRIPTION 
		"Sub-tree for products iAN4000."
	::= { utsProducts 4 }

utsVas  OBJECT-IDENTITY
	STATUS     current
	DESCRIPTION 
		"Sub-tree for products Vas."
	::= { utsProducts 5 }

utsMiniDslam  OBJECT-IDENTITY
	STATUS     current
	DESCRIPTION 
		"Sub-tree for products Mini DSLAM."
	::= { utsProducts 6 }

utsL2Switch  OBJECT-IDENTITY
	STATUS     current
	DESCRIPTION 
		"Sub-tree for products L2Switch."
	::= { utsProducts 7 }

utsUmts  OBJECT-IDENTITY
	STATUS     current
	DESCRIPTION 
		"Sub-tree for products UMTS."
	::= { utsProducts 8 }

-- ************************************************
-- *  First level expansion for UMTS product line *
-- ************************************************

utUmtsFunctions  OBJECT-IDENTITY
	STATUS     current
	DESCRIPTION 
		"Sub-tree to cover UMTS functional elements, such as CS and PS 
		        functions."
	::= { utsUmts 1 }

utUmtsServices  OBJECT-IDENTITY
	STATUS     current
	DESCRIPTION 
		"Sub-tree to cover UMTS service management aspects, which will be
		        realized at various UTStarcom UMTS network elements. For example, 
		        the APN profile management (its scope spans across OSS, NMS, DNS,
		        IP network, and one or more GGSNs)."
	::= { utsUmts 2 }

utsSp8000           OBJECT-IDENTITY
	STATUS     current
	DESCRIPTION 
		""
	::= { utsProducts 9 }

utsBroadbandSwitch  OBJECT-IDENTITY
	STATUS     current
	DESCRIPTION 
		""
	::= { utsProducts 10 }

utsMediaSwitch  OBJECT-IDENTITY
	STATUS     current
	DESCRIPTION 
		""
	::= { utsProducts 11 }

utsAirStarEp  OBJECT-IDENTITY
	STATUS     current
	DESCRIPTION 
		""
	::= { utsProducts 12 }
	
utsMswitch  OBJECT-IDENTITY
	STATUS     current
	DESCRIPTION 
		""
	::= { utsProducts 13 }

utsDslam  OBJECT-IDENTITY
	STATUS     current
	DESCRIPTION 
		""
	::= { utsProducts 14 }
	
utsAN2000B300   OBJECT-IDENTITY
	STATUS     current
	DESCRIPTION 
		""
	::= { utsDslam 1 }

utDslamCommon   OBJECT-IDENTITY
	STATUS     current
	DESCRIPTION 
		""
	::= { utsDslam 2 }
	
utsWlan   OBJECT-IDENTITY
	STATUS     current
	DESCRIPTION 
		""
	::= { utsProducts 15 }

utsCpe   OBJECT-IDENTITY
	STATUS     current
	DESCRIPTION 
		""
	::= { utsProducts 16 }
	
utsCdma2000   OBJECT-IDENTITY
	STATUS     current
	DESCRIPTION 
		""
	::= { utsProducts 17 }	
	
-- ************************************************
-- *  First level expansion for CDMA2000 product line *
-- ************************************************

utCdma2000Functions  OBJECT-IDENTITY
	STATUS     current
	DESCRIPTION 
		"Sub-tree to cover CDMA2000 functional elements, such as MSC, BSC and BTS 
		        functions."
	::= { utsCdma2000 1 }

utCdma2000Services  OBJECT-IDENTITY
	STATUS     current
	DESCRIPTION 
		"Sub-tree to cover CDMA2000 service management aspects, which will be
		        realized at various UTStarcom CDMA2000 network elements."
	::= { utsCdma2000 2 }

-- ****************************************************
-- *  First level expansion for CDMA2000 Functional View  *
-- ****************************************************

utBtsFunctions  OBJECT-IDENTITY
	STATUS     current
	DESCRIPTION 
		""
	::= { utCdma2000Functions 1 }

utBscFunctions  OBJECT-IDENTITY
	STATUS     current
	DESCRIPTION 
		""
	::= { utCdma2000Functions 2 }
	
utMscFunctions  OBJECT-IDENTITY
	STATUS     current
	DESCRIPTION 
		""
	::= { utCdma2000Functions 3 }

-- *****************************************************
-- *  Second level expansion for CDMA2000 Functional View *
-- *****************************************************	

utiCellBtsFunctions   OBJECT-IDENTITY
	STATUS     current
	DESCRIPTION 
		""
	::= { utBtsFunctions 1 }
	
utHsiBtsFunctions    OBJECT-IDENTITY
	STATUS     current
	DESCRIPTION 
		""
	::= { utBtsFunctions 2 }

utiCellBscFunctions   OBJECT-IDENTITY
	STATUS     current
	DESCRIPTION 
		""
	::= { utBscFunctions 1 }
	
utHsiBscFunctions    OBJECT-IDENTITY
	STATUS     current
	DESCRIPTION 
		""
	::= { utBscFunctions 2 }

utSonataMscFunctions     OBJECT-IDENTITY
	STATUS     current
	DESCRIPTION 
		""
	::= { utMscFunctions 1 }
	
-- ************************************************
-- *  End of expansion for CDMA2000 product line  *
-- ************************************************	

utsMsan  OBJECT-IDENTITY
	STATUS     current
	DESCRIPTION 
		""
	::= { utsProducts 18 }

utiAN8000    OBJECT-IDENTITY
	STATUS     current
	DESCRIPTION 
		""
	::= { utsMsan 1 }
	
utsPwlan   OBJECT-IDENTITY
	STATUS     current
	DESCRIPTION 
		""
	::= { utsProducts 19 }	

utsRfOverlay   OBJECT-IDENTITY
	STATUS     current
	DESCRIPTION 
		""
	::= { utsProducts 20 }	
		
-- MIB_REGION_BEGIN

utsPlatform  OBJECT-IDENTITY
	STATUS     current
	DESCRIPTION 
		"Sub-tree for defining platform objects and events that are shared by
		        all UTStarcom product lines, including Chassis management objects,
		        common protocol stacks, etc."
	::= { utstarcom 2 }

-- ******************
-- *    Platforms   *
-- ******************

utEmbeddedPlatform  OBJECT-IDENTITY
	STATUS     current
	DESCRIPTION 
		"Sub-tree for Embedded platforms management."
	::= { utsPlatform 1 }

utChassis  OBJECT-IDENTITY
	STATUS     current
	DESCRIPTION 
		"Sub-tree for Embedded platform chassis management."
	::= { utEmbeddedPlatform 1 }

utRem  OBJECT-IDENTITY
	STATUS     current
	DESCRIPTION 
		"Sub-tree for Embedded platform rem board management."
	::= { utEmbeddedPlatform 100 }

utServerPlatform  OBJECT-IDENTITY
	STATUS     current
	DESCRIPTION 
		"Sub-tree for Server platforms management."
	::= { utsPlatform 2 }

utCommonPlatform  OBJECT-IDENTITY
	STATUS     current
	DESCRIPTION 
		""
	::= { utsPlatform 3 }

-- MIB_REGION_BEGIN

utCommonProtocol  OBJECT-IDENTITY
	STATUS     current
	DESCRIPTION 
		""
	::= { utCommonPlatform 1 }

-- MIB_REGION_BEGIN

utCommonOam  OBJECT-IDENTITY
	STATUS     current
	DESCRIPTION 
		""
	::= { utCommonPlatform 2 }

utCommonSyslog       OBJECT IDENTIFIER ::= { utCommonPlatform 3 }

utsExperiment  OBJECT-IDENTITY
	STATUS     current
	DESCRIPTION 
		"Sub-tree for defining objects and events that are experimental in
		        nature."
	::= { utstarcom 100 }
END


-- This MIB was created using NuDesign Team's Visual MIBuilder (Ver 4.3).

-- *****************************************************************************
-- Filename:        epon-utConfigure.mib
-- Description:     Contains iSwitch MIB Extension.
-- MIB Version:     1.00
-- 
-- Copyright (C) 2001 by UTStarcom, Inc. All rights reserved.
-- Reproduction of this document is authorized on the condition that
-- the foregoing copyright notice is included.
--
-- NOTE:  The contents of this document are subject to change without notice
-- *****************************************************************************

-- *****************************************************************************
-- Version:        $Id:  $
-- Last Modified:  $DateTime:  $
-- Change List #:  $Change:  $
-- *****************************************************************************

UTEPON4000CONF-MIB DEFINITIONS ::= BEGIN

    IMPORTS	
        MODULE-IDENTITY, OBJECT-TYPE, IpAddress FROM SNMPv2-SMI
        
        Counter, TimeTicks		FROM RFC1155-SMI            
        RowStatus, TruthValue,
        TEXTUAL-CONVENTION              FROM SNMPv2-TC
        InterfaceIndex			FROM IF-MIB 
        ifIndex					FROM IF-MIB
        InterfaceIndexOrZero    FROM IF-MIB
        DisplayString          		FROM SNMPv2-TC
        PhysAddress				FROM SNMPv2-TC
        MacAddress                      FROM BRIDGE-MIB
        BridgeId				FROM BRIDGE-MIB 
        Timeout					FROM BRIDGE-MIB 
        utsGeponBBS4000       FROM UTS-BBS-COMMON-MIB;


   utsGeponBBS4000Configuration  MODULE-IDENTITY
        LAST-UPDATED "9407272253Z"      -- Wed Jul 27 22:53:04 PDT 1994
        ORGANIZATION "UTSTARcom Inc"
        CONTACT-INFO
            "Postal: UTSTARcom Inc
             Alameda, California 9xxxx
             Tel:    +1 510 555 1212
             E-Mail: mibs@utstar.com "
      DESCRIPTION
         "Contains UT EPON MIB Extensions."
     ::= { utsGeponBBS4000 2 } 


    UtsSyslogServerityLevelType ::= TEXTUAL-CONVENTION
        STATUS  current
        DESCRIPTION
            "The Syslog serverity types used by UT's BBS1000
             SyslogServerTable."
        SYNTAX  INTEGER {
			emergencies(1),
			alerts(2),
			critical(3),
			errors(4),
			warnings(5),
			notifications(6),
			informational(7),
			debugging(8)
			--,disabled(9)
        }

    UtsConfStationIdType ::= TEXTUAL-CONVENTION
        STATUS    current
        DESCRIPTION
            "The station Id to identify the issued configuration command"
        SYNTAX DisplayString(SIZE(0..16))
        
    UtsConfStatusType ::= TEXTUAL-CONVENTION
        STATUS    current
        DESCRIPTION
            "Confiuration/Test command result."
        SYNTAX INTEGER
        {
            success(1),
            failure(2),
            busy(3)
        }
        
--
--  epon objects extersion
--

utsSystemConfExt     OBJECT IDENTIFIER ::= { utsGeponBBS4000Configuration 1 }

utsEthIfConfExt     OBJECT IDENTIFIER ::= { utsGeponBBS4000Configuration 2 }

utsEfmPonConfExt     OBJECT IDENTIFIER ::= { utsGeponBBS4000Configuration 3 }

utsServiceConfExt   OBJECT IDENTIFIER ::= { utsGeponBBS4000Configuration 4 } 

--
--  epon system and module extension
--

utsSystemExtObjects OBJECT IDENTIFIER ::= { utsSystemConfExt 1 }

eponOamInitAlm  OBJECT IDENTIFIER ::= { utsSystemConfExt 2 }


------ 
------ epon module table
------

--
--  chassis slot physical board info
--
   utsEponModuleBoardTable  OBJECT-TYPE
        SYNTAX      SEQUENCE OF UtsEponModuleBoardEntry
        MAX-ACCESS  not-accessible
        STATUS      current
        DESCRIPTION
            "A list of board information in a EPON box."
       ::= { utsSystemExtObjects 1 }


   utsEponModuleBoardEntry OBJECT-TYPE
       SYNTAX       UtsEponModuleBoardEntry
       MAX-ACCESS   not-accessible
       STATUS       current
       DESCRIPTION
          "An entry contains board information on a module."
      INDEX { utsEponModuleBoardPhyId }
      ::= { utsEponModuleBoardTable 1 }


    UtsEponModuleBoardEntry ::=
        SEQUENCE {
            utsEponModuleBoardPhyId
                INTEGER,
            utsEponModuleBoardType
                INTEGER,
  	         utsEponModulePhyPresenceStat
                INTEGER,
            utsEponModuleAdminState
                INTEGER,
            utsEponModuleOperationState
                INTEGER,
            utsEponModuleRedundancyState
                INTEGER,
            utsEponModulePhyicalUptime
		          TimeTicks,
	         utsEponOpStateUptime
		          TimeTicks,
	         utsEponModuleCSMSwitchtime
		          TimeTicks,
            utsEponModuleBoardSwVer
                DisplayString,
            utsEponModuleBoardBootromVer
                DisplayString,
            utsEponModuleBoardPassaveVer
                DisplayString,
            utsEponModuleBoardCurTemp
        	       INTEGER,
            utsEponModuleBoardTempUpLimit
        	       INTEGER,
        	  utsEponModuleBoardTempUpClearLimit
        	       INTEGER,
        	  utsEponModuleBoardLastAdminStateChangetime
        	       TimeTicks,
        	  utsEponModuleBoardLastOperationStateChangetime
        	       TimeTicks,
        	  utsEponModuleBoardDisableCause
        	       INTEGER,
        	  utsEponModuleBoardHwVer
        	       DisplayString,
        	  utsEponModuleBoardCpldVer
        	       DisplayString,
        	  utsEponModuleBoardSerialNumber
        	       DisplayString,
        	  utsEponModuleBoard2424Information
        	       DisplayString,
        	  utsEponModuleBoardHASyncStatus
        	  	   INTEGER,
        	  utsEponModuleBoardCpuUtil
        	       INTEGER,
        	  utsEponModuleBoardMemUtil 
        	       INTEGER
        }

    utsEponModuleBoardPhyId OBJECT-TYPE
        SYNTAX      INTEGER (1..14)
        MAX-ACCESS  read-only
        STATUS      current
        DESCRIPTION
           "The physical module number, 1-12 means service card, 13 means CSM A, 14 means CSM B. "
       ::= { utsEponModuleBoardEntry 1 }

    utsEponModuleBoardType OBJECT-TYPE
        SYNTAX      INTEGER
        {
			other(1),
			csm(2),
			epm04a(3),
			epm04b(4),
			epm04c(5),
			gem04a(6), 		
			gem04b(7),
			xgm01a(8),
			osm04a(9),
			gpm02a(10)			
        }
        MAX-ACCESS  read-only
        STATUS      current
        DESCRIPTION
           "The line card type. In bbs4000, current 4 kind board are supported:
            csm(2) -- controller and switch fabric card,
            epm04a(3) -- epon service access line card using the Passave Chip,
            epm04b(4) -- epon service access line card using the ImmenStar Chip,
            epm04c(5) -- epon service access line card(reserved),
            gem04(6) -- giga Ethernet service card,            
            gem04a(8) -- giga Ethernet service card with opper port only.
            "
       ::= { utsEponModuleBoardEntry 2 }
       
    utsEponModulePhyPresenceStat OBJECT-TYPE
        SYNTAX      INTEGER
        {
            installed(1),
            not-installed(2)
        }
        MAX-ACCESS  read-only
        STATUS      current
        DESCRIPTION
           "The line card type. In EPON, BCM, OLT are supported"
       ::= { utsEponModuleBoardEntry 3 }

    utsEponModuleAdminState OBJECT-TYPE
        SYNTAX      INTEGER
        {
            locked(1),
            unlocked(2),
            reset(8)     -- write to reset this board
        }
        MAX-ACCESS  read-write
        STATUS      current
        DESCRIPTION
           "administrative state changed by operator, 
            locked(1) -- the slot is disabled for service
            unlocked (2) -- the slot can provide service
            reset(8) -- reset the  slot
            "
       ::= { utsEponModuleBoardEntry 4 }
       
    utsEponModuleOperationState OBJECT-TYPE
        SYNTAX      INTEGER
        {
            inactive(2), -- read-only status.
            active(3)   -- read-only status.                
         }
        MAX-ACCESS  read-only
        STATUS      current
        DESCRIPTION
           "The internal state of line card"
       ::= { utsEponModuleBoardEntry 5 }       
       

    utsEponModuleRedundancyState OBJECT-TYPE
    SYNTAX INTEGER 
        {
          other(1),
          active(2),
          standby(3) 
        }
        MAX-ACCESS  read-only
        STATUS      current
        DESCRIPTION
           "The redundancy state of CSM module, for other line card, the unique state is other(1)."
       ::= { utsEponModuleBoardEntry 6 }

	 utsEponModulePhyicalUptime OBJECT-TYPE
        SYNTAX TimeTicks 
        MAX-ACCESS  read-only
        STATUS      current
        DESCRIPTION
           "when the physical module is up."
       ::= { utsEponModuleBoardEntry 8 }
       
	 utsEponOpStateUptime OBJECT-TYPE
        SYNTAX TimeTicks 
        MAX-ACCESS  read-only
        STATUS      current
        DESCRIPTION
           "when the oepration state of this module become active."
       ::= { utsEponModuleBoardEntry 9 }
       
       
    utsEponModuleCSMSwitchtime OBJECT-TYPE
        SYNTAX TimeTicks 
        MAX-ACCESS  read-only
        STATUS      current
        DESCRIPTION
           "when the oepration state of this module become active."
       ::= { utsEponModuleBoardEntry 11 }

    utsEponModuleBoardSwVer OBJECT-TYPE
        SYNTAX      DisplayString(SIZE(0..63))
        MAX-ACCESS  read-only
        STATUS      current
        DESCRIPTION
           "Software version of the board. The software verion is applicable
           to the whole box and therefore belongs to the GSM board.  For LTM
           boards, the this object returns 'None'."
       ::= { utsEponModuleBoardEntry 12 }

    utsEponModuleBoardBootromVer OBJECT-TYPE
        SYNTAX      DisplayString(SIZE(0..63))
        MAX-ACCESS  read-only
        STATUS      current
        DESCRIPTION
           "The Bootrom version of the board. The Bootrom verion is
           applicable to the whole box and therefore belongs to the GSM board.
           For LTM boards, the this object returns 'None'."
       ::= { utsEponModuleBoardEntry 13 }

    utsEponModuleBoardPassaveVer OBJECT-TYPE
        SYNTAX      DisplayString(SIZE(0..63))
        MAX-ACCESS  read-only
        STATUS      current
        DESCRIPTION
           "The Passave Olt Firmware revision for the LTM board.  Each of the
           two LTM boards has a copy of the firmware running therefore both 
           will show a firmware version.  For now, however, the two are always
           the same.  For GSM boards, the this object returns 'None'."
       ::= { utsEponModuleBoardEntry 14 }        	
        	       
     utsEponModuleBoardCurTemp OBJECT-TYPE
    		SYNTAX INTEGER         
        MAX-ACCESS  read-only
        STATUS      current
        DESCRIPTION
           "The current temperature of physical slot."
       ::= { utsEponModuleBoardEntry 15 }
       
     utsEponModuleBoardTempUpLimit OBJECT-TYPE
    	SYNTAX INTEGER(0..70)         
        MAX-ACCESS  read-write
        STATUS      current
        DESCRIPTION
           "The maximum threshold of physical slot temperature. The default value is 70.
            It is suggested this value shall be greater than up clear limit value for 5."
        DEFVAL      {70}           
       ::= { utsEponModuleBoardEntry 16 }
       
     utsEponModuleBoardTempUpClearLimit OBJECT-TYPE
    	SYNTAX INTEGER(0..70)         
        MAX-ACCESS  read-write
        STATUS      current
        DESCRIPTION
           "The up clear limit of physical slot temperature. The default value is 65.
            It is suggested this value shall be lower than up limit value for 5."            
        DEFVAL      {65}
       ::= { utsEponModuleBoardEntry 17 }
       
     utsEponModuleBoardLastAdminStateChangetime OBJECT-TYPE
        SYNTAX TimeTicks 
        MAX-ACCESS  read-only
        STATUS      current
        DESCRIPTION
           "Last Administrative State Change Time Till Now (TimeTicks)."
       ::= { utsEponModuleBoardEntry 18 }
       
     utsEponModuleBoardLastOperationStateChangetime OBJECT-TYPE
        SYNTAX TimeTicks 
        MAX-ACCESS  read-only
        STATUS      current
        DESCRIPTION
           "Last Operational State Change Time Till Now (TimeTicks)."
       ::= { utsEponModuleBoardEntry 19 }
       
     utsEponModuleBoardDisableCause OBJECT-TYPE
        SYNTAX INTEGER 
        {
        		adminlock(1),
        		lostcurrentstate(2),
        		serviceunavailable(3)        		
        }
        MAX-ACCESS  read-only
        STATUS      current
        DESCRIPTION
           "The disable Cause."
       ::= { utsEponModuleBoardEntry 20 }
     
     utsEponModuleBoardHwVer OBJECT-TYPE
        SYNTAX      DisplayString(SIZE(0..63))
        MAX-ACCESS  read-only
        STATUS      current
        DESCRIPTION
           "Hw version of the board"
       ::= { utsEponModuleBoardEntry 21 }
     
     utsEponModuleBoardCpldVer OBJECT-TYPE
        SYNTAX      DisplayString(SIZE(0..63))
        MAX-ACCESS  read-only
        STATUS      current
        DESCRIPTION
           "CPLD version of the board"
       ::= { utsEponModuleBoardEntry 22 }
       
     utsEponModuleBoardSerialNumber OBJECT-TYPE
        SYNTAX      DisplayString(SIZE(0..63))
        MAX-ACCESS  read-only
        STATUS      current
        DESCRIPTION
           "SN information of the board"
       ::= { utsEponModuleBoardEntry 23 }
       
     utsEponModuleBoard2424Information OBJECT-TYPE
        SYNTAX      DisplayString(SIZE(0..63))
        MAX-ACCESS  read-only
        STATUS      current
        DESCRIPTION
           "2424 information of the board"
       ::= { utsEponModuleBoardEntry 24 }
     
     utsEponModuleBoardHASyncStatus OBJECT-TYPE
        SYNTAX INTEGER 
        {
        		notstart(1),
        		syncing(2),
        		syncover(3),
        		syncfail(4)        		
        }
        MAX-ACCESS  read-only
        STATUS      current
        DESCRIPTION
           "The HA Sync status for the initial sync when the standby card insert."
       ::= { utsEponModuleBoardEntry 26 }
       
     utsEponModuleBoardCpuUtil OBJECT-TYPE
    		SYNTAX INTEGER         
        MAX-ACCESS  read-only
        STATUS      current
        DESCRIPTION
           "The current cpu util of the board, in the current system, only csm board should be readed, and 
            the value should be from 0 to 1000."
       ::= { utsEponModuleBoardEntry 27 }  	   	   
     
     utsEponModuleBoardMemUtil OBJECT-TYPE
    		SYNTAX INTEGER         
        MAX-ACCESS  read-only
        STATUS      current
        DESCRIPTION
           "The current memory util of the board, in the current system, only csm board should be readed, and 
            the value should be from 0 to 1000."
       ::= { utsEponModuleBoardEntry 28 }
     
--
--  epon configuration management system group
--

utsManagementConfExt OBJECT IDENTIFIER ::= { utsSystemExtObjects 4 }

utsSystemConfGroup OBJECT IDENTIFIER ::= { utsManagementConfExt 1 }

utsFTPConfGroup OBJECT IDENTIFIER ::= { utsManagementConfExt 2 }

utsFileSystemGroup OBJECT IDENTIFIER ::= { utsManagementConfExt 3 }

utsChassisConfGroup OBJECT IDENTIFIER ::= { utsManagementConfExt 4 }

utsTFTPConfGroup OBJECT IDENTIFIER ::= { utsManagementConfExt 5 }   

utsLedMgmtConfExt OBJECT IDENTIFIER ::= { utsManagementConfExt 6 }

--  BBS Chassis System Configuration
--
utsBBSChassisPwrType OBJECT-TYPE
        SYNTAX INTEGER
        {
            ac(1),    -- read-only status.
            dc(2)  -- read-only status.
        }
        MAX-ACCESS read-only
        STATUS  current
        DESCRIPTION
            "bbs power supply module type, AC or DC."
        ::= { utsChassisConfGroup 1 }
        
utsBBSChassisPwrLowSlot OBJECT-TYPE
        SYNTAX INTEGER
        {
            empty(1),
            installed-not-work(2),
            installed-and-work(3)
        }
        MAX-ACCESS read-only
        STATUS current
        DESCRIPTION
            "whether the chassis power module in low slot exist and work normally"
        ::= { utsChassisConfGroup 2 }

utsBBSChassisPwrHighSlot OBJECT-TYPE
        SYNTAX INTEGER
        {
            empty(1),
            installed-not-work(2),
            installed-and-work(3)
        }
        MAX-ACCESS read-only
        STATUS current
        DESCRIPTION
            "whether the chassis power module in high slot exist and work normally"
        ::= { utsChassisConfGroup 3 }
        
utsBBSChassisInternalPowerStat OBJECT-TYPE
        SYNTAX INTEGER
        {
            normal(1),
	          abnormal(2)
        }
        MAX-ACCESS read-only
        STATUS current
        DESCRIPTION
            "chassis the system power module status, such as over voltage, low voltage, etc"
        ::= { utsChassisConfGroup 4 }

utsBBSChassisFanTrayStat OBJECT-TYPE
        SYNTAX INTEGER
        {
            normal  (1),
            abnormal (2)
        }
        MAX-ACCESS read-only
        STATUS current
        DESCRIPTION
            "whether the chassis Fan tray module exist"
        ::= { utsChassisConfGroup 5 }

-- Deleted by Zhaoxf Dec 10, 2006
        
-- utsBBSChassisTempCur OBJECT-TYPE
--        SYNTAX INTEGER
--        MAX-ACCESS read-only
--        STATUS current
--        DESCRIPTION
--            "chassis CURRENT temperature "
--        ::= { utsChassisConfGroup 6 }
        
-- utsBBSChassisTempUpLimit OBJECT-TYPE
--      SYNTAX INTEGER
--        MAX-ACCESS read-write
--        STATUS current
--        DESCRIPTION
--            "the threshold of chassis module temperature"
--        ::= { utsChassisConfGroup 7 }
        
utsBBSChassisLeftFanTrayStat OBJECT-TYPE
        SYNTAX INTEGER
        {
            empty(1),
            installed-not-work(2),
            installed-and-work(3)
        }
        MAX-ACCESS read-only
        STATUS current
        DESCRIPTION
            "The state of left fan."
        ::= { utsChassisConfGroup 8 }
        
utsBBSChassisMiddleFanTrayStat OBJECT-TYPE
        SYNTAX INTEGER
        {            
            empty(1),
            installed-not-work(2),
            installed-and-work(3)
        }
        MAX-ACCESS read-only
        STATUS current
        DESCRIPTION
            "The state of middle fan."
        ::= { utsChassisConfGroup 9 }
        
utsBBSChassisRightFanTrayStat OBJECT-TYPE
        SYNTAX INTEGER
        {
        		empty(1),
            installed-not-work(2),
            installed-and-work(3)
        }
        MAX-ACCESS read-only
        STATUS current
        DESCRIPTION
            "The state of right fan"
        ::= { utsChassisConfGroup 10 }     
        
--
-- BBS4000 LED state display mib definition
--

utsLedCSMLedDispGroup OBJECT IDENTIFIER ::= { utsLedMgmtConfExt 1 }

--
-- BBS4000 chassis LED state display mib group
--

   utsBBSLEDCSMAPowerLedState OBJECT-TYPE
        SYNTAX INTEGER
        {
            green-on(1),    -- Power on.
            green-off(2)    -- Power off.
        }
        MAX-ACCESS read-only
        STATUS  current
        DESCRIPTION
            "bbs LED state display: CSM A power LED."
        ::= { utsLedCSMLedDispGroup 1 }

   utsBBSLEDCSMAActiveLedState OBJECT-TYPE
        SYNTAX INTEGER
        {
            green-on(1),    -- Modular is active.
            green-off(2)    -- Modular is standby.
        }
        MAX-ACCESS read-only
        STATUS  current
        DESCRIPTION
            "bbs LED state display: CSM A Active LED."
        ::= { utsLedCSMLedDispGroup 2 }   
  
  utsBBSLEDCSMARunLedState OBJECT-TYPE
        SYNTAX INTEGER
        {
            green-on(1),    -- Modular Operation is normal.
            green-off(2),   -- Modular is not run.
            flashing(3)     -- Modular is in initiation stage.
        }
        MAX-ACCESS read-only
        STATUS  current
        DESCRIPTION
            "bbs LED state display: CSM A Run LED."
        ::= { utsLedCSMLedDispGroup 3 }
  
  utsBBSLEDCSMACriticalAlarmLedState OBJECT-TYPE
        SYNTAX INTEGER
        {
            red-on(1),    -- Modular has critical alarm.
            red-off(2)    -- Modular has not critical alarm.
        }
        MAX-ACCESS read-only
        STATUS  current
        DESCRIPTION
            "bbs LED state display: CSM A Critical Alarm LED."
        ::= { utsLedCSMLedDispGroup 4 }

  utsBBSLEDCSMAMajorAlarmLedState OBJECT-TYPE
        SYNTAX INTEGER
        {
            red-on(1),    -- Modular has major alarm.
            red-off(2)    -- Modular has not major alarm.
        }
        MAX-ACCESS read-only
        STATUS  current
        DESCRIPTION
            "bbs LED state display: CSM A Major Alarm LED."
        ::= { utsLedCSMLedDispGroup 5 }
        
  utsBBSLEDCSMAMinorAlarmLedState OBJECT-TYPE
        SYNTAX INTEGER
        {
            yellow-on(1),    -- Modular has minor alarm.
            yellow-off(2)   -- Modular has not minor alarm.
        }
        MAX-ACCESS read-only
        STATUS  current
        DESCRIPTION
            "bbs LED state display: CSM A Minor Alarm LED."
        ::= { utsLedCSMLedDispGroup 6 } 
   
  utsBBSLEDCSMAHotSwapLedState OBJECT-TYPE
        SYNTAX INTEGER
        {
            yellow-on(1),    -- Modular Can Be Unplugged.
            yellow-off(2),   -- Modular Can Not Unplugged.
            flashing(3)      -- Module Is Waiting For Host to Confirm Unplug request
        }
        MAX-ACCESS read-only
        STATUS  current
        DESCRIPTION
            "bbs LED state display: CSM A Hot Swap LED."
        ::= { utsLedCSMLedDispGroup 7 } 
  
  utsBBSLEDCSMAEmsPortLinkLedState OBJECT-TYPE
        SYNTAX INTEGER
        {
            green-on(1),    -- Link is on.
            green-off(2),   -- Link is off.
            flashing(3)     -- Transmitting/Receiving activity.
        }
        MAX-ACCESS read-only
        STATUS  current
        DESCRIPTION
            "bbs LED state display: CSM A Ems Port Link LED."
        ::= { utsLedCSMLedDispGroup 8 } 
  
  utsBBSLEDCSMAEmsPortSpeedLedState OBJECT-TYPE
        SYNTAX INTEGER
        {
            yellow-on(1),    -- 100M Speed.
            yellow-off(2)    -- 10M Speed.            
        }
        MAX-ACCESS read-only
        STATUS  current
        DESCRIPTION
            "bbs LED state display: CSM A Ems Port Speed LED."
        ::= { utsLedCSMLedDispGroup 9 }   
        
  utsBBSLEDCSMBPowerLedState OBJECT-TYPE
        SYNTAX INTEGER
        {
            green-on(1),    -- Power on.
            green-off(2)    -- Power off.
        }
        MAX-ACCESS read-only
        STATUS  current
        DESCRIPTION
            "bbs LED state display: CSM B power LED."
        ::= { utsLedCSMLedDispGroup 10 }

   utsBBSLEDCSMBActiveLedState OBJECT-TYPE
        SYNTAX INTEGER
        {
            green-on(1),    -- Modular is active.
            green-off(2)    -- Modular is standby.
        }
        MAX-ACCESS read-only
        STATUS  current
        DESCRIPTION
            "bbs LED state display: CSM B Active LED."
        ::= { utsLedCSMLedDispGroup 11 }   
  
  utsBBSLEDCSMBRunLedState OBJECT-TYPE
        SYNTAX INTEGER
        {
            green-on(1),    -- Modular Operation is normal.
            green-off(2),   -- Modular is not run.
            flashing(3)     -- Modular is in initiation stage.
        }
        MAX-ACCESS read-only
        STATUS  current
        DESCRIPTION
            "bbs LED state display: CSM B Run LED."
        ::= { utsLedCSMLedDispGroup 12 }
  
  utsBBSLEDCSMBCriticalAlarmLedState OBJECT-TYPE
        SYNTAX INTEGER
        {
            red-on(1),    -- Modular has critical alarm.
            red-off(2)    -- Modular has not critical alarm.
        }
        MAX-ACCESS read-only
        STATUS  current
        DESCRIPTION
            "bbs LED state display: CSM B Critical Alarm LED."
        ::= { utsLedCSMLedDispGroup 13 }

  utsBBSLEDCSMBMajorAlarmLedState OBJECT-TYPE
        SYNTAX INTEGER
        {
            red-on(1),    -- Modular has major alarm.
            red-off(2)    -- Modular has not major alarm.
        }
        MAX-ACCESS read-only
        STATUS  current
        DESCRIPTION
            "bbs LED state display: CSM B Major Alarm LED."
        ::= { utsLedCSMLedDispGroup 14 }
        
  utsBBSLEDCSMBMinorAlarmLedState OBJECT-TYPE
        SYNTAX INTEGER
        {
            yellow-on(1),    -- Modular has minor alarm.
            yellow-off(2)   -- Modular has not minor alarm.
        }
        MAX-ACCESS read-only
        STATUS  current
        DESCRIPTION
            "bbs LED state display: CSM B Minor Alarm LED."
        ::= { utsLedCSMLedDispGroup 15 } 
   
  utsBBSLEDCSMBHotSwapLedState OBJECT-TYPE
        SYNTAX INTEGER
        {
            yellow-on(1),    -- Modular Can Be Unplugged.
            yellow-off(2),   -- Modular Can Not Unplugged.
            flashing(3)      -- Module Is Waiting For Host to Confirm Unplug request
        }
        MAX-ACCESS read-only
        STATUS  current
        DESCRIPTION
            "bbs LED state display: CSM B Hot Swap LED."
        ::= { utsLedCSMLedDispGroup 16 } 
  
  utsBBSLEDCSMBEmsPortLinkLedState OBJECT-TYPE
        SYNTAX INTEGER
        {
            green-on(1),    -- Link is on.
            green-off(2),   -- Link is off.
            flashing(3)     -- Transmitting/Receiving activity.
        }
        MAX-ACCESS read-only
        STATUS  current
        DESCRIPTION
            "bbs LED state display: CSM B Ems Port Link LED."
        ::= { utsLedCSMLedDispGroup 17 } 
  
  utsBBSLEDCSMBEmsPortSpeedLedState OBJECT-TYPE
        SYNTAX INTEGER
        {
            yellow-on(1),    -- 100M Speed.
            yellow-off(2)    -- 10M Speed.            
        }
        MAX-ACCESS read-only
        STATUS  current
        DESCRIPTION
            "bbs LED state display: CSM B Ems Port Speed LED."
        ::= { utsLedCSMLedDispGroup 18 }

--
--  pon slot led state display table
--

utsLedPonSlotLedDispObjs OBJECT IDENTIFIER ::= { utsLedMgmtConfExt 2 }

    utsLedPonSlotLedDispTable  OBJECT-TYPE
        SYNTAX      SEQUENCE OF UtsLedPonSlotLedDispEntry
        MAX-ACCESS  not-accessible
        STATUS      current
        DESCRIPTION
            "bbs system PON slot LED state display table."
       ::= { utsLedPonSlotLedDispObjs 1 }

utsLedPonSlotLedDispEntry OBJECT-TYPE
   SYNTAX       UtsLedPonSlotLedDispEntry
   MAX-ACCESS   not-accessible
       STATUS       current
       DESCRIPTION
          "An entry containing led state information of a pon slot."
      INDEX { utsLedPonSlotLedDispSlotId }
      ::= { utsLedPonSlotLedDispTable 1 }

     UtsLedPonSlotLedDispEntry ::=
        SEQUENCE {
            utsLedPonSlotLedDispSlotId
                INTEGER,
            utsLedPonSlotLedDispPowLedStat
                INTEGER,
            utsLedPonSlotLedDispRunLedStat
                INTEGER,
	        utsLedPonSlotLedDispFaultLedStat
                INTEGER,
            utsLedPonSlotLedDispSwapLedStat
                INTEGER,
            utsLedPonSlotLedDispPonPort1OprLedStat
                INTEGER,
            utsLedPonSlotLedDispPonPort1FaultLedStat
                INTEGER,
	    	utsLedPonSlotLedDispPonPort2OprLedStat
			 	INTEGER,
			utsLedPonSlotLedDispPonPort2FaultLedStat
			 	INTEGER,
            utsLedPonSlotLedDispPonPort3OprLedStat
                INTEGER,
            utsLedPonSlotLedDispPonPort3FaultLedStat
                INTEGER,
            utsLedPonSlotLedDispPonPort4OprLedStat
                INTEGER,
            utsLedPonSlotLedDispPonPort4FaultLedStat
                INTEGER					
       }
 	  
    utsLedPonSlotLedDispSlotId OBJECT-TYPE
        SYNTAX      INTEGER
        MAX-ACCESS  read-only
        STATUS      current
        DESCRIPTION
           "A read-only value that identifies the pon module slot id."	
       ::= { utsLedPonSlotLedDispEntry 1 }

    utsLedPonSlotLedDispPowLedStat OBJECT-TYPE
        SYNTAX      INTEGER
        {
          green-on(1),
          green-off(2)
        }
        MAX-ACCESS  read-only
        STATUS      current
        DESCRIPTION
           "pon slot power supply LED state."	
       ::= { utsLedPonSlotLedDispEntry 2 } 
    
    utsLedPonSlotLedDispRunLedStat OBJECT-TYPE
        SYNTAX      INTEGER
        {
          green-on(1),    -- Modular Operation is normal.
          green-off(2),   -- Modular is not run.
          flashing(3)     -- Modular is in initiation stage.
        }
        MAX-ACCESS  read-only
        STATUS      current
        DESCRIPTION
           "pon slot run LED state."	
       ::= { utsLedPonSlotLedDispEntry 3 }    

    utsLedPonSlotLedDispFaultLedStat OBJECT-TYPE
        SYNTAX      INTEGER
        {
          red-on(1),
          red-off(2)
        }
        MAX-ACCESS  read-only
        STATUS      current
        DESCRIPTION
           "pon slot fault LED state."	
       ::= { utsLedPonSlotLedDispEntry 4 }

    utsLedPonSlotLedDispSwapLedStat OBJECT-TYPE
        SYNTAX      INTEGER
        {
            yellow-on(1),    -- Modular Can Be Unplugged.
            yellow-off(2),   -- Modular Can Not Unplugged.
            flashing(3)      -- Module Is Waiting For Host to Confirm Unplug request
        }
        MAX-ACCESS  read-only
        STATUS      current
        DESCRIPTION
           "pon slot hot swap LED state."	
       ::= { utsLedPonSlotLedDispEntry 5 }

    utsLedPonSlotLedDispPonPort1OprLedStat OBJECT-TYPE
        SYNTAX      INTEGER
        {
          green-on(1),      -- OLT Operation Is ON
          green-off(2),     -- OLT Operation Is OFF
          flashing(3)       -- OLT Is Under Test
        }
        MAX-ACCESS  read-only
        STATUS      current
        DESCRIPTION
           "pon slot pon port 1 Operation LED state."	
       ::= { utsLedPonSlotLedDispEntry 6 }
       
    utsLedPonSlotLedDispPonPort1FaultLedStat OBJECT-TYPE
        SYNTAX      INTEGER
        {
          red-on(1),      -- OLT Internal Fail Indication
          red-off(2)      -- OLT Operation Is Normal          
        }
        MAX-ACCESS  read-only
        STATUS      current
        DESCRIPTION
           "pon slot pon port 1 Fault LED state."	
       ::= { utsLedPonSlotLedDispEntry 7 } 
       
    utsLedPonSlotLedDispPonPort2OprLedStat OBJECT-TYPE
        SYNTAX      INTEGER
        {
          green-on(1),      -- OLT Operation Is ON
          green-off(2),     -- OLT Operation Is OFF
          flashing(3)       -- OLT Is Under Test
        }
        MAX-ACCESS  read-only
        STATUS      current
        DESCRIPTION
           "pon slot pon port 2 Operation LED state."	
       ::= { utsLedPonSlotLedDispEntry 8 }
       
    utsLedPonSlotLedDispPonPort2FaultLedStat OBJECT-TYPE
        SYNTAX      INTEGER
        {
          red-on(1),      -- OLT Internal Fail Indication
          red-off(2)      -- OLT Operation Is Normal          
        }
        MAX-ACCESS  read-only
        STATUS      current
        DESCRIPTION
           "pon slot pon port 2 Fault LED state."	
       ::= { utsLedPonSlotLedDispEntry 9 } 
       
    utsLedPonSlotLedDispPonPort3OprLedStat OBJECT-TYPE
        SYNTAX      INTEGER
        {
          green-on(1),      -- OLT Operation Is ON
          green-off(2),     -- OLT Operation Is OFF
          flashing(3)       -- OLT Is Under Test
        }
        MAX-ACCESS  read-only
        STATUS      current
        DESCRIPTION
           "pon slot pon port 3 Operation LED state."	
       ::= { utsLedPonSlotLedDispEntry 10 }
       
    utsLedPonSlotLedDispPonPort3FaultLedStat OBJECT-TYPE
        SYNTAX      INTEGER
        {
          red-on(1),      -- OLT Internal Fail Indication
          red-off(2)      -- OLT Operation Is Normal          
        }
        MAX-ACCESS  read-only
        STATUS      current
        DESCRIPTION
           "pon slot pon port 3 Fault LED state."	
       ::= { utsLedPonSlotLedDispEntry 11 }
       
    utsLedPonSlotLedDispPonPort4OprLedStat OBJECT-TYPE
        SYNTAX      INTEGER
        {
          green-on(1),      -- OLT Operation Is ON
          green-off(2),     -- OLT Operation Is OFF
          flashing(3)       -- OLT Is Under Test
        }
        MAX-ACCESS  read-only
        STATUS      current
        DESCRIPTION
           "pon slot pon port 4 Operation LED state."	
       ::= { utsLedPonSlotLedDispEntry 12 }
       
    utsLedPonSlotLedDispPonPort4FaultLedStat OBJECT-TYPE
        SYNTAX      INTEGER
        {
          red-on(1),      -- OLT Internal Fail Indication
          red-off(2)      -- OLT Operation Is Normal          
        }
        MAX-ACCESS  read-only
        STATUS      current
        DESCRIPTION
           "pon slot pon port 4 Fault LED state."	
       ::= { utsLedPonSlotLedDispEntry 13 }     
       
--
--  GE port slot led state display table
--

utsLedGEPortSlotLedDispObjs OBJECT IDENTIFIER ::= { utsLedMgmtConfExt 3 }

    utsLedGEPortSlotLedDispTable  OBJECT-TYPE
        SYNTAX      SEQUENCE OF UtsLedGEPortSlotLedDispEntry
        MAX-ACCESS  not-accessible
        STATUS      current
        DESCRIPTION
            "bbs system GE Port slot LED state display table."
       ::= { utsLedGEPortSlotLedDispObjs 1 }

utsLedGEPortSlotLedDispEntry OBJECT-TYPE
   SYNTAX       UtsLedGEPortSlotLedDispEntry
   MAX-ACCESS   not-accessible
       STATUS       current
       DESCRIPTION
          "An entry containing led state information of a GE port slot."
      INDEX { utsLedGEPortSlotLedDispSlotId }
      ::= { utsLedGEPortSlotLedDispTable 1 }

     UtsLedGEPortSlotLedDispEntry ::=
        SEQUENCE {
            utsLedGEPortSlotLedDispSlotId
                INTEGER,
            utsLedGEPortSlotLedDispPowLedStat
                INTEGER,
            utsLedGEPortSlotLedDispRunLedStat
                INTEGER,
	        utsLedGEPortSlotLedDispFaultLedStat
                INTEGER,
            utsLedGEPortSlotLedDispSwapLedStat
                INTEGER,
            utsLedGEPortSlotLedDispPort1LinkLedStat
                INTEGER,           
	    	utsLedGEPortSlotLedDispPort2LinkLedStat
			 	INTEGER,			
            utsLedGEPortSlotLedDispPort3LinkLedStat
                INTEGER,            
            utsLedGEPortSlotLedDispPort4LinkLedStat
                INTEGER            					
       }
 	  
    utsLedGEPortSlotLedDispSlotId OBJECT-TYPE
        SYNTAX      INTEGER
        MAX-ACCESS  read-only
        STATUS      current
        DESCRIPTION
           "A read-only value that identifies the GE module slot id."	
       ::= { utsLedGEPortSlotLedDispEntry 1 }

    utsLedGEPortSlotLedDispPowLedStat OBJECT-TYPE
        SYNTAX      INTEGER
        {
          green-on(1),
          green-off(2)
        }
        MAX-ACCESS  read-only
        STATUS      current
        DESCRIPTION
           "GE port slot power supply LED state."	
       ::= { utsLedGEPortSlotLedDispEntry 2 } 
    
    utsLedGEPortSlotLedDispRunLedStat OBJECT-TYPE
        SYNTAX      INTEGER
        {
          green-on(1),    -- Modular Operation is normal.
          green-off(2),   -- Modular is not run.
          flashing(3)     -- Modular is in initiation stage.
        }
        MAX-ACCESS  read-only
        STATUS      current
        DESCRIPTION
           "GE port slot run LED state."	
       ::= { utsLedGEPortSlotLedDispEntry 3 }    

    utsLedGEPortSlotLedDispFaultLedStat OBJECT-TYPE
        SYNTAX      INTEGER
        {
          red-on(1),
          red-off(2)
        }
        MAX-ACCESS  read-only
        STATUS      current
        DESCRIPTION
           "GE port slot fault LED state."	
       ::= { utsLedGEPortSlotLedDispEntry 4 }

    utsLedGEPortSlotLedDispSwapLedStat OBJECT-TYPE
        SYNTAX      INTEGER
        {
            yellow-on(1),    -- Modular Can Be Unplugged.
            yellow-off(2),   -- Modular Can Not Unplugged.
            flashing(3)      -- Module Is Waiting For Host to Confirm Unplug request
        }
        MAX-ACCESS  read-only
        STATUS      current
        DESCRIPTION
           "GE port slot hot swap LED state."	
       ::= { utsLedGEPortSlotLedDispEntry 5 }

    utsLedGEPortSlotLedDispPort1LinkLedStat OBJECT-TYPE
        SYNTAX      INTEGER
        {
          green-on(1),      
          green-off(2)      
        }
        MAX-ACCESS  read-only
        STATUS      current
        DESCRIPTION
           "GE slot GE port 1 Link LED state,if the board type is xgm01a,then use this item only."	
       ::= { utsLedGEPortSlotLedDispEntry 6 }   
     
       
    utsLedGEPortSlotLedDispPort2LinkLedStat OBJECT-TYPE
        SYNTAX      INTEGER
        {
          green-on(1),      
          green-off(2)      
        }
        MAX-ACCESS  read-only
        STATUS      current
        DESCRIPTION
           "GE slot GE port 2 Link LED state."	
       ::= { utsLedGEPortSlotLedDispEntry 8 }       
           
    utsLedGEPortSlotLedDispPort3LinkLedStat OBJECT-TYPE
        SYNTAX      INTEGER
        {
          green-on(1),      
          green-off(2)     
        }
        MAX-ACCESS  read-only
        STATUS      current
        DESCRIPTION
           "GE slot GE port 3 Link LED state."	
       ::= { utsLedGEPortSlotLedDispEntry 10 }       
           
    utsLedGEPortSlotLedDispPort4LinkLedStat OBJECT-TYPE
        SYNTAX      INTEGER
        {
          green-on(1),      
          green-off(2)      
        }
        MAX-ACCESS  read-only
        STATUS      current
        DESCRIPTION
           "GE slot GE port 4 Link LED state."	
       ::= { utsLedGEPortSlotLedDispEntry 12 }       


utsHAMgmtConfExt OBJECT IDENTIFIER ::= { utsManagementConfExt 8 }
utsHAMgmtConfObjs OBJECT IDENTIFIER ::= { utsHAMgmtConfExt 1 }
utsHAMgmtConfGroup OBJECT IDENTIFIER ::= { utsHAMgmtConfObjs 1 }

utsHAMgmtManualSwitchOver OBJECT-TYPE
	        SYNTAX INTEGER
	        {
	          switch(1)  -- write only
	        }
	        MAX-ACCESS read-write
	        STATUS  current
	        DESCRIPTION
	            "HA management manual force switch over"
	        ::= { utsHAMgmtConfGroup 1 }   
	        
utsHAMgmtRebootWholeSystem OBJECT-TYPE
	        SYNTAX INTEGER
	        {
	          reboot(1)  -- write only
	        }
	        MAX-ACCESS read-write
	        STATUS  current
	        DESCRIPTION
	            "HA management reboot whole system"
	        ::= { utsHAMgmtConfGroup 2 }    
	        
utsHAMgmtMasterBoardBootFileName OBJECT-TYPE
        SYNTAX DisplayString(SIZE(0..63))
        MAX-ACCESS read-write
        STATUS current
        DESCRIPTION
            "bbs system boot image file name with path for master board"
        ::= { utsHAMgmtConfGroup 3 }

utsHAMgmtSlaveBoardBootFileName OBJECT-TYPE
        SYNTAX DisplayString(SIZE(0..63))
        MAX-ACCESS read-write
        STATUS current
        DESCRIPTION
            "bbs system boot image file name with path for slave board"
        ::= { utsHAMgmtConfGroup 4 }



--
--  BBS System boot Configuration For BBS 4000 only
--
	utsBBSVlanVPNTPID OBJECT-TYPE
	        SYNTAX INTEGER(1..65535)
	        MAX-ACCESS read-write
	        STATUS  current
	        DESCRIPTION
	            "bbs system vlan vpn tpid.The default value is 0x8100"
	        ::= { utsSystemConfGroup 1 }
	
	utsBBSVlanVPNTunnel OBJECT-TYPE
	        SYNTAX INTEGER
	        {
	           enable(1),      
	           disable(2)
	        }
	        MAX-ACCESS read-write
	        STATUS  current
	        DESCRIPTION
            "bbs system vlan vpn tunnle enable/disable, the default value is disable."
           ::= { utsSystemConfGroup 2 }
	        
    utsBBSVlanVPNPRISource OBJECT-TYPE
	        SYNTAX INTEGER
	        {
	           customertag(1),
	           llid(2)
	        }
	        MAX-ACCESS read-only
	        STATUS  current
	        DESCRIPTION
	            "The outer tag PRI source setting, the default value is customertag!"
	        ::= { utsSystemConfGroup 3 }  
	        
	utsBBSMaxFrameSize OBJECT-TYPE
		   SYNTAX  INTEGER (64..16368)
	       MAX-ACCESS  read-write
	       STATUS  current
	       DESCRIPTION
	           "Max receive frame size setting, all the frame size greater than it 
	            will be dropped.  (Max-frame 64-16368). the default value 1518.
	           "
	        ::= { utsSystemConfGroup 4 }

--
--  ethernet interface extersion
--

	utsEthIfExtObjects OBJECT IDENTIFIER ::= { utsEthIfConfExt 1 }

--
--  Layer 2 conf ext
--

	utsLayer2ConfExt	OBJECT IDENTIFIER ::= { utsEthIfExtObjects 5 } 
	
-- 
-- monitor session table BBS 4000 support up to 4 sessions. 
--

	utsMonitorSessionObjects OBJECT IDENTIFIER ::= { utsLayer2ConfExt 3 }
	
	utsMonitorSessionControlTable OBJECT-TYPE
	SYNTAX  SEQUENCE OF UtsMonitorSessionControlEntry
	        MAX-ACCESS  not-accessible
	        STATUS  current
	        DESCRIPTION
			"Table for monitor session MIB objects."
	        ::= { utsMonitorSessionObjects 1 }
	
	utsMonitorSessionControlEntry OBJECT-TYPE
	SYNTAX  UtsMonitorSessionControlEntry
	       MAX-ACCESS  not-accessible
	       STATUS  current
	       DESCRIPTION
		   "An entry in the monitor session control MIB table."
	       INDEX  {utsMonitorSessionID }
	       ::= { utsMonitorSessionControlTable 1 }
	
	UtsMonitorSessionControlEntry ::=
	       SEQUENCE {
	          utsMonitorSessionID                   INTEGER,
	          utsMonitorSessionModule				INTEGER,       
	          utsMonitorSessionPort					INTEGER,
	          utsMonitorSessionIngressPortBitLists	  OCTET STRING,       
	          utsMonitorSessionEngressPortBitLists	  OCTET STRING,
	          utsMonitorSessionActive				INTEGER,       
	          utsMonitorSessionRowStatus              RowStatus	          
	       } 
	
	utsMonitorSessionID OBJECT-TYPE
		SYNTAX  INTEGER(1..4)
		MAX-ACCESS  read-create
		STATUS  current
		DESCRIPTION
			"Monitor session ID."
        ::= { utsMonitorSessionControlEntry 1 } 	
	       
	utsMonitorSessionModule OBJECT-TYPE
		SYNTAX  INTEGER
		MAX-ACCESS  read-write
		STATUS  current
		DESCRIPTION
			"Monitor session control module number."
        ::= { utsMonitorSessionControlEntry 2 }        


   utsMonitorSessionPort OBJECT-TYPE
		SYNTAX  INTEGER
		MAX-ACCESS  read-write
		STATUS  current
		DESCRIPTION
			"Monitor session control port umber."
        ::= { utsMonitorSessionControlEntry 3 }    


   utsMonitorSessionIngressPortBitLists OBJECT-TYPE
		SYNTAX  OCTET STRING
		MAX-ACCESS  read-write
		STATUS  current
		DESCRIPTION
			"Monitor session control ingress port bit lists ."
        ::= { utsMonitorSessionControlEntry 4 }    


   utsMonitorSessionEngressPortBitLists OBJECT-TYPE
		SYNTAX  OCTET STRING
		MAX-ACCESS  read-write
		STATUS  current
		DESCRIPTION
			"Monitor session control ingress port bit lists ."
        ::= { utsMonitorSessionControlEntry 5 }


   utsMonitorSessionActive OBJECT-TYPE
		SYNTAX  INTEGER 
		{
			enable(1),
			disable(2)
		}
		MAX-ACCESS  read-write
		STATUS  current
		DESCRIPTION
			"Monitor session enable or disable."
        ::= { utsMonitorSessionControlEntry 6 }

        
   utsMonitorSessionRowStatus OBJECT-TYPE
			SYNTAX RowStatus
			MAX-ACCESS read-create
			STATUS current
			DESCRIPTION
				"Row status"
			::= { utsMonitorSessionControlEntry 7 }

--
--   ACL extension
--


utsAclExt OBJECT IDENTIFIER ::=  { utsServiceConfExt  2 }

--
--   ACL Profile Table
--
--utsAclExtProfileTable  OBJECT-TYPE
--    SYNTAX       SEQUENCE OF UtsAclExtProfileEntry
--	MAX-ACCESS   not-accessible
--	STATUS       current
--	DESCRIPTION
--	   "A list of ACL Profile information."
--    ::= { utsAclExt 1 }
--	
--utsAclExtProfileEntry OBJECT-TYPE
--    SYNTAX       UtsAclExtProfileEntry
--	MAX-ACCESS   not-accessible
--	STATUS       current
--	DESCRIPTION
--	   "An entry in the ACL MIB extension table."
--	INDEX { utsAclExtProfileId,
-- 		    utsAclExtProfileFieldId,
--	 	    utsAclExtProfileRuleId }
--    ::= { utsAclExtProfileTable 1 }
--
--UtsAclExtProfileEntry ::=
--    SEQUENCE  {
--	utsAclExtProfileId                 			INTEGER,
--	utsAclExtProfileFieldId            			INTEGER,
--	utsAclExtProfileRuleId             			INTEGER,
--	utsAclExtProfileName               			DisplayString,
--    utsAclExtProfileFieldName          			DisplayString,  
--    utsAclExtProfileRuleName           			DisplayString,
--    utsAclExtProfileFieldBitmap        			INTEGER,
--		
--	utsAclExtProfileFieldMaskDstMac          		MacAddress,
--	utsAclExtProfileFieldMaskSrcMac          		MacAddress,
--    utsAclExtProfileFieldMaskArpTargetMac			MacAddress,	
--    utsAclExtProfileFieldMaskArpSendMac     		MacAddress,
--	utsAclExtProfileFieldMaskSrcIp           		IpAddress,
--	utsAclExtProfileFieldMaskDstIp           		IpAddress,
--    utsAclExtProfileFieldMaskVlan           		INTEGER,
--	utsAclExtProfileFieldMaskEtherType       		INTEGER,
--	
--   for BBS1000/1000+ only
--	utsAclExtProfileFieldMaskTcpSrcPort      		INTEGER,
--	utsAclExtProfileFieldMaskTcpDstPort      		INTEGER,  
--   1000 end
--
--   for BBS4000 only	
--	utsAclExtProfileFieldMaskSrcPortMin        	INTEGER,
--	utsAclExtProfileFieldMaskSrcPortMax        	INTEGER,
--	utsAclExtProfileFieldMaskDstPortMin        	INTEGER,
--	utsAclExtProfileFieldMaskDstPortMax        	INTEGER,
--   	4000 end
--
--	utsAclExtProfileFieldMaskTagPri          		INTEGER,
--	utsAclExtProfileFieldMaskDscp            		INTEGER,
--	utsAclExtProfileFieldMaskProtocol        		INTEGER,
--   zhaoxf modified Dec 11,2006
--  	utsAclExtProfileFieldMaskNewDscp         		INTEGER,
--  	utsAclExtProfileFieldMaskNewTagPri       		INTEGER,
--  	utsAclExtProfileFieldMaskNewRateLimit    		INTEGER,
--  	utsAclExtProfileFieldMaskAction          		INTEGER,
--    utsAclExtProfileFieldMaskIHL	                INTEGER, 
--    utsAclExtProfileFieldMaskFragmentOffset       INTEGER,
--    
--	utsAclExtProfileRuleValDstMac            	MacAddress,
--	utsAclExtProfileRuleValSrcMac            	MacAddress,
--    utsAclExtProfileRuleValArpTargetMac	 		MacAddress,
--    utsAclExtProfileRuleValArpSendMac        	MacAddress,
--	utsAclExtProfileRuleValSrcIp             	IpAddress,
--	utsAclExtProfileRuleValDstIp             	IpAddress,
--    utsAclExtProfileRuleValVlan              	INTEGER,
--	utsAclExtProfileRuleValEtherType         	INTEGER,
--
--   for BBS1000/1000+ only
--	utsAclExtProfileRuleValTcpSrcPort        	INTEGER,
--	utsAclExtProfileRuleValTcpDstPort        	INTEGER, 
--   end	                 
--
--   for BBS4000 only	
--	utsAclExtProfileRuleValSrcPortMin        	INTEGER,
--	utsAclExtProfileRuleValSrcPortMax        	INTEGER,
--	utsAclExtProfileRuleValDstPortMin        	INTEGER,
--	utsAclExtProfileRuleValDstPortMax        	INTEGER,
--   	4000 end                     
--
--	utsAclExtProfileRuleValTagPri            	INTEGER,
--	utsAclExtProfileRuleValDscp              	INTEGER,
--	utsAclExtProfileRuleValProtocol          	INTEGER,
--	utsAclExtProfileRuleValNewDscp           	INTEGER,
--	utsAclExtProfileRuleValNewTagPri         	INTEGER,
--	utsAclExtProfileRuleValNewbandwidth      	INTEGER,  
--   Added by Zhaoxf Dec 11,2006	
--	utsAclExtProfileRuleValNewBurstSize         INTEGER,
--	utsAclExtProfileRuleValNewOutPort           INTEGER,
--    utsAclExtProfileRuleValNewOutTag            INTEGER,
--    utsAclExtProfileRuleValIHL	                INTEGER, 
--    utsAclExtProfileRuleValFragmentOffset       INTEGER,
--	utsAclExtProfileRuleValAction            	INTEGER
--}
      	
END

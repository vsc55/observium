ARRIS-MOCA-MIB DEFINITIONS ::= BEGIN

IMPORTS
    MODULE-IDENTITY,
    OBJECT-TYPE,
    Unsigned32
        FROM SNMPv2-SMI
    arrisProducts
    FROM ARRIS-MIB
    TruthValue,
    TEXTUAL-CONVENTION
        FROM SNMPv2-TC;
         
arrisMoCAMib MODULE-IDENTITY
    LAST-UPDATED    "201408130000Z" -- August 13, 2014
    ORGANIZATION    "Arris Interactive"
    CONTACT-INFO
  "Donnie Tew
   Postal: Arris Interactive
   3871 Lakefield Drive
   Suite 300
   Suwanee, GA 30024-1242
   U.S.A.
   Phone:  +86 755 26735010 
   E-mail: cici.zhang@arrisi.com"
    DESCRIPTION
      "This MIB module supplies the basic proprietary 
          management objects for ARRIS MoCA devices on DOCSIS 3.0 modems."
          
-- Revision history
    REVISION    "201408130000Z" -- August 13, 2014
    DESCRIPTION
        "modify the description and format of the ArrisMocaChannelMsk bit definitions;
	 modify the description of the arrisMoCAChannelMsk object to match new ArrisMocaChannelMsk bits"
    REVISION    "201308210000Z" -- August 21, 2013
    DESCRIPTION
        "modify the description about ArrisMocaChannelMsk;
         add arrisMoCALOF and arrisMoCAPrimchnOff."
    REVISION    "201308010000Z" -- August 01, 2013
    DESCRIPTION
        "add ArrisMocaChannelMsk instead of ArrisMocaChannelType, 
         add ArrisMocaChannelMsk and ArrisMocaTabooChannelMsk."
    REVISION    "201306260000Z" -- June 26, 2013
    DESCRIPTION
        "Delete mib items:arrisMoCAManualChannel.
	 Change the vlaue of arrisMoCAApplySettings from applySettings to applySettings-Save and applySettings-NoSave "
    REVISION    "201306040000Z" -- June 4, 2012
    DESCRIPTION
        "Delete mib items:arrisMoCATabooEnable and arrisMoCAQoSEnable."
    REVISION    "201211180000Z" -- Nov 18, 2012
    DESCRIPTION
        "Add mib item:arrisMoCAApplySettings." 
    REVISION    "201211040000Z" -- Nov 4, 2012
    DESCRIPTION
        "Add ArrisMocaChannelType.
         Add mib item:arrisMoCAManulChannel.
         Modify mib item:arrisMoCATabooChannel."                                
    REVISION    "201210100000Z" -- Oct 10, 2012
    DESCRIPTION
        "Initial version"
    ::= { arrisProducts  21 }

--
-- Textual Conventions
--

ArrisMocaTabooChannelMsk ::= TEXTUAL-CONVENTION
    STATUS      current
    DESCRIPTION
        "Represent one or more taboo frequency of MoCA channels
        using a bitmask.  Bit 23 is the most significant bit, and bit 0
        is the least significant bit. 
        bit 0   center frequency at 1600 MHz
        bit 1   center frequency at 1575 MHz
        bit 2   center frequency at 1550 MHz
        bit 3   center frequency at 1525 MHz
        bit 4   center frequency at 1500 MHz
        bit 5   center frequency at 1475 MHz
        bit 6   center frequency at 1450 MHz
        bit 7   center frequency at 1425 MHz
        bit 8   center frequency at 1400 MHz
        bit 9   center frequency at 1375 MHz
        bit 10  center frequency at 1350 MHz
        bit 11  center frequency at 1325 MHz
        bit 12  center frequency at 1300 MHz
        bit 13  center frequency at 1275 MHz
        bit 14  center frequency at 1250 MHz
        bit 15  center frequency at 1225 MHz
        bit 16  center frequency at 1200 MHz
        bit 17  center frequency at 1175 MHz
        bit 18  center frequency at 1150 MHz
        bit 19  center frequency at 1125 MHz
        bit 20  center frequency at 1100 MHz
        bit 21  center frequency at 1075 MHz
        bit 22  center frequency at 1050 MHz
        bit 23  center frequency at 1025 MHz"
    SYNTAX      Unsigned32

ArrisMocaChannelMsk ::= TEXTUAL-CONVENTION
    STATUS      current
    DESCRIPTION
        "Represent one or more RF center frequency of MoCA channels
        using a bitmask.  Bit 31 is the most significant bit, and bit 0
        is the least significant bit. Not all bits are valid MoCA
        channels. Only bits 0 and 1 are currently used.
        bit 0  center frequency at 1600 MHz         
        bit 1  center frequency at 1625 MHz"
    SYNTAX      Unsigned32

arrisMoCAConfiguration OBJECT IDENTIFIER ::= { arrisMoCAMib 1 }

arrisMoCAChannelSelMethod OBJECT-TYPE
    SYNTAX      INTEGER { scan(1), manual(2) }
    MAX-ACCESS  read-write
    STATUS      current
    DESCRIPTION
        "Channel selection method on the MoCA network.
         If this value is 'scan(1)', scan selection;
         If this value is 'manual(2)', manual selection.
         Default methed is scan select"
    DEFVAL      { 1 }
    ::= { arrisMoCAConfiguration 1 }
    
arrisMoCAChannelMsk OBJECT-TYPE
    SYNTAX      ArrisMocaChannelMsk
    MAX-ACCESS  read-write
    STATUS      current
    DESCRIPTION
        "Specify a list of RF center frequencies represented by a
 	       bitmask which this MoCA node is allowed to form or join a MoCA
 	       network.
 	
 	       If the new list of frequencies does not contain the frequency
 	       this MoCA node is tuned to, this node must drop from the
 	       network.
 	       
         This MIB extends the range of center frequencies for MoCA 2.0 not supported by mocaIfChannelMask.
	 To select MoCA 1.1/2.0 frequencies from 800 MHz to 1575 MHz, please set mocaIfChannelMask also.
         bit 0  center frequency at 1600 MHz
         bit 1  center frequency at 1625 MHz"
    DEFVAL      { 1 }
    ::= { arrisMoCAConfiguration 2 }

arrisMoCATabooChannel OBJECT-TYPE
    SYNTAX      ArrisMocaTabooChannelMsk
    MAX-ACCESS  read-write
    STATUS      current
    DESCRIPTION
        "Indicate the list of taboo channels in this MoCA network
        represented as a bitmask.

        The range of mocaIfTabooChannelMask cannot cover all the taboo channels of moca2.0 supported, so extend this mib.
        The allowed Taboo Mask range is from 1025 to 1600 MHz.
				Bit 0: 1600
				Bit 1: 1575
				......
				Bit 23: 1025
				
        If this interface is not sending or receiving beacon, or there
        is no taboo channel in this MoCA network, report a value of
        '0'."
    DEFVAL      { 0 }
    ::= { arrisMoCAConfiguration 4 }
    
arrisMoCALOF OBJECT-TYPE
    SYNTAX      INTEGER { d1(1150), 
                          d2(1200),
                          d3(1250),
                          d4(1300),
                          d5(1350),
                          d6(1400),
                          d7(1450),
                          d8(1500),
                          d9(1550),
                          d10(1600) }
    MAX-ACCESS  read-write
    STATUS      current
    DESCRIPTION
        "Indicate the MoCA channel in MHz this interface is tuned to when it was last in the 'linkUp' state.
         The range of LOF is from 1150 to 1600, the value of it should in the range of 'arrisMoCAChannelMsk'."
    DEFVAL      { 1150 }
    ::= { arrisMoCAConfiguration 5 }
    
arrisMoCAPrimchnOff OBJECT-TYPE
    SYNTAX      INTEGER { same(0), 
                          above(1),
                          below(2)}
    MAX-ACCESS  read-write
    STATUS      current
    DESCRIPTION
        "This mib specifies offset of the center frequency of the primary channel relative
         to the beacon frequency.Since the MoCA2.0 channel is 100 MHz wide, the 50MHz wide
         beacon may be located at an offset of 25MHz above, below, or at the center of the
         100 MHz channel.The RF frequency of the beacon is the LOF parameter.
         0: same center frequency as the beacon(LOF) frequency
         1: 25MHz above the beacon(LOF) frequency
         2: 25MHz below the beacon(LOF) frequency "
    DEFVAL      { 0 }
    ::= { arrisMoCAConfiguration 6 }
    
arrisMoCAApplySettings OBJECT-TYPE
     SYNTAX      INTEGER { unknown(0), applySettings-Save(1),applySettings-NoSave(2) }
     MAX-ACCESS  read-write
     STATUS      current
     DESCRIPTION "This applies settings for the all MoCA MIB. After setting value, MoCA module will be restarted"
     ::= { arrisMoCAMib 2 }
     
END

ARRIS-HOT-PROTECTION-MODE-MIB DEFINITIONS ::= BEGIN

IMPORTS
   MODULE-IDENTITY, OBJECT-TYPE, Integer32, Counter32
      FROM SNMPv2-SMI
   arrisProdIdCM
      FROM ARRIS-MIB;

   arrisHorizOvertempProtModeMib MODULE-IDENTITY
      LAST-UPDATED    "201410010000Z" -- October 1, 2014 
      ORGANIZATION    "ARRIS Broadband"
      CONTACT-INFO    "ARRIS
                       Postal: ARRIS Broadband
                       3871 Lakefield Drive
                       Suite 300
                       Suwanee, GA 30024-1242
                       U.S.A.
                       Phone: 
                       E-mail: "
      DESCRIPTION
       "This MIB module supplies the basic management objects for the 
        Horizontal Over-Temperature feature."
    
      -- Revision history
        REVISION "201409050000Z" -- September 05, 2014
              DESCRIPTION
              "First release of ARRIS Horizontal Over-Temperature Protection Mode MIB."
        REVISION "201409240000Z" -- September 24, 2014
              DESCRIPTION
              "Corrected arrisHorizOvertempProtModeCount SYNTAX and DESCRIPTION, and updated default value
              of arrisHorizOvertempProtModeNormalOpRecoveryTemp."
        REVISION "201410010000Z" -- October 1, 2014
              DESCRIPTION
              "Added Counter32 to IMPORTS, modified mib file DESCRIPTION, defined arrisProdIdCM leaf to 16,
	      and defined a valid range from 15 to 65 for all temperature thresholds"
::= { arrisProdIdCM 16 }

arrisHorizOvertempProtModeMibObjects OBJECT IDENTIFIER ::= { arrisHorizOvertempProtModeMib 1 }
arrisHorizOvertempProtModeMonitoring OBJECT IDENTIFIER ::= { arrisHorizOvertempProtModeMibObjects 1 }
arrisHorizOvertempProtModeConfiguration OBJECT IDENTIFIER ::= { arrisHorizOvertempProtModeMibObjects 2 }


arrisHorizOvertempProtModeState OBJECT-TYPE
	SYNTAX      INTEGER { normal(1),
	                      thresholdExceededHOTPTier1(2),
	                      thresholdExceededHOTPTier2(3)
	                    }
	MAX-ACCESS  read-only
	STATUS      current
	DESCRIPTION "Indicates the current thermal state. The value 'normal(1)'
	             indicates the device is operating within the normal
	             temperature range and not running in Horizontal
	             Over-Temperature Protection Mode. The value 
	             'thresholdExceededHOTPTier1(2)' indicates the device exceeded
	             the maximum normal operating temperature and is in Tier 1
	             Horizontal Over-Temperature Protection Mode.  The value
	             'thresholdExceededHOTPTier2(3)' indicates the device exceeded
	             the maximum Tier 1 operating temperature and is in 
	             Tier 2 Horizontal Over-Temperature Protection Mode."
	::= { arrisHorizOvertempProtModeMonitoring 1 }

arrisHorizOvertempProtModeCount OBJECT-TYPE
	SYNTAX      Counter32
	MAX-ACCESS  read-only
	STATUS      current
	DESCRIPTION "Indicates the number of times the device has exceeded the
	             maximum temperature threshold and gone into Tier2 Horizontal
	             Over-Temperature Protection Mode.  This value is persistent
	             and only cleared by a restore to factory defaults."
	::= { arrisHorizOvertempProtModeMonitoring 2 }

arrisHorizOvertempProtModeTier1MinThreshold OBJECT-TYPE
	SYNTAX      Integer32 (15..65)
	MAX-ACCESS  read-write
	STATUS      current
	DESCRIPTION "Minimum temperature in Celcius that triggers device to
	             switch from normal operation to Tier 1 Over-Temperature
	             Protection Mode operation." 
	DEFVAL { 37 } 
	::= { arrisHorizOvertempProtModeConfiguration 1 }

arrisHorizOvertempProtModeTier1MaxThreshold OBJECT-TYPE
	SYNTAX      Integer32 (15..65)
	MAX-ACCESS  read-write
	STATUS      current
	DESCRIPTION "Maximum temperature in Celcius that the device continues
	             to operate in Tier 1 Over-Temperature Protection Mode before
	             switching to Tier 2 Over-Temperature Protection Mode
	             operation." 
	DEFVAL { 47 } 
	::= { arrisHorizOvertempProtModeConfiguration 2 } 
	
arrisHorizOvertempProtModeNormalOpRecoveryTemp OBJECT-TYPE
	SYNTAX      Integer32 (15..65)
	MAX-ACCESS  read-write
	STATUS      current
	DESCRIPTION "Temperature in Celcius that the device recovers back
	             to normal operation after being in Tier 1 Over-Temperature 
	             Protection Mode." 
	DEFVAL { 33 } 
	::= { arrisHorizOvertempProtModeConfiguration 3 }

END

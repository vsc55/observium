QTECH-GBNPlatformOAMSsh-MIB DEFINITIONS ::= BEGIN

    IMPORTS
        MODULE-IDENTITY, OBJECT-TYPE,
        Counter32, Gauge32,
        Unsigned32, Integer32,
        IpAddress, NOTIFICATION-TYPE            FROM SNMPv2-SMI

        RowStatus, TruthValue, 
        DisplayString, MacAddress               FROM SNMPv2-TC
        
        MODULE-COMPLIANCE, OBJECT-GROUP         FROM SNMPv2-CONF
        
        snmpTraps                               FROM SNMPv2-MIB
        
        gbnPlatformOAM                          FROM QTECH-GBNPlatformOAM-MIB;
    
    gbnPlatformOAMSsh  MODULE-IDENTITY
        LAST-UPDATED    "0505250000Z"  -- May 25, 2005
        ORGANIZATION    "QTECH LLC"
        CONTACT-INFO    "Basil Budko
                         E-mail: budko@qtech.ru"

        DESCRIPTION     "Ssh mib definition."

        REVISION        "0505250000Z"  -- May 25, 2005
        DESCRIPTION     "Initial MIB creation."

        ::= { gbnPlatformOAM 11 }
        
    sshVersion OBJECT-TYPE
        SYNTAX INTEGER {
            v1(1),
            v2(2)
        }
        MAX-ACCESS read-only
        STATUS current
        DESCRIPTION
            "SSH version."
            --SSH 版本。
        ::= { gbnPlatformOAMSsh 1 }

	sshState OBJECT-TYPE
        SYNTAX INTEGER {
            enable(1),
            disable(2)
        }
        MAX-ACCESS read-write
        STATUS current
        DESCRIPTION
            "enable or disable SSH."
            --打开或关闭SSH功能。
        ::= { gbnPlatformOAMSsh 2 } 

	sshKeyAvailable OBJECT-TYPE
        SYNTAX INTEGER {
            available(1),
            unavailable(2)
        }
        MAX-ACCESS read-only
        STATUS current
        DESCRIPTION
            "SSH key file state."
            --SSH密钥文件状态: 已从Flash中加载密钥文件则状态为available，否则为unavailable。
        ::= { gbnPlatformOAMSsh 3 }         
                                           
   END

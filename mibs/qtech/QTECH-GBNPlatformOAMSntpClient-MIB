QTECH-GBNPlatformOAMSntpClient-MIB DEFINITIONS ::= BEGIN

    IMPORTS
        MODULE-IDENTITY, OBJECT-TYPE,
        Counter32, Gauge32,
        Unsigned32, Integer32,
        IpAddress                               FROM SNMPv2-SMI

        RowStatus, TruthValue, 
        DisplayString, MacAddress               FROM SNMPv2-TC
        
        MODULE-COMPLIANCE, OBJECT-GROUP         FROM SNMPv2-CONF
        
        gbnPlatformOAM                          FROM QTECH-GBNPlatformOAM-MIB;
 
   
    gbnPlatformOAMSntpClient  MODULE-IDENTITY
        LAST-UPDATED    "0107152004Z"  -- July 15, 2004
        ORGANIZATION    "QTECH LLC"
        CONTACT-INFO    "Basil Budko
                         E-mail: budko@qtech.ru"

        DESCRIPTION     "SNTP mib definition."

        REVISION        "0107152004Z"  -- July 15, 2004
        DESCRIPTION     "Initial MIB creation."

        ::= { gbnPlatformOAM 8 }

------------------------------------------------------------------------------
------------------------------------------------------------------------------     
--  sntpClientGeneral:
------------------------------------------------------------------------------

    sntpClientGeneral         OBJECT IDENTIFIER ::= { gbnPlatformOAMSntpClient 1 }  
    
    sntpClientMode OBJECT-TYPE
       SYNTAX  INTEGER  {
                        unicast (1),
                        anycast(2),
                        broadcast(4),
                        multicast(8) }
        MAX-ACCESS  read-write
        STATUS  current
        DESCRIPTION
            "SNTP客户端的工作方式"   
        DEFVAL  { broadcast }            
        ::= { sntpClientGeneral 1 }  
        
    sntpClientPollInterval OBJECT-TYPE
        SYNTAX INTEGER( 64..1024 )
        MAX-ACCESS  read-write
        STATUS  current
        DESCRIPTION
            "发送请求的间隔，用于单播和任意播方式"      
        DEFVAL  { 1000 }                 
        ::= { sntpClientGeneral 2 }              
       
    sntpClientRetransInterval OBJECT-TYPE
        SYNTAX INTEGER( 1..30 )
        MAX-ACCESS  read-write
        STATUS  current
        DESCRIPTION
            "客户端重传请求的间隔"    
        DEFVAL  { 5 }                 
        ::= { sntpClientGeneral 3 }  
        
    sntpClientRetransTimes OBJECT-TYPE
        SYNTAX INTEGER( 0..10 )
        MAX-ACCESS  read-write
        STATUS  current
        DESCRIPTION
            "客户端没有收到回应时，重传请求的次数，用于单播和任意播方式"   
        DEFVAL  { 0 }            
        ::= { sntpClientGeneral 4 }       
        
    sntpClientServer OBJECT-TYPE
        SYNTAX IpAddress
        MAX-ACCESS  read-write
        STATUS  current
        DESCRIPTION
            "正在使用的服务器地址，用于出单播和任意播方式"
        ::= { sntpClientGeneral 5 }  
        
    sntpClientSynthFlag OBJECT-TYPE
        SYNTAX TruthValue
        MAX-ACCESS  read-only
        STATUS  current
        DESCRIPTION
            "客户端的时间是否被同步"
        ::= { sntpClientGeneral 6 }               
        
    sntpClientState OBJECT-TYPE
        SYNTAX INTEGER
        MAX-ACCESS  read-only
        STATUS  current
        DESCRIPTION
            "客户端当前的状态，空闲状态或等待回应报文状态"
        ::= { sntpClientGeneral 7 }  
        
    sntpClientLastSynthTime OBJECT-TYPE
        SYNTAX Integer32
        MAX-ACCESS  read-only
        STATUS  current
        DESCRIPTION
            "客户端最后一次同步的时间"
        ::= { sntpClientGeneral 8 }               
        
    sntpClientLastSynthErrno OBJECT-TYPE
        SYNTAX INTEGER
        MAX-ACCESS  read-only
        STATUS  current
        DESCRIPTION
            "客户端最后一次同步若失败时的错误码。"
        ::= { sntpClientGeneral 9 }      
        
    sntpClientAdminStatus OBJECT-TYPE
        SYNTAX INTEGER{
                     enable(1),
                     disable(2)
                     }
        MAX-ACCESS  read-write
        STATUS  current
        DESCRIPTION
            "客户端打开和关闭状态"
        ::= { sntpClientGeneral 10 }    
        
    sntpClientBcastDelay OBJECT-TYPE
        SYNTAX INTEGER ( 1..9999 )    
        MAX-ACCESS  read-write
        STATUS  current
        DESCRIPTION
            "客户端工作在广播方式下的估计传输延时(毫秒数)"
        ::= { sntpClientGeneral 11 }  
        
     sntpClientMcastTtl OBJECT-TYPE
        SYNTAX INTEGER ( 1..255 )    
        MAX-ACCESS  read-write
        STATUS  current
        DESCRIPTION
            "客户端工作在组播方式下的TTL值"
        ::= { sntpClientGeneral 12 }  
    
      sntpClientAuthFlag OBJECT-TYPE
        SYNTAX TruthValue    
        MAX-ACCESS  read-write
        STATUS  current
        DESCRIPTION
            "authentication enable flag"  
             --认证使能标记，TRUE：打开认证，FALSE：关闭认证--
        ::= { sntpClientGeneral 13 }   
        
      sntpClientUniKeyID OBJECT-TYPE
        SYNTAX Unsigned32    
        MAX-ACCESS  read-write
        STATUS  current
        DESCRIPTION
            "in client/server mode, client send request with this keyID"  
             --在客户端/服务器模式下，客户端发送请求使用的keyID--
        ::= { sntpClientGeneral 14 }         
   
      sntpClientAnyKeyID OBJECT-TYPE
        SYNTAX Unsigned32    
        MAX-ACCESS  read-write
        STATUS  current
        DESCRIPTION
            "in anycast mode, client send request with this keyID"  
             --在任意播模式下，客户端使用广（组）播发送请求使用的keyID--
        ::= { sntpClientGeneral 15 }                   
    
------------------------------------------------------------------------------     
--  sntpValidSrcTable:
------------------------------------------------------------------------------
    
  sntpClientValidServerTable OBJECT-TYPE
        SYNTAX   SEQUENCE OF SntpClientValidServerEntry
        MAX-ACCESS   not-accessible
        STATUS   current
        DESCRIPTION
           "合法服务器网段表，SNTP根据次表检查报文源地址，只有源地址落在这个这个
            表中的报文才为合法报文，否则丢弃。相当于访问控制列表"
       ::= { gbnPlatformOAMSntpClient 2 }

    sntpClientValidServerEntry OBJECT-TYPE
        SYNTAX   SntpClientValidServerEntry
        MAX-ACCESS   not-accessible
        STATUS   current
        DESCRIPTION
           "定义一条合法服务器列表."
       INDEX { sntpClientValidServerNet, sntpClientValidServerMask }
       ::= { sntpClientValidServerTable 1 } 
         
    SntpClientValidServerEntry ::=
	    SEQUENCE {
	        sntpClientValidServerNet
	            IpAddress,
	        sntpClientValidServerMask
	            IpAddress,
	        sntpClientValidServerRowStatus
	            RowStatus        	            
	        }   
	        
    sntpClientValidServerNet OBJECT-TYPE
        SYNTAX   IpAddress
        MAX-ACCESS   read-only
        STATUS   current
        DESCRIPTION
           "源地址所在网段号"
        ::= { sntpClientValidServerEntry 1 } 
        
    sntpClientValidServerMask OBJECT-TYPE
        SYNTAX   IpAddress
        MAX-ACCESS   read-only
        STATUS   current
        DESCRIPTION
           "源地址所在网段掩码"
        ::= { sntpClientValidServerEntry 2 }         
                                                
    sntpClientValidServerRowStatus OBJECT-TYPE
        SYNTAX   RowStatus
        MAX-ACCESS   read-write
        STATUS   current
        DESCRIPTION
           "行状态"
        ::= { sntpClientValidServerEntry 3 }   
        
------------------------------------------------------------------------------     
--  sntpAuthKeyTable:
------------------------------------------------------------------------------
    
  sntpAuthKeyTable OBJECT-TYPE
        SYNTAX   SEQUENCE OF SntpAuthKeyEntry
        MAX-ACCESS   not-accessible
        STATUS   current
        DESCRIPTION
           "keys userd for SNTP authentication"  
           --用于SNTP认证的密码表--
       ::= { gbnPlatformOAMSntpClient 3 }

    sntpAuthKeyEntry OBJECT-TYPE
        SYNTAX   SntpAuthKeyEntry
        MAX-ACCESS   not-accessible
        STATUS   current
        DESCRIPTION
           "define a key item."   
           --定义一个密码表项--
       INDEX { sntpAuthKeyId }
       ::= { sntpAuthKeyTable 1 } 
         
    SntpAuthKeyEntry ::=
	    SEQUENCE {
	        sntpAuthKeyId
	            Unsigned32,
	        sntpAuthKeyValue
	            DisplayString (SIZE (1..16)),  
	        sntpAuthKeyTrustFlag
	            TruthValue,
	        sntpAuthKeyRowStatus
	            RowStatus        	            
	        }   
	        
    sntpAuthKeyId OBJECT-TYPE
        SYNTAX   Unsigned32  ( 1..4294967295 )  
        MAX-ACCESS   read-only
        STATUS   current
        DESCRIPTION
           "key number" 
           --key ID--
        ::= { sntpAuthKeyEntry 1 } 
        
    sntpAuthKeyValue OBJECT-TYPE
        SYNTAX   DisplayString (SIZE (1..16))
        MAX-ACCESS   read-write
        STATUS   current
        DESCRIPTION
           "key value"    
           --一个最长为16字节的字符串--
        ::= { sntpAuthKeyEntry 2 }    
        
    sntpAuthKeyTrustFlag OBJECT-TYPE
        SYNTAX   TruthValue
        MAX-ACCESS   read-write
        STATUS   current
        DESCRIPTION
           "whether the key is trusted" 
           --此密码是否为可信任的标记--
        ::= { sntpAuthKeyEntry 3 }   
                                                
    sntpAuthKeyRowStatus OBJECT-TYPE
        SYNTAX   RowStatus
        MAX-ACCESS   read-write
        STATUS   current
        DESCRIPTION
           "row status"
           --行状态，用于删除--
        ::= { sntpAuthKeyEntry 4 }                                                                             
                               
   END
